module Cisco-IOS-XE-policymap-target-oper {
  yang-version 1.1;
  namespace "http://cisco.com/ns/yang/Cisco-IOS-XE-policymap-target-oper";
  prefix policymap-target-oper;

  import Cisco-IOS-XE-sdwan-types {
    prefix ios-xe-sdwan-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for operational data.
     Copyright (c) 2024-2025 by Cisco Systems, Inc.
     All rights reserved.";

  revision 2025-07-01 {
    description
      "Initial revision";
    reference
      "1.0.0";
    cisco-semver:module-version "1.0.0";
  }

  grouping policy-stats-type {
    description
      "Basic policy statistics";
    leaf pre-policy-pkts {
      type uint64;
      description
        "Total number of pre-policy packets";
    }
    leaf pre-policy-bytes {
      type uint64;
      description
        "Total number of pre-policy bytes";
    }
    leaf post-policy-pkts {
      type uint64;
      description
        "Total number of post-policy packets";
    }
    leaf post-policy-bytes {
      type uint64;
      description
        "Total number of post-policy bytes";
    }
    leaf drop-pkts {
      type uint64;
      description
        "Total number of dropped packets";
    }
    leaf drop-bytes {
      type uint64;
      description
        "Total number of dropped bytes";
    }
    leaf stats-time {
      type yang:date-and-time;
      description
        "The time when the stats was generated";
    }
  }

  grouping tunnel-endpoint {
    description
      "Keys of tunnel endpoint used by per-tunnel QoS";
    leaf local-sys-addr {
      type inet:ip-address;
      description
        "Local system address";
    }
    leaf local-color {
      type ios-xe-sdwan-types:sdwan-color-enum;
      description
        "Local color";
    }
    leaf remote-sys-addr {
      type inet:ip-address;
      description
        "Remote system address";
    }
    leaf remote-color {
      type ios-xe-sdwan-types:sdwan-color-enum;
      description
        "Remote color";
    }
    leaf proto {
      type ios-xe-sdwan-types:sdwan-encap-enum;
      description
        "Encapsulation protocol";
    }
  }

  grouping diffserv-mpoint-clf-stats-key {
    description
      "Diffserv multipoint classifier statistics key";
    leaf policy {
      type string;
      description
        "Policy name";
    }
    leaf class {
      type string;
      description
        "Class name";
    }
    leaf child-policy {
      type string;
      description
        "Child policy name";
    }
    leaf child-class {
      type string;
      description
        "Child class name";
    }
  }

  grouping diffserv-mpoint-clf-stats {
    description
      "Diffserv multipoint classifier statistics";
    container policy-stats {
      description
        "Basic policy statistics";
      uses policymap-target-oper:policy-stats-type;
    }
    leaf has-child {
      type boolean;
      description
        "Class has child policy flag";
    }
  }

  grouping tunnel-qos-stats {
    description
      "Diffserv target data";
    list diffserv-info {
      key "policy class child-policy child-class";
      description
        "Statistics for each Classifier Entry in a Policy";
      uses policymap-target-oper:diffserv-mpoint-clf-stats-key;
      uses policymap-target-oper:diffserv-mpoint-clf-stats;
    }
  }

  container policymap-target-oper-data {
    config false;
    description
      "App cFlowd flow operational data";
    list mpoint-summary {
      key "local-sys-addr local-color remote-sys-addr remote-color proto";
      description
        "List of multipoint QoS summary data";
      uses policymap-target-oper:tunnel-endpoint;
      uses policymap-target-oper:policy-stats-type;
    }
    list mpoint-stats {
      key "local-sys-addr local-color remote-sys-addr remote-color proto";
      description
        "List of multipoint QoS per-class data";
      uses policymap-target-oper:tunnel-endpoint;
      uses policymap-target-oper:tunnel-qos-stats;
    }
  }
}
