module Cisco-IOS-XE-service-chain-oper {
  yang-version 1.1;
  namespace "http://cisco.com/ns/yang/Cisco-IOS-XE-service-chain-oper";
  prefix service-chain-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definition
     for service chain operational data.
     Copyright (c) 2024 by Cisco Systems, Inc.
     All rights reserved.";

  revision 2024-11-01 {
    description
      "Initial revision";
    reference
      "1.0.0";
    cisco-semver:module-version "1.0.0";
  }

  typedef ha-pair-trust {
    type enumeration {
      enum svc-ha-pair-trst {
        value 1;
        description
          "HA pair is trusted";
      }
      enum svc-ha-pair-untrst {
        value 2;
        description
          "HA pair is not trusted";
      }
    }
    description
      "HA pair trust posture";
  }

  typedef ha-type {
    type enumeration {
      enum ha-pair-type-none {
        value 0;
        description
          "HA Pair type is none";
      }
      enum ha-pair-type-tunnel {
        value 1;
        description
          "HA Pair type is tunnel";
      }
      enum ha-pair-type-ipv4 {
        value 2;
        description
          "HA Pair type is IPv4 INTF";
      }
      enum ha-pair-type-ipv6 {
        value 3;
        description
          "HA Pair type is IPv6 INTF";
      }
    }
    description
      "HA Pair type";
  }

  typedef svc-chain-elements-state {
    type enumeration {
      enum state-down {
        value 0;
        description
          "Service chain/service/transport element status is down";
      }
      enum state-up {
        value 1;
        description
          "Service chain/service/transport element status is up";
      }
    }
    description
      "Service chain/service/transport element status";
  }

  grouping tp-pair-element {
    description
      "An individual interface with associated tracker with tracker name, endpoint, and status.";
    leaf tp-status {
      type service-chain-ios-xe-oper:svc-chain-elements-state;
      description
        "Interface status";
    }
    leaf if-name {
      type string;
      description
        "Interface  name";
    }
    leaf svc-ip-address {
      type inet:ip-address;
      description
        "Address or domain name of the endpoint";
    }
    leaf tracker-name {
      type string;
      description
        "Tracker name";
    }
  }

  grouping tpt-pair {
    description
      "Transport pair consisting of either transmitting
       (tx) or receiving (rx) interfaces.";
    leaf is-current {
      type boolean;
      description
        "Flag to check the current active node";
    }
    container tx {
      description
        "Transmitting interface";
      uses service-chain-ios-xe-oper:tp-pair-element;
    }
    container rx {
      description
        "Receiving interface";
      uses service-chain-ios-xe-oper:tp-pair-element;
    }
  }

  grouping svc-ha-pair {
    description
      "Transport High-Availability (HA) Pair.
       A transport HA pair consists of either an active
       or backup transport or both. A backup transport
       is used as a fallback in case the active transport
       is operationally down.";
    leaf ha-pair-id {
      type uint32;
      description
        "Transport pair ID";
    }
    leaf trust-posture {
      type service-chain-ios-xe-oper:ha-pair-trust;
      description
        "Trust posture configured: trusted/untrusted";
    }
    leaf ha-pair-type {
      type service-chain-ios-xe-oper:ha-type;
      description
        "HA Pair type configured: v4/v6/tunnel";
    }
    leaf is-backup-present {
      type empty;
      description
        "Flag to check if backup transport is present";
    }
    container active {
      description
        "Active transport";
      uses service-chain-ios-xe-oper:tpt-pair;
    }
    container backup {
      when 'boolean(../is-backup-present)';
      description
        "Backup transport";
      uses service-chain-ios-xe-oper:tpt-pair;
    }
  }

  grouping sc-svc-entry {
    description
      "Service in the service chain";
    leaf svc-name {
      type string;
      description
        "Service name";
    }
    leaf svc-status {
      type service-chain-ios-xe-oper:svc-chain-elements-state;
      description
        "The operational status of the service (up/down)";
    }
    leaf is-track-enable {
      type boolean;
      description
        "Tracker enable state for this service";
    }
    leaf svc-seq {
      type uint32;
      description
        "Sequence number of the service";
    }
    list svc-ha-pair {
      key "ha-pair-id";
      description
        "List of IPv4 and IPv6 HA pairs";
      uses service-chain-ios-xe-oper:svc-ha-pair;
    }
  }

  grouping svc-chain-status {
    description
      "Service chain status";
    leaf sc-id-str {
      type string;
      description
        "Service chain ID";
    }
    leaf sc-name {
      type string;
      description
        "Service chain name";
    }
    leaf sc-status {
      type service-chain-ios-xe-oper:svc-chain-elements-state;
      description
        "Operational status of the service chain (up/down)";
    }
    leaf vpn {
      type string;
      description
        "VPN id where the service chain is configured";
    }
    leaf sc-label {
      type uint32;
      description
        "Service chain Label";
    }
    leaf sc-track-obj {
      type uint32;
      description
        "Service Chain track object number";
    }
    leaf sc-affect-bfd {
      type boolean;
      description
        "Does the service chain state affect the BFD";
    }
    list sc-svc-entry {
      key "svc-seq";
      description
        "List of services in the service chain";
      uses service-chain-ios-xe-oper:sc-svc-entry;
    }
  }

  grouping sc-stats {
    description
      "Service Chain (tx) or receiving (rx) statistics";
    leaf tx-stats {
      type uint64;
      description
        "Transmitting interface";
    }
    leaf rx-stats {
      type uint64;
      description
        "Receiving interface";
    }
  }

  grouping sc-tracker-stats {
    description
      "Service Chain tracker statistics";
    leaf sent {
      type uint64;
      description
        "Tracker packets sent statistics";
    }
    leaf dropped {
      type uint64;
      description
        "Tracker packets dropped statistics";
    }
    leaf rtt {
      type uint32;
      units "milliseconds";
      description
        "Tracker packets round trip time";
    }
  }

  grouping sc-tp-pair {
    description
      "Transport pair consisting of data and tracker statistics";
    container v4-stats {
      description
        "Transport Pair IPV4 statistics";
      uses service-chain-ios-xe-oper:sc-stats;
    }
    container v6-stats {
      description
        "Transport Pair IPV6 statistics";
      uses service-chain-ios-xe-oper:sc-stats;
    }
    container tx-tracker {
      description
        "Transmitting tracker statistics";
      uses service-chain-ios-xe-oper:sc-tracker-stats;
    }
    container rx-tracker {
      description
        "Receiving tracker statistics";
      uses service-chain-ios-xe-oper:sc-tracker-stats;
    }
  }

  grouping svc-ha-pair-stats {
    description
      "Transport High-Availability (HA) Pair.
       A transport HA pair consists of either an active
       or backup transport or both. A backup transport
       is used as a fallback in case the active transport
       is operationally down. Active transports in
       separate services can also be used for load
       balancing.";
    leaf ha-pair-id {
      type uint32;
      description
        "Transport pair ID";
    }
    leaf ha-pair-type {
      type service-chain-ios-xe-oper:ha-type;
      description
        "HA Pair type configured: v4/v6/tunnel";
    }
    leaf is-bckp-present {
      type empty;
      description
        "Flag to check if backup transport statistics are present";
    }
    container actv-stats {
      description
        "Active transport statistics";
      uses service-chain-ios-xe-oper:sc-tp-pair;
    }
    container bckp-stats {
      when 'boolean(../is-bckp-present)';
      description
        "Backup transport statistics";
      uses service-chain-ios-xe-oper:sc-tp-pair;
    }
  }

  grouping sc-svc-stats {
    description
      "Service in the service chain";
    leaf svc-name {
      type string;
      description
        "Service name";
    }
    leaf svc-seq {
      type uint32;
      description
        "Sequence number of the service";
    }
    leaf svc-status {
      type service-chain-ios-xe-oper:svc-chain-elements-state;
      description
        "Operational status of the service (up/down)";
    }
    container svc-stats {
      description
        "Service level tx and rx statistics";
      uses service-chain-ios-xe-oper:sc-stats;
    }
    list svc-ha-pair-stats {
      key "ha-pair-id";
      description
        "List of IPv4 and IPv6 HA pairs statistics";
      uses service-chain-ios-xe-oper:svc-ha-pair-stats;
    }
  }

  grouping svc-chain-stats {
    description
      "Service chain statistics";
    leaf sc-id-str {
      type string;
      description
        "Service chain ID";
    }
    leaf sc-name {
      type string;
      description
        "Service chain name";
    }
    leaf sc-status {
      type service-chain-ios-xe-oper:svc-chain-elements-state;
      description
        "Operational status of the service chain (up/down)";
    }
    leaf vpn {
      type string;
      description
        "VPN id where the service chain is configured";
    }
    leaf sc-label {
      type uint32;
      description
        "Service chain Label";
    }
    list sc-svc-stats {
      key "svc-seq";
      description
        "List of service statistics  in the service chain";
      uses service-chain-ios-xe-oper:sc-svc-stats;
    }
  }

  container service-chain-oper-data {
    config false;
    description
      "Service chain operational data";
    list svc-chain-status {
      key "sc-id-str";
      description
        "Operational status of service chains and the
         services that compose the chain(s). Each
         service chain contains a list of services, and
         each service contains a list of active/backup
         transports for each address family. Each
         transport has either a transmitting interface
         or a receiving interface. Each interface has
         an associated tracker with an operational
         state, or an element. The tracker status of these
         interfaces ultimately determine the status
         of each service, which in turn determine the status
         of each service chain.";
      uses service-chain-ios-xe-oper:svc-chain-status;
    }
    list svc-chain-stats {
      key "sc-id-str";
      description
        "Operational statistics of service chains and the
         services that compose the chain(s). Each
         service chain contains a list of services, and
         each service contains a list of active/backup
         transports for each address family. Each
         transport has  transmitting interface
         or a receiving stats. Each interface has
         an associated tracker with an operational
         state, or an element. The tracker statistics has the
         details of packets sent, dropped and round trip
         time of the tracker interface";
      uses service-chain-ios-xe-oper:svc-chain-stats;
    }
  }
}
