module Cisco-IOS-XE-device-hardware-oper {
  yang-version 1.1;
  namespace "http://cisco.com/ns/yang/Cisco-IOS-XE-device-hardware-oper";
  prefix device-hardware-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Device Hardware operational data.
     Copyright (c) 2017-2020, 2022-2024 by Cisco Systems, Inc.
     All rights reserved.";

  revision 2025-03-01 {
    description
      "- Added cloud ID information programmed into the device";
    reference
      "1.12.0";
    cisco-semver:module-version "1.12.0";
  }
  revision 2024-11-01 {
    description
      "- Added configuration register support";
    reference
      "1.11.0";
    cisco-semver:module-version "1.11.0";
  }
  revision 2024-03-01 {
    description
      "- Expanded reload history details to include FRU identity, HA role, SW version and crash file location.
       - Expanded entity information details to include list of ROMMON environment variables
       - Added an additional module status:
         This status represents module creation and its initial states,
         as well as any mismatches in version and features";
    reference
      "1.10.0";
    cisco-semver:module-version "1.10.0";
  }
  revision 2023-11-01 {
    description
      "- Added MAC address of the device:
         It represents MAC address of active module or chassis";
    reference
      "1.9.0";
    cisco-semver:module-version "1.9.0";
  }
  revision 2023-03-01 {
    description
      "- Added reload history support:
         The feature maintains a history of reload reasons.
         Platforms supporting this feature will be able to
         access the history upto last 10 reloads. Each reload
         shall have category, severity, timestamp along with
         description";
    reference
      "1.8.0";
    cisco-semver:module-version "1.8.0";
  }
  revision 2022-11-01 {
    description
      "- Update yang-version to 1.1
       - Added additional module status enumerations";
    reference
      "1.7.0";
    cisco-semver:module-version "1.7.0";
  }
  revision 2021-03-01 {
    description
      "- Added hardware type SSD
       - Added 'lifetime' information for hardware type SSD";
    reference
      "1.6.0";
    cisco-semver:module-version "1.6.0";
  }
  revision 2020-11-01 {
    description
      "- Added BP FRU type
       - Added a changed configuration leaf";
    reference
      "1.5.0";
    cisco-semver:module-version "1.5.0";
  }
  revision 2020-07-01 {
    description
      "- Added device-system-data type 'reboot-reason-type'.
       - Added FC FRU type";
    reference
      "1.4.0";
    cisco-semver:module-version "1.4.0";
  }
  revision 2019-11-01 {
    description
      "Update copyright";
    reference
      "1.3.1";
    cisco-semver:module-version "1.3.1";
  }
  revision 2019-03-28 {
    description
      "- Added device alarm type 'Info'.
       - Added semantic version";
    reference
      "1.3.0";
    cisco-semver:module-version "1.3.0";
  }
  revision 2018-10-29 {
    description
      "- Added extensions to device inventory
       - Cleaned up spelling errors in descriptions.";
    reference
      "1.2.0";
    cisco-semver:module-version "1.2.0";
  }
  revision 2018-06-18 {
    description
      "Add entity information";
    reference
      "1.1.0";
    cisco-semver:module-version "1.1.0";
  }
  revision 2017-11-01 {
    description
      "Initial revision";
    reference
      "1.0.0";
    cisco-semver:module-version "1.0.0";
  }

  typedef b-fru {
    type enumeration {
      enum device-hardware-fru-rp {
        value 0;
        description
          "A Route Processor";
      }
      enum device-hardware-fru-esp {
        value 1;
        description
          "An Embedded Services Processor";
      }
      enum device-hardware-fru-cp {
        value 2;
        description
          "A Carrier Card";
      }
      enum device-hardware-fru-max {
        value 3;
        description
          "An illegal value for FRU type";
      }
      enum device-hardware-fru-fc {
        value 4;
        description
          "A Fabric Card";
      }
      enum device-hardware-fru-bp {
        value 5;
        description
          "A Bootstrap Plane";
      }
    }
    description
      "The Field Replaceable Unit type";
  }

  typedef high-availability-role {
    type enumeration {
      enum ha-role-active {
        value 0;
        description
          "The role is Active ";
      }
      enum ha-role-standby {
        value 1;
        description
          "The role is Standby";
      }
      enum ha-role-unknown {
        value 2;
        description
          "The role is unknown";
      }
    }
    description
      "The High Availability role";
  }

  typedef reboot-reason-type {
    type enumeration {
      enum normal {
        value 0;
        description
          "System reboot reason is determined to be
           normal and intentional";
      }
      enum abnormal {
        value 1;
        description
          "System reboot reason is determined to be
           abnormal or unintentional";
      }
    }
    description
      "Reboot-reason normality classification type";
  }

  typedef hw-type {
    type enumeration {
      enum hw-type-unknown {
        value 0;
        description
          "Unknown Hardware Type";
      }
      enum hw-type-chassis {
        value 1;
        description
          "Chassis";
      }
      enum hw-type-cpu {
        value 2;
        description
          "Central Processing Unit";
      }
      enum hw-type-dram {
        value 3;
        description
          "Dynamic Random Access Memory";
      }
      enum hw-type-flash {
        value 4;
        description
          "Flash";
      }
      enum hw-type-emmc {
        value 5;
        description
          "embedded Memory Controller";
      }
      enum hw-type-sdcard {
        value 6;
        description
          "SD-Card";
      }
      enum hw-type-usb {
        value 7;
        description
          "Universal Serial Bus";
      }
      enum hw-type-pim {
        value 8;
        description
          "Pluggable interface model";
      }
      enum hw-type-transceiver {
        value 9;
        description
          "Transceiver";
      }
      enum hw-type-fantray {
        value 10;
        description
          "Fan tray";
      }
      enum hw-type-pem {
        value 11;
        description
          "Power Entry Module";
      }
      enum hw-type-ssd {
        value 12;
        description
          "SSD Memory";
      }
    }
    description
      "The broad type of hardware device";
  }

  typedef alarm-severity {
    type enumeration {
      enum alarm-severity-critical {
        value 0;
        description
          "Critical Alarms";
      }
      enum alarm-severity-major {
        value 1;
        description
          "Major Alarms";
      }
      enum alarm-severity-minor {
        value 2;
        description
          "Minor Alarms";
      }
      enum alarm-severity-info {
        value 3;
        description
          "INFO Alarms";
      }
    }
    description
      "Alarm severity";
  }

  typedef hw-category {
    type enumeration {
      enum hw-class-virtual {
        value 0;
        description
          "Internal Virtual Device";
      }
      enum hw-class-physical {
        value 1;
        description
          "Physical HW Device";
      }
    }
    description
      "Device Category";
  }

  typedef reload-category {
    type enumeration {
      enum rc-unknown {
        value 0;
        description
          "Unknown reload category";
      }
      enum rc-smu-install {
        value 1;
        description
          "Reload after SMU installation";
      }
      enum rc-sp-install {
        value 2;
        description
          "Reload after Sub Package installation";
      }
      enum rc-smu-issu {
        value 3;
        description
          "Reload for in-service cold SMU
           installation to take effect";
      }
      enum rc-sp-issu {
        value 4;
        description
          "Reload for in-service Sub Package
           installation to take effect";
      }
      enum rc-img-install {
        value 5;
        description
          "Reload after Image installation";
      }
      enum rc-img-issu {
        value 6;
        description
          "Reload for in-service
           image installation to take effect";
      }
      enum rc-img-install-fsu {
        value 7;
        description
          "Reload after extended Fast Software
           Upgrade that keeps dataplane functional";
      }
      enum rc-install-rb {
        value 8;
        description
          "Reload for SMU rollback to take effect";
      }
      enum rc-sp-install-rb {
        value 9;
        description
          "Reload for Sub package
           rollback to take effect";
      }
      enum rc-img-install-rb {
        value 10;
        description
          "Reload for image rollback
           to take effect";
      }
      enum rc-smu-install-abort {
        value 11;
        description
          "Reload due to aborting of
           SMU installation";
      }
      enum rc-img-install-abort {
        value 12;
        description
          "Reload due to aborting of
           image installation";
      }
      enum rc-sp-install-abort {
        value 13;
        description
          "Reload due to aborting of
           Sub Package installation";
      }
      enum rc-rld-fast {
        value 14;
        description
          "Reload after a reload fast trigger,
           after a reduced downtime";
      }
      enum rc-rld-pause {
        value 15;
        description
          "Reload after a pause as requested
           by the user";
      }
      enum rc-rld {
        value 16;
        description
          "Reload after a normal reload trigger";
      }
      enum rc-force-switchover {
        value 17;
        description
          "Reload after a forced switchover";
      }
      enum rc-factory-reset {
        value 18;
        description
          "Reload after factory reset";
      }
      enum rc-bootrom-upg {
        value 19;
        description
          "Reload after boot ROM upgrade";
      }
      enum rc-bootrom-upg-fail {
        value 20;
        description
          "Reload after boot ROM upgrade failed";
      }
      enum rc-resource-unavailable {
        value 21;
        description
          "Reload due to non availability
           of a critical resource";
      }
      enum rc-crit-proc-fault {
        value 22;
        description
          "Reload due to a critical process failure";
      }
      enum rc-other {
        value 23;
        description
          "Unclassified reload category";
      }
    }
    description
      "Reload category";
  }

  typedef module-status {
    type enumeration {
      enum module-status-invalid {
        value 0;
        description
          "An invalid value for module status";
      }
      enum module-status-unknown {
        value 1;
        description
          "An unknown value for module status";
      }
      enum module-status-booting {
        value 2;
        description
          "The module is currently booting";
      }
      enum module-status-online {
        value 3;
        description
          "The module is online and operational";
      }
      enum module-status-disabled {
        value 4;
        description
          "The module is disabled";
      }
      enum module-status-failed {
        value 5;
        description
          "The module has failed";
      }
      enum module-status-removed {
        value 6;
        description
          "The module has been removed";
      }
      enum module-status-stopped {
        value 7;
        description
          "The module is stopped.";
      }
      enum module-status-incompatible {
        value 8;
        description
          "The module hardware version is incompatible
           with the current software version";
      }
      enum module-status-cpld-failed {
        value 9;
        description
          "A Complex Programmable Logic Device (CPLD)
           has failed. The module will not be usable";
      }
      enum module-status-actrpcpldfailed {
        value 10;
        description
          "A Complex Programmable Logic Device (CPLD)
           has failed on the active RP. The module will
           not be usable";
      }
      enum module-status-mdr {
        value 11;
        description
          "The module is currently undergoing a Minimal
           Disruptive Restart";
      }
      enum module-status-pwr-denied {
        value 12;
        description
          "Module status is power denied";
      }
      enum module-status-pwr-down {
        value 13;
        description
          "Module status is power down";
      }
      enum module-status-auto-lc-shutdown {
        value 14;
        description
          "Module status is auto linecard shutdown";
      }
      enum module-status-waiting {
        value 15;
        description
          "The module is currently waiting";
      }
      enum module-status-init {
        value 16;
        description
          "Module is initializing";
      }
      enum module-status-version-mismatch {
        value 17;
        description
          "Module software version is mismatch with the
           current active module software version";
      }
      enum module-status-feature-mismatch {
        value 18;
        description
          "Module feature version is mismatch with the
           current active module feature version";
      }
      enum module-status-created {
        value 19;
        description
          "The module is created";
      }
    }
    description
      "The status that the module is in";
  }

  typedef config-register-bits {
    type bits {
      bit cg-bt-in-rommon {
        position 0;
        description
          "If set, boot will stay at bootstrap prompt";
      }
      bit cg-bt-first-sysimg {
        position 1;
        description
          "If set, device will boot with first sys img from EPROM ";
      }
      bit cg-bt-sys-cmd {
        position 2;
        description
          "If set, a default filename can be specified. It will enable
           boot system cmd that override the default filename";
      }
      bit cg-cl-spd0 {
        position 3;
        description
          "Bit 0 of console line speed";
      }
      bit cg-ign-saved-cnts {
        position 4;
        description
          "If set, saved contents will be ignored";
      }
      bit cg-oem-mode {
        position 5;
        description
          "If set, OEM mode is enabled";
      }
      bit cg-no-break {
        position 6;
        description
          "If set, break will be disabled";
      }
      bit cg-sel-sec-bstrap {
        position 7;
        description
          "If set, system will select secondary bootstrap";
      }
      bit cg-ip-bcast-all-zeros {
        position 8;
        description
          "If set, IP broadcast with all zeros will be used";
      }
      bit cg-cl-spd1 {
        position 9;
        description
          "Bit 1 of console line speed";
      }
      bit cg-cl-spd2 {
        position 10;
        description
          "Bit 2 of console line speed";
      }
      bit cg-bt-def-rom-sw-if-nw-bt-fail {
        position 11;
        description
          "If set, default ROM software will be booted if nw boot fails";
      }
      bit cg-ip-bcasts-no-net-num {
        position 12;
        description
          "If set, use the highest address in the subnet as the
           broadcast IPv4 address";
      }
      bit cg-en-diag-msg-ign-saved-cnts {
        position 13;
        description
          "If set, diagnostic msg will be enabled and
           saved contents will be ignored";
      }
      bit cg-baud-rate-1200 {
        position 14;
        description
          "This bit represents 1200 console speed";
      }
      bit cg-baud-rate-2400 {
        position 15;
        description
          "This bit represents 2400 console speed";
      }
      bit cg-baud-rate-4800 {
        position 16;
        description
          "This bit represents 4800 console speed";
      }
      bit cg-baud-rate-9600 {
        position 17;
        description
          "This bit represents 9600 console speed";
      }
      bit cg-baud-rate-19200 {
        position 18;
        description
          "This bit represents 19200 console speed";
      }
      bit cg-baud-rate-38400 {
        position 19;
        description
          "This bit represents 38400 console speed";
      }
      bit cg-baud-rate-57600 {
        position 20;
        description
          "This bit represents 57600 console speed";
      }
      bit cg-baud-rate-115200 {
        position 21;
        description
          "This bit represents 115200 console speed";
      }
    }
    description
      "Configuration register bits";
  }

  grouping svc-loc {
    description
      "Service Location details";
    leaf fru {
      type device-hardware-xe-oper:b-fru;
      description
        "Field Replaceable Unit type";
    }
    leaf slotnum {
      type int16;
      description
        "Slot number";
    }
    leaf baynum {
      type int16;
      description
        "Bay number";
    }
    leaf chassisnum {
      type int16;
      description
        "Chassis number";
    }
  }

  grouping hw-alarm-key {
    description
      "The key to the hardware table";
    leaf alarm-id {
      type uint32;
      description
        "The Alarm Identifier";
    }
    leaf alarm-instance {
      type uint32;
      description
        "The instance of this alarm. This corresponds to the
         entity index";
    }
  }

  grouping hw-alarm {
    description
      "The alarm information";
    leaf alarm-name {
      type string;
      description
        "The name of the alarm";
    }
    leaf alarm-category {
      type device-hardware-xe-oper:alarm-severity;
      description
        "The category (or severity) of the alarm that is being asserted";
    }
    leaf alarm-time {
      type yang:date-and-time;
      description
        "Time the alarm was raised";
    }
    leaf alarm-description {
      type string;
      description
        "Description of the alarm";
    }
  }

  grouping reload-history-element {
    description
      "Reload history element gives information
       about one occurrence of a reload";
    leaf reload-category {
      type device-hardware-xe-oper:reload-category;
      description
        "Reload category of reload reason";
    }
    leaf reload-desc {
      type string;
      description
        "Reload description";
    }
    leaf reload-time {
      type yang:date-and-time;
      description
        "Time at when reload happened";
    }
    leaf reload-severity {
      type device-hardware-xe-oper:reboot-reason-type;
      description
        "Indicates if reload is normal or abnormal";
    }
    leaf sw-ver {
      type string;
      description
        "Software version running at the time of the reload";
    }
    leaf ha-role {
      type device-hardware-xe-oper:high-availability-role;
      description
        "High availability role of the reloaded FRU";
    }
    leaf crash-data-file {
      type string;
      description
        "Full path to the crash data file generated during system crash";
    }
  }

  grouping reload-history-list {
    description
      "Reload history list";
    list rl-history {
      max-elements 10;
      description
        "Reload history, each element contains
         reload related information of one occurrence";
      uses device-hardware-xe-oper:reload-history-element;
    }
    leaf fru-type {
      type device-hardware-xe-oper:b-fru;
      description
        "FRU type of the device that experienced reload";
    }
    leaf fru-id {
      type int16;
      description
        "FRU identification of the device that experienced reload";
    }
  }

  grouping confreg {
    description
      "Details about configuration register";
    leaf cr {
      type device-hardware-xe-oper:config-register-bits;
      description
        "The value of configuration register with which
         the processor module booted";
    }
    leaf cr-next {
      type device-hardware-xe-oper:config-register-bits;
      description
        "The value of configuration register with which
         the processor module will boot at next reboot";
    }
    leaf cr-hex {
      type yang:hex-string;
      description
        "The hex value of configuration register with which
         the processor module booted";
    }
    leaf cr-next-hex {
      type yang:hex-string;
      description
        "The hex value of configuration register with which
         the processor module will boot at next reboot";
    }
  }

  grouping device-system-data {
    description
      "Device system data";
    leaf current-time {
      type yang:date-and-time;
      description
        "Current time on device in UTC";
    }
    leaf boot-time {
      type yang:date-and-time;
      description
        "This timestamp indicates the time that the system was last
         restarted.  The value is the timestamp in seconds relative
         to the Unix Epoch (Jan 1, 1970 00:00:00 UTC).";
    }
    leaf software-version {
      type string;
      description
        "Software version";
    }
    leaf rommon-version {
      type string;
      description
        "Rommon version";
    }
    leaf last-reboot-reason {
      type string;
      description
        "Last reboot reason";
    }
    leaf reason-severity {
      type device-hardware-xe-oper:reboot-reason-type;
      description
        "Reboot reason severity,
         either normal, i.e. intentional;
         or abnormal, i.e., unintentional";
    }
    leaf unsaved-config {
      type boolean;
      description
        "Indicate whether the device configuration has changed,
         but has not been saved to non volatile RAM. This leaf
         mirrors the state used when IOS asks the user about
         config that has changed upon issuing a reload. As such,
         it might indicate that the configuration is dirty, when
         there are no actual changes.";
    }
    leaf reload-history-support {
      type empty;
      description
        "Indicates if platform supports
         reload history feature or not";
    }
    container reload-history {
      when 'boolean(../reload-history-support)';
      description
        "Reload History list, each element in the list
         represents one occurrence of a reload";
      uses device-hardware-xe-oper:reload-history-list;
    }
    leaf mac-address {
      type yang:mac-address;
      description
        "The MAC address of the device which represents
         MAC address of active module or chassis";
    }
    leaf cloud-id-supported {
      type empty;
      description
        "When present, the Cloud ID information is valid";
    }
    leaf cloud-id {
      when 'boolean(../cloud-id-supported)';
      type string;
      description
        "Cloud ID is the Meraki serial number programmed in the hardware security
         chip.  This is valid only if the device supports Cloud ID";
    }
  }

  grouping device-inventory-key {
    description
      "Key to the device inventory";
    leaf hw-type {
      type device-hardware-xe-oper:hw-type;
      description
        "Type of the hardware being represented";
    }
    leaf hw-dev-index {
      type uint32;
      description
        "The physical index of the inventory item";
    }
  }

  grouping device-inventory {
    description
      "inventory";
    leaf version {
      type string;
      description
        "Version of this device";
    }
    leaf part-number {
      type string;
      description
        "The part number of this device. This
         is only valid if the device is a field replaceable
         unit";
    }
    leaf serial-number {
      type string;
      description
        "The serial number of the device. This is only
         valid if the device is individually trackable";
    }
    leaf hw-description {
      type string;
      description
        "Description of the device";
    }
    leaf dev-name {
      type string;
      description
        "Name of the Device";
    }
    leaf field-replaceable {
      type boolean;
      description
        "The device is field replaceable or not";
    }
    leaf hw-class {
      type device-hardware-xe-oper:hw-category;
      description
        "The Device Category";
    }
    choice hw-type-discr-choice {
      description
        "Hardware Type options";
      case hw-type-ssd {
        leaf lifetime {
          type uint16;
          units "percentage";
          description
            "Lifetime of SSD";
        }
      }
    }
  }

  grouping device-hardware {
    description
      "Device hardware";
    list device-inventory {
      key "hw-type hw-dev-index";
      description
        "All the inventory in the hardware";
      uses device-hardware-xe-oper:device-inventory-key;
      uses device-hardware-xe-oper:device-inventory;
    }
    list device-alarm {
      key "alarm-id alarm-instance";
      description
        "The current alarms";
      uses device-hardware-xe-oper:hw-alarm-key;
      uses device-hardware-xe-oper:hw-alarm;
    }
    container device-system-data {
      presence "device-system-data";
      description
        "The current device system data";
      uses device-hardware-xe-oper:device-system-data;
    }
  }

  grouping rommon-entry {
    description
      "Details about the ROMMON environment variable";
    leaf var-name {
      type string;
      description
        "Name of the ROMMON environment variable";
    }
    leaf var-value {
      type string;
      description
        "Definition of the ROMMON environment variable";
    }
  }

  grouping entity-information {
    description
      "Information that describes the entity at the service location";
    leaf physical-index {
      type uint32;
      description
        "The SNMP physical index of this entity";
    }
    leaf status {
      type device-hardware-xe-oper:module-status;
      description
        "The current status of the entity";
    }
    leaf description {
      type string;
      description
        "The detailed description of this entity";
    }
    leaf status-last-change {
      type yang:date-and-time;
      description
        "The timestamp when the entity transitioned into
         its reported status";
    }
    leaf high-availability-state {
      type device-hardware-xe-oper:high-availability-role;
      description
        "The location's high availability state";
    }
    leaf chassis-state {
      type device-hardware-xe-oper:high-availability-role;
      description
        "The chassis role status";
    }
    list rommon-entry {
      key "var-name";
      description
        "The ROM Monitor (ROMMON) is a bootstrap program
         that initializes the hardware and boots the Cisco IOS XE software
         when powered on. The ROMMON environment variables connects ROMMON
         with Cisco IOS XE software. It define the attributes of the ROMMON.
         The Environment variables settings are entered in capital letters
         followed by a definition. This contains the list of ROMMON
         environment variables";
      uses device-hardware-xe-oper:rommon-entry;
    }
    container cr-info {
      description
        "The configuration register values of device";
      uses device-hardware-xe-oper:confreg;
    }
  }

  container device-hardware-data {
    config false;
    description
      "Device Hardware";
    list entity-information {
      key "fru slotnum baynum chassisnum";
      description
        "The entity information";
      uses device-hardware-xe-oper:svc-loc;
      uses device-hardware-xe-oper:entity-information;
    }
    container device-hardware {
      presence "device-hardware";
      description
        "The device hardware model";
      uses device-hardware-xe-oper:device-hardware;
    }
  }
}
