module Cisco-IOS-XE-common-types {
  yang-version 1.1;
  namespace "http://cisco.com/ns/yang/Cisco-IOS-XE-common-types";
  prefix common-types-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains type definitions common to all Cisco IOS XE native models

     Copyright (c) 2016-2020, 2022, 2025 by Cisco Systems, Inc.
     All rights reserved.";

  revision 2026-02-01 {
    description
      "Added an enumerated type for download error reporting.";
    reference
      "2.8.0";
    cisco-semver:module-version "2.8.0";
  }
  revision 2023-11-01 {
    description
      "Added network instance type";
    reference
      "2.7.0";
    cisco-semver:module-version "2.7.0";
  }
  revision 2023-07-01 {
    description
      "Added option type";
    reference
      "2.6.0";
    cisco-semver:module-version "2.6.0";
  }
  revision 2022-11-01 {
    description
      "Update yang-version to 1.1";
    reference
      "2.5.0";
    cisco-semver:module-version "2.5.0";
  }
  revision 2021-03-01 {
    description
      "Added password-encryption-type";
    reference
      "2.4.0";
    cisco-semver:module-version "2.4.0";
  }
  revision 2020-11-01 {
    description
      "Added BP FRU type";
    reference
      "2.3.0";
    cisco-semver:module-version "2.3.0";
  }
  revision 2020-07-01 {
    description
      "Added extended location type and FC FRU type";
    reference
      "2.2.0";
    cisco-semver:module-version "2.2.0";
  }
  revision 2019-05-01 {
    description
      "Added semantic version";
    reference
      "2.1.0";
    cisco-semver:module-version "2.1.0";
  }
  revision 2019-01-02 {
    description
      "Remove mcp-bytestr type
       Added the high availability states";
    reference
      "2.0.0";
    cisco-semver:module-version "2.0.0";
  }
  revision 2018-05-25 {
    description
      "Add internal location types";
    reference
      "1.2.0";
    cisco-semver:module-version "1.2.0";
  }
  revision 2017-12-01 {
    description
      "- Properly indicate leaf-list ordering
       - Add addr-type to represent IP address types";
    reference
      "1.1.0";
    cisco-semver:module-version "1.1.0";
  }
  revision 2017-05-05 {
    description
      "Initial revision";
    reference
      "1.0.0";
    cisco-semver:module-version "1.0.0";
  }

  typedef addr-type {
    type enumeration {
      enum address-none {
        value 0;
      }
      enum ipv4-address {
        value 1;
      }
      enum ipv6-address {
        value 2;
      }
      enum ipv4-address-mcast {
        value 3;
      }
      enum ipv6-address-mcast {
        value 4;
      }
    }
    description
      "IP address type";
  }

  typedef password-encryption-type {
    type enumeration {
      enum pw-encryption-clear {
        value 0;
        description
          "Clear text password";
      }
      enum pw-encryption-sha {
        value 4;
        description
          "SHA encrypted password";
      }
      enum pw-encryption-md5 {
        value 5;
        description
          "MD5 encrypted password";
      }
      enum pw-encryption-ike-aes {
        value 6;
        description
          "IKE AES encrypted password";
      }
      enum pw-encryption-type7 {
        value 7;
        description
          "Type 7 encrypted password";
      }
      enum pw-encryption-aes {
        value 8;
        description
          "AES encrypted password";
      }
      enum pw-encryption-clear-to-sha {
        value 40;
        description
          "Transition from clear text to SHA encrypted password";
      }
      enum pw-encryption-clear-to-md5 {
        value 50;
        description
          "Transition from clear text to MD5 encrypted password";
      }
      enum pw-encryption-clear-to-ike-aes {
        value 60;
        description
          "Transition from clear text to IKE AES encrypted password";
      }
      enum pw-encryption-clear-to-type7 {
        value 70;
        description
          "Transition from clear text to Type 7 encrypted password";
      }
      enum pw-encryption-clear-to-aes {
        value 80;
        description
          "Transition from clear text to AES encrypted password";
      }
    }
    description
      "Password encryption type";
  }

  typedef option-type {
    type enumeration {
      enum option-disabled {
        value 0;
        description
          "Option is disabled";
      }
      enum option-enabled {
        value 1;
        description
          "Option is enabled";
      }
    }
    description
      "optional attribute type";
  }

  typedef net-inst-type {
    type enumeration {
      enum net-inst-default {
        value 0;
        description
          "Network instance is the default routing instance";
      }
      enum net-inst-vrf {
        value 1;
        description
          "Network instance is a user defined L3 VRF";
      }
    }
    description
      "Network instance type. Differentiates between the default routing instance and VRFs";
  }

  typedef dwnld-error-code {
    type enumeration {
      enum derr-ok {
        value 0;
        description
          "The operation completed successfully and no error occurred.";
      }
      enum derr-no-sup-proto {
        value 1;
        description
          "The protocol specified for the download operation is not supported.";
      }
      enum derr-failed-init {
        value 2;
        description
          "The initialization of the download process failed.";
      }
      enum derr-url-malformat {
        value 3;
        description
          "The URL provided for the download is malformed or invalid.";
      }
      enum derr-not-built-in {
        value 4;
        description
          "The requested feature or protocol is not built into the system.";
      }
      enum derr-no-resolve-proxy {
        value 5;
        description
          "The system failed to resolve the proxy server address specified for the download operation.";
      }
      enum derr-no-resolve-host {
        value 6;
        description
          "The system failed to resolve the host address specified for the download operation.";
      }
      enum derr-no-con {
        value 7;
        description
          "The system failed to establish a connection to the server for the download operation.";
      }
      enum derr-weird-srv-reply {
        value 8;
        description
          "The server returned an unexpected or malformed reply during the download operation.";
      }
      enum derr-remote-access-denied {
        value 9;
        description
          "Remote access was denied by the server during the download operation.";
      }
      enum derr-ftp-accept-failed {
        value 10;
        description
          "The FTP server failed to accept the connection during the download operation.";
      }
      enum derr-ftp-weird-pass-reply {
        value 11;
        description
          "The FTP server returned an unexpected response to the password authentication.";
      }
      enum derr-ftp-accept-tout {
        value 12;
        description
          "The FTP connection acceptance operation timed out during the download.";
      }
      enum derr-ftp-weird-pasv-reply {
        value 13;
        description
          "The FTP server returned an unexpected response to the passive mode command.";
      }
      enum derr-ftp-weird-227-format {
        value 14;
        description
          "The FTP server returned a malformed response to the passive mode command.";
      }
      enum derr-ftp-no-get-host {
        value 15;
        description
          "The FTP client failed to obtain the host information for the passive mode connection.";
      }
      enum derr-http2 {
        value 16;
        description
          "An error occurred with the HTTP version 2 protocol during the download operation.";
      }
      enum derr-ftp-no-set-type {
        value 17;
        description
          "The FTP client failed to set the transfer type for the download operation.";
      }
      enum derr-partial-file {
        value 18;
        description
          "The download operation resulted in only a partial file transfer.";
      }
      enum derr-ftp-no-retr-file {
        value 19;
        description
          "The FTP client failed to retrieve the file from the server.";
      }
      enum derr-quote-error {
        value 21;
        description
          "An error occurred while processing a quoted command during the download operation.";
      }
      enum derr-http-returned-error {
        value 22;
        description
          "The HTTP server returned an error status code during the download operation.";
      }
      enum derr-write-error {
        value 23;
        description
          "An error occurred while writing data to the local file during the download.";
      }
      enum derr-upload-failed {
        value 25;
        description
          "The upload operation failed during the file transfer.";
      }
      enum derr-read-error {
        value 26;
        description
          "An error occurred while reading data from the source during the download.";
      }
      enum derr-out-of-memory {
        value 27;
        description
          "The system ran out of memory during the download operation.";
      }
      enum derr-oper-tout {
        value 28;
        description
          "The download operation exceeded the configured timeout period.";
      }
      enum derr-ftp-port-failed {
        value 30;
        description
          "The FTP PORT command failed during the active mode connection setup.";
      }
      enum derr-ftp-no-use-rest {
        value 31;
        description
          "The FTP client failed to use the REST command for resuming the download.";
      }
      enum derr-range-error {
        value 33;
        description
          "An error occurred with the byte range specification during the download operation.";
      }
      enum derr-http-post-error {
        value 34;
        description
          "An error occurred during the HTTP POST operation for the download request.";
      }
      enum derr-ssl-con-error {
        value 35;
        description
          "An error occurred while establishing the SSL connection for the download.";
      }
      enum derr-bad-dwnld-resume {
        value 36;
        description
          "The download resume operation failed due to an invalid resume point.";
      }
      enum derr-file-no-read-file {
        value 37;
        description
          "The system failed to read from the local file during the download operation.";
      }
      enum derr-aborted-by-callback {
        value 42;
        description
          "The download operation was aborted by a user-defined callback function.";
      }
      enum derr-bad-function-arg {
        value 43;
        description
          "An invalid function argument was provided to the download operation.";
      }
      enum derr-interface-failed {
        value 45;
        description
          "The network interface failed during the download operation.";
      }
      enum derr-too-many-redirects {
        value 47;
        description
          "The download operation encountered too many HTTP redirects.";
      }
      enum derr-unknown-option {
        value 48;
        description
          "An unknown or unsupported option was specified for the download operation.";
      }
      enum derr-peer-failed-check {
        value 51;
        description
          "The remote peer failed SSL certificate or identity verification during the download.";
      }
      enum derr-got-nothing {
        value 52;
        description
          "The download operation completed but no data was received from the server.";
      }
      enum derr-send-error {
        value 55;
        description
          "An error occurred while sending data to the server during the download operation.";
      }
      enum derr-recv-error {
        value 56;
        description
          "An error occurred while receiving data from the server during the download operation.";
      }
      enum derr-ssl-cert-issue {
        value 58;
        description
          "A problem was encountered with the SSL certificate during the download operation.";
      }
      enum derr-ssl-cipher {
        value 59;
        description
          "An SSL cipher error occurred during the secure download operation.";
      }
      enum derr-ssl-cacert {
        value 60;
        description
          "An error occurred with the SSL Certificate Authority certificate verification.";
      }
      enum derr-bad-content-encode {
        value 61;
        description
          "The server returned data with an unsupported or malformed content encoding.";
      }
      enum derr-filesize-exceed {
        value 63;
        description
          "The downloaded file size exceeded the configured maximum file size limit.";
      }
      enum derr-use-ssl-failed {
        value 64;
        description
          "The attempt to establish an SSL connection for the download operation failed.";
      }
      enum derr-send-fail-rewind {
        value 65;
        description
          "A send operation failed and the data stream could not be rewound for retry.";
      }
      enum derr-login-denied {
        value 67;
        description
          "The login credentials were rejected by the server during the download operation.";
      }
      enum derr-remote-disk-full {
        value 70;
        description
          "The remote server disk is full and cannot complete the download operation.";
      }
      enum derr-remote-file-exists {
        value 73;
        description
          "The remote file already exists and cannot be overwritten during the upload operation.";
      }
      enum derr-ssl-cacert-bad-file {
        value 77;
        description
          "The SSL Certificate Authority certificate file is corrupted or invalid.";
      }
      enum derr-remote-file-not-found {
        value 78;
        description
          "The requested file was not found on the remote server.";
      }
      enum derr-ssh {
        value 79;
        description
          "An SSH protocol error occurred during the secure download operation.";
      }
      enum derr-ssl-shut-failed {
        value 80;
        description
          "The SSL connection shutdown process failed at the end of the download operation.";
      }
      enum derr-again {
        value 81;
        description
          "The download operation should be retried as it was temporarily unavailable.";
      }
      enum derr-ssl-crl-bad-file {
        value 82;
        description
          "The SSL Certificate Revocation List file is corrupted or invalid.";
      }
      enum derr-ssl-issuer-error {
        value 83;
        description
          "An error occurred while verifying the SSL certificate issuer information.";
      }
      enum derr-ftp-prep-xfer-failed {
        value 84;
        description
          "The FTP prepare transfer command failed before starting the download operation.";
      }
      enum derr-ftp-bad-file-list {
        value 87;
        description
          "The FTP server returned a malformed or invalid file listing.";
      }
      enum derr-chunk-failed {
        value 88;
        description
          "An error occurred while processing chunk-based transfer encoding during the download.";
      }
      enum derr-no-con-avail {
        value 89;
        description
          "No network connection is available for the download operation.";
      }
      enum derr-ssl-pin-key-mismatch {
        value 90;
        description
          "The server's public key does not match the expected pinned public key.";
      }
      enum derr-ssl-bad-cert-status {
        value 91;
        description
          "The SSL certificate status received from the server is invalid or unrecognized.";
      }
      enum derr-http2-stream {
        value 92;
        description
          "An error occurred with the HTTP version 2 stream during the download operation.";
      }
    }
    description
      "Download error code type";
  }

  typedef fru-type {
    type enumeration {
      enum fru-rp {
        value 0;
        description
          "A Route Processor FRU";
      }
      enum fru-fp {
        value 1;
        description
          "An Embedded Services Processor FRU";
      }
      enum fru-cc {
        value 2;
        description
          "A Carrier Card FRU";
      }
      enum fru-max {
        value 3;
        description
          "An illegal value for FRU type";
      }
      enum fru-fc {
        value 4;
        description
          "A Fabric Card FRU";
      }
      enum fru-bp {
        value 5;
        description
          "A Bootstrap Plane FRU";
      }
    }
    description
      "FRU type";
  }

  typedef high-availability-role {
    type enumeration {
      enum ha-role-active {
        value 0;
        description
          "The role is Active";
      }
      enum ha-role-standby {
        value 1;
        description
          "The role is Standby";
      }
      enum ha-role-unknown {
        value 2;
        description
          "The role is unknown";
      }
    }
    description
      "The High Availability role";
  }

  grouping internal-location {
    description
      "Service location details";
    leaf fru {
      type common-types-ios-xe:fru-type;
      description
        "Field replaceable unit type";
    }
    leaf slot {
      type int16;
      description
        "Slot number";
    }
    leaf bay {
      type int16;
      description
        "Bay number";
    }
    leaf chassis {
      type int16;
      description
        "Chassis number";
    }
  }

  grouping extended-location {
    description
      "Extended service location details";
    leaf fru {
      type common-types-ios-xe:fru-type;
      description
        "Field replaceable unit (FRU) type";
    }
    leaf slot {
      type int16;
      description
        "Slot number";
    }
    leaf bay {
      type int16;
      description
        "Bay number";
    }
    leaf chassis {
      type int16;
      description
        "Chassis number";
    }
    leaf node {
      type uint16;
      description
        "Node number";
    }
  }
}
