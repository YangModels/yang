module Cisco-IOS-XE-gnss-dr-oper {
  yang-version 1.1;
  namespace "http://cisco.com/ns/yang/Cisco-IOS-XE-gnss-dr-oper";
  prefix gnss-dr-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE GNSS Dead Reckoning
     operational data.
     Copyright (c) 2020-2022 by Cisco Systems, Inc.
     All rights reserved.";

  revision 2022-11-01 {
    description
      "Update yang-version to 1.1";
    reference
      "1.2.0";
    cisco-semver:module-version "1.2.0";
  }
  revision 2021-07-01 {
    description
      "- Added GNSS DR NMEA UDP socket support.";
    reference
      "1.1.0";
    cisco-semver:module-version "1.1.0";
  }
  revision 2021-03-01 {
    description
      "Initial revision";
    reference
      "1.0.0";
    cisco-semver:module-version "1.0.0";
  }

  typedef gnss-dr-feature-state {
    type enumeration {
      enum all-gnss-dr-features-disabled {
        value 0;
        description
          "GNSS/DR module features in disabled state";
      }
      enum gps-dr-feature-enabled {
        value 1;
        description
          "GNSS/DR module in GPS enabled state";
      }
    }
    description
      "GNSS/DR feature state";
  }

  typedef gnss-dr-nmea-udp-config-state {
    type enumeration {
      enum gnss-dr-nmea-udp-socket-disabled {
        value 0;
        description
          "GNSS/DR NMEA UDP socket in disabled state";
      }
      enum gnss-dr-nmea-udp-socket-enabled {
        value 1;
        description
          "GNSS/DR NMEA UDP socket in enabled state";
      }
    }
    description
      "GNSS/DR NMEA UDP socket configuration state";
  }

  typedef gnss-dr-nmea-udp-oper-state {
    type enumeration {
      enum gnss-dr-nmea-udp-socket-inactive {
        value 0;
        description
          "GNSS/DR NMEA UDP socket in oper inactive state";
      }
      enum gnss-dr-nmea-udp-socket-active {
        value 1;
        description
          "GNSS/DR NMEA UDP socket in oper active state";
      }
      enum gnss-dr-nmea-udp-socket-error {
        value 2;
        description
          "GNSS/DR NMEA UDP socket in oper error state";
      }
    }
    description
      "GNSS/DR NMEA UDP socket oper state";
  }

  typedef gnss-dr-state {
    type enumeration {
      enum gps-dr-state-disabled {
        value 1;
        description
          "GNSS/DR module is in GPS disabled state";
      }
      enum gps-dr-state-acquiring {
        value 2;
        description
          "GNSS/DR module in GPS acquiring state";
      }
      enum gps-dr-state-enabled {
        value 3;
        description
          "GNSS/DR module in GPS enabled state";
      }
      enum gps-dr-loc-error {
        value 4;
        description
          "GNSS/DR module in GPS location error state";
      }
    }
    description
      "GNSS/DR operation state";
  }

  typedef gnss-dr-loc {
    type enumeration {
      enum gps-dr-location-fix-disabled {
        value 0;
        description
          "DR location fix is disabled";
      }
      enum gps-dr-location-fix-not-in-use {
        value 1;
        description
          "DR location fix is not in use";
      }
      enum gps-dr-location-fix-in-use {
        value 2;
        description
          "DR location fix is in use";
      }
    }
    description
      "GNSS/DR location fix state";
  }

  grouping gnss-dr-data {
    description
      "GNSS DR status entry details";
    leaf feature-state {
      type gnss-dr-ios-xe-oper:gnss-dr-feature-state;
      description
        "GNSS/DR feature state";
    }
    leaf oper-state {
      when "../feature-state != 'all-gnss-dr-features-disabled'";
      type gnss-dr-ios-xe-oper:gnss-dr-state;
      description
        "GNSS/DR oper state";
    }
    leaf dr-loc-used {
      when "../feature-state != 'all-gnss-dr-features-disabled'";
      type gnss-dr-ios-xe-oper:gnss-dr-loc;
      description
        "status for DR used for location";
    }
    leaf latitude {
      when "../feature-state != 'all-gnss-dr-features-disabled'";
      type decimal64 {
        fraction-digits 6;
      }
      description
        "GNSS/DR latitude value";
    }
    leaf longitude {
      when "../feature-state != 'all-gnss-dr-features-disabled'";
      type decimal64 {
        fraction-digits 6;
      }
      description
        "GNSS/DR longitude value";
    }
    leaf timestamp {
      when "../feature-state != 'all-gnss-dr-features-disabled'";
      type yang:date-and-time;
      description
        "GNSS/DR timestamp value";
    }
    leaf udp-socket-config-state {
      when "../feature-state != 'all-gnss-dr-features-disabled'";
      type gnss-dr-ios-xe-oper:gnss-dr-nmea-udp-config-state;
      description
        "GNSS/DR NMEA UDP socket config state";
    }
    leaf udp-socket-oper-state {
      when "(../feature-state != 'all-gnss-dr-features-disabled') and (../udp-socket-config-state != 'gnss-dr-nmea-udp-socket-disabled')";
      type gnss-dr-ios-xe-oper:gnss-dr-nmea-udp-oper-state;
      description
        "GNSS/DR NMEA UDP socket oper state";
    }
  }

  container gnss-dr-oper-data {
    config false;
    description
      "GNSS Dead Reckoning operational data";
    container gnss-dr-data {
      presence "gnss-dr-data";
      description
        "GNSS Dead Reckoning data";
      uses gnss-dr-ios-xe-oper:gnss-dr-data;
    }
  }
}
