module Cisco-IOS-XE-vlan-vxe-deviation {
  yang-version 1.1;
  namespace "http://cisco.com/ns/yang/Cisco-IOS-XE-vlan-vxe-deviation";
  prefix ios-vlan-d;

  import Cisco-IOS-XE-native {
    prefix ios;
  }
  import Cisco-IOS-XE-vlan {
    prefix ios-vlan;
  }

  organization
    "Cisco Systems, Inc.";
  description
    "Cisco XE Native Line, Quake Deviation Yang Model.
     Copyright (c) 2024 by Cisco Systems, Inc.
     All rights reserved.";

  revision 2024-11-01 {
    description
      "- Added deviation for vlan internal allocation policy";
  }

  deviation "/ios:native/ios:vlan/ios-vlan:internal/ios-vlan:allocation/ios-vlan:policy" {
    deviate not-supported;
  }
}
