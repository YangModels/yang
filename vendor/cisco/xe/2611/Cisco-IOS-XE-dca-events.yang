module Cisco-IOS-XE-dca-events {
  yang-version 1.1;
  namespace "http://cisco.com/ns/yang/Cisco-IOS-XE-dca-events";
  prefix dca-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for platform dynamic core allocation change events.
     Copyright (c) 2020, 2022 by Cisco Systems, Inc.
     All rights reserved.";

  revision 2022-11-01 {
    description
      "Update yang-version to 1.1";
    reference
      "1.1.0";
    cisco-semver:module-version "1.1.0";
  }
  revision 2021-03-01 {
    description
      "Initial revision";
    reference
      "1.0.0";
    cisco-semver:module-version "1.0.0";
  }

  typedef dca-change-type {
    type enumeration {
      enum dca-service-plane-heavy {
        value 0;
        description
          "DCA change to service plane heavy";
      }
      enum dca-data-plane-heavy {
        value 1;
        description
          "DCA change to data plane heavy";
      }
    }
    description
      "Platform resource DCA change type";
  }

  typedef dca-change-result-type {
    type enumeration {
      enum dca-change-start {
        value 0;
        description
          "Platform resource DCA change start";
      }
      enum dca-change-complete {
        value 1;
        description
          "Platform resource DCA change complete";
      }
      enum dca-change-failure {
        value 2;
        description
          "Platform resource DCA failed";
      }
    }
    description
      "Platform resource DCA change result";
  }

  grouping dca-change {
    description
      "Platform resource DCA change";
    leaf severity-level {
      type ios-common-ios-xe-oper:notification-severity;
      description
        "Event severity";
    }
    leaf host-name {
      type string;
      description
        "Event severity";
    }
    leaf system-ip {
      type inet:ip-address;
      description
        "System IP";
    }
    leaf dca-change-type {
      type dca-ios-xe-events:dca-change-type;
      description
        "DCA change type";
    }
    leaf result {
      type dca-ios-xe-events:dca-change-result-type;
      description
        "DCA change result";
    }
  }

  notification dca-change-event {
    description
      "DCA change notification";
    uses dca-ios-xe-events:dca-change;
  }
}
