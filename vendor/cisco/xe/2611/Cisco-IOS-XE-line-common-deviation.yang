module Cisco-IOS-XE-line-common-deviation {
  yang-version 1.1;
  namespace "http://cisco.com/ns/yang/Cisco-IOS-XE-line-common-deviation";
  prefix ios-line-common-d;

  import Cisco-IOS-XE-native {
    prefix ios;
  }

  organization
    "Cisco Systems, Inc.";
  description
    "Cisco XE Native Line, Deviation Yang Model.
     Copyright (c) 2023 by Cisco Systems, Inc.
     All rights reserved.";

  revision 2023-11-01 {
    description
      "- Added default for aux and console stopbits";
  }

  deviation "/ios:native/ios:line/ios:aux/ios:stopbits" {
    deviate add {
      default "1";
    }
  }

  deviation "/ios:native/ios:line/ios:console/ios:stopbits" {
    deviate add {
      default "2";
    }
  }
}
