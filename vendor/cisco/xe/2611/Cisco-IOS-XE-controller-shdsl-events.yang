module Cisco-IOS-XE-controller-shdsl-events {
  yang-version 1.1;
  namespace "http://cisco.com/ns/yang/Cisco-IOS-XE-controller-shdsl-events";
  prefix shdsl-controller-ios-xe-events;

  import Cisco-IOS-XE-controller-shdsl-common {
    prefix shdsl-ios-xe-common;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring SHDSL events.
     Copyright (c) 2019-2020, 2022 by Cisco Systems, Inc.
     All rights reserved.";

  revision 2022-11-01 {
    description
      "Update yang-version to 1.1";
    reference
      "2.1.0";
    cisco-semver:module-version "2.1.0";
  }
  revision 2020-07-01 {
    description
      "- Remove unused empty container shdsl-events";
    reference
      "2.0.0";
    cisco-semver:module-version "2.0.0";
  }
  revision 2020-03-01 {
    description
      "Initial revision";
    reference
      "1.0.0";
    cisco-semver:module-version "1.0.0";
  }

  typedef shdsl-notification-severity {
    type enumeration {
      enum shdsl-notif-severity-critical {
        value 0;
        description
          "Critical severity";
      }
      enum shdsl-notif-severity-major {
        value 1;
        description
          "Major severity";
      }
      enum shdsl-notif-severity-minor {
        value 2;
        description
          "Minor severity";
      }
    }
    description
      "SHDSL notification severity";
  }

  grouping shdsl-dslgrp-state-update-data {
    description
      "SHDSL group up-down notification related data";
    leaf severity {
      type shdsl-controller-ios-xe-events:shdsl-notification-severity;
      description
        "Notification severity";
    }
    container shdsl-controller {
      description
        "SHDSL controller slot and subslot";
      uses shdsl-ios-xe-common:shdsl-slot-info-key;
    }
    leaf group {
      type uint8;
      description
        "Group";
    }
    leaf group-state {
      type shdsl-ios-xe-common:group-state;
      description
        "Group state";
    }
  }

  grouping shdsl-efmbond-link-rate-update-data {
    description
      "SHDSL EFM bond link rate change notification related data";
    leaf severity {
      type shdsl-controller-ios-xe-events:shdsl-notification-severity;
      description
        "Notification severity";
    }
    container shdsl-controller {
      description
        "SHDSL controller slot and subslot";
      uses shdsl-ios-xe-common:shdsl-slot-info-key;
    }
    leaf group {
      type uint8;
      description
        "Group";
    }
    leaf link {
      type uint8;
      description
        "Link number";
    }
    leaf link-rate {
      type uint32;
      units "kbps";
      description
        "Current SHDSL link rate";
    }
  }

  grouping shdsl-efmbond-config-mismatch-notification-data {
    description
      "SHDSL EFM bond configuration mismatch notification related data";
    leaf severity {
      type shdsl-controller-ios-xe-events:shdsl-notification-severity;
      description
        "Notification severity";
    }
    container shdsl-controller {
      description
        "SHDSL controller slot and subslot";
      uses shdsl-ios-xe-common:shdsl-slot-info-key;
    }
    leaf link {
      type uint8;
      description
        "Link number";
    }
  }

  grouping shdsl-tclayer-mismatch-notification-data {
    description
      "SHDSL TC layer mismatch notification related data";
    leaf severity {
      type shdsl-controller-ios-xe-events:shdsl-notification-severity;
      description
        "Notification severity";
    }
    container shdsl-controller {
      description
        "SHDSL controller slot and subslot";
      uses shdsl-ios-xe-common:shdsl-slot-info-key;
    }
    leaf group {
      type uint8;
      description
        "Group";
    }
    leaf link {
      type uint8;
      description
        "Link number";
    }
    leaf configured-mode {
      type shdsl-ios-xe-common:mode-type;
      description
        "Configured mode";
    }
  }

  grouping shdsl-dying-gasp-notification-data {
    description
      "SHDSL dying gasp notification related data";
    leaf severity {
      type shdsl-controller-ios-xe-events:shdsl-notification-severity;
      description
        "Notification severity";
    }
    container shdsl-controller {
      description
        "SHDSL controller slot and subslot";
      uses shdsl-ios-xe-common:shdsl-slot-info-key;
    }
    leaf group {
      type uint8;
      description
        "Group";
    }
    leaf link {
      type uint8;
      description
        "Link number";
    }
  }

  grouping shdsl-efm-frame-size-internal-error-notification-data {
    description
      "SHDSL internal error notification related data while configuring MTU";
    leaf severity {
      type shdsl-controller-ios-xe-events:shdsl-notification-severity;
      description
        "Notification severity";
    }
    container shdsl-controller {
      description
        "SHDSL controller slot and subslot";
      uses shdsl-ios-xe-common:shdsl-slot-info-key;
    }
  }

  notification shdsl-dslgrp-state-update {
    description
      "SHDSL group state change notification";
    uses shdsl-controller-ios-xe-events:shdsl-dslgrp-state-update-data;
  }

  notification shdsl-efmbond-link-rate-update {
    description
      "SHDSL EFM bond link rate change notification";
    uses shdsl-controller-ios-xe-events:shdsl-efmbond-link-rate-update-data;
  }

  notification shdsl-efmbond-config-mismatch-notification {
    description
      "SHDSL EFM bond configuration mismatch notification";
    uses shdsl-controller-ios-xe-events:shdsl-efmbond-config-mismatch-notification-data;
  }

  notification shdsl-tclayer-mismatch-notification {
    description
      "SHDSL TC layer mismatch notification";
    uses shdsl-controller-ios-xe-events:shdsl-tclayer-mismatch-notification-data;
  }

  notification shdsl-dying-gasp-notification {
    description
      "SHDSL dying gasp notification";
    uses shdsl-controller-ios-xe-events:shdsl-dying-gasp-notification-data;
  }

  notification shdsl-efm-frame-size-internal-error-notification {
    description
      "SHDSL EFM frame size error. Internal error while configuring MTU";
    uses shdsl-controller-ios-xe-events:shdsl-efm-frame-size-internal-error-notification-data;
  }
}
