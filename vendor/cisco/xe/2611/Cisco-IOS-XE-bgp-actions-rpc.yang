module Cisco-IOS-XE-bgp-actions-rpc {
  yang-version 1.1;
  namespace "http://cisco.com/ns/yang/Cisco-IOS-XE-bgp-actions-rpc";
  prefix bgp-ios-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for BGP RPC action data.
     Copyright (c) 2022 by Cisco Systems, Inc.
     All rights reserved.";

  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  typedef bgp-gshut-client-enum {
    type enumeration {
      enum gshut-vrfs {
        value 0;
        description
          "BGP graceful shutdown across VRF neighbors in BGP session";
      }
      enum gshut-neighbors {
        value 1;
        description
          "BGP graceful shutdown for all neighbors";
      }
    }
    description
      "BGP graceful shutdown client";
  }

  grouping bgp-gshut-activate-type {
    description
      "Activate BGP graceful shutdown on BGP neighbors";
    leaf client {
      type bgp-ios-actions-rpc:bgp-gshut-client-enum;
      mandatory true;
      description
        "Activate graceful shutdown across all neighbors or only across VRF neighbors for BGP sessions";
    }
  }

  rpc bgp-gshut-activate-cmd {
    description
      "BGP graceful shutdown activate RPC";
    input {
      uses bgp-ios-actions-rpc:bgp-gshut-activate-type;
    }
  }
}
