module Cisco-IOS-XE-msdp-oper {
  yang-version 1.1;
  namespace "http://cisco.com/ns/yang/Cisco-IOS-XE-msdp-oper";
  prefix msdp-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for Multicast Source Discovery Protocol Operational data.
     Copyright (c) 2022-2023 by Cisco Systems, Inc.
     All rights reserved.";

  revision 2023-07-01 {
    description
      "Initial revision";
    reference
      "1.0.0";
    cisco-semver:module-version "1.0.0";
  }

  typedef msdp-connection-states {
    type enumeration {
      enum msdp-invalid-state {
        value 0;
        description
          "MSDP peer is invalid";
      }
      enum msdp-down-state {
        value 1;
        description
          "MSDP peer is down";
      }
      enum msdp-listen-state {
        value 2;
        description
          "MSDP peer is in listening mode";
      }
      enum msdp-connect-state {
        value 3;
        description
          "MSDP peer is connected";
      }
      enum msdp-up-state {
        value 4;
        description
          "MSDP peer is up";
      }
      enum msdp-shut-state {
        value 5;
        description
          "MSDP peer is shutdown";
      }
    }
    description
      "Connection types used to describe the current status of a peer";
  }

  typedef sa-filt-type {
    type enumeration {
      enum msdp-no-sa-filter {
        value 0;
        description
          "Source Active filter is not configured";
      }
      enum msdp-acl-filter {
        value 1;
        description
          "The Source Active filter has ACL based filtering";
      }
      enum msdp-routemap-filter {
        value 2;
        description
          "The Source Active filter has Route-map based filtering";
      }
      enum msdp-peer-filter {
        value 3;
        description
          "The Source Active filter has peer based filtering";
      }
    }
    description
      "MSDP source active message filter types";
  }

  grouping peer-filter {
    description
      "Is peer based filtering configured or not";
    leaf enabled {
      type empty;
      description
        "Peer filtering is enabled and all the incoming SA messages received from the peer are filtered out";
    }
  }

  grouping sa-filter {
    description
      "The Source Active filter that is configured for this peer which mode it is in";
    choice type-choice {
      description
        "Choice of the Source Active filter";
      case msdp-acl-filter {
        leaf acl-name {
          type string;
          description
            "The name of the ACL which filters a particular (S, G) state information in the incoming MSDP Source Active messages ";
        }
      }
      case msdp-routemap-filter {
        leaf routemap-name {
          type string;
          description
            "The name of the Route-map which filters a particular (S, G) state information in the incoming MSDP Source Active messages";
        }
      }
      case msdp-peer-filter {
        container filter {
          description
            "All incoming MSDP Source Active messages are filtered out if this is turned on";
          uses msdp-ios-xe-oper:peer-filter;
        }
      }
    }
  }

  grouping msdp-pt-entry {
    description
      "Non key entries for MSDP Peer table data";
    leaf as {
      type uint32;
      description
        "The Autonomous System where the peer address resides on";
    }
    leaf state {
      type msdp-ios-xe-oper:msdp-connection-states;
      description
        "Connection state of the peer";
    }
    leaf upsince {
      type yang:date-and-time;
      description
        "The Absolute time since the peer has been up";
    }
    leaf reset-count {
      type uint16;
      description
        "Count of session reset";
    }
    leaf sa-count {
      type uint32;
      description
        "Count of SA learned from this peer";
    }
    leaf address-namestring {
      type string;
      description
        "DNS hostname given for an IP address";
    }
    leaf peer-descr {
      type string;
      description
        "Human readable description given to a peer";
    }
    leaf connect-src-if-name {
      type string;
      description
        "Source interface used for establishing the MSDP connection";
    }
    leaf connect-src-addr {
      type inet:ip-address;
      description
        "Source IP address used for establishing the MSDP connection";
    }
    leaf in-count {
      type uint32;
      description
        "Number of messages received from peer";
    }
    leaf out-count {
      type uint32;
      description
        "Number of messages sent to peer";
    }
    leaf outpak-discarded {
      type uint16;
      description
        "Number of outbound messages discarded";
    }
    leaf last-clear {
      type yang:date-and-time;
      description
        "Timestamp of last clear";
    }
    leaf mesh-group-name {
      type string;
      description
        "Name of peer's mesh group";
    }
    container in-filter {
      description
        "Source Active filter to filter a particular (S, G) state information in the incoming MSDP Source Active messages";
      uses msdp-ios-xe-oper:sa-filter;
    }
    leaf safilter-rp-in {
      type string;
      description
        "Access list to filter the incoming MSDP SA messages from a specific RP";
    }
    leaf routemap-rp-in {
      type string;
      description
        "Route map to filter the incoming MSDP SA messages from a specific RP";
    }
    container out-filter {
      description
        "Source Active filter to filter a particular (S, G) state information in the outgoing MSDP Source Active messages";
      uses msdp-ios-xe-oper:sa-filter;
    }
    leaf safilter-rp-out {
      type string;
      description
        "Access list to filter the outgoing MSDP SA messages from a specific RP";
    }
    leaf routemap-rp-out {
      type string;
      description
        "Route map to filter the outgoing MSDP SA messages from a specific RP";
    }
    leaf ttl-threshold {
      type uint8;
      description
        "Configured TTL threshold";
    }
    leaf sa-limit {
      type uint32;
      description
        "Maximum number of SA cache entries allowed to learn from this peer";
    }
    leaf estb-trans-count {
      type uint32;
      description
        "Number of MSDP state transitions to established state";
    }
    leaf inputq-count {
      type uint32;
      description
        "The number of packets in input queue";
    }
    leaf outputq-count {
      type uint32;
      description
        "The number of packets in output queue";
    }
    leaf password-enabled {
      type boolean;
      description
        "Is MD5 password enabled or not for the peer";
    }
    leaf rpf-failures {
      type uint32;
      description
        "The number of SA messages received from this peer that failed the Peer RPF check";
    }
    leaf in-sas {
      type uint32;
      description
        "The number of MSDP SA messages received from this peer";
    }
    leaf out-sas {
      type uint32;
      description
        "The number of MSDP SA messages sent to this peer";
    }
    leaf in-data-pkts {
      type uint32;
      description
        "The total number of encapsulated data packets received from this peer";
    }
    leaf out-data-pkts {
      type uint32;
      description
        "The total number of encapsulated data packets sent to this peer";
    }
    leaf estb-trans-time {
      type yang:date-and-time;
      description
        "This timestamp is set to the value of system uptime when a peer
         transitions into or out of the ESTABLISHED state. It is set to
         zero when the MSDP speaker is booted";
    }
    leaf last-input {
      type yang:date-and-time;
      description
        "Timestamp of last received input";
    }
    leaf peer-local-address {
      type inet:ip-address;
      description
        "The local IP address of the peer used for the MSDP connection";
    }
    leaf peer-connect-retry-intvl {
      type uint16;
      description
        "Interval that the MSDP peers wait before re-trying the connection";
    }
    leaf peer-hold-time {
      type uint32;
      description
        "Interval that the MSDP peer waits for keepalive messages before declaring the session as down";
    }
    leaf keepalive-period {
      type uint32;
      description
        "Interval at which the MSDP peer sends keepalive messages";
    }
    leaf peer-remote-port {
      type uint16;
      description
        "The remote port for the TCP connection between the MSDP peers";
    }
    leaf peer-local-port {
      type uint16;
      description
        "The local port for the TCP connection between the MSDP peers";
    }
    leaf connection-attempts {
      type uint32;
      description
        "The number of TCP connection attempts";
    }
  }

  grouping msdp-st-entry {
    description
      "Non key entries for MSDP SA Cache data";
    leaf as {
      type uint32;
      description
        "The Autonomous System where the peer address resides on";
    }
    leaf upsince {
      type yang:date-and-time;
      description
        "The Absolute time since the peer has been up";
    }
    leaf expires {
      type yang:date-and-time;
      description
        "The Time till the peer expires";
    }
    leaf peer {
      type inet:ip-address;
      description
        "The peer from which this SA Cache entry was created";
    }
    leaf num-in-sas {
      type uint32;
      description
        "The Number of SA messages relevant to this cache entry";
    }
    leaf num-in-data-pkts {
      type uint32;
      description
        "The Number of data packets received, relevant to this cache entry";
    }
    leaf rpf-peer {
      type inet:ip-address;
      description
        "The peer from which an SA message corresponding to this cache entry would be accepted";
    }
  }

  grouping msdp-peertype-table-key {
    description
      "MSDP peer table key";
    leaf vrf {
      type string;
      description
        "MSDP VRF name, if it is default vrf use 'IPv4 default'";
    }
    leaf peer-address {
      type inet:ip-address;
      description
        "MSDP Peer address";
    }
  }

  grouping msdp-statetype-table-key {
    description
      "MSDP SA Cache table key";
    leaf vrf {
      type string;
      description
        "MSDP VRF name, if it is default vrf use 'IPv4 default'";
    }
    leaf grp-addr {
      type inet:ip-address;
      description
        "The group address of the SA Cache entry";
    }
    leaf src-addr {
      type inet:ip-address;
      description
        "The source address of the SA Cache entry";
    }
    leaf rp-addr {
      type inet:ip-address;
      description
        "The Rendezvous Point of the SA Cache entry";
    }
  }

  container msdp-oper-data {
    config false;
    description
      "Multicast Source Discovery Protocol Operational data";
    list msdp-pt-entry {
      key "vrf peer-address";
      description
        "Non key entries for MSDP Peer table data";
      uses msdp-ios-xe-oper:msdp-pt-entry;
      uses msdp-ios-xe-oper:msdp-peertype-table-key;
    }
    list msdp-st-entry {
      key "vrf grp-addr src-addr rp-addr";
      description
        "Non key entries for MSDP SA Cache data";
      uses msdp-ios-xe-oper:msdp-st-entry;
      uses msdp-ios-xe-oper:msdp-statetype-table-key;
    }
  }
}
