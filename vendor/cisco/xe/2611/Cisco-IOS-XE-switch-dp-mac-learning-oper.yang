module Cisco-IOS-XE-switch-dp-mac-learning-oper {
  yang-version 1.1;
  namespace "http://cisco.com/ns/yang/Cisco-IOS-XE-switch-dp-mac-learning-oper";
  prefix switch-dp-mac-learning-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for switch device datapath MAC learning statistics
     Copyright (c) 2019-2020, 2022 by Cisco Systems, Inc.
     All rights reserved.";

  revision 2022-11-01 {
    description
      "Update yang-version to 1.1";
    reference
      "1.1.0";
    cisco-semver:module-version "1.1.0";
  }
  revision 2020-07-01 {
    description
      "Initial revision";
    reference
      "1.0.0";
    cisco-semver:module-version "1.0.0";
  }

  grouping learning-stats {
    description
      "Datapath MAC learning statistics";
    leaf learning-error-count {
      type uint32;
      description
        "Count of learning errors";
    }
    leaf learning-cache-count {
      type uint32;
      description
        "Count of learning cache entries";
    }
    leaf learning-cache-validation-failure {
      type uint32;
      description
        "Count of learning cache validation failures";
    }
  }

  grouping datapath-mac-learning-stats {
    description
      "MAC address learning statistics";
    leaf general-err-count {
      type uint32;
      description
        "Count of general errors";
    }
    leaf ios-notif-count {
      type uint32;
      description
        "Count of notifications sent to IOS process";
    }
    leaf ios-notif-cache-count {
      type uint32;
      description
        "Count of cached notifications sent to IOS process";
    }
    container l2-accumulated {
      description
        "Layer 2 learning counters";
      uses switch-dp-mac-learning-oper:learning-stats;
    }
    container l3-accumulated {
      description
        "Layer 3 learning counters";
      uses switch-dp-mac-learning-oper:learning-stats;
    }
  }

  grouping mac-learning-statistics {
    description
      "This object contains datapath MAC learning statistics";
    container stats {
      description
        "This object contains the counters";
      uses switch-dp-mac-learning-oper:datapath-mac-learning-stats;
    }
  }

  container switch-dp-mac-learning-oper-data {
    config false;
    description
      "Switching device datapath MAC learning operational data";
    list location {
      key "fru slot bay chassis node";
      description
        "A list of data provider locations";
      uses common-types-ios-xe:extended-location;
      container mac-learning-stats {
        presence "mac-learning-stats";
        description
          "This object contains MAC learning statistics";
        uses switch-dp-mac-learning-oper:mac-learning-statistics;
      }
    }
  }
}
