module Cisco-IOS-XE-mobileip {
  yang-version 1.1;
  namespace "http://cisco.com/ns/yang/Cisco-IOS-XE-mobileip";
  prefix ios-mobileip;

  import cisco-semver {
    prefix cisco-semver;
  }
  import ietf-inet-types {
    prefix inet;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Proxy Mobile IPv6 Yang model.
     Copyright (c) 2020 by Cisco Systems, Inc.
     All rights reserved.";

  revision 2022-11-01 {
    description
      "- Update yang-version to 1.1";
    cisco-semver:module-version "2.1.0";
  }
  revision 2020-11-01 {
    description
      "- Adding the remaining Local Mobility Anchor and MAG commands";
    cisco-semver:module-version "2.0.0";
  }
  revision 2020-07-01 {
    description
      "- Initial Version";
    cisco-semver:module-version "1.0.0";
  }

  grouping profile-definition-grouping {
    leaf loadbalance {
      description
        "Set load balance";
      type empty;
    }
    container jitter {
      description
        "Specify a jitter value";
      leaf value {
        description
          "DSCP for control plane msg";
        type uint16 {
          range "1..1000";
        }
      }
      leaf low-threshold {
        description
          "Jitter lower threshold value";
        type uint16 {
          range "1..1000";
        }
      }
    }
    container mos {
      description
        "Specify a mos value for voice";
      leaf value {
        description
          "mos vale * 100";
        type uint16 {
          range "1..60000";
        }
      }
      leaf low-threshold {
        description
          "MOS lower threshold";
        type uint16 {
          range "1..60000";
        }
      }
    }
    container packet-loss {
      description
        "Specify a packet loss value";
      leaf value {
        description
          "packet loss value in %";
        type uint8 {
          range "1..100";
        }
      }
      leaf low-threshold {
        description
          "packet-loss lower threshold value";
        type uint8 {
          range "1..100";
        }
      }
    }
    container rtt {
      description
        "Specify a rtt value";
      leaf value {
        description
          "rtt value in milli sec";
        type uint16 {
          range "1..5000";
        }
      }
      leaf low-threshold {
        description
          "RTT lower threshold value";
        type uint16 {
          range "1..5000";
        }
      }
    }
  }

  grouping mobile-network-option-grouping {
    container mobile-network {
      description
        "mobile router network";
      list pool {
        description
          "pool starting address";
        key "pool-ip-add";
        leaf pool-ip-add {
          description
            "pool starting address";
          type inet:ipv4-address;
        }
        leaf pool-prefix {
          description
            "v4 pool prefix length";
          type uint8 {
            range "8..24";
          }
        }
        leaf network-prefix {
          description
            "v4 network prefix length";
          type uint8 {
            range "8..32";
          }
        }
      }
      list v6pool {
        description
          "IPv6 pool starting address";
        key "pool-ipv6-add";
        leaf pool-ipv6-add {
          description
            "pool starting address";
          type inet:ipv6-address;
        }
        leaf pool-prefix {
          description
            "v6 pool prefix length";
          type uint8 {
            range "8..64";
          }
        }
        leaf network-prefix {
          description
            "v6 network prefix length";
          type uint8 {
            range "8..64";
          }
        }
      }
    }
  }

  grouping transport-default-grouping {
    container transport-default {
      description
        "Default transport configuration values";
      container transport {
        description
          "Default transport configuration values";
        presence "true";
        leaf ipv4-address {
          description
            "Configure Customer IPv4 Transport address";
          type inet:ipv4-address;
        }
        leaf ipv6-address {
          description
            "Configure Customer IPv6 Transport address";
          type inet:ipv6-address;
        }
      }
    }
  }

  grouping transport-vrf-grouping {
    container transport-vrf {
      description
        "Configure Transport or Peering VRF";
      list transport {
        description
          "Configure Transport or Peering VRF";
        key "vrf-name";
        leaf vrf-name {
          description
            "VRF Name";
          type string;
        }
        leaf ipv4-address {
          description
            "Configure Customer IPv4 Transport address";
          type inet:ipv4-address;
        }
        leaf ipv6-address {
          description
            "Configure Customer IPv6 Transport address";
          type inet:ipv6-address;
        }
      }
    }
  }

  grouping dscp-option-grouping {
    container dscp {
      description
        "DSCP setting";
      leaf control-plane {
        description
          "DSCP for control plane msg";
        type uint8 {
          range "1..63";
        }
      }
      leaf force {
        description
          "force";
        type empty;
      }
    }
  }

  grouping ignore-option-grouping {
    container ignore {
      description
        "Configure ignore options";
      leaf grekey {
        description
          "ignore keys for GRE encapsulation";
        type empty;
      }
      leaf home-address {
        description
          "ignore Home Address for MN";
        type empty;
      }
    }
  }

  grouping heartbeat-default-grouping {
    container heartbeat-default {
      description
        "Default heartbeat configuration values";
      container heartbeat {
        description
          "periodic verification of reachability";
        leaf interval {
          description
            "specify the interval periodicity (in secs)";
          must '(../ios-mobileip:retries) and (../ios-mobileip:timeout)' {
            error-message "Select all the three leaves.";
          }
          type uint16 {
            range "1..3600";
          }
        }
        leaf retries {
          description
            "Heartbeat Retries";
          must '(../ios-mobileip:interval) and (../ios-mobileip:timeout)' {
            error-message "Select all the three leaves.";
          }
          type uint8 {
            range "1..10";
          }
        }
        leaf timeout {
          description
            "specify the timeout periodicity (in secs)";
          must '(../ios-mobileip:interval) and (../ios-mobileip:retries)' {
            error-message "Select all the three leaves.";
          }
          type uint16 {
            range "1..3600";
          }
        }
      }
    }
  }

  grouping heartbeat-label-grouping {
    list heartbeat {
      description
        "heartbeat configuration per link label type";
      key "label";
      leaf interval {
        description
          "specify the interval periodicity (in secs)";
        type uint16 {
          range "1..3600";
        }
      }
      leaf retries {
        description
          "Heartbeat Retries";
        type uint8 {
          range "1..10";
        }
      }
      leaf label {
        description
          "link label name";
        type string;
      }
      leaf natreboot {
        description
          "detect nat reboot";
        type empty;
      }
      leaf timeout {
        description
          "specify the timeout periodicity (in secs)";
        mandatory true;
        type uint16 {
          range "1..3600";
        }
      }
    }
  }

  grouping pool-ipv6-grouping {
    container ipv6 {
      description
        "IPv6 pool configuration for network";
      leaf name {
        description
          "IPv6 address pool name";
        type string;
      }
      leaf pfxlen {
        description
          "length of the pool";
        type uint8 {
          range "0..128";
        }
      }
    }
  }

  grouping pool-ipv4-grouping {
    container ipv4 {
      description
        "IPv4 pool configuration for network";
      leaf name {
        description
          "IPv4 address pool name";
        type string;
      }
      leaf pfxlen {
        description
          "length of the pool";
        type uint8 {
          range "0..32";
        }
      }
    }
  }

  grouping tracing-option-grouping {
    leaf tracing {
      description
        "Enable Log Tracing";
      type empty;
    }
  }

  grouping multipath-option-grouping {
    leaf multipath {
      description
        "Enable multipath";
      type empty;
    }
  }

  grouping generate-option-grouping {
    container generate {
      description
        "generate gre key for MN";
      leaf grekey {
        description
          "GRE keys for MN";
        type boolean;
        default "true";
      }
    }
  }

  grouping bri-option-grouping {
    container bri {
      description
        "local mobility anchor BRI options";
      container delay {
        description
          "time to wait before sending bri msg";
        leaf min {
          description
            "minimum time delay to send BRI (in milliseconds)";
          must '. <= ../max' {
            error-message "Min value must be <= max value";
          }
          type uint16 {
            range "500..65535";
          }
          default "1000";
        }
        leaf max {
          description
            "maximum time delay to send BRI (in milliseconds)";
          must '. >= ../min' {
            error-message "Max value must be >= min value";
          }
          type uint16 {
            range "500..65535";
          }
          default "2000";
        }
      }
      leaf retries {
        description
          "Number of retransmissions allowed for BRI msg";
        type uint8 {
          range "1..10";
        }
        default "1";
      }
    }
  }

  grouping ani-option-grouping {
    leaf ani {
      description
        "Enable Access Network Identifier option";
      type empty;
    }
  }

  grouping auth-key-options-grouping {
    container key {
      description
        "Security key";
      choice key-options {
        description
          "Key type options";
        container key-opts {
          description
            "Non-Hex key options";
          leaf enc-type {
            description
              "Encryption type (0 - Not encrypted)";
            type uint8 {
              range "0..7";
            }
          }
          leaf ascii {
            description
              "Key entered in ASCII";
            type string;
          }
        }
        leaf hex {
          description
            "Key entered in hex string";
          type string {
            pattern '[0-9a-fA-F]+';
            length "2 .. 128";
          }
        }
      }
    }
  }

  grouping auth-option-grouping {
    container auth-option {
      description
        "Authentication Option";
      container spi {
        description
          "Security Parameter Index";
        choice spi-option {
          description
            "Given SPI choices";
          leaf hex-val {
            description
              "SPI hex value";
            type string;
          }
          leaf decimal {
            description
              "SPI decimal integer value";
            type uint32 {
              range "256..12345678";
            }
          }
        }
        uses auth-key-options-grouping;
      }
    }
  }

  grouping label-bandwidth-grouping {
    list label {
      description
        "label for link-type";
      key "label-name";
      leaf label-name {
        description
          "Label name";
        type string;
      }
      leaf bandwidth-ratio {
        description
          "bandwidth ratio";
        type uint8 {
          range "1..15";
        }
      }
    }
  }

  grouping sla-option-grouping {
    leaf frequency {
      description
        "Frequency of SLA operation";
      type uint32 {
        range "1..604800";
      }
    }
    leaf interval {
      description
        "Inter Packet Interval";
      type uint16 {
        range "4..6000";
      }
    }
    leaf num-packets {
      description
        "Number of Packets to be transmitted";
      type uint32 {
        range "1..100";
      }
    }
  }

  grouping mobility-service-mobile-local-loop-mnp-grouping {
    container customer {
      description
        "No of MNPs per customer";
      leaf maximum {
        description
          "maximum no of MNPs";
        type uint32 {
          range "1..4000000";
        }
        default "2000";
      }
    }
    container logical-mn {
      description
        "No of MNPs per logical-mn";
      leaf maximum {
        description
          "maximum no of MNPs";
        type uint8 {
          range "1..32";
        }
        default "16";
      }
    }
  }

  grouping mobility-service-mobile-local-loop-mnp {
    container mnp {
      description
        "mobile network prefix limits";
      container afi-all {
        description
          "All Address Family";
        uses mobility-service-mobile-local-loop-mnp-grouping;
      }
      container ipv4 {
        description
          "IPv4 Address Family";
        uses mobility-service-mobile-local-loop-mnp-grouping;
      }
      container ipv6 {
        description
          "IPv6 Address Family";
        uses mobility-service-mobile-local-loop-mnp-grouping;
      }
    }
  }

  grouping lma-address-grouping {
    container address {
      description
        "Specifies local mobility anchor ipv4 and ipv6 address";
      list ipv4 {
        description
          "local mobility anchor ipv4 address";
        key "address";
        leaf address {
          description
            "local mobility anchor ipv4 address";
          type inet:ipv4-address;
        }
      }
      list ipv6 {
        description
          "local mobility anchor ipv6 address";
        key "address";
        leaf address {
          description
            "local mobility anchor ipv6 address";
          type inet:ipv6-address;
        }
      }
    }
  }

  grouping customer-key-default-grouping {
    container gre-key-default {
      description
        "Default key for this customer for all labels";
      container gre-key {
        description
          "GRE key config for the customer";
        leaf symmetric {
          description
            "symmetric key for the customer";
          type uint32 {
            range "1..4294967295";
          }
        }
      }
    }
  }

  grouping customer-key-label-grouping {
    list gre-key {
      description
        "gre key for this customer";
      key "label";
      leaf symmetric {
        description
          "symmetric key for the customer";
        type uint32 {
          range "1..4294967295";
        }
      }
      leaf label {
        description
          "LABEL string";
        type string;
      }
    }
  }

  grouping tunnel-template-grouping {
    container tunnel-template-only {
      description
        "Configure a tunnel template for tunnels";
      container tunnel-template {
        description
          "Configure a tunnel template for tunnels";
        leaf Tunnel {
          description
            "Configure a tunnel template for tunnels";
          type string;
        }
      }
    }
  }

  grouping tunnel-template-label-grouping {
    list tunnel-template {
      description
        "Tunnel interface";
      key "label";
      leaf Tunnel {
        description
          "Tunnel interface";
        type string;
      }
      leaf label {
        description
          "tunnel template for specific label";
        type string;
      }
    }
  }

  grouping config-ipv6-mobileip-grouping {
    container mobile {
      description
        "Mobile IPv6";
      list pmipv6-domain {
        description
          "Proxy Mobile IPv6 Domain";
        max-elements 1;
        key "domain";
        leaf domain {
          description
            "Proxy Mobile IPv6 Domain";
          type string;
        }
        container domain-options {
          description
            "Domain options";
          uses auth-option-grouping;
          container encap {
            description
              "encapsulation type between MAG and local mobility anchor";
            leaf encap_type {
              description
                "encapsulation type options";
              type enumeration {
                enum gre-ipv4;
                enum gre-ipv6;
                enum udptunnel;
              }
            }
          }
          list lma {
            description
              "local mobility anchor identifier";
            key "identifier";
            leaf identifier {
              description
                "local mobility anchor identifier";
              type string;
            }
            leaf ipv4-address {
              description
                "A.B.C.D  local mobility anchor IPv4 address";
              type inet:ipv4-address;
            }
            leaf ipv6-address {
              description
                "X:X:X:X::X  local mobility anchor IPv6 address";
              type inet:ipv6-address;
            }
          }
          leaf local-routing-mag {
            description
              "Enable local routing for this MAG";
            type empty;
          }
          list mag {
            description
              "MAG identifier";
            key "identifier";
            leaf identifier {
              description
                "MAG identifier";
              type string;
            }
            leaf ipv4-address {
              description
                "A.B.C.D  MAG IPv4 address";
              type inet:ipv4-address;
            }
            leaf ipv6-address {
              description
                "X:X:X:X::X MAG IPv6 address";
              type inet:ipv6-address;
            }
          }
          leaf mn-profile-load-aaa {
            description
              "Pull MN profile from AAA for incoming requests";
            type empty;
          }
          list mobile-map {
            description
              "mobile map to enable on this Local Mobility Anchor";
            key "map-name sequence";
            leaf map-name {
              description
                "mobile map config for application based routing";
              type string;
            }
            leaf sequence {
              description
                "sequence to insert this map";
              type uint8 {
                range "1..255";
              }
            }
            container ip {
              description
                "setting ip options for this mobile map";
              leaf df {
                description
                  "Dont Fragment bit";
                type uint8 {
                  range "0..1";
                }
              }
            }
            leaf loadbalance {
              description
                "Enable per-flow load balance";
              type empty;
            }
            container match {
              description
                "setting match clause for this mobile map";
              leaf access-list {
                description
                  "access list name";
                type string;
              }
            }
            container setlink {
              description
                "setting link types for this mobile map";
              container link-type {
                description
                  "link type";
                leaf link1 {
                  description
                    "Link type 1 (NULL to drop, NULL must be the last input string)";
                  type string;
                }
                leaf link2 {
                  description
                    "Link type 2 (NULL to drop, NULL must be the last input string)";
                  type string;
                }
                leaf link3 {
                  description
                    "Link type 3 (NULL to drop, NULL must be the last input string)";
                  type string;
                }
                leaf link4 {
                  description
                    "Link type 4 (NULL to drop, NULL must be the last input string)";
                  type enumeration {
                    enum NULL;
                  }
                }
              }
            }
            container traffic-profile {
              description
                "Set traffic profile to apply";
              leaf prof-name {
                description
                  "profile string";
                type string;
              }
            }
          }
          list nai {
            description
              "Network access identifier or realm";
            key "realm";
            leaf realm {
              description
                "username@realm";
              type string;
            }
            leaf apn {
              description
                "APN name";
              type string;
            }
            uses auth-option-grouping;
            leaf customer {
              description
                "Customer name";
              type string;
            }
            container gre-encap-key {
              description
                "Configure gre encap key for up/down stream";
              leaf down {
                description
                  "downstream key";
                type uint32 {
                  range "1..4294967295";
                }
              }
              leaf up {
                description
                  "upstream key";
                type uint32 {
                  range "1..4294967295";
                }
              }
            }
            leaf lma {
              description
                "local mobility anchor identifier";
              type string;
            }
            container mobility-service {
              description
                "Service offered to this MN";
              leaf mobile-local-loop {
                description
                  "Wireless Private Routing";
                type empty;
              }
            }
            leaf network {
              description
                "Network name";
              type string;
            }
            container service {
              description
                "Specify the service provided to MN";
              leaf service-type {
                description
                  "Service options for MN";
                type enumeration {
                  enum dual;
                  enum ipv4;
                  enum ipv6;
                }
                default "ipv4";
              }
            }
          }
          container replay-protection {
            description
              "Configure replay protection mechanism within domain";
            container timestamp {
              description
                "timestamp option";
              leaf window {
                description
                  "configure the window value";
                type uint8 {
                  range "3..255";
                }
                default "7";
              }
            }
          }
        }
      }
      list pmipv6-lma {
        description
          "Proxy Mobile IPv6 local mobility anchor";
        key "lma-name domain";
        max-elements 1;
        leaf lma-name {
          description
            "Proxy Mobile IPv6 local mobility anchor";
          type string;
        }
        leaf domain {
          description
            "Domain name";
          type string;
          must '/ios:native/ios:ipv6/ios-mobileip:mobile/ios-mobileip:pmipv6-domain[ios-mobileip:domain=current()] ' {
            error-message "Domain name mismatch";
          }
        }
        uses ani-option-grouping;
        uses bri-option-grouping;
        uses generate-option-grouping;
        uses heartbeat-default-grouping;
        uses heartbeat-label-grouping;
        uses ignore-option-grouping;
        uses multipath-option-grouping;
        uses dscp-option-grouping;
        uses lma-address-grouping;
        container mobile-route {
          description
            "distance for local mobility anchor mobile routes";
          leaf admin-distance {
            description
              "distance metric";
            type uint8 {
              range "1..255";
            }
          }
        }
        container bce {
          description
            "local mobility anchor binding options";
          leaf create-wait-time {
            description
              "bce create wait time interval (in milliseconds)";
            type uint16 {
              range "1..65535";
            }
            default "1500";
          }
          leaf delete-wait-time {
            description
              "bce delete wait time interval (in milliseconds)";
            type uint16 {
              range "1..65535";
            }
            default "10000";
          }
          leaf lifetime {
            description
              "Maximum bce lifetime (in seconds)";
            type uint16 {
              range "10..65535";
            }
            default "3600";
          }
          leaf maximum {
            description
              "Maximum bce entries";
            type uint32 {
              range "1..128000";
            }
            default "128000";
          }
        }
        container default {
          description
            "default profile for this local mobility anchor";
          leaf profile {
            description
              "default profile for this local mobility anchor";
            type string;
          }
        }
        container dynamic {
          description
            "learn mag dynamically";
          container mag {
            description
              "Mobile Access Gateway";
            leaf learning {
              description
                "learn the connecting mag";
              type empty;
            }
          }
        }
        container enable {
          description
            "enable accounting for local mobility anchor";
          container aaa {
            description
              "AAA attributes";
            leaf accounting {
              description
                "Accounting";
              type empty;
            }
          }
        }
        container enforce {
          description
            "Enforcing HB values";
          leaf heartbeat-to-mag {
            description
              "send HB values to mag";
            type empty;
          }
        }
        list interface {
          description
            "Configure local mobility anchor correspondent node interface";
          key "interface-name";
          leaf interface-name {
            description
              "Name of the interface";
            type string;
          }
        }
        leaf mobile-map {
          description
            "mobile map to enable on this Local Mobility Anchor";
          must '../ios-mobileip:multipath' {
            error-message "Multipath not configured, cannot config mobile map";
          }
          type string;
        }
        container mobile-network {
          description
            "validate mobile network prefixes of MN";
          leaf mobile-network-type {
            description
              "Mobile NW prefix options for MN";
            type enumeration {
              enum unauthorized;
              enum aaa-authorized;
            }
          }
        }
        list rat {
          description
            "RAT type for this local mobility anchor";
          key "rat-type";
          leaf rat-type {
            description
              "RAT type for this local mobility anchor";
            type enumeration {
              enum 3GPP2_1_RTT;
              enum 3GPP2_EHRPD;
              enum 3GPP2_HRPD;
              enum 3GPP2_UMB;
              enum 3GPP_E_UTRAN;
              enum 3GPP_GERAN;
              enum 3GPP_UTRAN;
              enum ETHERNET;
              enum PPP;
              enum VIRTUAL;
              enum WIMAX;
              enum WLAN;
            }
          }
          leaf priority {
            description
              "priority value for the RAT type";
            type uint8;
          }
        }
        container replay-protection {
          description
            "Configure replay protection mechanism within domain";
          container timestamp {
            description
              "timestamp option";
            leaf window {
              description
                "configure the window value";
              type union {
                type uint8 {
                  range "3..255";
                }
                type enumeration {
                  enum ignore;
                }
              }
              default "7";
            }
          }
        }
        container tunnel {
          description
            "tunnel parameters for this local mobility anchor";
          leaf acl {
            description
              "Input acl to be applied";
            type string;
          }
          leaf mtu {
            description
              "tunnel ip mtu";
            type uint16 {
              range "68..17916";
            }
          }
        }
        list mag {
          description
            "MAG options for this local mobility anchor";
          key "mag-id domain-name";
          leaf mag-id {
            description
              "MAG identifier";
            type string;
          }
          leaf domain-name {
            description
              "Domain-name for this MAG";
            type string;
            must '/ios:native/ios:ipv6/ios-mobileip:mobile/ios-mobileip:pmipv6-domain[ios-mobileip:domain=current()] ' {
              error-message "Domain name mismatch";
            }
          }
          uses auth-option-grouping;
          uses dscp-option-grouping;
          container encap {
            description
              "encapsulation type between MAG and local mobility anchor";
            choice encap-type {
              description
                "encapsulation type choices";
              leaf gre-ipv4 {
                description
                  "GRE in V4 encapsulation";
                must '../../ios-mobileip:ipv4-address' {
                  error-message "Cannot Configure Encap gre-ipv4 without configuring ipv4 address in MAG";
                }
                type empty;
              }
              leaf gre-ipv6 {
                description
                  "GRE in V6 encapsulation";
                must "((../../ios-mobileip:ipv4-address)
                      or (../../ios-mobileip:ipv6-address))" {
                  error-message "Configuration of IPV6/IPV4 address for MAG is mandatory";
                }
                type empty;
              }
            }
          }
          leaf ipv4-address {
            description
              "MAG IPv4 address";
            type inet:ipv4-address;
          }
          leaf ipv6-address {
            description
              "MAG IPv6 address";
            type inet:ipv6-address;
          }
        }
        list network {
          description
            "network that this local mobility anchor supports";
          key "nw-name";
          leaf nw-name {
            description
              "network name";
            type string;
          }
          container pool {
            description
              "pool for ipv6/ipv4 prefixes";
            uses pool-ipv4-grouping;
            uses pool-ipv6-grouping;
          }
          container mobile-network {
            description
              "mobile router network";
            list pool {
              description
                "pool starting address";
              key "pool-ip-add";
              leaf pool-ip-add {
                description
                  "pool starting address";
                type inet:ipv4-address;
              }
              leaf pool-prefix {
                description
                  "v4 pool prefix length";
                type uint8 {
                  range "8..24";
                }
              }
              leaf network-prefix {
                description
                  "v4 network prefix length";
                type uint8 {
                  range "8..32";
                }
              }
            }
            list v6pool {
              description
                "IPv6 pool starting address";
              key "pool-ipv6-add";
              leaf pool-ipv6-add {
                description
                  "pool starting address";
                type inet:ipv6-address;
              }
              leaf pool-prefix {
                description
                  "v6 pool prefix length";
                type uint8 {
                  range "8..64";
                }
              }
              leaf network-prefix {
                description
                  "v6 network prefix length";
                type uint8 {
                  range "8..64";
                }
              }
            }
          }
          container dns {
            description
              "DNS address";
            container ip {
              description
                "DNS ip address";
              leaf pri-ip-add {
                description
                  "Primary DNS ip";
                type inet:ipv4-address;
              }
              leaf sec-ip-add {
                description
                  "Secondary DNS ip";
                type inet:ipv4-address;
              }
            }
          }
        }
        container mobility-service {
          description
            "Service support by this local mobility anchor";
          container hybrid-access {
            description
              "Hybrid Access for optimal routing";
            presence "true";
            leaf disable-sla {
              description
                "disable IP SLA probes";
              type boolean;
              default "true";
            }
            list enable-sla {
              description
                "Enable SLA configuration";
              key "sla-type name";
              leaf sla-type {
                description
                  "SLA type";
                type enumeration {
                  enum customer;
                  enum mag;
                }
              }
              leaf name {
                description
                  "SLA name";
                type string;
              }
              uses sla-option-grouping;
            }
            container sla {
              description
                "Hybrid ACCESS SLA configuration";
              when "../ios-mobileip:disable-sla = 'false'";
              uses sla-option-grouping;
            }
            container bandwidth-ratio {
              description
                "set bandwidth ratio for each link-type";
              presence "true";
              uses label-bandwidth-grouping;
              list mag {
                description
                  "set bandwidth ratio for each mag";
                key "mag-name";
                leaf mag-name {
                  description
                    "mag name";
                  type string;
                }
                uses label-bandwidth-grouping;
              }
            }
            list profile-definition {
              description
                "Traffic performance profile definition";
              key "name";
              leaf name {
                description
                  "Name";
                type string;
              }
              leaf loadbalance {
                description
                  "Mobile local loop";
                type empty;
              }
              container jitter {
                description
                  "Specify a jitter value";
                leaf value {
                  description
                    "jitter value";
                  type uint16 {
                    range "1..1000";
                  }
                }
                leaf low-threshold {
                  description
                    "Jitter lower threshold value";
                  type uint16 {
                    range "1..1000";
                  }
                }
              }
              container mos {
                description
                  "Specify a mos value for voice";
                leaf value {
                  description
                    "mos value * 100";
                  type uint16 {
                    range "1..60000";
                  }
                }
                leaf low-threshold {
                  description
                    "MOS lower threshold";
                  type uint16 {
                    range "1..60000";
                  }
                }
              }
              container packet-loss {
                description
                  "Specify a packet loss value";
                leaf value {
                  description
                    "packet loss value in %";
                  type uint16 {
                    range "1..100";
                  }
                }
                leaf low-threshold {
                  description
                    "Packet loss lower threshold";
                  type uint16 {
                    range "1..100";
                  }
                }
              }
              container rtt {
                description
                  "Specify a rtt value";
                leaf value {
                  description
                    "rtt value in milli sec";
                  type uint16 {
                    range "1..5000";
                  }
                }
                leaf low-threshold {
                  description
                    "RTT lower threshold";
                  type uint16 {
                    range "1..5000";
                  }
                }
              }
            }
          }
          container mobile-local-loop {
            description
              "Mobile local loop";
            presence "true";
            list customer {
              description
                "Customer configuration";
              key "name vrf";
              unique "vrf";
              leaf name {
                description
                  "Customer identifier";
                type string;
              }
              leaf vrf {
                description
                  "VRF name for this Customer";
                type string;
              }
              uses auth-option-grouping;
              uses customer-key-default-grouping;
              uses customer-key-label-grouping;
              uses heartbeat-default-grouping;
              list interface {
                description
                  "Choice of the interface";
                key "interface-name";
                leaf interface-name {
                  description
                    "Name of the interface";
                  type string;
                }
              }
              uses mobility-service-mobile-local-loop-mnp;
              leaf mobile-map {
                description
                  "mobile map to enable for this customer";
                type string;
              }
              container mobile-route {
                description
                  "distance for local mobility anchor mobile routes";
                leaf admin-distance {
                  description
                    "distance metric";
                  type uint8 {
                    range "1..255";
                  }
                }
              }
              container network {
                description
                  "network that this Customer belongs";
                list authorized {
                  must '(not (../unauthorized))' {
                    error-message "Remove unauthorized network and configure authorized network";
                  }
                  description
                    "network that this Customer belongs";
                  key "name";
                  leaf name {
                    description
                      "network name";
                    type string;
                  }
                  uses mobile-network-option-grouping;
                  container pool {
                    description
                      "pool for ipv6/ipv4 prefixes";
                    uses pool-ipv4-grouping;
                    uses pool-ipv6-grouping;
                  }
                }
                leaf unauthorized {
                  must '(not (../authorized))' {
                    error-message "Remove authorized network and configure unauthorized network";
                  }
                  description
                    "Disable Network Authorization for this Customer";
                  type empty;
                }
              }
              uses transport-default-grouping;
              uses transport-vrf-grouping;
            }
            uses mobility-service-mobile-local-loop-mnp;
          }
        }
      }
      list pmipv6-mag {
        description
          "Proxy Mobile IPv6 MAG";
        max-elements 1;
        key "mag-name domain";
        leaf mag-name {
          description
            "Proxy Mobile IPv6 MAG";
          type string {
            length "1..128";
          }
        }
        leaf domain {
          description
            "Domain name";
          type string;
          must '/ios:native/ios:ipv6/ios-mobileip:mobile/ios-mobileip:pmipv6-domain[ios-mobileip:domain=current()]' {
            error-message "Domain name mismatch";
          }
        }
        container address {
          description
            "Configure MAG address";
          container dynamic {
            description
              "Dynamic COA for MAG";
            must '(not (../static/ipv4)) and  (not (../static/ipv6))' {
              error-message "MAG address already configured, cannot add dynamic coa support";
            }
            presence "true";
            list roaming {
              description
                "specify the roaming interface for this MAG";
              key "interface";
              leaf interface {
                description
                  "roaming interface";
                type string;
              }
              leaf priority {
                description
                  "priority for this interface";
                type uint8 {
                  range "1..100";
                }
              }
              leaf egress-att {
                description
                  "Access Technology Type of this interface";
                type enumeration {
                  enum 3G;
                  enum ETHERNET;
                  enum LTE;
                  enum WLAN;
                }
              }
              leaf label {
                description
                  "Label for this interface";
                type string;
              }
            }
          }
          container static {
            description
              "Statically configure MAG address";
            leaf ipv4 {
              description
                "MAG's ipv4 address";
              must '(not (../../dynamic))' {
                error-message "MAG dynamic address already configured, cannot add static address";
              }
              type inet:ipv4-address;
            }
            leaf ipv6 {
              description
                "MAG's ipv6 address";
              must '(not (../../dynamic))' {
                error-message "MAG dynamic address already configured, cannot add static address";
              }
              type inet:ipv6-address;
            }
          }
        }
        leaf apn {
          description
            "APN name";
          type string;
        }
        container binding {
          description
            "MAG binding options";
          leaf lifetime {
            description
              "Maximum binding lifetime (should be multiple of 4)";
            must '. mod 4 = 0' {
              error-message "Maximum binding lifetime (should be multiple of 4)";
            }
            type uint16 {
              range "8..65532";
            }
            default "3600";
          }
          leaf init-retx-time {
            description
              "binding init retransmission time interval";
            must '. <= ../max-retx-time' {
              error-message "Init value must be <= max retransmission value";
            }
            type uint16 {
              range "100..65535";
            }
            default "1000";
          }
          leaf max-retx-time {
            description
              "binding maximum retransmission time interval. Must be greater than current/configured Init value";
            must '. >= ../init-retx-time' {
              error-message "Max value must be greater than current/configured init retransmission value";
            }
            type uint16 {
              range "100..65535";
            }
            default "32000";
          }
          leaf maximum {
            description
              "Maximum binding entries";
            type uint32 {
              range "1..128000";
            }
            default "10000";
          }
          leaf refresh-time {
            description
              "binding refresh interval (should be multiple of 4)";
            must '. mod 4 = 0' {
              error-message "Binding refresh-time (should be multiple of 4)";
            }
            type uint32 {
              range "4..65532";
            }
            default "300";
          }
        }
        leaf sessionmgr {
          description
            "Enable session management for this MAG";
          type boolean;
          default "false";
        }
        container discover-mn-detach {
          description
            "Periodic verification of MN attachment";
          container poll {
            description
              "Polling related configuration";
            leaf interval {
              description
                "Polling Interval";
              must '(../ios-mobileip:retries) and (../ios-mobileip:timeout)' {
                error-message "Select all the three leaves.";
              }
              type uint16 {
                range "10..36000";
              }
              default "10";
            }
            leaf timeout {
              description
                "Polling Timeout";
              must '(../ios-mobileip:interval) and (../ios-mobileip:retries)' {
                error-message "Select all the three leaves.";
              }
              type uint8 {
                range "1..10";
              }
              default "2";
            }
            leaf retries {
              description
                "Polling Retries";
              must '(../ios-mobileip:interval) and (../ios-mobileip:timeout)' {
                error-message "Select all the three leaves.";
              }
              type uint8 {
                range "1..10";
              }
              default "2";
            }
          }
        }
        container ssmo-format {
          description
            "Service Selection Mobility Option format to be used for encoding";
          leaf label {
            description
              "Label format as per Request for Comments 5149";
            type empty;
          }
        }
        container tunnel {
          description
            "tunnel configurations for MAG";
          leaf mtu {
            description
              "tunnel ip mtu for this mag";
            type uint16 {
              range "68..17916";
            }
          }
          leaf nat {
            description
              "nat configurations for this mag";
            type enumeration {
              enum inside;
              enum outside;
            }
          }
        }
        uses tunnel-template-grouping;
        leaf multipath {
          description
            "Enable multipath";
          type empty;
        }
        leaf mobile-map {
          description
            "mobile map to enable on this MAG";
          must '../ios-mobileip:multipath' {
            error-message "Multipath not configured, cannot config mobile map";
          }
          when '../ios-mobileip:multipath';
          type string;
        }
        list interface {
          description
            "Configure MAG enabled interfaces";
          key "interface-name";
          leaf interface-name {
            description
              "Interface name";
            type string;
          }
        }
        container mobility-service {
          description
            "Service support by this Mobile Access Gateway";
          container hybrid-access {
            description
              "Hybrid Access for optimal routing";
            presence "true";
            leaf disable-sla {
              description
                "disable IP SLA probes";
              type boolean;
              default "true";
            }
            container sla {
              description
                "Hybrid ACCESS SLA configuration";
              when "../ios-mobileip:disable-sla = 'false'";
              uses sla-option-grouping;
            }
            container sla-responder-stats {
              description
                "Sending of SLA stats to responder";
              leaf disable {
                description
                  "disable sending of stats";
                type empty;
              }
            }
            container bandwidth-ratio {
              description
                "set bandwidth ratio for each link-type";
              presence "true";
              uses label-bandwidth-grouping;
            }
            container profile-definition {
              list profile-definition {
                description
                  "Traffic performance profile definition";
                key "name";
                leaf name {
                  description
                    "Name";
                  type string;
                }
                uses profile-definition-grouping;
              }
            }
          }
          container mobile-local-loop {
            description
              "Mobile local loop service for MAG";
            presence "true";
            container ignore {
              description
                "Ignoring parameters";
              leaf home-address {
                description
                  "Ignoring Home Address assigned by Local Mobility Anchor";
                type empty;
              }
            }
            container reverse-tunnel {
              description
                "reverse tunneling mode for MAG Service";
              leaf default-route {
                description
                  "default route based reverse tunneling mode";
                type empty;
              }
              leaf value {
                description
                  "distance metric for this route";
                type uint8 {
                  range "1..255";
                }
              }
            }
            container egress {
              description
                "Egress interface which is not roaming";
              leaf interface {
                description
                  "Interface Name";
                type string;
              }
            }
          }
        }
        list logical-mn {
          description
            "Logical Network access identifier or realm";
          key "mn-id";
          leaf mn-id {
            description
              "username@realm";
            type string;
          }
          container home {
            description
              "Home interface of Logical MN";
            leaf interface {
              description
                "Loopback interface";
              type string;
            }
          }
          container mobile {
            description
              "Mobile Network of Logical MN";
            list network {
              description
                "Configure Logical MN Mobile networks";
              key "interface";
              leaf interface {
                description
                  "Interface Name";
                type string;
              }
              leaf label {
                description
                  "Label string";
                type string;
              }
              leaf learn-prefix {
                description
                  "learn prefix option";
                type empty;
              }
              leaf skip-register {
                description
                  "Skip Register option";
                type empty;
              }
            }
          }
          container address {
            description
              "Logical MN address";
            leaf dynamic {
              description
                "Dynamically assign";
              type empty;
            }
          }
          container fixed {
            description
              "watch primary link for this Logical MN";
            leaf interface {
              description
                "Interface Name";
              type string;
            }
            container watch {
              description
                "watch the prefix";
              leaf ipv4 {
                description
                  "ipv4 prefix to watch";
                type inet:ipv4-address;
              }
              leaf length {
                description
                  "prefix length";
                type uint8 {
                  range "0..32";
                }
              }
            }
          }
          leaf mobile-map {
            description
              "mobile map to enable on this logical mn";
            must '../../ios-mobileip:multipath' {
              error-message "Multipath not configured, cannot config mobile map";
            }
            when '../../ios-mobileip:multipath';
            type string;
          }
          container service {
            description
              "Specify the service provided to Logical MN";
            choice service-types {
              leaf dual {
                description
                  "Support both IPv4 and IPv6 mobile networks";
                must 'not(../../address/dynamic)' {
                  error-message "Service IPV6 or dual are not supported when lmn address dynamic is configured";
                }
                type empty;
              }
              leaf ipv6 {
                description
                  "Support only IPv6 mobile networks";
                must 'not(../../address/dynamic)' {
                  error-message "Service IPV6 or dual are not supported when lmn address dynamic is configured";
                }
                type empty;
              }
              leaf ipv4 {
                description
                  "Support only IPv4 mobile networks";
                type empty;
              }
            }
          }
          container reverse-tunnel {
            description
              "reverse tunneling for Logical MN mobile network prefix";
            container route {
              description
                "route to be added";
              list ipv4 {
                description
                  "ipv4 mobile network prefix";
                key "address prefix-len";
                leaf address {
                  description
                    "ipv4 mobile network prefix";
                  type inet:ipv4-address;
                }
                leaf prefix-len {
                  description
                    "prefix length";
                  type uint8 {
                    range "0..32";
                  }
                }
                leaf distance-metric {
                  description
                    "distance metric";
                  type uint8 {
                    range "1..255";
                  }
                }
              }
              list ipv6 {
                description
                  "ipv6 mobile network prefix";
                key "address prefix-len";
                leaf address {
                  description
                    "ipv6 mobile network prefix";
                  type inet:ipv6-address;
                }
                leaf prefix-len {
                  description
                    "prefix length";
                  type uint8 {
                    range "0..128";
                  }
                }
                leaf distance-metric {
                  description
                    "distance metric";
                  type uint8 {
                    range "1..255";
                  }
                }
              }
            }
          }
        }
        container local-routing-mag {
          description
            "Enable local routing for this MAG";
          must "../ios-mobileip:sessionmgr = 'false'" {
            error-message "Local routing is not supported for MAG when sessionmgr is configured. Disabling local routing for MAG";
          }
          when "../ios-mobileip:sessionmgr = 'false'";
          presence "true";
          leaf acl-name {
            description
              "Access list name to breakout traffic in MAG";
            type string;
          }
        }
        leaf role {
          description
            "role for this MAG";
          type enumeration {
            enum 3GPP;
            enum LTE;
            enum WIMAX;
            enum WLAN;
          }
          default "WLAN";
        }
        container replay-protection {
          description
            "Configure replay protection mechanism within mag";
          container timestamp {
            description
              "timestamp option";
            leaf window {
              description
                "configure the window value";
              type uint8 {
                range "3..255";
              }
              default "7";
            }
          }
        }
        uses heartbeat-default-grouping;
        uses heartbeat-label-grouping;
        uses ani-option-grouping;
        uses bri-option-grouping;
        uses dscp-option-grouping;
        uses generate-option-grouping;
        uses ignore-option-grouping;
        list lma {
          description
            "Local Mobility Anchor identifier";
          key "lma-id domain";
          leaf lma-id {
            description
              "Local Mobility Anchor identifier";
            type string;
          }
          leaf domain {
            description
              "Domain-name for this Local Mobility Anchor";
            type string;
            must '/ios:native/ios:ipv6/ios-mobileip:mobile/ios-mobileip:pmipv6-domain[ios-mobileip:domain=current()] ' {
              error-message "Domain name mismatch";
            }
          }
          uses auth-option-grouping;
          uses dscp-option-grouping;
          uses heartbeat-default-grouping;
          leaf-list ipv4-address {
            description
              "Configure V4 address of the Local Mobility Anchor";
            type inet:ipv4-address;
          }
          leaf-list ipv6-address {
            description
              "Configure V6 address of the Local Mobility Anchor";
            type inet:ipv6-address;
          }
          container encap {
            description
              "encapsulation type between MAG and local mobility anchor";
            choice encap-type {
              description
                "encapsulation type choices";
              leaf gre-ipv4 {
                description
                  "GRE in V4 encapsulation";
                must '../../ios-mobileip:ipv4-address' {
                  error-message "Cannot Configure Encap gre-ipv4 without configuring ipv4 address in MAG";
                }
                type empty;
              }
              leaf gre-ipv6 {
                description
                  "GRE in V6 encapsulation";
                must "((../../ios-mobileip:ipv4-address)
                      or (../../ios-mobileip:ipv6-address))" {
                  error-message "Configuration of IPV6/IPV4 address for MAG is mandatory";
                }
                type empty;
              }
            }
          }
          leaf vrfid {
            description
              "vrf that this Local Mobility Anchor belong to";
            must '/ios:native/ios:vrf/ios:definition[ios:name=current()]' {
              error-message "VRF must be created 1st";
            }
            type string;
          }
          uses tunnel-template-grouping;
          uses tunnel-template-label-grouping;
        }
      }
    }
  }

  augment "/ios:native/ios:ipv6" {
    uses config-ipv6-mobileip-grouping;
  }
}
