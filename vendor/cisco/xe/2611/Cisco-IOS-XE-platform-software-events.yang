module Cisco-IOS-XE-platform-software-events {
  yang-version 1.1;
  namespace "http://cisco.com/ns/yang/Cisco-IOS-XE-platform-software-events";
  prefix platform-sw-ios-xe-events;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for various platform software events.
     Copyright (c) 2020, 2022 by Cisco Systems, Inc.
     All rights reserved.";

  revision 2022-11-01 {
    description
      "Update yang-version to 1.1";
    reference
      "1.1.0";
    cisco-semver:module-version "1.1.0";
  }
  revision 2021-03-01 {
    description
      "Initial revision";
    reference
      "1.0.0";
    cisco-semver:module-version "1.0.0";
  }

  typedef process-run-state {
    type enumeration {
      enum process-run-state-up {
        value 0;
        description
          "Process state is up";
      }
      enum process-run-state-down {
        value 1;
        description
          "Process state is down";
      }
      enum process-run-state-held-down {
        value 2;
        description
          "Process state is held down";
      }
      enum process-run-state-baydeldown {
        value 3;
        description
          "The bay has been
           deleted which causes the process state to down";
      }
      enum process-run-state-installer-down {
        value 4;
        description
          "Process state is installer down. The process is
           in the process of being installed";
      }
      enum process-run-state-planned-down {
        value 5;
        description
          "Process state is planned down.";
      }
      enum process-run-state-invalid {
        value 6;
        description
          "Invalid process state";
      }
    }
    description
      "An enumeration categorizing the run state";
  }

  grouping process-state {
    description
      "Process state";
    leaf name {
      type string;
      description
        "Name of the process";
    }
    container location {
      description
        "Location of the process";
      uses common-types-ios-xe:extended-location;
    }
    leaf new-state {
      type platform-sw-ios-xe-events:process-run-state;
      description
        "State that the process has transitioned to";
    }
    leaf instance {
      type uint8;
      description
        "The instance of the process";
    }
    leaf pid {
      type uint32;
      description
        "The identifier of the process";
    }
  }

  notification process-state-event {
    description
      "Process state events";
    uses platform-sw-ios-xe-events:process-state;
  }
}
