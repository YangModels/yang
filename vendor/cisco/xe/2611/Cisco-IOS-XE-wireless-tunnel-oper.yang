module Cisco-IOS-XE-wireless-tunnel-oper {
  yang-version 1.1;
  namespace "http://cisco.com/ns/yang/Cisco-IOS-XE-wireless-tunnel-oper";
  prefix tunnel-oper-data;

  import Cisco-IOS-XE-tunnel-types {
    prefix tunnel-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing Tunnel Operational data in Wireless deployments
     Copyright (c) 2022-2023 by Cisco Systems, Inc.
     All rights reserved.";

  revision 2023-11-01 {
    description
      "Initial revision";
    reference
      "1.0.0";
    cisco-semver:module-version "1.0.0";
  }

  grouping ewlc-tunnel-key {
    description
      "Tunnel key";
    leaf ap {
      type yang:mac-address;
      description
        "AP MAC address";
    }
    leaf name {
      type string;
      description
        "Tunnel Gateway name";
    }
  }

  grouping tunnel-ap-domain-key {
    description
      "Tunnel Domain AP key";
    leaf ap-mac {
      type yang:mac-address;
      description
        "AP MAC address";
    }
    leaf domain-name {
      type string;
      description
        "Domain name";
    }
  }

  grouping st-tunnel-ap-domain-data {
    description
      "Tunnel Domain AP data";
    leaf active-gateway {
      type string;
      description
        "Active Gateway";
    }
  }

  grouping st-tunnel-gw-data {
    description
      "Tunnel Gateway data";
    leaf gw-name {
      type string;
      description
        "Gateway name";
    }
    leaf gateway-address {
      type inet:ip-address;
      description
        "Gateway IP address";
    }
    leaf type {
      type tunnel-types:tunnel-domain-mode;
      description
        "Tunnel mode";
    }
    leaf intf-type {
      type tunnel-types:tunnel-intf-mode;
      description
        "Tunnel interface type";
    }
    leaf status {
      type tunnel-types:tunnel-intf-status;
      description
        "Tunnel interface status";
    }
    leaf admin-status {
      type tunnel-types:tunnel-intf-status;
      description
        "Tunnel interface admin status";
    }
    leaf mtu {
      type uint32;
      units "bytes";
      description
        "MTU of the interface";
    }
    container stats {
      description
        "Tunnel statistics";
      uses tunnel-types:tunnel-stats;
    }
    leaf source-interface {
      type string;
      description
        "Tunnel source interface";
    }
    leaf source-address {
      type inet:ip-address;
      description
        "Tunnel source interface IP address";
    }
  }

  container tunnel-oper-data {
    config false;
    description
      "Tunnel oper";
    list tunnel-ap-gw-data {
      key "ap name";
      description
        "Tunnel Gateway representation on AP";
      uses tunnel-oper-data:ewlc-tunnel-key;
      uses tunnel-oper-data:st-tunnel-gw-data;
    }
    list tunnel-domain-ap-data {
      key "ap-mac domain-name";
      description
        "Tunnel Domain representation on AP";
      uses tunnel-oper-data:st-tunnel-ap-domain-data;
      uses tunnel-oper-data:tunnel-ap-domain-key;
    }
  }
}
