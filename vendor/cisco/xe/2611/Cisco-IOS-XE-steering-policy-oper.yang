module Cisco-IOS-XE-steering-policy-oper {
  yang-version 1.1;
  namespace "http://cisco.com/ns/yang/Cisco-IOS-XE-steering-policy-oper";
  prefix steering-policy-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for the runtime operational information of the traffic
     steering policies and services.
     Copyright (c) 2024-2025 by Cisco Systems, Inc.
     All rights reserved.";

  revision 2025-03-01 {
    description
      "Initial revision";
    reference
      "1.0.0";
    cisco-semver:module-version "1.0.0";
  }

  typedef rloc-status-st {
    type enumeration {
      enum rloc-not-initiated {
        value 0;
        description
          "RLOC request from LISP is not initiated";
      }
      enum rloc-requested {
        value 1;
        description
          "RLOC query from LISP is requested";
      }
      enum rloc-received {
        value 2;
        description
          "RLOC query response from LISP is received";
      }
      enum rloc-request-failed {
        value 3;
        description
          "RLOC request from LISP failed";
      }
    }
    description
      "Status of RLOC resolution query to LISP";
  }

  typedef firewall-status-st {
    type enumeration {
      enum fw-status-down {
        value 0;
        description
          "Firewall status is down";
      }
      enum fw-status-up {
        value 1;
        description
          "Firewall status is up";
      }
    }
    description
      "Firewall status of steering service into the data path";
  }

  typedef prov-status {
    type enumeration {
      enum provision-failed {
        value 0;
        description
          "Policy or service failed to provision";
      }
      enum provision-success {
        value 1;
        description
          "Policy or service successfully provisioned";
      }
    }
    description
      "Programming status of steering policy or service into the data path";
  }

  grouping steering-rloc {
    description
      "This contains the list of routing locator(RLOC)
       received from LISP, containing RLOC IP, weight,
       priority and the best RLOC";
    leaf addr {
      type inet:ip-address;
      description
        "The IP address of the RLOC";
    }
    leaf weight {
      type uint8;
      description
        "A load-balancing metric used for traffic distribution among RLOCs";
    }
    leaf priority {
      type uint8;
      description
        "Sets the priority level for using this RLOC. A lower number has higher priority";
    }
    leaf best-rloc {
      type boolean;
      description
        "Best RLOC based on weight and priority";
    }
  }

  grouping steering-service {
    description
      "This represents the
       firewall service information to be used
       in the steering policy";
    leaf name {
      type string;
      description
        "The name assigned to the service";
    }
    leaf ref-count {
      type uint32;
      description
        "Number of policy instances in which this service is used";
    }
    leaf rloc-qry-status {
      type steering-policy-ios-xe-oper:rloc-status-st;
      description
        "Represents the query status of the RLOC information from LISP map-server";
    }
    leaf extranet-iid {
      type int32;
      description
        "Identifies the extranet associated with the service";
    }
    leaf num-of-rlocs {
      type uint8;
      description
        "The count of RLOCs associated with the service";
    }
    list steering-rloc {
      key "addr";
      description
        "Routing locator information";
      uses steering-policy-ios-xe-oper:steering-rloc;
    }
    leaf status {
      type steering-policy-ios-xe-oper:prov-status;
      description
        "Service provision status";
    }
    leaf fw-status {
      type steering-policy-ios-xe-oper:firewall-status-st;
      description
        "Firewall provision status";
    }
  }

  grouping steering-policy-rule {
    description
      "A steering policy rule is a directive in a network
       policy that defines how certain types of packet
       should be redirected based on specific matching criteria.
       Steering policy rules are used to control packet flow,
       directing it to particular services or network functions,
       based on factors like protocol, port";
    leaf seq-num {
      type uint16;
      description
        "Defines the order of the rule within the policy";
    }
    leaf match-count {
      type uint64;
      description
        "Number of packets matched the policy rule";
    }
  }

  grouping steering-policy {
    description
      "Traffic steering Policy information is a network configuration that
       defines how and where specific types of network packet should be
       redirected based on policy rules.";
    leaf name {
      type string;
      description
        "The name assigned to the policy";
    }
    leaf status {
      type steering-policy-ios-xe-oper:prov-status;
      description
        "Policy provision status";
    }
    list steering-policy-rule {
      key "seq-num";
      description
        "Steering Policy rules";
      uses steering-policy-ios-xe-oper:steering-policy-rule;
    }
  }

  container steering-policy-oper-data {
    config false;
    description
      "Steering operational data";
    list steering-service {
      key "name";
      description
        "Steering service data";
      uses steering-policy-ios-xe-oper:steering-service;
    }
    list steering-policy {
      key "name";
      description
        "Steering policy data";
      uses steering-policy-ios-xe-oper:steering-policy;
    }
  }
}
