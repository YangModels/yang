module Cisco-IOS-XE-lorawan-oper {
  yang-version 1.1;
  namespace "http://cisco.com/ns/yang/Cisco-IOS-XE-lorawan-oper";
  prefix lorawan-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for LORAWAN operational data.
     Copyright (c) 2021-2022 by Cisco Systems, Inc.
     All rights reserved.";

  revision 2023-03-01 {
    description
      "- Added log level, lines to CPF config.
       - Added GPS info on a per LORAWAN interface basis.";
    reference
      "1.1.0";
    cisco-semver:module-version "1.1.0";
  }
  revision 2022-11-01 {
    description
      "Initial revision";
    reference
      "1.0.0";
    cisco-semver:module-version "1.0.0";
  }

  typedef lorawan-cpf-auth-mode {
    type enumeration {
      enum cpf-auth-mode-none {
        value 0;
        description
          "No Authentication Mode";
      }
      enum cpf-auth-mode-cli-srv {
        value 1;
        description
          "Client and Server Authentication Mode";
      }
      enum cpf-auth-mode-srv {
        value 2;
        description
          "Server Authentication Mode";
      }
      enum cpf-auth-mode-sudi {
        value 3;
        description
          "Server Authentication Mode";
      }
    }
    description
      "LORAWAN CPF Authentication Mode";
  }

  typedef lorawan-status-cp-type {
    type enumeration {
      enum lorawan-cp-tdl-invalid {
        value 0;
        description
          "Invalid channel plan type";
      }
      enum lorawan-cp-tdl-msf {
        value 1;
        description
          "MSF channel type";
      }
      enum lorawan-cp-tdl-std {
        value 2;
        description
          "Standard channel type";
      }
      enum lorawan-cp-tdl-fsk {
        value 3;
        description
          "FSK channel type";
      }
    }
    description
      "Channel plan type for LORAWAN";
  }

  typedef lorawan-config-channel-plan {
    type enumeration {
      enum cp-eu868 {
        value 0;
        description
          "Channel plan EU 868";
      }
      enum cp-us915 {
        value 1;
        description
          "Channel plan US 915";
      }
      enum cp-au915 {
        value 2;
        description
          "Channel plan AU 915";
      }
      enum cp-as923-1 {
        value 3;
        description
          "Channel plan AS 923-1";
      }
      enum cp-as923-2 {
        value 4;
        description
          "Channel plan AS 923-2";
      }
      enum cp-as923-3 {
        value 5;
        description
          "Channel plan AS 923-3";
      }
      enum cp-in865 {
        value 6;
        description
          "Channel plan IN 865";
      }
      enum cp-kr920 {
        value 7;
        description
          "Channel plan KR 920";
      }
      enum cp-ru864 {
        value 8;
        description
          "Channel plan RU 864";
      }
      enum cp-invalid {
        value 9;
        description
          "Invalid channel plan ";
      }
    }
    description
      "LORAWAN channel plans";
  }

  typedef lorawan-cpf-antenna-type {
    type enumeration {
      enum cpf-antenna-type-none {
        value 0;
        description
          "No antenna";
      }
      enum cpf-antenna-type-omni {
        value 1;
        description
          "Omni type antenna";
      }
      enum cpf-antenna-type-sector {
        value 2;
        description
          "Sector type antenna";
      }
    }
    description
      "Antenna type for LORAWAN";
  }

  typedef lorawan-oper-region {
    type enumeration {
      enum lorawan-region-albania {
        value 0;
        description
          "ALBANIA";
      }
      enum lorawan-region-andorra {
        value 1;
        description
          "ANDORRA";
      }
      enum lorawan-region-armenia {
        value 2;
        description
          "ARMENIA";
      }
      enum lorawan-region-argentina {
        value 3;
        description
          "ARGENTINA";
      }
      enum lorawan-region-austria {
        value 4;
        description
          "AUSTRIA";
      }
      enum lorawan-region-australia {
        value 5;
        description
          "AUSTRALIA";
      }
      enum lorawan-region-azerbaijan {
        value 6;
        description
          "AZERBAIJAN";
      }
      enum lorawan-region-belarus {
        value 7;
        description
          "BELARUS";
      }
      enum lorawan-region-belgium {
        value 8;
        description
          "BELGIUM";
      }
      enum lorawan-region-bosnia {
        value 9;
        description
          "BOSNIA";
      }
      enum lorawan-region-brazil {
        value 10;
        description
          "BRAZIL";
      }
      enum lorawan-region-brunei {
        value 11;
        description
          "BRUNEI";
      }
      enum lorawan-region-bulgaria {
        value 12;
        description
          "BULGARIA";
      }
      enum lorawan-region-cambodia {
        value 13;
        description
          "CAMBODIA";
      }
      enum lorawan-region-canada {
        value 14;
        description
          "CANADA";
      }
      enum lorawan-region-chile {
        value 15;
        description
          "CHILE";
      }
      enum lorawan-region-china {
        value 16;
        description
          "CHINA";
      }
      enum lorawan-region-colombia {
        value 17;
        description
          "COLOMBIA";
      }
      enum lorawan-region-croatia {
        value 18;
        description
          "CROATIA";
      }
      enum lorawan-region-cyprus {
        value 19;
        description
          "CYPRUS";
      }
      enum lorawan-region-czechrepublic {
        value 20;
        description
          "CZECH REPUBLIC";
      }
      enum lorawan-region-denmark {
        value 21;
        description
          "DENMARK";
      }
      enum lorawan-region-egypt {
        value 22;
        description
          "EGYPT";
      }
      enum lorawan-region-estonia {
        value 23;
        description
          "ESTONIA";
      }
      enum lorawan-region-finland {
        value 24;
        description
          "FINLAND";
      }
      enum lorawan-region-france {
        value 25;
        description
          "FRANCE";
      }
      enum lorawan-region-germany {
        value 26;
        description
          "GERMANY";
      }
      enum lorawan-region-greece {
        value 27;
        description
          "GREECE";
      }
      enum lorawan-region-hongkong {
        value 28;
        description
          "HONGKONG";
      }
      enum lorawan-region-hungary {
        value 29;
        description
          "HUNGARY";
      }
      enum lorawan-region-iceland {
        value 30;
        description
          "ICELAND";
      }
      enum lorawan-region-ireland {
        value 31;
        description
          "IRELAND";
      }
      enum lorawan-region-india {
        value 32;
        description
          "INDIA";
      }
      enum lorawan-region-indonesia {
        value 33;
        description
          "INDONESIA";
      }
      enum lorawan-region-italy {
        value 34;
        description
          "ITALY";
      }
      enum lorawan-region-japan {
        value 35;
        description
          "JAPAN";
      }
      enum lorawan-region-korea {
        value 36;
        description
          "KOREA";
      }
      enum lorawan-region-laos {
        value 37;
        description
          "LAOS REGION";
      }
      enum lorawan-region-latvia {
        value 38;
        description
          "LATVIA";
      }
      enum lorawan-region-lebanon {
        value 39;
        description
          "LEBANON";
      }
      enum lorawan-region-liechtenstein {
        value 40;
        description
          "LIECHTENSTEIN";
      }
      enum lorawan-region-lithuania {
        value 41;
        description
          "LITHUANIA";
      }
      enum lorawan-region-luxembourg {
        value 42;
        description
          "LUXEMBOURG";
      }
      enum lorawan-region-macedonia {
        value 43;
        description
          "MACEDONIA";
      }
      enum lorawan-region-malaysia {
        value 44;
        description
          "MALAYSIA";
      }
      enum lorawan-region-mexico {
        value 45;
        description
          "MEXICO";
      }
      enum lorawan-region-moldova {
        value 46;
        description
          "MOLDOVA";
      }
      enum lorawan-region-montenegro {
        value 47;
        description
          "MONTENEGRO";
      }
      enum lorawan-region-netherlands {
        value 48;
        description
          "NETHERLANDS";
      }
      enum lorawan-region-newzealand {
        value 49;
        description
          "NEW ZEALAND";
      }
      enum lorawan-region-norway {
        value 50;
        description
          "NORWAY";
      }
      enum lorawan-region-poland {
        value 51;
        description
          "POLAND";
      }
      enum lorawan-region-portugal {
        value 52;
        description
          "PORTUGAL";
      }
      enum lorawan-region-puertorico {
        value 53;
        description
          "PUERTO RICO";
      }
      enum lorawan-region-romania {
        value 54;
        description
          "ROMANIA";
      }
      enum lorawan-region-serbia {
        value 55;
        description
          "SERBIA";
      }
      enum lorawan-region-russia {
        value 56;
        description
          "RUSSIA";
      }
      enum lorawan-region-saudiarabia {
        value 57;
        description
          "SAUDI ARABIA";
      }
      enum lorawan-region-singapore {
        value 58;
        description
          "SINGAPORE";
      }
      enum lorawan-region-slovakia {
        value 59;
        description
          "SLOVAKIA";
      }
      enum lorawan-region-slovenia {
        value 60;
        description
          "SLOVENIA";
      }
      enum lorawan-region-southafrica {
        value 61;
        description
          "SOUTH AFRICA";
      }
      enum lorawan-region-spain {
        value 62;
        description
          "SPAIN";
      }
      enum lorawan-region-sweden {
        value 63;
        description
          "SWEDEN";
      }
      enum lorawan-region-switzerland {
        value 64;
        description
          "SWITZERLAND";
      }
      enum lorawan-region-thailand {
        value 65;
        description
          "THAILAND";
      }
      enum lorawan-region-turkey {
        value 66;
        description
          "TURKEY";
      }
      enum lorawan-region-unitedkingdom {
        value 67;
        description
          "UNITED KINGDOM";
      }
      enum lorawan-region-ukraine {
        value 68;
        description
          "UKRAINE";
      }
      enum lorawan-region-unitedarabemirates {
        value 69;
        description
          "UNITED ARAB EMIRATES";
      }
      enum lorawan-region-unitedstates {
        value 70;
        description
          "UNITED STATES";
      }
      enum lorawan-region-vaticancity {
        value 71;
        description
          "VATICAN CITY";
      }
      enum lorawan-region-vietnam {
        value 72;
        description
          "VIETNAM";
      }
      enum lorawan-region-invalid {
        value 73;
        description
          "VIETNAM";
      }
    }
    description
      "LORAWAN country/region enumeration";
  }

  typedef lorawan-cpf-log-lvl {
    type enumeration {
      enum cpf-log-lvl-info {
        value 0;
        description
          "Log Level Information";
      }
      enum cpf-log-lvl-dbg {
        value 1;
        description
          "Log Level debug";
      }
      enum cpf-log-lvl-xdbg {
        value 2;
        description
          "Log Level X debug";
      }
    }
    description
      "LORAWAN CPF Log level";
  }

  typedef lorawan-gps-status {
    type enumeration {
      enum gps-data-available {
        value 0;
        description
          "GPS Data is available";
      }
      enum gps-data-not-available {
        value 1;
        description
          "GPS Data is not available";
      }
    }
    description
      "LORAWAN GPS Status";
  }

  grouping lorawan-intf-config {
    description
      "LORAWAN interface config output";
    leaf use-cpf {
      type boolean;
      description
        "Whether CPF is used at current interface";
    }
    leaf linestate-up {
      type boolean;
      description
        "Line state";
    }
  }

  grouping lorawan-cpf-config {
    description
      "LORAWAN CPF configuration file output";
    leaf antenna-type {
      type lorawan-ios-xe-oper:lorawan-cpf-antenna-type;
      description
        "Antenna type";
    }
    leaf auth-mode {
      type lorawan-ios-xe-oper:lorawan-cpf-auth-mode;
      description
        "Authentication mode";
    }
    leaf brd-bw {
      type uint32;
      units "HZ";
      description
        "The board bandwidth";
    }
    leaf brd-freq {
      type uint32;
      units "HZ";
      description
        "The board frequency";
    }
    leaf country {
      type lorawan-ios-xe-oper:lorawan-oper-region;
      description
        "The Country where the antenna is located";
    }
    leaf channel-plan {
      type lorawan-ios-xe-oper:lorawan-config-channel-plan;
      description
        "The CPF channel plan";
    }
    leaf gw-id {
      type string;
      description
        "The gateway id";
    }
    leaf gps {
      type empty;
      description
        "GPS is enabled";
    }
    leaf lns {
      type string;
      description
        "The host name or ip address";
    }
    leaf lns-port {
      type uint16;
      description
        "The interface port";
    }
    leaf sni-en {
      type empty;
      description
        "SNI is enabled";
    }
    leaf cpf-en {
      type empty;
      description
        "CPF is enabled";
    }
    leaf log-lvl {
      type lorawan-ios-xe-oper:lorawan-cpf-log-lvl;
      description
        "Log level used";
    }
    leaf log-lines {
      type uint16;
      description
        "Number of log lines";
    }
  }

  grouping lorawan-cpf-config-layout {
    description
      "lorawan configuration";
    leaf if-name {
      type string;
      description
        "The interface name";
    }
    container cpf-config {
      description
        "lorawan CPF configuration";
      uses lorawan-ios-xe-oper:lorawan-cpf-config;
    }
  }

  grouping lorawan-show-config {
    description
      "lorawan configuration";
    leaf if-name {
      type string;
      description
        "The interface name";
    }
    container intf-config {
      description
        "lorawan interface configuration";
      uses lorawan-ios-xe-oper:lorawan-intf-config;
    }
    container cpf-config {
      description
        "lorawan CPF configuration";
      uses lorawan-ios-xe-oper:lorawan-cpf-config;
    }
  }

  grouping lorawan-cp-msf {
    description
      "lorawan channel info";
    leaf cp-type {
      type lorawan-ios-xe-oper:lorawan-status-cp-type;
      description
        "Channel plan type";
    }
    leaf index {
      type uint8;
      description
        "lorawan channel index/slot number";
    }
    leaf freq {
      type decimal64 {
        fraction-digits 2;
      }
      units "MHZ";
      description
        "Frequency";
    }
    leaf rf {
      type uint32;
      description
        "RF chain";
    }
    leaf dr {
      type uint8;
      description
        "Data rate code";
    }
  }

  grouping lorawan-cp-bw {
    description
      "lorawan std/fsk channel info";
    leaf cp-type {
      type lorawan-ios-xe-oper:lorawan-status-cp-type;
      description
        "Channel plan type";
    }
    leaf freq {
      type decimal64 {
        fraction-digits 2;
      }
      units "MHZ";
      description
        "Frequency";
    }
    leaf rf {
      type uint32;
      description
        "RF chain";
    }
    leaf dr {
      type uint8;
      description
        "Data rate code";
    }
    leaf bw {
      type uint32;
      units "KHZ";
      description
        "Bandwidth";
    }
  }

  grouping lorawan-oper-status-stats {
    description
      "lorawan statistics info";
    leaf dn-msg {
      type uint32;
      description
        "Downlink message";
    }
    leaf dn-sched-msg {
      type uint32;
      description
        "Downlink scheduled MSG";
    }
    leaf rx-msg {
      type uint32;
      description
        "Received message";
    }
  }

  grouping lorawan-oper-channel-plan {
    description
      "LORAWAN channel plan";
    list msf {
      max-elements 8;
      description
        "MSF channel info";
      uses lorawan-ios-xe-oper:lorawan-cp-msf;
    }
    container fsk {
      description
        "FSK channel info";
      uses lorawan-ios-xe-oper:lorawan-cp-bw;
    }
    container std {
      description
        "Standard channel info";
      uses lorawan-ios-xe-oper:lorawan-cp-bw;
    }
  }

  grouping lorawan-oper-cpf-status {
    description
      "LORAWAN CPF status";
    leaf cpf-running {
      type boolean;
      description
        "CPF status";
    }
    leaf lns-cert-installed {
      type boolean;
      description
        "LNS certificate status";
    }
    leaf gw-cert-installed {
      type boolean;
      description
        "Gateway certificate status";
    }
    leaf gwkey-installed {
      type boolean;
      description
        "Gateway key status";
    }
    leaf lns-connected {
      type boolean;
      description
        "LNS connection status";
    }
    container cp {
      description
        "LORAWAN Channel Plan";
      uses lorawan-ios-xe-oper:lorawan-oper-channel-plan;
    }
    container stats {
      description
        "LORAWAN Channel Plan";
      uses lorawan-ios-xe-oper:lorawan-oper-status-stats;
    }
  }

  grouping lorawan-cpf-status-content {
    description
      "lorawan CPF config file";
    leaf if-name {
      type string;
      description
        "lorawan interface name";
    }
    container status {
      description
        "CPF status content";
      uses lorawan-ios-xe-oper:lorawan-oper-cpf-status;
    }
  }

  grouping lorawan-gps-data {
    description
      "LORAWAN GPS data";
    leaf timestamp {
      type yang:date-and-time;
      description
        "Timestamp when location details are recorded";
    }
    leaf latitude {
      type decimal64 {
        fraction-digits 6;
      }
      description
        "Latitude of the location";
    }
    leaf longitude {
      type decimal64 {
        fraction-digits 6;
      }
      description
        "Longitude of the location";
    }
    leaf height {
      type decimal64 {
        fraction-digits 2;
      }
      description
        "Height of the location";
    }
  }

  grouping lorawan-gps-data-layout {
    description
      "LORAWAN GPS data";
    leaf if-name {
      type string;
      description
        "LORAWAN interface name";
    }
    leaf status {
      type lorawan-ios-xe-oper:lorawan-gps-status;
      description
        "Indicates the status of GPS";
    }
    container gps-data {
      when "../status != 'gps-data-not-available'";
      description
        "GPS data";
      uses lorawan-ios-xe-oper:lorawan-gps-data;
    }
  }

  container lorawan-oper-data {
    config false;
    description
      "Lorawan IOS emulation data";
    list lorawan-config {
      key "if-name";
      description
        "Lorawan configure data";
      uses lorawan-ios-xe-oper:lorawan-show-config;
    }
    list lorawan-cpf-from-app {
      key "if-name";
      description
        "Lorawan cpf file configuration data";
      uses lorawan-ios-xe-oper:lorawan-cpf-config-layout;
    }
    list lorawan-cpf-status {
      key "if-name";
      description
        "Lorawan cpf status data";
      uses lorawan-ios-xe-oper:lorawan-cpf-status-content;
    }
    list lorawan-gps {
      key "if-name";
      description
        "LORAWAN GPS data";
      uses lorawan-ios-xe-oper:lorawan-gps-data-layout;
    }
  }
}
