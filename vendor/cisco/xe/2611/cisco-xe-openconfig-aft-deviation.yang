module cisco-xe-openconfig-aft-deviation {
  namespace "http://cisco.com/ns/cisco-xe-openconfig-aft-deviation";
  prefix oc-aft-devs;

  import openconfig-network-instance {
    prefix oc-netinst;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-aft module.";

  revision 2025-07-01 {
    description
      "Deviating unsupported leafs from AFT Model";
  }
  revision 2018-12-05 {
    description
      "Initial Revision";
  }

  deviation "/oc-netinst:network-instances/oc-netinst:network-instance/oc-netinst:afts/oc-netinst:ipv4-unicast/oc-netinst:ipv4-entry/oc-netinst:state/oc-netinst:decapsulate-header" {
    deviate not-supported;
    description
      "Not supported in IOS-XE";
  }

  deviation "/oc-netinst:network-instances/oc-netinst:network-instance/oc-netinst:afts/oc-netinst:ipv4-unicast/oc-netinst:ipv4-entry/oc-netinst:state/oc-netinst:entry-metadata" {
    deviate not-supported;
    description
      "Not supported in IOS-XE";
  }

  deviation "/oc-netinst:network-instances/oc-netinst:network-instance/oc-netinst:afts/oc-netinst:ipv4-unicast/oc-netinst:ipv4-entry/oc-netinst:state/oc-netinst:counters/oc-netinst:packets-forwarded-backup" {
    deviate not-supported;
    description
      "Not supported in IOS-XE";
  }

  deviation "/oc-netinst:network-instances/oc-netinst:network-instance/oc-netinst:afts/oc-netinst:ipv4-unicast/oc-netinst:ipv4-entry/oc-netinst:state/oc-netinst:counters/oc-netinst:octets-forwarded-backup" {
    deviate not-supported;
    description
      "Not supported in IOS-XE";
  }

  deviation "/oc-netinst:network-instances/oc-netinst:network-instance/oc-netinst:afts/oc-netinst:ipv6-unicast/oc-netinst:ipv6-entry/oc-netinst:state/oc-netinst:decapsulate-header" {
    deviate not-supported;
    description
      "Not supported in IOS-XE";
  }

  deviation "/oc-netinst:network-instances/oc-netinst:network-instance/oc-netinst:afts/oc-netinst:ipv6-unicast/oc-netinst:ipv6-entry/oc-netinst:state/oc-netinst:entry-metadata" {
    deviate not-supported;
    description
      "Not supported in IOS-XE";
  }

  deviation "/oc-netinst:network-instances/oc-netinst:network-instance/oc-netinst:afts/oc-netinst:ipv6-unicast/oc-netinst:ipv6-entry/oc-netinst:state/oc-netinst:counters/oc-netinst:packets-forwarded-backup" {
    deviate not-supported;
    description
      "Not supported in IOS-XE";
  }

  deviation "/oc-netinst:network-instances/oc-netinst:network-instance/oc-netinst:afts/oc-netinst:ipv6-unicast/oc-netinst:ipv6-entry/oc-netinst:state/oc-netinst:counters/oc-netinst:octets-forwarded-backup" {
    deviate not-supported;
    description
      "Not supported in IOS-XE";
  }

  deviation "/oc-netinst:network-instances/oc-netinst:network-instance/oc-netinst:afts/oc-netinst:next-hops/oc-netinst:next-hop/oc-netinst:state/oc-netinst:mac-address" {
    deviate not-supported;
    description
      "Not supported in IOS-XE";
  }

  deviation "/oc-netinst:network-instances/oc-netinst:network-instance/oc-netinst:afts/oc-netinst:next-hops/oc-netinst:next-hop/oc-netinst:state/oc-netinst:pushed-mpls-label-stack" {
    deviate not-supported;
    description
      "Not supported in IOS-XE";
  }

  deviation "/oc-netinst:network-instances/oc-netinst:network-instance/oc-netinst:afts/oc-netinst:next-hops/oc-netinst:next-hop/oc-netinst:state/oc-netinst:decapsulate-header" {
    deviate not-supported;
    description
      "Not supported in IOS-XE";
  }

  deviation "/oc-netinst:network-instances/oc-netinst:network-instance/oc-netinst:afts/oc-netinst:next-hops/oc-netinst:next-hop/oc-netinst:state/oc-netinst:origin-protocol" {
    deviate not-supported;
    description
      "Not supported in IOS-XE";
  }

  deviation "/oc-netinst:network-instances/oc-netinst:network-instance/oc-netinst:afts/oc-netinst:next-hops/oc-netinst:next-hop/oc-netinst:state/oc-netinst:lsp-name" {
    deviate not-supported;
    description
      "Not supported in IOS-XE";
  }

  deviation "/oc-netinst:network-instances/oc-netinst:network-instance/oc-netinst:afts/oc-netinst:next-hops/oc-netinst:next-hop/oc-netinst:state/oc-netinst:programmed-index" {
    deviate not-supported;
    description
      "Not supported in IOS-XE";
  }

  deviation "/oc-netinst:network-instances/oc-netinst:network-instance/oc-netinst:afts/oc-netinst:next-hops/oc-netinst:next-hop/oc-netinst:state/oc-netinst:pop-top-label" {
    deviate not-supported;
    description
      "Not supported in IOS-XE";
  }

  deviation "/oc-netinst:network-instances/oc-netinst:network-instance/oc-netinst:afts/oc-netinst:next-hops/oc-netinst:next-hop/oc-netinst:ip-in-ip/oc-netinst:state/oc-netinst:src-ip" {
    deviate not-supported;
    description
      "Not supported in IOS-XE";
  }

  deviation "/oc-netinst:network-instances/oc-netinst:network-instance/oc-netinst:afts/oc-netinst:next-hops/oc-netinst:next-hop/oc-netinst:ip-in-ip/oc-netinst:state/oc-netinst:dst-ip" {
    deviate not-supported;
    description
      "Not supported in IOS-XE";
  }

  deviation "/oc-netinst:network-instances/oc-netinst:network-instance/oc-netinst:afts/oc-netinst:next-hop-groups/oc-netinst:next-hop-group/oc-netinst:conditional" {
    deviate not-supported;
    description
      "Not supported in IOS-XE";
  }

  deviation "/oc-netinst:network-instances/oc-netinst:network-instance/oc-netinst:afts/oc-netinst:next-hop-groups/oc-netinst:next-hop-group/oc-netinst:state/oc-netinst:programmed-id" {
    deviate not-supported;
    description
      "Not supported in IOS-XE";
  }

  deviation "/oc-netinst:network-instances/oc-netinst:network-instance/oc-netinst:afts/oc-netinst:next-hop-groups/oc-netinst:next-hop-group/oc-netinst:state/oc-netinst:color" {
    deviate not-supported;
    description
      "Not supported in IOS-XE";
  }

  deviation "/oc-netinst:network-instances/oc-netinst:network-instance/oc-netinst:afts/oc-netinst:next-hop-groups/oc-netinst:next-hop-group/oc-netinst:state/oc-netinst:backup-next-hop-group" {
    deviate not-supported;
    description
      "Not supported in IOS-XE";
  }

  deviation "/oc-netinst:network-instances/oc-netinst:network-instance/oc-netinst:afts/oc-netinst:policy-forwarding" {
    deviate not-supported;
    description
      "Not supported in IOS-XE";
  }

  deviation "/oc-netinst:network-instances/oc-netinst:network-instance/oc-netinst:afts/oc-netinst:mpls" {
    deviate not-supported;
    description
      "Not supported in IOS-XE";
  }

  deviation "/oc-netinst:network-instances/oc-netinst:network-instance/oc-netinst:afts/oc-netinst:state-synced" {
    deviate not-supported;
    description
      "Not supported in IOS-XE";
  }
}
