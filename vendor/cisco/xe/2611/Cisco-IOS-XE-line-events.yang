module Cisco-IOS-XE-line-events {
  yang-version 1.1;
  namespace "http://cisco.com/ns/yang/Cisco-IOS-XE-line-events";
  prefix line-ios-xe-events;

  import Cisco-IOS-XE-ios-common-oper {
    prefix ios-common-ios-xe-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for line event notification.
     Copyright (c) 2024 by Cisco Systems, INC.
     All rights reserved.";

  revision 2024-11-01 {
    description
      "Initial revision";
    reference
      "1.0.0";
    cisco-semver:module-version "1.0.0";
  }

  typedef e-line-state-event-type {
    type enumeration {
      enum line-state-event-to-in-use {
        value 0;
        description
          "Line state changes to in-use (busy)";
      }
      enum line-state-event-to-free {
        value 1;
        description
          "Line state changes to free";
      }
    }
    description
      "Line state change event types";
  }

  grouping line-state-event-data {
    description
      "Data item for the list of line state change events";
    leaf number {
      type uint32;
      description
        "Line number";
    }
    leaf type {
      type line-ios-xe-events:e-line-state-event-type;
      description
        "Line state change event type";
    }
  }

  grouping line-state-event-notification {
    description
      "Line state event notification";
    leaf severity {
      type ios-common-ios-xe-oper:notification-severity;
      description
        "Notification severity";
    }
    leaf host-name {
      type string;
      description
        "Host name";
    }
    list state-event-list {
      description
        "List of line state change events";
      uses line-ios-xe-events:line-state-event-data;
    }
  }

  notification line-state-event {
    description
      "line state event notification";
    uses line-ios-xe-events:line-state-event-notification;
  }
}
