module Cisco-IOS-XE-cli-rpc {
  yang-version 1.1;
  namespace "http://cisco.com/ns/yang/Cisco-IOS-XE-cli-rpc";
  prefix cli-ios-xe-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for RPCs related to the Command Line Interface (CLI).
     Copyright (c) 2022 by Cisco Systems, Inc.
     All rights reserved.";

  revision 2026-02-01 {
    description
      "Added new leaf to config-ios-cli-rpc";
    cisco-semver:module-version "1.3.0";
  }
  revision 2024-07-01 {
    description
      "Added config-ios-config-show rpc and added new leaf to config-ios-cli-rpc";
    cisco-semver:module-version "1.2.0";
  }
  revision 2022-11-01 {
    description
      "Update yang-version to 1.1";
    cisco-semver:module-version "1.1.0";
  }
  revision 2022-07-01 {
    description
      "Initial revision";
    reference
      "1.0.0";
    cisco-semver:module-version "1.0.0";
  }

  grouping config-ios-cli-input {
    description
      "Configuration CLI parameters";
    leaf config-clis {
      type string {
        length "1..60000";
      }
      mandatory true;
      description
        "Configuration CLI commands";
    }
    leaf timeout {
      type uint32 {
        range "10..1800";
      }
      default "300";
      units "seconds";
      description
        "Configurable timeout for the RPC";
    }
    list error-patterns {
      key "error-tag";
      max-elements 10;
      description
        "This list error pattern used
         to verify status of the CLI execution.";
      leaf error-tag {
        type string {
          length "1..64";
        }
        description
          "Tag returned in the response if parser response matches
           the error-pattern";
      }
      leaf error-pattern {
        type string {
          length "1..256";
        }
        description
          "error pattern to check against the parser response.";
      }
    }
  }

  grouping config-ios-cli-output {
    description
      "Output data";
    leaf result {
      type string;
      description
        "Output returned by the network element";
    }
    leaf lineno {
      type int16;
      description
        "line number of the failed CLI";
    }
    leaf error-code {
      type int16;
      description
        "Error code returned by the parser";
    }
    leaf error-string {
      type string;
      description
        "Error string";
    }
    leaf error-tag {
      type string {
        length "1..64";
      }
      description
        "supplied error tag that matched the error-pattern";
    }
  }

  rpc config-ios-cli-rpc {
    description
      "Configure CLIs directly to the IOS, bypassing NETCONF transaction";
    input {
      uses cli-ios-xe-rpc:config-ios-cli-input;
    }
    output {
      uses cli-ios-xe-rpc:config-ios-cli-output;
    }
  }

  rpc config-ios-cli-trans {
    description
      "Configure using modelled config CLI.
       Wireless,  app-hosting, telemetry features are not
       supported through this RPC.";
    input {
      leaf clis {
        type string {
          length "1..524288";
        }
        mandatory true;
        description
          "Configuration CLI commands";
      }
      leaf do-commit {
        type boolean;
        default "true";
        description
          "Copy the CLI commands from candidate datastore
           to running datastore in candidate mode. ";
      }
      leaf operation {
        type enumeration {
          enum merge;
          enum selective-replace;
          enum full-replace;
        }
        default "merge";
        description
          "Operations have the following effects:
           merge: append the supplied contents of this RPC into the
                  currently configured datastore
           selective-replace: overwrite the submode config of the
                              specified cli in the currently
                              configured datastore with the
                              contents of this RPC (supported
                              use only covers submode modification)
           full-replace: overwrite the complete configuration
                         stored in the configured datastore with
                         the contents of this RPC";
      }
      leaf label {
        type string;
        description
          "Set rollback label.";
      }
      leaf comment {
        type string;
        description
          "Set rollback comment.";
      }
    }
    output {
      leaf result {
        type string;
        description
          "Output returned by the network element";
      }
      leaf error-message {
        type string;
        description
          "Error returned by the network element";
      }
    }
  }

  rpc get-modelled-config-clis {
    description
      "Retrieve configuration in CLI format from Running or Candidate
       datastore. Wireless, app-hosting, telemetry features are not
       supported through this RPC.";
    input {
      leaf datastore {
        type enumeration {
          enum running;
          enum candidate;
        }
        default "running";
        description
          "Datastore to retrieve configuration.";
      }
    }
    output {
      leaf result {
        type string;
        description
          "Output returned by network element";
      }
      leaf error-message {
        type string;
        description
          "Error returned by the network element";
      }
    }
  }
}
