module Cisco-IOS-XE-uplink-autoconfig-oper {
  yang-version 1.1;
  namespace "http://cisco.com/ns/yang/Cisco-IOS-XE-uplink-autoconfig-oper";
  prefix uplink-autoconfig-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for uplink auto config operational data.
     Copyright (c) 2023-2025 by Cisco Systems, Inc.
     All rights reserved.";

  revision 2026-02-01 {
    description
      "- Added a new leaf indicating whether IP address is static vs obtained via DHCP
       - Added a new score from device tracking table with a DHCP offered IP address for the preferred uplink
       - Added network instance support for cloud mgmt uplink interface
       - Clarified the descriptions of the IPv4 and IPv6 address mode indicator leaf";
    reference
      "1.2.0";
    cisco-semver:module-version "1.2.0";
  }
  revision 2025-07-01 {
    description
      "- Added a new score for the preferred uplink.";
    reference
      "1.1.0";
    cisco-semver:module-version "1.1.0";
  }
  revision 2024-07-01 {
    description
      "Initial revision";
    reference
      "1.0.0";
    cisco-semver:module-version "1.0.0";
  }

  typedef uac-addr-type {
    type enumeration {
      enum uac-addr-none {
        value 0;
        description
          "None address type";
      }
      enum uac-ipv4-addr {
        value 1;
        description
          "IPv4 address type";
      }
      enum uac-ipv6-addr {
        value 2;
        description
          "IPv6 address type";
      }
    }
    description
      "Uplink IP address type";
  }

  typedef uplink-score {
    type enumeration {
      enum uac-score-bad {
        value 0;
        description
          "Lowest score";
      }
      enum uac-score-nw-ua {
        value 1;
        description
          "Existing configuration, that is not known to be working or faced error previously";
      }
      enum uac-score-ddhcp {
        value 2;
        description
          "Discovered vlan with a DHCP offered IP address and known to be working";
      }
      enum uac-score-cdhcp {
        value 3;
        description
          "Configured vlan with a DHCP offered IP address and known to be working";
      }
      enum uac-score-cstatic {
        value 4;
        description
          "Configured vlan with a static IP address and known to be working";
      }
      enum uac-score-pdhcp {
        value 5;
        description
          "User preferred and configured vlan with a DHCP offered IP address that is known to be working";
      }
      enum uac-score-pstatic {
        value 6;
        description
          "User preferred and configured vlan with static IP address that is known to be working";
      }
      enum uac-score-lk {
        value 7;
        description
          "Vlan that is known to be working before reload";
      }
      enum uac-score-if-lk {
        value 8;
        description
          "User preferred and configured vlan when another pre-reboot, working, uplink present";
      }
      enum uac-score-cb-dhcp {
        value 9;
        description
          "Configured port set as backup with DHCP IP address";
      }
      enum uac-score-cb-static {
        value 10;
        description
          "Configured port set as backup with static IP address";
      }
      enum uac-score-rpc-chk {
        value 11;
        description
          "User preferred and configured VLAN is checked with a RPC message";
      }
      enum uac-score-ip-dt-dhcp {
        value 12;
        description
          "Discovered VLAN from device tracking table with a DHCP offered IP address and known to be working";
      }
    }
    description
      "Uplink score of interface, based on configuration and the status of probes";
  }

  grouping uplink-if-key {
    description
      "Key for uplink interface table which uniquely identifies uplink interface for IPV4 and IPV6";
    leaf ipaddr-type {
      type uplink-autoconfig-ios-xe-oper:uac-addr-type;
      description
        "Address type for uplink interface. It can be IPV4/IPV6";
    }
  }

  grouping uplink-ipv4-if {
    description
      "Uplink Interface IPV4 data";
    leaf if-name {
      type string;
      description
        "Interface name for IPV4 uplink interface";
    }
    leaf vlan-id {
      type uint16;
      description
        "Vlan id for IPV4 uplink interface";
    }
    leaf uac-addr {
      type inet:ip-address;
      description
        "IPV4 address of uplink interface";
    }
    leaf subnet {
      type inet:ip-address;
      description
        "Subnet mask for IPV4 uplink interface";
    }
    leaf uac-gw {
      type inet:ip-address;
      description
        "Gateway IP address for IPV4 uplink interface";
    }
    leaf gw-mac {
      type yang:mac-address;
      description
        "Gateway MAC of IPV4 uplink";
    }
    leaf uac-score {
      type uplink-autoconfig-ios-xe-oper:uplink-score;
      description
        "Score of IPV4 uplink interface";
    }
    leaf is-feature-created {
      type boolean;
      description
        "The IPV4 interface is created by device feature or by user";
    }
    leaf port-name {
      type string;
      description
        "Port name for IPV4 uplink interface";
    }
    leaf is-ip-static {
      type boolean;
      description
        "Indicates whether the IPv4 address is statically configured (true) or assigned via DHCP (false).";
    }
    leaf ni-type {
      type common-types-ios-xe:net-inst-type;
      description
        "Network instance type. Differentiates between the
         default routing instance and VRFs";
    }
    leaf ni-name {
      type string;
      description
        "Network instance name. If the type is
         net-inst-default, the name is not meaningful";
    }
  }

  grouping uplink-ipv6-if {
    description
      "Uplink Interface IPV6 data";
    leaf if-name {
      type string;
      description
        "Interface name for IPV6 uplink interface";
    }
    leaf vlan-id {
      type uint16;
      description
        "Vlan ID chosen for IPV6 uplink interface";
    }
    leaf-list uac-addr {
      type inet:ip-prefix;
      max-elements 16;
      ordered-by user;
      description
        "List of IPV6 addresses of uplink interface";
    }
    leaf-list uac-gw {
      type inet:ipv6-address;
      max-elements 16;
      ordered-by user;
      description
        "Gateway IP address for IPV6 uplink interface";
    }
    leaf gw-mac {
      type yang:mac-address;
      description
        "Gateway MAC of IPV6 uplink";
    }
    leaf uac-score {
      type uplink-autoconfig-ios-xe-oper:uplink-score;
      description
        "Score of IPV6 uplink interface";
    }
    leaf is-feature-created {
      type boolean;
      description
        "The IPV6 interface is created by device feature or by user";
    }
    leaf port-name {
      type string;
      description
        "Port name for IPV6 uplink interface";
    }
    leaf is-ip-static {
      type boolean;
      description
        "Indicates whether the IPv6 address is statically configured (true) or assigned via DHCP (false).";
    }
    leaf ni-type {
      type common-types-ios-xe:net-inst-type;
      description
        "Network instance type. Differentiates between the
         default routing instance and VRFs";
    }
    leaf ni-name {
      type string;
      description
        "Network instance name. If the type is
         net-inst-default, the name is not meaningful";
    }
  }

  grouping uplink-if {
    description
      "Uplink interface details";
    container uplink-ipv4 {
      description
        "Uplink IPV4 interface details";
      uses uplink-autoconfig-ios-xe-oper:uplink-ipv4-if;
    }
    container uplink-ipv6 {
      description
        "Uplink IPV6 interface details";
      uses uplink-autoconfig-ios-xe-oper:uplink-ipv6-if;
    }
  }

  grouping uplink-sr-key {
    description
      "Uplink static route details";
    leaf dst-addr {
      type inet:ip-address;
      description
        "Destination address configured for uplink static route";
    }
    leaf dst-mask {
      type inet:ip-address;
      description
        "Destination mask configured for uplink static route";
    }
    leaf vlan-id {
      type uint16;
      description
        "Vlan interface for uplink static route";
    }
    leaf nh-addr {
      type inet:ip-address;
      description
        "Next hop address for uplink static route";
    }
  }

  container uplink-autoconfig-oper-data {
    config false;
    description
      "This model provides details of selected IPV4/IPV6 uplink interface and static route created by the uplink auto config feature";
    list uplink-if {
      key "ipaddr-type";
      description
        "Uplink interface details for IPV4/IPV6";
      uses uplink-autoconfig-ios-xe-oper:uplink-if;
      uses uplink-autoconfig-ios-xe-oper:uplink-if-key;
    }
    list uplink-sr {
      key "dst-addr dst-mask vlan-id nh-addr";
      description
        "Static route details for uplink interface";
      uses uplink-autoconfig-ios-xe-oper:uplink-sr-key;
    }
  }
}
