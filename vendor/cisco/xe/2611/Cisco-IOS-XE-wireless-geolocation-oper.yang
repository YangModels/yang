module Cisco-IOS-XE-wireless-geolocation-oper {
  yang-version 1.1;
  namespace "http://cisco.com/ns/yang/Cisco-IOS-XE-wireless-geolocation-oper";
  prefix wireless-geolocation-oper;

  import Cisco-IOS-XE-wireless-geolocation-types {
    prefix wireless-geolocation-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing geolocation information
     Copyright (c) 2022 by Cisco Systems, Inc.
     All rights reserved.";

  revision 2022-11-01 {
    description
      "Initial revision";
    reference
      "1.0.0";
    cisco-semver:module-version "1.0.0";
  }

  container geolocation-oper-data {
    config false;
    description
      "Wireless geolocation operational data model";
    list ap-geo-loc-data {
      key "ap-mac";
      description
        "AP geolocation data";
      uses wireless-geolocation-types:ap-geo-loc-data;
    }
    container ap-geo-loc-stats {
      presence "ap-geo-loc-stats";
      description
        "AP geolocation statistics";
      uses wireless-geolocation-types:ap-geo-loc-stats;
    }
  }
}
