module Cisco-IOS-XE-cloud-services-rpc {
  yang-version 1.1;
  namespace "http://cisco.com/ns/yang/Cisco-IOS-XE-cloud-services-rpc";
  prefix cloud-services-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     OTP token import.
     Copyright (c) 2022, 2024, 2026 by Cisco Systems, Inc.
     All rights reserved.";

  revision 2026-02-01 {
    description
      "- Import public key for spaces cloud services";
    reference
      "1.2.0";
    cisco-semver:module-version "1.2.0";
  }
  revision 2024-07-01 {
    description
      "Added spaces OTP token";
    reference
      "1.1.0";
    cisco-semver:module-version "1.1.0";
  }
  revision 2023-03-01 {
    description
      "Initial revision";
    reference
      "1.0.0";
    cisco-semver:module-version "1.0.0";
  }

  grouping clear-token {
    description
      "Clear token grouping";
    leaf service {
      type string;
      mandatory true;
      description
        "Service name to clear tokens for";
    }
  }

  grouping otp-token-import {
    description
      "OTP upgrade token related grouping";
    leaf otp-token {
      type string {
        length "1..4095";
      }
      mandatory true;
      description
        "OTP upgrade token";
    }
  }

  grouping otp-pkey-import {
    description
      "Public key related grouping";
    leaf otp-pkey {
      type string {
        length "1..4095";
        pattern '[A-Za-z0-9/+-_=.]+';
      }
      mandatory true;
      description
        "Public key to validate OTP (authorization code)";
    }
  }

  rpc cloudm-otp-token-import {
    description
      "import OTP upgrade token for cloud services";
    input {
      uses cloud-services-rpc:otp-token-import;
    }
  }

  rpc cloudm-spaces-otp-token-import {
    description
      "import OTP (authorization code) for spaces cloud services";
    input {
      uses cloud-services-rpc:otp-token-import;
    }
  }

  rpc cloudm-spaces-tokens-clear {
    description
      "clear all tokens (persistent and temporary ones) for spaces cloud services";
    input {
      uses cloud-services-rpc:clear-token;
    }
  }

  rpc cloudm-spaces-pkey-import {
    description
      "import public key for spaces cloud services";
    input {
      uses cloud-services-rpc:otp-pkey-import;
    }
  }
}
