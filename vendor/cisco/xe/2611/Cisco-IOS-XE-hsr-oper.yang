module Cisco-IOS-XE-hsr-oper {
  yang-version 1.1;
  namespace "http://cisco.com/ns/yang/Cisco-IOS-XE-hsr-oper";
  prefix hsr-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for ( High-Availability Seamless Redundancy ) HSR operational data.
     Copyright (c) 2022 by Cisco Systems, Inc.
     All rights reserved.";

  revision 2022-11-01 {
    description
      "Initial revision";
    reference
      "1.0.0";
    cisco-semver:module-version "1.0.0";
  }

  typedef hsr-oper-state {
    type enumeration {
      enum hsr-ring-in-error-state {
        value 0;
        description
          "HSR Ring is in either unknown or error state";
      }
      enum hsr-ring-not-in-use-state {
        value 1;
        description
          "HSR Ring is down";
      }
      enum hsr-ring-in-use-state {
        value 2;
        description
          "HSR Ring is up";
      }
      enum hsr-ring-down-admin-state {
        value 3;
        description
          "HSR Ring is down as it has
           been shut down administratively";
      }
      enum hsr-ring-suspended-state {
        value 4;
        description
          "HSR Ring is in suspended state";
      }
    }
    description
      "State of the HSR Ring";
  }

  typedef hsr-oper-nw-layer {
    type enumeration {
      enum hsr-ring-nw-layer-in-error {
        value 0;
        description
          "Network layer is either unknown or in error state";
      }
      enum hsr-ring-nw-layer-2 {
        value 1;
        description
          "Network layer associated with the ring is L2";
      }
      enum hsr-ring-nw-layer-3 {
        value 2;
        description
          "Network layer associated with the ring is L3";
      }
    }
    description
      "Network Layer at which the given the HSR Ring is operating";
  }

  typedef hsr-oper-work-mode {
    type enumeration {
      enum hsr-ring-op-mode-invalid {
        value 0;
        description
          "Operating mode of the ring is either unknown or in error state";
      }
      enum hsr-ring-op-mode-h {
        value 1;
        description
          "HSR Ring is operating in H mode";
      }
      enum hsr-ring-op-mode-n {
        value 2;
        description
          "HSR Ring is operating in N mode";
      }
      enum hsr-ring-op-mode-tt {
        value 3;
        description
          "HSR Ring is operating in T mode";
      }
      enum hsr-ring-op-mode-m {
        value 4;
        description
          "HSR Ring is operating in M mode";
      }
      enum hsr-ring-op-mode-u {
        value 5;
        description
          "HSR Ring is operating in U mode";
      }
      enum hsr-ring-op-mode-x {
        value 6;
        description
          "HSR Ring is operating in X mode";
      }
    }
    description
      "Operating mode of the HSR Ring";
  }

  typedef hsr-oper-proto-status {
    type enumeration {
      enum hsr-ring-protocol-status {
        value 0;
        description
          "Status of protocol of the ring is either unknown or in error state";
      }
      enum hsr-protocol-enabled {
        value 1;
        description
          "Protocol has been enabled";
      }
      enum hsr-protocol-disabled {
        value 2;
        description
          "Protocol has been disabled";
      }
    }
    description
      "Protocol status of the HSR Ring";
  }

  typedef hsr-oper-redbox-mode {
    type enumeration {
      enum hsr-ring-rebox-mode-disabled {
        value 0;
        description
          "The redundant box is either not present or has been disabled from use";
      }
      enum hsr-ring-rebox-mode-hsr-san {
        value 1;
        description
          "Mode of the redundant box is HSR SAN";
      }
      enum hsr-ring-rebox-mode-hsr-prp-lan-a {
        value 2;
        description
          "Mode of the redundant box is HSR PRP LAN A";
      }
      enum hsr-ring-rebox-mode-hsr-prp-lan-b {
        value 3;
        description
          "Mode of the redundant box is HSR PRP LAN B";
      }
      enum hsr-ring-rebox-mode-hsr-hsr {
        value 4;
        description
          "Mode of the redundant box is HSR HSR";
      }
    }
    description
      "Mode of the redundant box of the HSR Ring";
  }

  typedef hsr-oper-node-type {
    type enumeration {
      enum hsr-ring-node-type-invalid {
        value 0;
        description
          "Type of node is ether not-known or invalid";
      }
      enum hsr-ring-node-type-san-a {
        value 1;
        description
          "Singly attached node on port a";
      }
      enum hsr-ring-node-type-san-b {
        value 2;
        description
          "Singly attached node on port b";
      }
      enum hsr-ring-node-type-danh {
        value 3;
        description
          "Dual attached node";
      }
    }
    description
      "Mode of the Redundant Box of the HSR Ring";
  }

  grouping hsr-ring-identity {
    description
      "HSR Ring Identity, combination of id and name";
    leaf id {
      type uint8;
      description
        "Unique ID of the HSR Ring";
    }
    leaf name {
      type string;
      description
        "Name of the HSR Ring";
    }
  }

  grouping hsr-ring-port {
    description
      "Information of ports configured in the HSR Ring";
    leaf name {
      type string;
      description
        "Name of HSR port";
    }
    leaf slot {
      type uint8;
      description
        "Port Slot Number";
    }
    leaf subslot {
      type uint8;
      description
        "Port Subslot Number";
    }
    leaf state {
      type hsr-ios-xe-oper:hsr-oper-state;
      description
        "State of the port belonging to the HSR Ring";
    }
  }

  grouping hsr-ring-summary {
    description
      "Summary of the HSR Ring parameters";
    leaf nw-layer {
      type hsr-ios-xe-oper:hsr-oper-nw-layer;
      description
        "Network layer of HSR Interface: [L2/L3]";
    }
    leaf op-mode {
      type hsr-ios-xe-oper:hsr-oper-work-mode;
      description
        "Operational mode of the HSR Ring";
    }
    leaf state {
      type hsr-ios-xe-oper:hsr-oper-state;
      description
        "Current state of the HSR Ring";
    }
    leaf proto-status {
      type hsr-ios-xe-oper:hsr-oper-proto-status;
      description
        "Information on Ring protocol status";
    }
    leaf redbox-mode {
      type hsr-ios-xe-oper:hsr-oper-redbox-mode;
      description
        "Current Redundant Box Mode";
    }
    leaf redbox-path-id {
      type int32;
      description
        "Redundant Box Path ID";
    }
    leaf max-ports {
      type uint8;
      description
        "Maximum possible number of ports in a Ring";
    }
    list port-info {
      description
        "Information of all the ports of the Ring";
      uses hsr-ios-xe-oper:hsr-ring-port;
    }
  }

  grouping hsr-ring-details {
    description
      "Details of the HSR Ring configuration parameters";
    leaf redbox-mac-addr {
      type yang:mac-address;
      description
        "MAC address of Redundant Box";
    }
    leaf node-forget-time {
      type uint16;
      units "milliseconds";
      description
        "Time interval after which the node
         will be forgotten";
    }
    leaf node-reboot-time {
      type uint16;
      units "milliseconds";
      description
        "Time interval after which the node
         will be reboot";
    }
    leaf entry-forget-time {
      type uint16;
      units "milliseconds";
      description
        "Time interval after which the entry
         will be forgotten";
    }
    leaf proxy-node-forget-time {
      type uint16;
      units "milliseconds";
      description
        "Time interval after which the node
         will be forgotten";
    }
    leaf supframe-cos-opt {
      type uint8;
      description
        "Class of Service (COS) option to be set
         in the VLAN tag of the Supervision frame";
    }
    leaf supframe-cfi-opt {
      type uint8;
      description
        "Canonical Format Indicator (CFI)
         for Vlan Tagged Supervision frame";
    }
    leaf uses-vlan-tag {
      type boolean;
      description
        "Is VLAN tag being used?";
    }
    leaf supframe-mac-da {
      type uint8;
      units "Byte";
      description
        "Last octet of Supervision frame
         Destination MAC address";
    }
    leaf supframe-vlan-id {
      type uint16;
      description
        "VLAN ID of the Supervision frame";
    }
    leaf supframe-time {
      type uint16;
      units "milliseconds";
      description
        "Time interval between two supervision
         frames being sent";
    }
    leaf life-check-interval {
      type uint16;
      units "milliseconds";
      description
        "life check interval time value for supervision frames";
    }
    leaf pause-time {
      type uint16;
      units "milliseconds";
      description
        "Pause time for Supervision frames";
    }
    leaf is-uplink-fpga-enbl {
      type boolean;
      description
        "Field Programmable Gate Array dual
         uplink enhancement is enabled/disabled";
    }
  }

  grouping hsr-ring-info {
    description
      "Information regarding HSR Ring parameters";
    container summary {
      description
        "Summary of the HSR Ring parameters";
      uses hsr-ios-xe-oper:hsr-ring-summary;
    }
    container details {
      description
        "Details of the HSR Ring configuration parameters";
      uses hsr-ios-xe-oper:hsr-ring-details;
    }
  }

  grouping hsr-ring-vlan-block {
    description
      "Blocked VLAN Address in HSR Ring";
    leaf vlan-lower {
      type uint16;
      description
        "Start Octet of VLAN range";
    }
    leaf vlan-upper {
      type uint16;
      description
        "End Octet of VLAN range";
    }
  }

  grouping hsr-ring-vlan-filter {
    description
      "List of all the Blocked VLANs";
    list hsr-ring-vlan-block {
      key "vlan-lower vlan-upper";
      description
        "VLAN filters in HSR Ring";
      uses hsr-ios-xe-oper:hsr-ring-vlan-block;
    }
  }

  grouping hsr-ring-node-entry {
    description
      "Entry of a Node attached with HSR Ring";
    leaf index {
      type uint32;
      description
        "Unique ID of node entry";
    }
    leaf mac-addr {
      type yang:mac-address;
      description
        "MAC address of the node";
    }
    leaf node-type {
      type hsr-ios-xe-oper:hsr-oper-node-type;
      description
        "HSR Node Role or Type";
    }
    leaf is-dynamic {
      type boolean;
      description
        "HSR Node was learned or configured";
    }
    leaf ttl {
      type yang:date-and-time;
      description
        "Absolute time and date (UTC) after which node entry will be
         deleted in case of node being unresponsive";
    }
  }

  grouping hsr-ring-node-table {
    description
      "List of all the nodes attached to the Ring";
    list hsr-ring-node-entry {
      key "index";
      description
        "Entry of a node attached with this HSR Ring";
      uses hsr-ios-xe-oper:hsr-ring-node-entry;
    }
  }

  grouping hsr-ring-vdan-entry {
    description
      "HSR Virtual Doubly Attached Node entry";
    leaf index {
      type uint32;
      description
        "Unique ID of Virtual Doubly Attached Node entry";
    }
    leaf mac-addr {
      type yang:mac-address;
      description
        "MAC address of the Node";
    }
    leaf is-dynamic {
      type boolean;
      description
        "HSR Node was learned or configured";
    }
    leaf ttl {
      type yang:date-and-time;
      description
        "Absolute time and date (UTC) after which node entry will be
         deleted in case of a node being unresponsive";
    }
  }

  grouping hsr-ring-vdan-table {
    description
      "List of all the VDAN nodes attached to the Ring";
    list hsr-ring-vdan-entry {
      key "index";
      description
        "Entry of a VDAN node attached to the Ring";
      uses hsr-ios-xe-oper:hsr-ring-vdan-entry;
    }
  }

  grouping hsr-ring-node-tbl-stats {
    description
      "HSR Ring Node Table Statistics";
    leaf proxynode-tbl-err {
      type uint32;
      description
        "Proxy Node table errors count";
    }
    leaf proxynode-tbl-num {
      type uint32;
      description
        "Count of Proxy Node table entries";
    }
    leaf node-tbl-err {
      type uint32;
      description
        "Node table errors count";
    }
    leaf node-tbl-num {
      type uint32;
      description
        "Count of Node table entries";
    }
  }

  grouping hsr-ring-ingress-stats {
    description
      "Ingress Statistics HSR Ring";
    leaf pkts-port-a {
      type uint64;
      description
        "Received packets on Port a";
    }
    leaf pkts-port-b {
      type uint64;
      description
        "Received packets on Port b";
    }
    leaf crc-port-a {
      type uint64;
      description
        "Received CRC on Port a";
    }
    leaf crc-port-b {
      type uint64;
      description
        "Received CRC on Port b";
    }
    leaf danh-pkts-accpt {
      type uint64;
      description
        "Received packets accepted from DAN-H";
    }
    leaf danh-pkts-dscrd {
      type uint64;
      description
        "Received packets discarded from DAN-H";
    }
    leaf supframes-rcv-a {
      type uint64;
      description
        "Received super-frames count on Port a";
    }
    leaf supframes-rcv-b {
      type uint64;
      description
        "Received super-frames count on Port b";
    }
    leaf over-pkts-a {
      type uint64;
      description
        "Received over packets count on Port a";
    }
    leaf over-pkts-b {
      type uint64;
      description
        "Received over packets count on Port b";
    }
    leaf pri-over-pkts-a {
      type uint64;
      description
        "Received pri over packets count on Port a";
    }
    leaf pri-over-pkts-b {
      type uint64;
      description
        "Received pri over packets count on Port b";
    }
    leaf oversize-pkts-a {
      type uint64;
      description
        "Received over-sized packets count on Port a";
    }
    leaf oversize-pkts-b {
      type uint64;
      description
        "Received over-sized packets count on Port b";
    }
    leaf bytes-port-a {
      type uint64;
      description
        "Total received byte count on Port a";
    }
    leaf bytes-port-b {
      type uint64;
      description
        "Total received byte count on Port b";
    }
    leaf sent-switch {
      type uint64;
      description
        "Received sent switch count";
    }
  }

  grouping hsr-ring-egress-stats {
    description
      "HSR Ring Egress Statistics";
    leaf dup-pkts {
      type uint64;
      description
        "Count of duplicate packets sent";
    }
    leaf supframes-sent {
      type uint64;
      description
        "Count of Supervision frames sent";
    }
    leaf pkts-port-a {
      type uint64;
      description
        "Count of egress frames on Port a";
    }
    leaf pkts-port-b {
      type uint64;
      description
        "Count of egress frames on Port b";
    }
    leaf bytes-port-a {
      type uint64;
      description
        "Egress byte count on Port a";
    }
    leaf bytes-port-b {
      type uint64;
      description
        "Egress byte count on Port b";
    }
    leaf recv-switch {
      type uint64;
      description
        "Egress receive switch";
    }
    leaf overruns {
      type uint64;
      description
        "Egress Overrun packets";
    }
    leaf overruns-drop {
      type uint64;
      description
        "Egress overrun dropped packets";
    }
  }

  grouping hsr-ring-pauseframe-stats {
    description
      "HSR Ring Pause Frame Statistics";
    leaf pf-sent {
      type uint32;
      description
        "Count of Pause frames sent";
    }
  }

  grouping hsr-ring-stats {
    description
      "HSR Ring all statistics";
    container ingress {
      description
        "Ingress Statistics of the HSR Ring";
      uses hsr-ios-xe-oper:hsr-ring-ingress-stats;
    }
    container egress {
      description
        "Egress statistics of the HSR Ring";
      uses hsr-ios-xe-oper:hsr-ring-egress-stats;
    }
    container pause-frame {
      description
        "Pause Frame statistics of the HSR Ring";
      uses hsr-ios-xe-oper:hsr-ring-pauseframe-stats;
    }
    container node-tbl {
      description
        "Node Table statistics of the HSR Ring";
      uses hsr-ios-xe-oper:hsr-ring-node-tbl-stats;
    }
  }

  container hsr-oper-data {
    config false;
    description
      "HSR operational data";
    list hsr-ring-summary {
      key "id name";
      description
        "Summary of the HSR Ring parameters";
      uses hsr-ios-xe-oper:hsr-ring-identity;
      uses hsr-ios-xe-oper:hsr-ring-summary;
    }
    list hsr-ring-info {
      key "id name";
      description
        "Detailed information of the HSR
         Ring configuration parameters";
      uses hsr-ios-xe-oper:hsr-ring-identity;
      uses hsr-ios-xe-oper:hsr-ring-info;
    }
    list hsr-ring-vlan-filter {
      key "id name";
      description
        "List of VLANs blocked in this HSR Ring";
      uses hsr-ios-xe-oper:hsr-ring-identity;
      uses hsr-ios-xe-oper:hsr-ring-vlan-filter;
    }
    list hsr-ring-node-table {
      key "id name";
      description
        "List of attached HSR nodes";
      uses hsr-ios-xe-oper:hsr-ring-identity;
      uses hsr-ios-xe-oper:hsr-ring-node-table;
    }
    list hsr-ring-vdan-table {
      key "id name";
      description
        "List of HSR Ring Virtual Doubly Attached Nodes (VDAN)";
      uses hsr-ios-xe-oper:hsr-ring-identity;
      uses hsr-ios-xe-oper:hsr-ring-vdan-table;
    }
    list hsr-ring-stats {
      key "id name";
      description
        "HSR Ring statistics information";
      uses hsr-ios-xe-oper:hsr-ring-identity;
      uses hsr-ios-xe-oper:hsr-ring-stats;
    }
  }
}
