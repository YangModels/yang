module Cisco-IOS-XE-dns-defense {
  yang-version 1.1;
  namespace "http://cisco.com/ns/yang/Cisco-IOS-XE-dns-defense";
  prefix ios-dns-defense;

  import Cisco-IOS-XE-umbrella {
    prefix ios-umbrella;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native DNS Defense Yang model.
     This module defines the DNS Defense configuration.
     Copyright (c) 2025 by Cisco Systems, Inc.
     All rights reserved.";

  revision 2026-02-01 {
    description
      "Initial revision of the DNS Defense YANG model.";
  }

  grouping dns-defense-global-grouping {
    description
      "Grouping for DNS Defense global configuration.";
    container dns-defense {
      description
        "DNS Defense mode";
      container global {
        description
          "dns-defense global parameter-map";
        presence "true";
        uses ios-umbrella:umbrella-dns-defense-global-grouping;
        must 'not(/ios:native/ios:parameter-map/ios:type/ios-umbrella:umbrella/ios-umbrella:global)' {
          error-message "dns-defense cannot be configured with umbrella";
        }
      }
    }
  }

  augment "/ios:native/ios:parameter-map/ios:type" {
    uses dns-defense-global-grouping;
  }
}
