submodule Cisco-IOS-XE-location {
  yang-version 1.1;
  belongs-to Cisco-IOS-XE-native {
    prefix ios;
  }

  import cisco-semver {
    prefix cisco-semver;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Native Location Yang Model.
     Copyright (c) 2022 by Cisco Systems, Inc.
     All rights reserved.";

  revision 2022-11-01 {
    description
      "- Update yang-version to 1.1";
    cisco-semver:module-version "1.1.0";
  }
  revision 2022-07-01 {
    description
      "- Initial Native Location revision";
    cisco-semver:module-version "1.0.0";
  }

  typedef loc-resolution-type {
    type string {
      pattern '([0-9]+(\.[0-9]+)?)';
    }
  }

  grouping config-location-grouping {
    container location {
      description
        "Global location configuration commands";
      container civic-location {
        description
          "Civic location information";
        list identifier {
          description
            "Set the identifier";
          key "identifier";
          leaf identifier {
            type string;
          }
          leaf building {
            description
              "Building information";
            type string;
          }
          leaf floor {
            description
              "Floor number";
            type string;
          }
          leaf landmark {
            description
              "Landmark";
            type string;
          }
          leaf name {
            description
              "Resident name";
            type string;
          }
          leaf number {
            description
              "Street number";
            type string;
          }
          leaf country {
            description
              "Country code";
            type string {
              length "2";
            }
          }
          leaf state {
            description
              "State name";
            type string;
          }
          leaf city {
            description
              "City name";
            type string;
          }
          leaf postal-code {
            description
              "Postal code";
            type string;
          }
        }
      }
      container geo-location {
        description
          "Geo-spatial location information";
        list identifier {
          description
            "Set the identifier";
          key "id";
          leaf id {
            type string {
              length "1..215";
            }
          }
          container latitude {
            description
              "Set latitude information";
            presence "true";
            leaf value {
              description
                "Latitude coordinate in degrees or decimal degrees (e.g. [+-]ddd[.ddddd] [mm[.mm]] [ss[.ss]])";
              mandatory true;
              type string {
                length "1..18";
                pattern '(([+-]?((90(\.0+)?)|([1-8]?[0-9](\.[0-9]+)?)))( [0-9]+(\.[0-9]+)?){0,2})';
              }
            }
            leaf resolution {
              description
                "Latitude coordinate resolution in meters";
              type loc-resolution-type;
            }
          }
          container longitude {
            description
              "Set longitude information";
            presence "true";
            leaf value {
              description
                "Longitude coordinate in degrees or decimal degrees (e.g. [-]ddd[.ddddd] [mm[.mm]] [ss[.ss]])";
              mandatory true;
              type string {
                length "1..18";
                pattern '(([+-]?(180(\.0+)?|(((1[0-7][0-9])|([1-9]?[0-9]))(\.[0-9]+)?))( [0-9]+(\.[0-9]+)?){0,2}))';
              }
            }
            leaf resolution {
              description
                "Longitude coordinate resolution in meters";
              type loc-resolution-type;
            }
          }
          container altitude {
            description
              "Set altitude information";
            presence "true";
            leaf value {
              description
                "Altitude coordinate value (in meters, feet or floors)";
              mandatory true;
              type string {
                length "1..18";
                pattern '([+-]?[0-9]+(\.[0-9]*)?)';
              }
            }
            container unit {
              choice unit-choice {
                mandatory true;
                case meters {
                  leaf meters {
                    description
                      "Set meters as altitude measurement unit";
                    type empty;
                  }
                }
                case feet {
                  leaf feet {
                    description
                      "Set feet as altitude measurement unit";
                    type empty;
                  }
                }
                case floor {
                  leaf floor {
                    description
                      "Set floors as altitude measurement unit";
                    type empty;
                  }
                }
              }
            }
            leaf resolution {
              when 'not(../unit/floor)';
              description
                "Altitude resolution expressed in the same unit of measurement as altitude";
              type loc-resolution-type;
            }
          }
          leaf resolution {
            description
              "Latitude/Longitude resolution value. Applied only if no specific coordinate resolution is configured";
            type loc-resolution-type;
          }
        }
      }
    }
  }
}
