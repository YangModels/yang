module Cisco-IOS-XE-kron {
  yang-version 1.1;
  namespace "http://cisco.com/ns/yang/Cisco-IOS-XE-kron";
  prefix ios-kron;

  import Cisco-IOS-XE-native {
    prefix ios;
  }
  import Cisco-IOS-XE-types {
    prefix ios-types;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE kron YANG model.
     Copyright (c) 2024 by Cisco Systems, Inc.
     All rights reserved.";

  revision 2024-11-01 {
    description
      "-Added support for kron YANG model";
  }

  typedef mmm-type {
    type string {
      pattern '([0-9]|[1-5][0-9])';
    }
  }

  typedef hhhmm-type {
    type string {
      pattern '([0-9]|[1][0-9]|2[0-3]):([0-9]|[1-5][0-9])';
    }
  }

  typedef dddhhmm-type {
    type string {
      pattern '([0-9]|[1-9][0-9]|[1-2][0-9][0-9]|3[0-5][0-9]|36[0-5]):([0-9]|[1][0-9]|2[0-3]):([0-9]|[1-5][0-9])';
    }
  }

  grouping config-kron-grouping {
    container kron {
      description
        "Kron interval Facility";
      list occurrence {
        description
          "Define the name, time, interval of kron occurrence";
        ordered-by user;
        key "name";
        leaf name {
          description
            "The name of this occurrence";
          type string;
        }
        choice option-at-in {
          case at {
            container at {
              description
                "Date of kron occurrence eg. 14:30 Feb 13";
              leaf time {
                description
                  "Time of day for occurrence (hh:min eg. 14:30)";
                type ios-types:hhmm-type;
              }
              leaf recurring {
                description
                  "Schedule kron occurrence repeatedly";
                type empty;
              }
            }
          }
          case in {
            container in {
              description
                "Delta time to kron occurrence";
              leaf delay {
                description
                  "Delay before occurrence";
                type union {
                  type mmm-type;
                  type hhhmm-type;
                  type dddhhmm-type;
                }
              }
              leaf recurring {
                description
                  "Schedule kron occurrence repeatedly";
                type empty;
              }
            }
          }
        }
        list policy-list {
          description
            "Define the name and type of policy-list";
          ordered-by user;
          key "policy_label";
          leaf policy_label {
            description
              "Name of Policy to be executed";
            type string;
          }
        }
      }
      list policy-list {
        description
          "Define the name and type of policy-list";
        ordered-by user;
        key "policy_label";
        leaf policy_label {
          description
            "Name of the policy-list being defined";
          type string;
        }
        leaf cli {
          description
            "Specify the exec level cli to be executed";
          type string;
        }
      }
    }
  }

  augment "/ios:native" {
    uses config-kron-grouping;
  }
}
