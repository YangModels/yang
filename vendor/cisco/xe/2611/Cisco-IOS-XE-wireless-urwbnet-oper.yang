module Cisco-IOS-XE-wireless-urwbnet-oper {
  yang-version 1.1;
  namespace "http://cisco.com/ns/yang/Cisco-IOS-XE-wireless-urwbnet-oper";
  prefix wireless-oper-urwbnet;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for URWB(Ultra Reliable Wireless Backhaul) network global
     operational data.
     Copyright (c) 2025 by Cisco Systems, Inc.
     All rights reserved.";

  revision 2026-02-01 {
    description
      "- Added timestamp field to URWB oper data to indicate last update time.
       - Added URWB profile name and radio MAC address.
       - Added MCS data rate and NSS information to URWB network configuration.";
    reference
      "1.1.0";
    cisco-semver:module-version "1.1.0";
  }
  revision 2025-07-01 {
    description
      "Initial revision";
    reference
      "1.0.0";
    cisco-semver:module-version "1.0.0";
  }

  typedef uar {
    type enumeration {
      enum uar-fixed {
        value 0;
        description
          "AP role fixed node";
      }
      enum uar-client-pri {
        value 1;
        description
          "AP role mobility client primary";
      }
      enum uar-client-sec {
        value 2;
        description
          "AP role mobility client secondary";
      }
      enum uar-coord {
        value 3;
        description
          "AP role Coordinator";
      }
      enum uar-coord-backup {
        value 4;
        description
          "AP role Coordinator Backup";
      }
    }
    description
      "Enum for URWB network ap role information";
  }

  typedef urr {
    type enumeration {
      enum urr-fixed-base {
        value 0;
        description
          "AP radio role fixed base";
      }
      enum urr-ptmp-prim {
        value 1;
        description
          "AP radio role PTMP primary";
      }
      enum urr-ptmp-sec {
        value 2;
        description
          "AP radio role PTMP secondary";
      }
      enum urr-fl-base {
        value 3;
        description
          "AP radio role mobility base";
      }
      enum urr-fl-client {
        value 4;
        description
          "AP radio role mobility client";
      }
    }
    description
      "Enum for URWB network radio role information";
  }

  typedef urwbnet-bw {
    type enumeration {
      enum urwbnet-bw20m {
        value 0;
        description
          "URWB network bandwidth 20MHz";
      }
      enum urwbnet-bw40m {
        value 1;
        description
          "URWB network bandwidth 40MHz";
      }
      enum urwbnet-bw80m {
        value 2;
        description
          "URWB network bandwidth 80MHz";
      }
      enum urwbnet-bw160m {
        value 3;
        description
          "URWB network bandwidth 160MHz";
      }
    }
    description
      "Enum for URWB network bandwidth information";
  }

  typedef urwb-network-mcstype {
    type enumeration {
      enum urwbnet-mcs-noht {
        value 0;
        description
          "URWB network MCS type not high throughput";
      }
      enum urwbnet-mcs-ht {
        value 1;
        description
          "URWB network MCS type high throughput (80211n)";
      }
      enum urwbnet-mcs-vht {
        value 2;
        description
          "URWB network MCS type very high throughput";
      }
      enum urwbnet-he {
        value 3;
        description
          "URWB network MCS type HE (80211ax)";
      }
    }
    description
      "Enum for URWB network MCS type information";
  }

  typedef urwb-network-gi {
    type enumeration {
      enum urwbnet-gi-gi08 {
        value 0;
        description
          "URWB network guard interval 800 nano seconds";
      }
      enum urwbnet-gi-gi04 {
        value 1;
        description
          "URWB network guard interval 400 nano seconds";
      }
      enum urwbnet-gi-gi16 {
        value 2;
        description
          "URWB network guard interval 1.6 micro seconds";
      }
      enum urwbnet-gi-gi32 {
        value 3;
        description
          "URWB network guard interval 3.2 micro seconds";
      }
    }
    description
      "Enum for URWB network guard interval information";
  }

  typedef urwb-mcs-index {
    type enumeration {
      enum mcs-0 {
        value 0;
        description
          "MCS Index 0";
      }
      enum mcs-1 {
        value 1;
        description
          "MCS Index 1";
      }
      enum mcs-2 {
        value 2;
        description
          "MCS Index 2";
      }
      enum mcs-3 {
        value 3;
        description
          "MCS Index 3";
      }
      enum mcs-4 {
        value 4;
        description
          "MCS Index 4";
      }
      enum mcs-5 {
        value 5;
        description
          "MCS Index 5";
      }
      enum mcs-6 {
        value 6;
        description
          "MCS Index 6";
      }
      enum mcs-7 {
        value 7;
        description
          "MCS Index 7";
      }
      enum mcs-8 {
        value 8;
        description
          "MCS Index 8";
      }
      enum mcs-9 {
        value 9;
        description
          "MCS Index 9";
      }
      enum mcs-10 {
        value 10;
        description
          "MCS Index 10";
      }
      enum mcs-11 {
        value 11;
        description
          "MCS Index 11";
      }
    }
    description
      "Enum for MCS index information";
  }

  typedef urwb-network-conn-type {
    type enumeration {
      enum urwb-network-conn-wired {
        value 0;
        description
          "URWB network wired link";
      }
      enum urwb-network-conn-wireless {
        value 1;
        description
          "URWB network wireless link";
      }
    }
    description
      "Enum for URWB network link type";
  }

  grouping st-urwbnet-inaddr {
    description
      "URWB network interface address information";
    leaf addr {
      type inet:ip-address;
      description
        "URWB network interface address";
    }
  }

  grouping st-urwbnet-mesh-id {
    description
      "URWB network mesh identifier";
    leaf addr {
      type inet:ip-address;
      description
        "URWB network mesh identifier address";
    }
  }

  grouping st-urwbnet-link-id {
    description
      "URWB link identifier";
    leaf src {
      type inet:ip-address;
      description
        "Source identifier";
    }
    leaf dest {
      type inet:ip-address;
      description
        "Destination identifier";
    }
  }

  grouping st-urwbnet-conn-dev {
    description
      "URWB network connected devices";
    leaf ip {
      type inet:ip-address;
      description
        "IP Address of device";
    }
    leaf vlan-id {
      type uint32;
      description
        "Vlan ID of device";
    }
  }

  grouping st-urwbnet-node-intf {
    description
      "URWB network node interfaces statistics";
    container intf-id {
      description
        "URWB network node interface id";
      uses wireless-oper-urwbnet:st-urwbnet-inaddr;
    }
    leaf intf-enabled {
      type boolean;
      description
        "URWB network node interface enable status";
    }
    leaf role {
      type wireless-oper-urwbnet:urr;
      description
        "URWB network node interface radio role";
    }
    leaf freq {
      type int32;
      units "MHz";
      description
        "URWB network node interface radio frequency";
    }
    leaf bw {
      type wireless-oper-urwbnet:urwbnet-bw;
      description
        "URWB network node interface bandwidth";
    }
    leaf tx-power {
      type int32;
      units "dBm";
      description
        "URWB network node interface tx power";
    }
    leaf is-tdma {
      type boolean;
      description
        "URWB network node interface is time division multiple access";
    }
    leaf freq-scan {
      type boolean;
      description
        "URWB network node interface frequency scan status";
    }
  }

  grouping st-urwbnet-mob-link {
    description
      "URWB network mobility link";
    container id {
      description
        "Identifier for the mobility link";
      uses wireless-oper-urwbnet:st-urwbnet-link-id;
    }
    container prim-id {
      description
        "Primary mobility link identifier";
      uses wireless-oper-urwbnet:st-urwbnet-mesh-id;
    }
    leaf client-id {
      type int32;
      description
        "Client ID";
    }
    leaf ho-seq-nu {
      type uint32;
      description
        "Handoff sequence number";
    }
    list sec-mesh-id {
      max-elements 16;
      description
        "Secondary mesh ids";
      uses wireless-oper-urwbnet:st-urwbnet-mesh-id;
    }
  }

  grouping st-urwbnet-wfm {
    description
      "URWB network wireless link waveform";
    leaf bw {
      type wireless-oper-urwbnet:urwbnet-bw;
      units "MHz";
      description
        "Wireless link waveform bandwidth";
    }
    leaf mcs {
      type wireless-oper-urwbnet:urwb-network-mcstype;
      description
        "MCS Type";
    }
    leaf mcs-index {
      type uint32;
      description
        "MCS Index";
    }
    leaf gi {
      type wireless-oper-urwbnet:urwb-network-gi;
      units "nanoseconds/microseconds";
      description
        "Guard Interval";
    }
    leaf mcs-val {
      type wireless-oper-urwbnet:urwb-mcs-index;
      units "Mbps";
      description
        "Indicates the effective MCS data rate used for packet transmission/reception. Derived from the MCS index received from the access point";
    }
    leaf nss {
      type uint8;
      description
        "Indicates the number of spatial streams (NSS), representing the number of simultaneous data streams transmitted over different spatial paths. Derived from the MCS index received from the access point";
    }
  }

  grouping st-urwbnet-wl-tx {
    description
      "URWB network wireless link stats tx";
    leaf tstamp {
      type yang:date-and-time;
      description
        "Time of transmit statistics collection";
    }
    leaf sent {
      type uint64;
      units "packets";
      description
        "Tx packets sent";
    }
    leaf failed {
      type uint64;
      description
        "Tx fail count";
    }
    leaf retries {
      type uint64;
      description
        "Tx retries";
    }
    leaf bytes {
      type uint64;
      units "bytes";
      description
        "Tx bytes";
    }
    container tx-wfm {
      description
        "wireless link waveform information";
      uses wireless-oper-urwbnet:st-urwbnet-wfm;
    }
  }

  grouping st-urwbnet-wl-rx {
    description
      "URWB network wireless link stats rx";
    leaf tstamp {
      type yang:date-and-time;
      description
        "Time of receive statistics collection";
    }
    leaf rssi {
      type int32;
      units "dBm";
      description
        "Received Signal Strength";
    }
    leaf recv {
      type uint64;
      description
        "Received packet count";
    }
    leaf bytes {
      type uint64;
      units "bytes";
      description
        "Rx bytes";
    }
    container rx-wfm {
      description
        "Wireless link waveform information";
      uses wireless-oper-urwbnet:st-urwbnet-wfm;
    }
  }

  grouping st-urwbnet-wlink-stats {
    description
      "URWB network wireless link stats";
    container link-id {
      description
        "Wireless link identifier";
      uses wireless-oper-urwbnet:st-urwbnet-link-id;
    }
    container rx-stats {
      description
        "Wireless link rx stats";
      uses wireless-oper-urwbnet:st-urwbnet-wl-rx;
    }
    container tx-stats {
      description
        "Wireless link tx stats";
      uses wireless-oper-urwbnet:st-urwbnet-wl-tx;
    }
  }

  grouping st-urwbnet-fix-lnk {
    description
      "URWB fixed links";
    container id {
      description
        "Identifier for the fixed link";
      uses wireless-oper-urwbnet:st-urwbnet-link-id;
    }
    leaf type {
      type wireless-oper-urwbnet:urwb-network-conn-type;
      description
        "Type of the link";
    }
  }

  grouping st-urwbnet-coord-rt {
    description
      "URWB network coordinator routes";
    leaf index {
      type uint32;
      description
        "Coordinator route index";
    }
    list peer {
      max-elements 64;
      description
        "Coordinator route peer list";
      uses wireless-oper-urwbnet:st-urwbnet-mesh-id;
    }
  }

  grouping st-urwbnet-node {
    description
      "URWB network node statistics";
    container id {
      description
        "URWB network node id";
      uses wireless-oper-urwbnet:st-urwbnet-mesh-id;
    }
    leaf name {
      type string;
      description
        "URWB network node name";
    }
    leaf device-model {
      type string;
      description
        "URWB network node device model";
    }
    leaf role {
      type wireless-oper-urwbnet:uar;
      description
        "URWB network node role";
    }
    leaf ip-addr {
      type inet:ip-address;
      description
        "URWB network node IP address";
    }
    leaf net-mask {
      type inet:ip-address;
      description
        "URWB network node netmask";
    }
    list node-if {
      max-elements 16;
      description
        "URWB network node interface list";
      uses wireless-oper-urwbnet:st-urwbnet-node-intf;
    }
    leaf conn-dev-count {
      type uint8;
      description
        "URWB network connected device count";
    }
    leaf urwb-prof {
      type string;
      description
        "URWB profile in use for this node";
    }
    leaf radio-mac {
      type yang:mac-address;
      description
        "Radio MAC address of this URWB node";
    }
  }

  grouping st-urwb-node-link-id {
    description
      "Node link id list";
    container lnk-id {
      description
        "Link id";
      uses wireless-oper-urwbnet:st-urwbnet-link-id;
    }
    leaf rad-role {
      type wireless-oper-urwbnet:urr;
      description
        "Radio role";
    }
    leaf last-update {
      type yang:date-and-time;
      description
        "Specifies the timestamp when this node link entry was last updated in the URWB operational telemetry data.";
    }
  }

  grouping st-urwbnet-node-g {
    description
      "URWB network node global statistics";
    container id {
      description
        "URWB network node id";
      uses wireless-oper-urwbnet:st-urwbnet-mesh-id;
    }
    container coord-id {
      description
        "Coordinator id of the network node";
      uses wireless-oper-urwbnet:st-urwbnet-mesh-id;
    }
    leaf coord-mac {
      type yang:mac-address;
      description
        "Coordinator mac address of the network node";
    }
    leaf dev-count {
      type uint32;
      description
        "Connected device count";
    }
    list urwbnet-conn-dev {
      key "ip";
      description
        "Connected device list";
      uses wireless-oper-urwbnet:st-urwbnet-conn-dev;
    }
    list urwbnet-lnk-id {
      key "src dest";
      description
        "Link id list";
      uses wireless-oper-urwbnet:st-urwbnet-link-id;
      uses wireless-oper-urwbnet:st-urwb-node-link-id;
    }
    leaf last-update {
      type yang:date-and-time;
      description
        "Specifies the timestamp when this node global entry was last updated in the URWB operational telemetry data.";
    }
  }

  grouping st-urwbnet-subnet {
    description
      "URWB network state information";
    leaf mac {
      type yang:mac-address;
      description
        "Coordinator MAC address";
    }
    container gw {
      description
        "Gateway identifier";
      uses wireless-oper-urwbnet:st-urwbnet-mesh-id;
    }
    leaf nodes-cnt {
      type uint32;
      description
        "URWB network node count";
    }
    list urwbnet-node {
      key "addr";
      description
        "URWB network nodes";
      uses wireless-oper-urwbnet:st-urwbnet-mesh-id;
      uses wireless-oper-urwbnet:st-urwbnet-node;
    }
    leaf coord-rt-cnt {
      type uint32;
      description
        "URWB network coordinator route count";
    }
    list urwbnet-coord-routes {
      key "index";
      description
        "URWB network coordinator routes";
      uses wireless-oper-urwbnet:st-urwbnet-coord-rt;
    }
    leaf fix-lnk-cnt {
      type uint32;
      description
        "URWB network fixed link count";
    }
    list urwbnet-fixed-links {
      key "src dest";
      description
        "URWB fixed links";
      uses wireless-oper-urwbnet:st-urwbnet-fix-lnk;
      uses wireless-oper-urwbnet:st-urwbnet-link-id;
    }
    leaf mob-lnk-cnt {
      type uint32;
      description
        "URWB network mobility link count";
    }
    list urwbnet-mobility-links {
      key "src dest";
      description
        "URWB mobility links";
      uses wireless-oper-urwbnet:st-urwbnet-link-id;
      uses wireless-oper-urwbnet:st-urwbnet-mob-link;
    }
    leaf wlinks-cnt {
      type uint32;
      description
        "URWB wireless link count";
    }
    list urwbnet-wlink-stats {
      key "src dest";
      description
        "URWB wireless links";
      uses wireless-oper-urwbnet:st-urwbnet-link-id;
      uses wireless-oper-urwbnet:st-urwbnet-wlink-stats;
    }
    leaf coord-name {
      type string;
      description
        "URWB coordinator AP name";
    }
  }

  container urwbnet-oper-data {
    config false;
    description
      "URWB network operational data";
    list urwbnet-stats {
      key "mac";
      description
        "List of URWB network operational data per coordinator";
      uses wireless-oper-urwbnet:st-urwbnet-subnet;
    }
    list urwbnet-node-g {
      key "addr";
      description
        "List of URWB network Nodes";
      uses wireless-oper-urwbnet:st-urwbnet-mesh-id;
      uses wireless-oper-urwbnet:st-urwbnet-node-g;
    }
  }
}
