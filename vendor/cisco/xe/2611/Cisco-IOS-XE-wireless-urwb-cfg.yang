module Cisco-IOS-XE-wireless-urwb-cfg {
  yang-version 1.1;
  namespace "http://cisco.com/ns/yang/Cisco-IOS-XE-wireless-urwb-cfg";
  prefix wireless-urwb-cfg;

  import Cisco-IOS-XE-wireless-enum-types {
    prefix wireless-enum-types;
  }
  import Cisco-IOS-XE-wireless-urwb-common-types {
    prefix wireless-urwb-common-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Ultra Reliable Wireless Backhaul (URWB) configuration data.
     Copyright (c) 2025 by Cisco Systems, Inc.
     All rights reserved.";

  revision 2026-02-01 {
    description
      "- Fix model constraint for URWB profile description leaf by adding a space to the list of allowed characters
       - Added new configuration reliability parameters for URWB
       - Added passphrase type and updated passphrase pattern";
    reference
      "2.0.0";
    cisco-semver:module-version "2.0.0";
  }
  revision 2025-07-01 {
    description
      "Initial revision";
    reference
      "1.0.0";
    cisco-semver:module-version "1.0.0";
  }

  grouping st-ethertype-list {
    description
      "This contains all attributes for mpls ether type";
    leaf ethertype {
      type uint16;
      description
        "This value indicates the ether type used";
    }
  }

  grouping st-urwb-rel {
    description
      "URWB reliability configuration";
    leaf grat-arp {
      type wireless-enum-types:urwb-grat-arp;
      default "urwb-grat-arp-disable";
      description
        "Specifies the URWB gratuitous ARP management mode";
    }
    leaf grat-arp-delay {
      type uint32 {
        range "0 .. 2147483647";
      }
      units "milliseconds";
      default "150";
      description
        "Specifies the delay time before sending URWB gratuitous ARP packets";
    }
    leaf qosmap-pri-0 {
      type uint8 {
        range "0 .. 7";
      }
      default "0";
      description
        "Specifies the URWB Quality of Service (QoS) mapping for priority 0";
    }
    leaf qosmap-pri-1 {
      type uint8 {
        range "0 .. 7";
      }
      default "1";
      description
        "Specifies the URWB Quality of Service (QoS) mapping for priority 1";
    }
    leaf qosmap-pri-2 {
      type uint8 {
        range "0 .. 7";
      }
      default "2";
      description
        "Specifies the URWB Quality of Service (QoS) mapping for priority 2";
    }
    leaf qosmap-pri-3 {
      type uint8 {
        range "0 .. 7";
      }
      default "3";
      description
        "Specifies the URWB Quality of Service (QoS) mapping for priority 3";
    }
    leaf qosmap-pri-4 {
      type uint8 {
        range "0 .. 7";
      }
      default "4";
      description
        "Specifies the URWB Quality of Service (QoS) mapping for priority 4";
    }
    leaf qosmap-pri-5 {
      type uint8 {
        range "0 .. 7";
      }
      default "5";
      description
        "Specifies the URWB Quality of Service (QoS) mapping for priority 5";
    }
    leaf qosmap-pri-6 {
      type uint8 {
        range "0 .. 7";
      }
      default "6";
      description
        "Specifies the URWB Quality of Service (QoS) mapping for priority 6";
    }
    leaf qosmap-pri-7 {
      type uint8 {
        range "0 .. 7";
      }
      default "7";
      description
        "Specifies the URWB Quality of Service (QoS) mapping for priority 7";
    }
  }

  grouping urwb-profile {
    description
      "URWB profile configuration";
    leaf profile-name {
      type string {
        length "1..128" {
          error-message "URWB profile-name should not be greater than 128 characters";
          error-app-tag "must-violation";
        }
        pattern '[!-~]([ -~]*[!-~])?';
        pattern '[!-~]([ -~]*[!-~])?' {
          error-message "URWB profile name must use ASCII 1-126 characters and must not contain leading or trailing spaces";
          error-app-tag "pattern-violation";
        }
      }
      description
        "URWB profile name";
    }
    leaf descp {
      type string {
        length "0..128";
        pattern '([!-~]([ -~]*[!-~])?)?';
      }
      default "";
      description
        "Description for URWB profile. Description may contain only printable ASCII characters with no leading or trailing spaces";
    }
    leaf enabled {
      type boolean;
      default "false";
      description
        "This value indicates whether URWB feature is enabled";
    }
    leaf passphr {
      type string {
        length "0..64";
        pattern '[0-9a-zA-Z\-_`^]*';
      }
      default "";
      description
        "This value indicates the URWB network-key";
    }
    leaf passphr-type {
      type wireless-enum-types:crypt-type;
      default "clear";
      description
        "Indicates the encryption type for the URWB passphrase.";
    }
    container mob {
      description
        "URWB mobility configuration";
      uses wireless-urwb-common-types:st-urwb-mob;
    }
    container mpls {
      description
        "URWB mpls configuration";
      uses wireless-urwb-common-types:st-urwb-mpls;
    }
    container mpo {
      description
        "URWB MPO configuration";
      uses wireless-urwb-common-types:st-urwb-mpo;
    }
    leaf mcast {
      type wireless-enum-types:urwb-mcast;
      default "urwb-mcast-dis";
      description
        "URWB multicast configuration";
    }
    leaf strong-netkey {
      type boolean;
      default "false";
      description
        "Indicates whether strong network key is enabled";
    }
    container ethertype-lists {
      description
        "URWB ether types list configuration";
      list ethertype-list {
        key "ethertype";
        description
          "URWB ether types list configuration";
        uses wireless-urwb-cfg:st-ethertype-list;
      }
    }
    container rel {
      description
        "URWB reliability parameters";
      uses wireless-urwb-cfg:st-urwb-rel;
    }
  }

  container urwb-cfg-data {
    description
      "URWB backhaul configuration data";
    container urwb-profiles {
      description
        "URWB policy configuration profiles for APs";
      list urwb-profile {
        key "profile-name";
        description
          "URWB policy configuration for AP";
        uses wireless-urwb-cfg:urwb-profile;
      }
    }
  }
}
