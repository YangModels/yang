module Cisco-IOS-XE-ospf-deviation {
  yang-version 1.1;
  namespace "http://cisco.com/ns/yang/Cisco-IOS-XE-ospf-deviation";
  prefix ios-ospf-deviation;

  import Cisco-IOS-XE-native {
    prefix ios;
  }
  import Cisco-IOS-XE-ospf {
    prefix ios-ospf;
  }
  import cisco-semver {
    prefix cisco-semver;
  }

  description
    "Copyright (c) 2021 by Cisco Systems, Inc.All rights reserved.";

  revision 2023-07-01 {
    description
      "Adding deviation for redistribution of unsupported protocols into OSPF";
    cisco-semver:module-version "1.4.0";
  }
  revision 2022-11-01 {
    description
      "- Update yang-version to 1.1";
    cisco-semver:module-version "1.1.0";
  }
  revision 2021-11-01 {
    description
      "Adding deviation for microloop avoidance for VRF instance";
    cisco-semver:module-version "1.0.0";
  }

  deviation "/ios:native/ios:router/ios-ospf:router-ospf/ios-ospf:ospf/ios-ospf:process-id-vrf/ios-ospf:microloop" {
    deviate not-supported;
  }

  deviation "/ios:native/ios:router/ios-ospf:router-ospf/ios-ospf:ospf/ios-ospf:process-id/ios-ospf:redistribute/ios-ospf:vrf/ios-ospf:isis" {
    deviate not-supported;
  }

  deviation "/ios:native/ios:router/ios-ospf:router-ospf/ios-ospf:ospf/ios-ospf:process-id/ios-ospf:redistribute/ios-ospf:vrf/ios-ospf:isis-area-tag" {
    deviate not-supported;
  }

  deviation "/ios:native/ios:router/ios-ospf:router-ospf/ios-ospf:ospf/ios-ospf:process-id/ios-ospf:redistribute/ios-ospf:vrf/ios-ospf:lisp" {
    deviate not-supported;
  }

  deviation "/ios:native/ios:router/ios-ospf:router-ospf/ios-ospf:ospf/ios-ospf:process-id/ios-ospf:redistribute/ios-ospf:vrf/ios-ospf:mobile" {
    deviate not-supported;
  }

  deviation "/ios:native/ios:router/ios-ospf:router-ospf/ios-ospf:ospf/ios-ospf:process-id/ios-ospf:redistribute/ios-ospf:vrf/ios-ospf:nat-route" {
    deviate not-supported;
  }

  deviation "/ios:native/ios:router/ios-ospf:router-ospf/ios-ospf:ospf/ios-ospf:process-id/ios-ospf:redistribute/ios-ospf:vrf/ios-ospf:nhrp" {
    deviate not-supported;
  }

  deviation "/ios:native/ios:router/ios-ospf:router-ospf/ios-ospf:ospf/ios-ospf:process-id/ios-ospf:redistribute/ios-ospf:vrf/ios-ospf:odr" {
    deviate not-supported;
  }

  deviation "/ios:native/ios:router/ios-ospf:router-ospf/ios-ospf:ospf/ios-ospf:process-id/ios-ospf:redistribute/ios-ospf:vrf/ios-ospf:omp" {
    deviate not-supported;
  }

  deviation "/ios:native/ios:router/ios-ospf:router-ospf/ios-ospf:ospf/ios-ospf:process-id/ios-ospf:redistribute/ios-ospf:vrf/ios-ospf:rip" {
    deviate not-supported;
  }

  deviation "/ios:native/ios:router/ios-ospf:router-ospf/ios-ospf:ospf/ios-ospf:process-id-vrf/ios-ospf:redistribute/ios-ospf:vrf/ios-ospf:isis" {
    deviate not-supported;
  }

  deviation "/ios:native/ios:router/ios-ospf:router-ospf/ios-ospf:ospf/ios-ospf:process-id-vrf/ios-ospf:redistribute/ios-ospf:vrf/ios-ospf:isis-area-tag" {
    deviate not-supported;
  }

  deviation "/ios:native/ios:router/ios-ospf:router-ospf/ios-ospf:ospf/ios-ospf:process-id-vrf/ios-ospf:redistribute/ios-ospf:vrf/ios-ospf:lisp" {
    deviate not-supported;
  }

  deviation "/ios:native/ios:router/ios-ospf:router-ospf/ios-ospf:ospf/ios-ospf:process-id-vrf/ios-ospf:redistribute/ios-ospf:vrf/ios-ospf:mobile" {
    deviate not-supported;
  }

  deviation "/ios:native/ios:router/ios-ospf:router-ospf/ios-ospf:ospf/ios-ospf:process-id-vrf/ios-ospf:redistribute/ios-ospf:vrf/ios-ospf:nat-route" {
    deviate not-supported;
  }

  deviation "/ios:native/ios:router/ios-ospf:router-ospf/ios-ospf:ospf/ios-ospf:process-id-vrf/ios-ospf:redistribute/ios-ospf:vrf/ios-ospf:nhrp" {
    deviate not-supported;
  }

  deviation "/ios:native/ios:router/ios-ospf:router-ospf/ios-ospf:ospf/ios-ospf:process-id-vrf/ios-ospf:redistribute/ios-ospf:vrf/ios-ospf:odr" {
    deviate not-supported;
  }

  deviation "/ios:native/ios:router/ios-ospf:router-ospf/ios-ospf:ospf/ios-ospf:process-id-vrf/ios-ospf:redistribute/ios-ospf:vrf/ios-ospf:omp" {
    deviate not-supported;
  }

  deviation "/ios:native/ios:router/ios-ospf:router-ospf/ios-ospf:ospf/ios-ospf:process-id-vrf/ios-ospf:redistribute/ios-ospf:vrf/ios-ospf:ospfv3" {
    deviate not-supported;
  }

  deviation "/ios:native/ios:router/ios-ospf:router-ospf/ios-ospf:ospf/ios-ospf:process-id-vrf/ios-ospf:redistribute/ios-ospf:vrf/ios-ospf:rip" {
    deviate not-supported;
  }

  deviation "/ios:native/ios:router/ios-ospf:router-ospf/ios-ospf:ospf/ios-ospf:process-id/ios-ospf:redistribute/ios-ospf:application/ios-ospf:translate-rib-metric" {
    deviate not-supported;
  }

  deviation "/ios:native/ios:router/ios-ospf:router-ospf/ios-ospf:ospf/ios-ospf:process-id/ios-ospf:redistribute/ios-ospf:eigrp/ios-ospf:translate-rib-metric" {
    deviate not-supported;
  }

  deviation "/ios:native/ios:router/ios-ospf:router-ospf/ios-ospf:ospf/ios-ospf:process-id/ios-ospf:redistribute/ios-ospf:lisp/ios-ospf:translate-rib-metric" {
    deviate not-supported;
  }

  deviation "/ios:native/ios:router/ios-ospf:router-ospf/ios-ospf:ospf/ios-ospf:process-id/ios-ospf:redistribute/ios-ospf:mobile/ios-ospf:translate-rib-metric" {
    deviate not-supported;
  }

  deviation "/ios:native/ios:router/ios-ospf:router-ospf/ios-ospf:ospf/ios-ospf:process-id/ios-ospf:redistribute/ios-ospf:nat-route/ios-ospf:translate-rib-metric" {
    deviate not-supported;
  }

  deviation "/ios:native/ios:router/ios-ospf:router-ospf/ios-ospf:ospf/ios-ospf:process-id/ios-ospf:redistribute/ios-ospf:nhrp/ios-ospf:translate-rib-metric" {
    deviate not-supported;
  }

  deviation "/ios:native/ios:router/ios-ospf:router-ospf/ios-ospf:ospf/ios-ospf:process-id/ios-ospf:redistribute/ios-ospf:odr/ios-ospf:translate-rib-metric" {
    deviate not-supported;
  }

  deviation "/ios:native/ios:router/ios-ospf:router-ospf/ios-ospf:ospf/ios-ospf:process-id/ios-ospf:redistribute/ios-ospf:rip/ios-ospf:translate-rib-metric" {
    deviate not-supported;
  }

  deviation "/ios:native/ios:router/ios-ospf:router-ospf/ios-ospf:ospf/ios-ospf:process-id/ios-ospf:redistribute/ios-ospf:vrf/ios-ospf:application/ios-ospf:translate-rib-metric" {
    deviate not-supported;
  }

  deviation "/ios:native/ios:router/ios-ospf:router-ospf/ios-ospf:ospf/ios-ospf:process-id/ios-ospf:redistribute/ios-ospf:vrf/ios-ospf:eigrp/ios-ospf:translate-rib-metric" {
    deviate not-supported;
  }

  deviation "/ios:native/ios:router/ios-ospf:router-ospf/ios-ospf:ospf/ios-ospf:process-id-vrf/ios-ospf:redistribute/ios-ospf:application/ios-ospf:translate-rib-metric" {
    deviate not-supported;
  }

  deviation "/ios:native/ios:router/ios-ospf:router-ospf/ios-ospf:ospf/ios-ospf:process-id-vrf/ios-ospf:redistribute/ios-ospf:eigrp/ios-ospf:translate-rib-metric" {
    deviate not-supported;
  }

  deviation "/ios:native/ios:router/ios-ospf:router-ospf/ios-ospf:ospf/ios-ospf:process-id-vrf/ios-ospf:redistribute/ios-ospf:lisp/ios-ospf:translate-rib-metric" {
    deviate not-supported;
  }

  deviation "/ios:native/ios:router/ios-ospf:router-ospf/ios-ospf:ospf/ios-ospf:process-id-vrf/ios-ospf:redistribute/ios-ospf:mobile/ios-ospf:translate-rib-metric" {
    deviate not-supported;
  }

  deviation "/ios:native/ios:router/ios-ospf:router-ospf/ios-ospf:ospf/ios-ospf:process-id-vrf/ios-ospf:redistribute/ios-ospf:nat-route/ios-ospf:translate-rib-metric" {
    deviate not-supported;
  }

  deviation "/ios:native/ios:router/ios-ospf:router-ospf/ios-ospf:ospf/ios-ospf:process-id-vrf/ios-ospf:redistribute/ios-ospf:nhrp/ios-ospf:translate-rib-metric" {
    deviate not-supported;
  }

  deviation "/ios:native/ios:router/ios-ospf:router-ospf/ios-ospf:ospf/ios-ospf:process-id-vrf/ios-ospf:redistribute/ios-ospf:odr/ios-ospf:translate-rib-metric" {
    deviate not-supported;
  }

  deviation "/ios:native/ios:router/ios-ospf:router-ospf/ios-ospf:ospf/ios-ospf:process-id-vrf/ios-ospf:redistribute/ios-ospf:rip/ios-ospf:translate-rib-metric" {
    deviate not-supported;
  }

  deviation "/ios:native/ios:router/ios-ospf:router-ospf/ios-ospf:ospf/ios-ospf:process-id-vrf/ios-ospf:redistribute/ios-ospf:vrf/ios-ospf:application/ios-ospf:translate-rib-metric" {
    deviate not-supported;
  }

  deviation "/ios:native/ios:router/ios-ospf:router-ospf/ios-ospf:ospf/ios-ospf:process-id-vrf/ios-ospf:redistribute/ios-ospf:vrf/ios-ospf:eigrp/ios-ospf:translate-rib-metric" {
    deviate not-supported;
  }
}
