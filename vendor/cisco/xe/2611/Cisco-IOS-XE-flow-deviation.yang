module Cisco-IOS-XE-flow-deviation {
  yang-version 1.1;
  namespace "http://cisco.com/ns/yang/Cisco-IOS-XE-flow-deviation";
  prefix ios-flow-cdev;

  import Cisco-IOS-XE-native {
    prefix ios;
  }
  import Cisco-IOS-XE-flow {
    prefix ios-flow;
  }

  deviation "/ios:native/ios:sampler/ios-flow:mode/ios-flow:random/ios-flow:out-of" {
    deviate replace {
      type uint16 {
        range "2..32768";
      }
    }
  }
}
