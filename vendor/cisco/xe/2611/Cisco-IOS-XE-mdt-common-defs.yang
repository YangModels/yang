module Cisco-IOS-XE-mdt-common-defs {
  yang-version 1.1;
  namespace "http://cisco.com/ns/yang/Cisco-IOS-XE-mdt-common-defs";
  prefix mdt-common-defs;

  import Cisco-IOS-XE-common-types {
    prefix common-types-ios-xe;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of common YANG
     definitions for streaming telemetry.
     Copyright (c) 2016-2023, 2025 by Cisco Systems, Inc.
     All rights reserved.";

  revision 2026-02-01 {
    description
      "- Added support for poll/once subscriptions
       - Added TDL over gRPC protocols";
    reference
      "4.0.0";
    cisco-semver:module-version "4.0.0";
  }
  revision 2023-11-01 {
    description
      "- Added support for pull mode receivers";
    reference
      "3.6.0";
    cisco-semver:module-version "3.6.0";
  }
  revision 2023-07-01 {
    description
      "- Added support for gNMI receiver type";
    reference
      "3.5.0";
    cisco-semver:module-version "3.5.0";
  }
  revision 2023-03-01 {
    description
      "- Added support for NETCONF receiver type
       - Added support for dampening-period for on-change subscription";
    reference
      "3.4.0";
    cisco-semver:module-version "3.4.0";
  }
  revision 2022-11-01 {
    description
      "Update yang-version to 1.1";
    reference
      "3.3.0";
    cisco-semver:module-version "3.3.0";
  }
  revision 2022-03-01 {
    description
      "- Added support for RFC5277 receiver type";
    reference
      "3.2.0";
    cisco-semver:module-version "3.2.0";
  }
  revision 2021-07-01 {
    description
      "- Add support for gRPC configured receivers";
    reference
      "3.1.0";
    cisco-semver:module-version "3.1.0";
  }
  revision 2021-03-01 {
    description
      "- Changed status of receiver id.";
    reference
      "3.0.0";
    cisco-semver:module-version "3.0.0";
  }
  revision 2020-11-01 {
    description
      "- Additional host and receiver parameter types";
    reference
      "2.2.0";
    cisco-semver:module-version "2.2.0";
  }
  revision 2020-07-01 {
    description
      "- Add host type";
    reference
      "2.1.0";
    cisco-semver:module-version "2.1.0";
  }
  revision 2019-05-01 {
    description
      "- Change connection ID VRF identifier.
       - Added semantic version";
    reference
      "2.0.0";
    cisco-semver:module-version "2.0.0";
  }
  revision 2018-10-29 {
    description
      "Cleaned up spelling errors in descriptions.
       Add connection ID type.";
    reference
      "1.4.0";
    cisco-semver:module-version "1.4.0";
  }
  revision 2018-03-19 {
    description
      "Recursive URI support for Native stream";
    reference
      "1.3.0";
    cisco-semver:module-version "1.3.0";
  }
  revision 2018-02-12 {
    description
      "TRANSFORM support for Native stream";
    reference
      "1.2.0";
    cisco-semver:module-version "1.2.0";
  }
  revision 2017-07-01 {
    description
      "Add support for VRFs";
    reference
      "1.1.0";
    cisco-semver:module-version "1.1.0";
  }
  revision 2017-03-02 {
    description
      "Initial revision";
    reference
      "1.0.0";
    cisco-semver:module-version "1.0.0";
  }

  typedef host-etype {
    type enumeration {
      enum host-type-unspecified {
        value 0;
        description
          "Host type is not specified";
      }
      enum host-type-ip-addr {
        value 1;
        description
          "Host is identified using an IP address";
      }
      enum host-type-hostname {
        value 2;
        description
          "Host is identified using hostname";
      }
    }
    description
      "Types of network host identifiers";
  }

  typedef mdt-rcvr-type {
    type enumeration {
      enum rcvr-type-unspecified {
        value 0;
        description
          "Indicates that the receiver type extension is not specified or is unset.";
      }
      enum rcvr-type-protocol {
        value 1;
        description
          "Indicates that the receiver is a protocol-based receiver, which uses protocol-specific parameters for configuration.";
      }
      enum rcvr-type-pullmode {
        value 2;
        description
          "Receiver is a pull-mode based receiver";
      }
    }
    description
      "Types of receivers";
  }

  typedef mdt-rcvr-type-extn {
    type enumeration {
      enum rcvr-type-unset-extn {
        value 0;
        description
          "Indicates that the receiver type extension is not specified or is unset.";
      }
      enum rcvr-type-proto-extn {
        value 1;
        description
          "Indicates that the receiver is a protocol-based receiver, which uses protocol-specific parameters for configuration.";
      }
    }
    description
      "Types of receivers";
  }

  typedef prot-rcvr-protocol {
    type enumeration {
      enum prot-rcvr-unspec {
        value 0;
        description
          "Protocol type is not specified";
      }
      enum native {
        value 1;
        description
          "Native protocol";
      }
      enum tls-native {
        value 2;
        description
          "Native TLS protocol";
      }
      enum cntp-tcp {
        value 3;
        description
          "CNTP TCP protocol";
      }
      enum cntp-tls {
        value 4;
        description
          "CNTP TLS protocol";
      }
      enum cloud-native {
        value 5;
        description
          "Native Cloud protocol";
      }
      enum grpc-tcp {
        value 6;
        description
          "gRPC TCP protocol";
      }
      enum grpc-tls {
        value 7;
        description
          "gRPC TLS protocol";
      }
      enum rfc5277 {
        value 8;
        description
          "RFC5277 protocol";
      }
      enum netconf {
        value 9;
        description
          "NETCONF protocol";
      }
      enum gnmi {
        value 10;
        description
          "gNMI protocol";
      }
      enum grpc-tdl-tcp {
        value 11;
        description
          "TDL over gRPC protocol";
      }
      enum grpc-tdl-tls {
        value 12;
        description
          "TDL over gRPC TLS protocol";
      }
    }
    description
      "Types of protocols";
  }

  typedef mdt-sub-filter-type {
    type enumeration {
      enum sub-filter-type-none {
        value 0;
        description
          "Indicates that no filter has been specified";
      }
      enum sub-filter-type-xpath {
        value 1;
        description
          "Xpath defining the data items of interest.
           A limited set of the Xpath 1.0 expressions is
           supported";
      }
      enum sub-filter-type-tdl-uri {
        value 2;
        description
          "TDL-URI defining the data items of interest";
      }
      enum sub-filter-type-tdl-transform {
        value 3;
        description
          "tdl-transform define transform scheme
           to be subscribed";
      }
      enum sub-filter-type-nested-uri {
        value 4;
        description
          "Nested-URI defining the data items of interest";
      }
    }
    description
      "Types of subscription filters";
  }

  typedef mdt-sub-update-trigger {
    type enumeration {
      enum sub-upd-trig-none {
        value 0;
        description
          "Indicates trigger has not been specified";
      }
      enum sub-upd-trig-periodic {
        value 1;
        description
          "Subscription is triggered on a periodic basis";
      }
      enum sub-upd-trig-on-change {
        value 2;
        status deprecated;
        description
          "Subscription is triggered when a value changes (deprecated).
           Use sub-upd-trig-on-change-v2 instead.";
      }
      enum sub-upd-trig-on-change-v2 {
        value 3;
        description
          "Subscription is triggered when a value changes";
      }
      enum sub-upd-trig-poll {
        value 4;
        description
          "Subscription is triggered in response to subscriber input";
      }
      enum sub-upd-trig-once {
        value 5;
        description
          "Subscription sends a single set of updates";
      }
    }
    description
      "Types of subscription update triggers";
  }

  grouping host {
    description
      "A network host";
    choice type-choice {
      default "host-type-unspecified";
      description
        "How the network host is identified";
      case host-type-unspecified {
        description
          "Host type is not specified";
        leaf unspecified {
          type empty;
          description
            "An unspecified host type";
        }
      }
      case host-type-ip-addr {
        description
          "Host is specified using an IP address";
        leaf address {
          type inet:ip-address;
          description
            "IP address of the host";
        }
      }
      case host-type-hostname {
        description
          "Host is specified using hostname";
        leaf hostname {
          type string {
            length "1..250";
            pattern "[\\] A-Za-z0-9!\"#%&()*+,\\-./:;<=>^?@\\\\$_`{|}\\[']+";
          }
          description
            "Hostname or network identifier supporting ASCII printable characters; non-ASCII characters must be encoded as XML character references per XML 1.0 standard";
        }
      }
    }
  }

  grouping mdt-rcvr-params-protoc {
    description
      "Parameters for an protocol receiver";
    container p-host {
      description
        "Specifies the host name or IP address of the proxy server used for forwarding telemetry data.";
      uses mdt-common-defs:host;
    }
    leaf p-port {
      type uint16;
      description
        "Specifies the host name or IP address of the proxy server used for forwarding telemetry data.";
    }
    leaf p-user {
      type string {
        length "1..200";
        pattern "[\\] A-Za-z0-9!\"#%&()*+,\\-./:;<=>^?@\\\\$_`{|}\\[']+";
      }
      description
        "Specifies the user name used to authenticate with the proxy server for telemetry data forwarding.";
    }
    leaf p-pass {
      type string {
        length "1..200";
        pattern "[\\] A-Za-z0-9!\"#%&()*+,\\-./:;<=>^?@\\\\$_`{|}\\[']+";
      }
      description
        "Specifies the password used to authenticate with the proxy server for telemetry data forwarding.";
    }
    leaf p-pass-type {
      type common-types-ios-xe:password-encryption-type;
      description
        "Indicates the type of password encryption used for the proxy server (e.g., clear text or AES).";
    }
  }

  grouping mdt-rcvr-params-extn {
    description
      "Parameters common to all receiver types";
    choice type-extn-choice {
      description
        "Specifies the parameters that are specific to the receiver type extension, such as protocol-based receiver settings.";
      case rcvr-type-proto-extn {
        description
          "Indicates a protocol receiver";
        container proto {
          description
            "Specifies the configuration parameters required for a protocol-based receiver, such as proxy host, port, user, and password.";
          uses mdt-common-defs:mdt-rcvr-params-protoc;
        }
      }
    }
  }

  grouping mdt-rcvr-params {
    description
      "Parameters common to all receiver types";
    container rcvr-extn {
      description
        "Specifies the extension parameters for the receiver, allowing for additional configuration options beyond the standard set.";
      uses mdt-common-defs:mdt-rcvr-params-extn;
    }
    choice type-choice {
      default "rcvr-type-unspecified";
      description
        "The type specific parameters";
      case rcvr-type-unspecified {
        description
          "Receiver type is not specified";
        leaf unset {
          type empty;
          description
            "An unspecified receiver type";
        }
      }
      case rcvr-type-protocol {
        description
          "Indicates a protocol based receiver";
        leaf protocol {
          type mdt-common-defs:prot-rcvr-protocol;
          default "prot-rcvr-unspec";
          description
            "Name of the protocol";
        }
        container host {
          description
            "Network host identity of the receiver";
          uses mdt-common-defs:host;
        }
        leaf port {
          type uint16;
          description
            "Port number of the receiver";
        }
      }
      case rcvr-type-pullmode {
        description
          "Indicates a pull-mode based receiver";
        leaf fn-prefix {
          type string;
          description
            "Name prefix for pull mode storage";
        }
        leaf size {
          type uint64 {
            range "81920 .. 2147483648";
          }
          description
            "Per subscription buffer size";
        }
      }
    }
  }

  grouping mdt-sub-poll-params {
    description
      "Parameters for a poll subscription";
    leaf poll {
      type empty;
      description
        "Subscription is triggered in response to subscriber input";
    }
  }

  grouping mdt-sub-once-params {
    description
      "Parameters for a once subscription";
    leaf once {
      type empty;
      description
        "Subscription sends a single set of updates";
    }
  }

  grouping mdt-subscription-base {
    description
      "Base subscription information. This is
       common to both operational and configuration
       table records";
    leaf stream {
      type string;
      default "NETCONF";
      description
        "The name of the event stream being subscribed to";
    }
    leaf encoding {
      type string;
      default "encode-xml";
      description
        "Update notification encoding";
    }
    leaf source-vrf {
      type string;
      description
        "Network instance name for the VRF";
    }
    leaf source-address {
      type inet:ip-address;
      description
        "The source address for the notifications";
    }
    leaf rcvr-type {
      type mdt-common-defs:mdt-rcvr-type;
      default "rcvr-type-unspecified";
      description
        "Receiver type used by all named receivers of this subscription.
         It is used to determine the specific receiver-type global list
         that defines the receiver. It may specify a related group of
         receivers without identifying a specific receiver-type.
         Cannot be used with the deprecated receiver configuration.";
    }
    choice update-trigger-choice {
      default "sub-upd-trig-none";
      description
        "Update trigger of the subscription";
      case sub-upd-trig-none {
        description
          "Indicates trigger has not been specified";
        leaf no-trigger {
          type uint32;
          default "0";
          description
            "Placeholder for unset value";
        }
      }
      case sub-upd-trig-periodic {
        description
          "Subscription is triggered on a periodic basis";
        leaf period {
          type uint32;
          units "centiseconds";
          mandatory true;
          description
            "Period of update notifications in hundredths
             of a second";
        }
      }
      case sub-upd-trig-on-change {
        status deprecated;
        description
          "Subscription is triggered when a value changes (deprecated).
           Use sub-upd-trig-on-change-v2 instead.";
        leaf no-synch-on-start {
          type boolean;
          description
            "If true, there is no initial update notification
             with the current value of all the data.
             NOT CURRENTLY SUPPORTED. If specified, must
             be false";
        }
      }
      case sub-upd-trig-on-change-v2 {
        description
          "Subscription is triggered when a value changes";
        leaf no-synch-on-start-v2 {
          type boolean;
          default "false";
          description
            "If true, there is no initial update notification
             with the current value of all the data.
             NOT CURRENTLY SUPPORTED. If specified, must
             be false";
        }
        leaf dampening-period {
          type uint32;
          units "centiseconds";
          default "0";
          description
            "Dampening period of update notifications in hundredths
             of a second";
        }
      }
      case sub-upd-trig-poll {
        description
          "Subscription is triggered in response to subscriber input";
        container poll-params {
          description
            "Parameters for a poll subscription";
          uses mdt-common-defs:mdt-sub-poll-params;
        }
      }
      case sub-upd-trig-once {
        description
          "Subscription sends a single set of updates";
        container once-params {
          description
            "Parameters for a once subscription";
          uses mdt-common-defs:mdt-sub-once-params;
        }
      }
    }
    choice filter-type-choice {
      default "sub-filter-type-none";
      description
        "The type of filter chosen to select the events or the data
         for the update notification";
      case sub-filter-type-none {
        description
          "Indicates that no filter has been specified";
        leaf no-filter {
          type uint32;
          default "0";
          description
            "Placeholder for unset value";
        }
      }
      case sub-filter-type-xpath {
        description
          "Xpath defining the data items of interest.
           A limited set of the Xpath 1.0 expressions is
           supported";
        leaf xpath {
          type string;
          description
            "XPath expression describing the set of objects
             wanted as part of the subscription";
        }
      }
      case sub-filter-type-tdl-uri {
        description
          "TDL-URI defining the data items of interest";
        leaf tdl-uri {
          type string;
          description
            "TDL-URI expression describing the set of objects
             wanted as part of the subscription";
        }
      }
      case sub-filter-type-tdl-transform {
        leaf transform-name {
          type string;
          description
            "Transform name is the reference to
             tdl transform scheme";
        }
      }
      case sub-filter-type-nested-uri {
        description
          "NESTED-URI defining the data items of interest";
        leaf nested-uri {
          type string;
          description
            "TDL-URI-Recursive expression describing the set of objects
             wanted as part of the subscription";
        }
      }
    }
  }

  grouping mdt-receiver-id {
    description
      "Receiver identifier
       Use of this is deprecated. Use named receivers instead.";
    leaf address {
      type inet:ip-address;
      mandatory true;
      description
        "IP address of the receiver";
    }
    leaf port {
      type uint16;
      mandatory true;
      description
        "Network port of the receiver";
    }
  }

  grouping mdt-connection-id {
    description
      "Connection identifier";
    leaf address {
      type inet:ip-address;
      description
        "IP address";
    }
    leaf port {
      type uint16;
      description
        "Network port";
    }
    leaf vrf-table-id {
      type uint32;
      description
        "Network instance table ID for the VRF that the
         connection originates from";
    }
    leaf source-address {
      type inet:ip-address;
      description
        "The source address used for the connection";
    }
  }
}
