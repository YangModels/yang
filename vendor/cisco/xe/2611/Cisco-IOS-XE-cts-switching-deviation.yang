module Cisco-IOS-XE-cts-switching-deviation {
  yang-version 1.1;
  namespace "http://cisco.com/ns/yang/Cisco-IOS-XE-cts-switching-deviation";
  prefix ios-cts-d;

  import Cisco-IOS-XE-native {
    prefix ios;
  }
  import Cisco-IOS-XE-cts {
    prefix ios-cts;
  }
  import cisco-semver {
    prefix cisco-semver;
  }

  organization
    "Cisco Systems";
  description
    "Cisco XE Native Deviation YANG module for IOS
     Copyright (c) 2021 by Cisco Systems, Inc.
     All rights reserved.";

  revision 2022-11-01 {
    description
      "- Update yang-version to 1.1";
    cisco-semver:module-version "1.4.0";
  }
  revision 2021-07-01 {
    description
      "Added enforcement deviation for LISP interface";
    cisco-semver:module-version "1.0.0";
  }

  deviation "/ios:native/ios:interface/ios:FortyGigabitEthernet/ios-cts:cts/ios-cts:role-based/ios-cts:sgt-map" {
    deviate not-supported;
    description
      "cts role-based sgt-map configurations are not supported for FortyGigabitEthernet interface.";
  }

  deviation "/ios:native/ios:interface/ios:LISP/ios-cts:cts/ios-cts:role-based/ios-cts:enforcement-switching" {
    deviate not-supported;
    description
      "cts role-based enforcement configurations are not supported for LISP interface.";
  }
}
