module Cisco-IOS-XE-switchport-oper {
  yang-version 1.1;
  namespace "http://cisco.com/ns/yang/Cisco-IOS-XE-switchport-oper";
  prefix switchport-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring switchport information.
     Copyright (c) 2023 by Cisco Systems, Inc.
     All rights reserved.";

  revision 2024-03-01 {
    description
      "Initial revision";
    reference
      "1.0.0";
    cisco-semver:module-version "1.0.0";
  }

  typedef switchport-admin-mode {
    type enumeration {
      enum admin-unknown {
        value 0;
        description
          "Admin unknown state. The administrative state is not found.";
      }
      enum admin-stat-acc {
        value 1;
        description
          "Admin static access. Interface is set to static access.";
      }
      enum admin-dyn-acc {
        value 2;
        description
          "Admin dynamic access. Interface is set to dynamic access.";
      }
      enum admin-tunnel {
        value 3;
        description
          "Admin tunnel. Interface is set to 802.1Q tunneling mode.";
      }
      enum admin-trunk {
        value 4;
        description
          "Admin trunk. Interface is unconditionally a trunk port.";
      }
      enum admin-dyn-auto {
        value 5;
        description
          "Admin dynamic auto. Interface is set to become trunking via DTP if the neighbor is set to trunk or desirable.";
      }
      enum admin-dyn-des {
        value 6;
        description
          "Admin dynamic desirable. Interface is set to become trunking if the neighbor is set to trunk, auto, or desirable.";
      }
      enum admin-multi {
        value 7;
        description
          "Admin multi. Interface is set to multi-VLAN.";
      }
      enum admin-pvlan-host {
        value 8;
        description
          "Admin private VLAN host. Interface is set to be a private VLAN host port.";
      }
      enum admin-pvlan-prom {
        value 9;
        description
          "Admin private VLAN promiscuous. Interface is set to be a private VLAN promiscuous port.";
      }
      enum admin-pvlan-sec {
        value 10;
        description
          "Admin private VLAN trunking secondary. Interface is set to be an isolated private VLAN trunk port.";
      }
      enum admin-pvlan-trunk-prom {
        value 11;
        description
          "Admin private VLAN trunking promiscuous. Interface is set to be a promiscuous private VLAN trunk port.";
      }
      enum admin-loopback {
        value 12;
        description
          "Admin loopback. Interface is set to be a loopback interface.";
      }
    }
    description
      "Admin mode";
  }

  typedef oper-mode {
    type enumeration {
      enum oper-unknown {
        value 0;
        description
          "Operational unknown state. The operational mode is not found.";
      }
      enum oper-down {
        value 1;
        description
          "Operational down.";
      }
      enum oper-stat-acc {
        value 2;
        description
          "Operational static access. Interface is operating in static access.";
      }
      enum oper-dyn-acc {
        value 3;
        description
          "Operational dynamic access. Interface is operating in dynamic access.";
      }
      enum oper-tunnel {
        value 4;
        description
          "Operational tunnel. Interface is operating in 802.1Q tunneling mode.";
      }
      enum oper-trunk {
        value 5;
        description
          "Operational trunk. Interface is operating in trunking.";
      }
      enum oper-multi {
        value 6;
        description
          "Operational multi. Interface is operating in multi.";
      }
      enum oper-pvlan-host {
        value 7;
        description
          "Operational private VLAN host. Interface is operating in private VLAN host.";
      }
      enum oper-pvlan-prom {
        value 8;
        description
          "Operational private VLAN promiscuous. Interface is operating in private VLAN promiscuous port.";
      }
      enum oper-pvlan-sec {
        value 9;
        description
          "Operational private VLAN trunking secondary. Interface is operating in private VLAN promiscuous port.";
      }
      enum oper-pvlan-trunk-prom {
        value 10;
        description
          "Operational private VLAN promiscuous. Interface is operating in private VLAN promiscuous trunk port.";
      }
      enum oper-loopback {
        value 11;
        description
          "Operational loopback. Interface is operating in a loopback state.";
      }
    }
    description
      "Operational mode";
  }

  typedef switchport-access-state {
    type enumeration {
      enum acc-unknown {
        value 0;
        description
          "Access VLAN state is unknown.";
      }
      enum acc-active {
        value 1;
        description
          "Access VLAN is active.";
      }
      enum acc-inactive {
        value 2;
        description
          "Access VLAN is inactive.";
      }
      enum acc-unassign {
        value 3;
        description
          "Access VLAN is unassigned.";
      }
      enum acc-suspend {
        value 4;
        description
          "Access VLAN is suspended.";
      }
      enum acc-pvlan-unknown {
        value 5;
        description
          "Access VLAN is a private VLAN in an unknown state.";
      }
      enum acc-pvlan-normal {
        value 6;
        description
          "Access VLAN is a private VLAN in a normal state.";
      }
      enum acc-pvlan-primary {
        value 7;
        description
          "Access VLAN is a primary private VLAN.";
      }
      enum acc-pvlan-isolated {
        value 8;
        description
          "Access VLAN is an isolated private VLAN.";
      }
      enum acc-pvlan-community {
        value 9;
        description
          "Access VLAN is a community private VLAN.";
      }
      enum acc-pvlan-twoway {
        value 10;
        description
          "Access VLAN is a two-way community private VLAN.";
      }
    }
    description
      "The current state of the access mode VLAN.";
  }

  typedef switchport-trunk-nat-state {
    type enumeration {
      enum trunk-nat-unknown {
        value 0;
        description
          "Trunking native VLAN state is unknown.";
      }
      enum trunk-nat-active {
        value 1;
        description
          "Trunking native VLAN is active.";
      }
      enum trunk-nat-inactive {
        value 2;
        description
          "Trunking native VLAN is inactive.";
      }
      enum trunk-nat-suspend {
        value 3;
        description
          "Trunking native VLAN is suspended.";
      }
    }
    description
      "The current state of the trunking native VLAN.";
  }

  typedef switchport-voice-state {
    type enumeration {
      enum voice-unknown {
        value 0;
        description
          "Voice VLAN state is unknown.";
      }
      enum voice-active {
        value 1;
        description
          "Voice VLAN is active.";
      }
      enum voice-inactive {
        value 2;
        description
          "Voice VLAN is inactive.";
      }
      enum voice-untagged {
        value 3;
        description
          "Voice VLAN is untagged.";
      }
      enum voice-none {
        value 4;
        description
          "Voice VLAN is not found.";
      }
      enum voice-dot1p {
        value 5;
        description
          "Voice VLAN uses 802.1P Class of Service to indicate priority level.";
      }
    }
    description
      "The current state of the voice VLAN.";
  }

  grouping switchport-vlans {
    description
      "Range of VLANs, inclusive. Can be a single VLAN.";
    leaf start-id {
      type uint16;
      description
        "Starting VLAN ID. May be the same as end-id.";
    }
    leaf end-id {
      type uint16;
      description
        "Ending VLAN ID. May be the same as start-id.";
    }
  }

  grouping port-oper-info {
    description
      "If the hardware is present, operational interface information.";
    leaf oper-mode {
      type switchport-ios-xe-oper:oper-mode;
      description
        "Operational switchport mode, showing the actual status of the interface after negotiation.";
    }
    leaf agport-if-name {
      type string;
      description
        "If the interface is in an aggregate port bundle, the bundle name.";
    }
    leaf is-agport-suspend {
      when "../agport-if-name != ''";
      type boolean;
      description
        "If the interface is in an aggregate port bundle, displays if the port bundle is suspended.";
    }
    leaf access-mode-id {
      when "../access-state != 'acc-unknown'
             and ../access-state != 'acc-unassign'";
      type uint16;
      description
        "The VLAN ID of the access mode VLAN.";
    }
    leaf access-mode-name {
      when "../access-state != 'acc-unknown'
             and ../access-state != 'acc-unassign'";
      type string;
      description
        "The name of the access mode VLAN.";
    }
    leaf access-state {
      type switchport-ios-xe-oper:switchport-access-state;
      description
        "The current operational state of the access mode VLAN.";
    }
    leaf trunk-nat-mode-id {
      when "../trunk-nat-state != 'trunk-nat-unknown'";
      type uint16;
      description
        "The VLAN ID of the trunking native mode VLAN.";
    }
    leaf trunk-nat-mode-name {
      when "../trunk-nat-state != 'trunk-nat-unknown'";
      type string;
      description
        "The name of the trunking native mode VLAN.";
    }
    leaf trunk-nat-state {
      type switchport-ios-xe-oper:switchport-trunk-nat-state;
      description
        "The current operational state of the trunking native mode VLAN.";
    }
    leaf voice-id {
      when "../voice-state = 'voice-active'
             or ../voice-state = 'voice-inactive'";
      type uint16;
      description
        "The VLAN ID of the voice VLAN.";
    }
    leaf voice-name {
      when "../voice-state = 'voice-active'
             or ../voice-state = 'voice-inactive'";
      type string;
      description
        "The name of the voice VLAN.";
    }
    leaf voice-state {
      type switchport-ios-xe-oper:switchport-voice-state;
      description
        "The current operational state of the voice VLAN.";
    }
    list trunk-vlan {
      description
        "List of allowed trunking VLANs when in trunking mode.";
      uses switchport-ios-xe-oper:switchport-vlans;
    }
    list pruning-vlan {
      description
        "List of VLANs enabled for pruning when in trunking mode.";
      uses switchport-ios-xe-oper:switchport-vlans;
    }
  }

  grouping switchport-info {
    description
      "List of switchport information.";
    leaf if-name {
      type string;
      description
        "Interface name.";
    }
    leaf enabled {
      type empty;
      description
        "Port is in switchport when enabled. Otherwise, it is in routed mode.";
    }
    leaf admin-mode {
      when 'boolean(../enabled)';
      type switchport-ios-xe-oper:switchport-admin-mode;
      description
        "Administratively configured switchport mode.";
    }
    container port-details {
      when 'boolean(../hardware-present)';
      description
        "The operational statuses of the port.";
      uses switchport-ios-xe-oper:port-oper-info;
    }
    leaf hardware-present {
      when 'boolean(../enabled)';
      type empty;
      description
        "The Field Replaceable Unit, or hardware module, is present.";
    }
  }

  container switchport-oper-data {
    config false;
    description
      "This is the top level container for switchport operational data.";
    list switchport-info {
      key "if-name";
      description
        "Switchport operational information of the interface.";
      uses switchport-ios-xe-oper:switchport-info;
    }
  }
}
