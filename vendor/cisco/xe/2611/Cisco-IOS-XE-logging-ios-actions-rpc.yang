module Cisco-IOS-XE-logging-ios-actions-rpc {
  yang-version 1.1;
  namespace "http://cisco.com/ns/yang/Cisco-IOS-XE-logging-ios-actions-rpc";
  prefix logging-ios-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for LOGGING RPC action data.
     Copyright (c) 2022 by Cisco Systems, Inc.
     All rights reserved.";

  revision 2023-03-01 {
    description
      "Initial revision";
    reference
      "1.0.0";
    cisco-semver:module-version "1.0.0";
  }

  grouping log-parameters {
    description
      "Parameters to execute the send log.";
    leaf facility {
      type string {
        length "1..256";
        pattern '[^ ]*';
      }
      must 'string-length(../mnemonics) > 0';
      description
        "Facility name";
    }
    leaf mnemonics {
      type string {
        length "1..256";
        pattern '[^ ]*';
      }
      must 'string-length(../facility) > 0';
      description
        "Mnemonics";
    }
    leaf message {
      type string {
        length "1..256";
      }
      mandatory true;
      description
        "Logging message";
    }
    leaf severity {
      type uint32 {
        range "0..7";
      }
      default "7";
      description
        "Severity";
    }
  }

  rpc send-log {
    description
      "To send a syslog message.";
    input {
      uses logging-ios-actions-rpc:log-parameters;
    }
  }
}
