module cisco-xe-openconfig-qos-deviation {
  namespace "http://openconfig.net/yang/cisco-xe-openconfig-qos-deviation";
  prefix oc-qos-devs;

  import openconfig-qos {
    prefix oc-qos;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-qos module.";

  revision 2025-07-01 {
    description
      "Deviations for openconfig-qos";
  }

  deviation "/oc-qos:qos/oc-qos:config" {
    deviate not-supported;
    description
      "not supported in IOS XE";
  }

  deviation "/oc-qos:qos/oc-qos:state" {
    deviate not-supported;
    description
      "not supported in IOS XE";
  }

  deviation "/oc-qos:qos/oc-qos:classifiers" {
    deviate not-supported;
    description
      "not supported in IOS XE";
  }

  deviation "/oc-qos:qos/oc-qos:interfaces/oc-qos:interface/oc-qos:state" {
    deviate not-supported;
    description
      "not supported in IOS XE";
  }

  deviation "/oc-qos:qos/oc-qos:interfaces/oc-qos:interface/oc-qos:interface-ref" {
    deviate not-supported;
    description
      "not supported in IOS XE";
  }

  deviation "/oc-qos:qos/oc-qos:interfaces/oc-qos:interface/oc-qos:input/oc-qos:state" {
    deviate not-supported;
    description
      "not supported in IOS XE";
  }

  deviation "/oc-qos:qos/oc-qos:interfaces/oc-qos:interface/oc-qos:input/oc-qos:classifiers" {
    deviate not-supported;
    description
      "not supported in IOS XE";
  }

  deviation "/oc-qos:qos/oc-qos:interfaces/oc-qos:interface/oc-qos:input/oc-qos:queues/oc-qos:queue/oc-qos:state/oc-qos:queue-management-profile" {
    deviate not-supported;
    description
      "not supported in IOS XE";
  }

  deviation "/oc-qos:qos/oc-qos:interfaces/oc-qos:interface/oc-qos:input/oc-qos:queues/oc-qos:queue/oc-qos:state/oc-qos:max-queue-len" {
    deviate not-supported;
    description
      "not supported in IOS XE";
  }

  deviation "/oc-qos:qos/oc-qos:interfaces/oc-qos:interface/oc-qos:input/oc-qos:queues/oc-qos:queue/oc-qos:state/oc-qos:avg-queue-len" {
    deviate not-supported;
    description
      "not supported in IOS XE";
  }

  deviation "/oc-qos:qos/oc-qos:interfaces/oc-qos:interface/oc-qos:input/oc-qos:queues/oc-qos:queue/oc-qos:state/oc-qos:transmit-pkts" {
    deviate not-supported;
    description
      "not supported in IOS XE";
  }

  deviation "/oc-qos:qos/oc-qos:interfaces/oc-qos:interface/oc-qos:input/oc-qos:queues/oc-qos:queue/oc-qos:state/oc-qos:transmit-octets" {
    deviate not-supported;
    description
      "not supported in IOS XE";
  }

  deviation "/oc-qos:qos/oc-qos:interfaces/oc-qos:interface/oc-qos:input/oc-qos:queues/oc-qos:queue/oc-qos:state/oc-qos:dropped-octets" {
    deviate not-supported;
    description
      "not supported in IOS XE";
  }

  deviation "/oc-qos:qos/oc-qos:interfaces/oc-qos:interface/oc-qos:input/oc-qos:queues/oc-qos:queue/oc-qos:state/oc-qos:ecn-marked-pkts" {
    deviate not-supported;
    description
      "not supported in IOS XE";
  }

  deviation "/oc-qos:qos/oc-qos:interfaces/oc-qos:interface/oc-qos:input/oc-qos:queues/oc-qos:queue/oc-qos:state/oc-qos:ecn-marked-octets" {
    deviate not-supported;
    description
      "not supported in IOS XE";
  }

  deviation "/oc-qos:qos/oc-qos:interfaces/oc-qos:interface/oc-qos:input/oc-qos:queues/oc-qos:queue/oc-qos:state/oc-qos:ecn-selected-pkts" {
    deviate not-supported;
    description
      "not supported in IOS XE";
  }

  deviation "/oc-qos:qos/oc-qos:interfaces/oc-qos:interface/oc-qos:input/oc-qos:queues/oc-qos:queue/oc-qos:state/oc-qos:ecn-selected-octets" {
    deviate not-supported;
    description
      "not supported in IOS XE";
  }

  deviation "/oc-qos:qos/oc-qos:interfaces/oc-qos:interface/oc-qos:input/oc-qos:scheduler-policy" {
    deviate not-supported;
    description
      "not supported in IOS XE";
  }

  deviation "/oc-qos:qos/oc-qos:interfaces/oc-qos:interface/oc-qos:input/oc-qos:virtual-output-queues" {
    deviate not-supported;
    description
      "not supported in IOS XE";
  }

  deviation "/oc-qos:qos/oc-qos:interfaces/oc-qos:interface/oc-qos:output" {
    deviate not-supported;
    description
      "not supported in IOS XE";
  }
}
