module Cisco-IOS-XE-switch-ptp-dp-oper {
  yang-version 1.1;
  namespace "http://cisco.com/ns/yang/Cisco-IOS-XE-switch-ptp-dp-oper";
  prefix switch-ptp-dp-oper;

  import Cisco-IOS-XE-common-types {
    prefix common-types-ios-xe;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "A collection of YANG definitions for PTP
     Switch operational data.
     Copyright (c) 2022 by Cisco Systems, Inc.
     All rights reserved.";

  revision 2023-03-01 {
    description
      "Initial revision";
    reference
      "1.0.0";
    cisco-semver:module-version "1.0.0";
  }

  grouping ptp-dp-msg-counter {
    description
      "PTP message counter";
    leaf if-name {
      type string;
      description
        "PTP interface name";
    }
    leaf sync-seq-num {
      type uint32;
      description
        "Sync sequence number";
    }
    leaf delay-req-seq-num {
      type uint32;
      description
        "Delay request sequence num";
    }
    leaf sync-msg-tx {
      type uint32;
      description
        "Sync message transmitted";
    }
    leaf sync-msg-rx {
      type uint32;
      description
        "Sync message received";
    }
    leaf followup-msg-tx {
      type uint32;
      description
        "Follow up message transmitted";
    }
    leaf followup-msg-rx {
      type uint32;
      description
        "Follow up message received";
    }
    leaf pdelay-req-tx {
      type uint32;
      description
        "Peer delay request message transmitted";
    }
    leaf pdelay-req-rx {
      type uint32;
      description
        "Peer delay request message received ";
    }
    leaf pdelay-res-tx {
      type uint32;
      description
        "Peer delay response message transmitted ";
    }
    leaf pdelay-res-rx {
      type uint32;
      description
        "Peer delay response message received ";
    }
    leaf pdelay-followup-res-tx {
      type uint32;
      description
        "Peer delay follow up response transmitted";
    }
    leaf pdelay-followup-res-rx {
      type uint32;
      description
        "Peer delay follow up response received";
    }
    leaf delay-req-tx {
      type uint32;
      description
        "Delay request message transmitted";
    }
    leaf delay-req-rx {
      type uint32;
      description
        "Delay request message received";
    }
    leaf delay-res-tx {
      type uint32;
      description
        "Delay response message transmitted";
    }
    leaf delay-res-rx {
      type uint32;
      description
        "Delay response received";
    }
  }

  container switch-ptp-dp-oper-data {
    config false;
    description
      "Precision Time Protocol Switch operational data";
    list location {
      key "fru slot bay chassis node";
      description
        "A list of data provider locations";
      uses common-types-ios-xe:extended-location;
      list ptp-dp-msg-counter-data {
        key "if-name";
        description
          "PTP message counter information";
        uses switch-ptp-dp-oper:ptp-dp-msg-counter;
      }
    }
  }
}
