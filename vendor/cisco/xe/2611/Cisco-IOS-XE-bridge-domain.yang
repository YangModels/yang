module Cisco-IOS-XE-bridge-domain {
  yang-version 1.1;
  namespace "http://cisco.com/ns/yang/Cisco-IOS-XE-bridge-domain";
  prefix ios-bd;

  import cisco-semver {
    prefix cisco-semver;
  }
  import ietf-inet-types {
    prefix inet;
  }
  import Cisco-IOS-XE-native {
    prefix ios;
  }
  import Cisco-IOS-XE-l2vpn {
    prefix ios-l2vpn;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Bridge Domain Yang model
     Copyright (c) 2017 - 2024 by Cisco Systems, Inc.
     All rights reserved.";

  revision 2026-02-01 {
    description
      "- Obsolete deprecated models in member EVPN instance";
    cisco-semver:module-version "4.1.0";
  }
  revision 2024-11-01 {
    description
      "- Add configurable ethernet-tag for vlan-aware EVI member
       - Fix ordering issue for evpn-instance-v2
       - Modify the allowed range of SDWAN instance member in the
         bridge-domain to align with service VPN";
    cisco-semver:module-version "4.0.0";
  }
  revision 2024-07-01 {
    description
      "- Change error message for L2VPN SDWAN related commands";
    cisco-semver:module-version "3.1.0";
  }
  revision 2024-03-01 {
    description
      "- Add support for L2VPN SDWAN related commands
       - Changed deprecated models to obsolete
       - Added new tailf recursive delete to bridge domain
       - Remove vlan-based member and rename vlan-service-id to vc-id for
         L2VPN SDWAN";
    cisco-semver:module-version "3.0.0";
  }
  revision 2023-07-01 {
    description
      "- Add support for EVPN profile related commands
       - Move old evpn-instance list into a new container";
    cisco-semver:module-version "2.4.0";
  }
  revision 2022-11-01 {
    description
      "- Update yang-version to 1.1
       - Fixed EVPN member for vxlan encap";
    cisco-semver:module-version "2.3.0";
  }
  revision 2020-11-01 {
    description
      "- Added Unknown Unicast Flooding Suppression
       - Accept virtual interface name patterns for member interface";
    cisco-semver:module-version "2.2.0";
  }
  revision 2020-03-01 {
    description
      "- Changed leaf node service-instance to a list node";
    cisco-semver:module-version "2.1.0";
  }
  revision 2019-11-01 {
    description
      "- Added pseudo wire config";
    cisco-semver:module-version "2.0.0";
  }
  revision 2019-07-01 {
    description
      "- Establish semantic version baseline
       - Add bridge-domain member BD-VIF";
    cisco-semver:module-version "1.0.0";
  }
  revision 2018-11-07 {
    description
      "Cleanup spelling errors in description statements";
  }
  revision 2018-07-30 {
    description
      "Support EVPN instance";
  }
  revision 2017-02-07 {
    description
      "Initial revision";
  }

  typedef bdomain-member-interface {
    type string {
      pattern '([Ff][Aa][Ss][Tt][Ee][Tt][Hh][Ee][Rr][Nn][Ee][Tt]|[Gg][Ii][Gg][Aa][Bb][Ii][Tt][Ee][Tt][Hh][Ee][Rr][Nn][Ee][Tt]|[Tt][Ww][Oo][Gg][Ii][Gg][Aa][Bb][Ii][Tt][Ee][Tt][Hh][Ee][Rr][Nn][Ee][Tt]|[Ff][Ii][Vv][Ee][Gg][Ii][Gg][Aa][Bb][Ii][Tt][Ee][Tt][Hh][Ee][Rr][Nn][Ee][Tt]|[Aa][Pp][Pp][Gg][Ii][Gg][Aa][Bb][Ii][Tt][Ee][Tt][Hh][Ee][Rr][Nn][Ee][Tt]|[Tt][Ee][Nn][Gg][Ii][Gg][Aa][Bb][Ii][Tt][Ee][Tt][Hh][Ee][Rr][Nn][Ee][Tt]|[Tt][Ww][Ee][Nn][Tt][Yy][Ff][Ii][Vv][Ee][Gg][Ii][Gg][Ee]|[Ff][Oo][Rr][Tt][Yy][Gg][Ii][Gg][Aa][Bb][Ii][Tt][Ee][Tt][Hh][Ee][Rr][Nn][Ee][Tt]|[Hh][Uu][Nn][Dd][Rr][Ee][Dd][Gg][Ii][Gg][Ee]|[Pp][Oo][Rr][Tt]-[Cc][Hh][Aa][Nn][Nn][Ee][Ll]|VirtualPortGroup|Virtual-Template|Vlan).*';
    }
  }

  grouping config-bdomain-mode-grouping {
    container ip {
      description
        "IP related commands";
      container igmp {
        description
          "IP igmp commands";
        container snooping {
          description
            "IP igmp snooping commands";
          presence "true";
          container check {
            description
              "enforce TTL or Rtr-Alert Option checking";
            leaf rtr-alert-option-boolean {
              description
                "Only accept IGMP packets with router-alert option";
              type boolean;
              default "true";
            }
            leaf rtr-alert-option {
              status obsolete;
              description
                "Only accept IGMP packets with router-alert option, Obsolete and replaced by rtr-alert-option-boolean";
              type empty;
            }
            leaf ttl-boolean {
              description
                "Only accept IGMP packets with TTL=1";
              type boolean;
              default "true";
            }
            leaf ttl {
              status obsolete;
              description
                "Only accept IGMP packets with TTL=1, Obsolete and replaced by ttl-boolean";
              type empty;
            }
          }
          container explicit-tracking {
            description
              "IGMP explicit host tracking configuration";
            leaf limit-value {
              description
                "Explicit Host Tracking DB limit";
              type uint32 {
                range "0..128000";
              }
            }
            leaf limit {
              status obsolete;
              description
                "Explicit Host Tracking DB limit";
              type empty;
            }
          }
          leaf immediate-leave {
            description
              "Enable IGMPv2 immediate leave processing";
            type empty;
          }
          leaf last-member-query-count {
            description
              "Last member query count";
            type uint8 {
              range "1..7";
            }
          }
          leaf last-member-query-interval {
            description
              "Last member query interval";
            type uint16 {
              range "100..32767";
            }
          }
          container mrouter {
            description
              "Configure an L2 port as a multicast router port";
            list interface-cfg {
              description
                "next-hop interface to mrouter";
              key "name";
              leaf name {
                type string {
                  pattern '[FfGgTtPp][OoIiEeWw].*';
                }
              }
              leaf efp_id {
                description
                  "efp number on the interface";
                type uint16 {
                  range "1..8000";
                }
              }
            }
            leaf interface {
              status obsolete;
              description
                "next-hop interface to mrouter";
              type empty;
            }
          }
          container querier {
            description
              "Enable IGMP querier for this Bdomain";
            presence "true";
            leaf address-value {
              description
                "IGMP querier source IP address";
              type inet:ipv4-address;
            }
            leaf address {
              status obsolete;
              description
                "IGMP querier source IP address";
              type empty;
            }
            leaf max-response-time-value {
              description
                "IGMP querier maximum response time (sec)";
              type uint8 {
                range "1..25";
              }
            }
            leaf max-response-time {
              status obsolete;
              description
                "IGMP querier maximum response time (sec)";
              type empty;
            }
            leaf query-interval-value {
              description
                "IGMP querier query interval (sec)";
              type uint16 {
                range "1..18000";
              }
            }
            leaf query-interval {
              status obsolete;
              description
                "IGMP querier query interval (sec)";
              type empty;
            }
            container tcn-parameters {
              description
                "IGMP querier TCN related parameters";
              container query {
                leaf count {
                  description
                    "IGMP querier TCN query count";
                  type uint16 {
                    range "1..10";
                  }
                }
                leaf interval {
                  description
                    "IGMP querier TCN query interval (sec)";
                  type uint16 {
                    range "1..255";
                  }
                }
              }
            }
            leaf tcn {
              status obsolete;
              description
                "IGMP querier TCN related parameters";
              type empty;
            }
            container timer-expiry {
              description
                "IGMP other querier timer";
              leaf expiry {
                description
                  "IGMP querier other querier time out (sec)";
                type uint16 {
                  range "60..300";
                }
              }
            }
            leaf timer {
              status obsolete;
              description
                "IGMP other querier timer";
              type empty;
            }
            leaf version-value {
              description
                "IGMP version";
              type uint8 {
                range "1..3";
              }
            }
            leaf version {
              status obsolete;
              description
                "IGMP version";
              type empty;
            }
          }
          leaf report-suppression-boolean {
            description
              "Enable IGMP report suppression";
            type boolean;
            default "true";
          }
          leaf report-suppression {
            status obsolete;
            description
              "Enable IGMP report suppression, Obsolete and replaced by report-suppression-boolean";
            type empty;
          }
          leaf robustness-variable {
            description
              "IGMP snooping bdomain robustness variable";
            type uint8 {
              range "1..3";
            }
          }
          list static-cfg {
            description
              "Configure an L2 port as a member of a group";
            key "group-addr";
            leaf group-addr {
              description
                "IP address of the group";
              type inet:ipv4-address;
            }
            list interface {
              description
                "Specify an interface statically configured";
              key "name";
              leaf name {
                type string {
                  pattern '[FfGgTtPp][OoIiEeWw].*';
                }
              }
            }
            list source {
              description
                "a source of the group";
              key "source-ip-addr interface";
              leaf source-ip-addr {
                description
                  "IP address of the source";
                type inet:ipv4-address;
              }
              leaf interface {
                description
                  "Specify an interface statically configured";
                type string {
                  pattern '[FfGgTtPp][OoIiEeWw].*';
                }
              }
              leaf service-instance {
                description
                  "service instance number";
                type uint16 {
                  range "1..8000";
                }
              }
            }
          }
          leaf static {
            status obsolete;
            description
              "Configure an L2 port as a member of a group";
            type inet:ipv4-address;
          }
        }
      }
    }
    container mac {
      description
        "MAC Address related commands";
      leaf aging-time {
        description
          "Set age time of mac addresses per bridge domain";
        type uint16 {
          range "30..21600";
        }
      }
      leaf learning-boolean {
        description
          "Disable mac learning on bridge domain";
        type boolean;
        default "true";
      }
      leaf learning {
        status obsolete;
        description
          "Disable mac learning on bridge domain, Obsolete and replaced by learning-boolean";
        type empty;
      }
      container limit {
        description
          "Limit the MAC Addresses learnt";
        container action {
          description
            "action when exceeding the limit";
          container flooding {
            description
              "Mac flooding";
            leaf disable {
              description
                "disable";
              type empty;
            }
          }
        }
        container maximum {
          description
            "Maximum";
          leaf addresses {
            description
              "Addresses";
            type uint32 {
              range "1..65536";
            }
          }
        }
      }
    }
    container member {
      description
        "bridge-domain member";
      list mem-ipv4 {
        key "mem-ipv4";
        leaf mem-ipv4 {
          description
            "IP address of the peer";
          type inet:ipv4-address;
        }
        list mem-vcid {
          key "mem-vcid";
          leaf mem-vcid {
            description
              "<1..4294967295>;;Enter VC ID value";
            type uint32 {
              range "1..4294967295";
            }
          }
          container encapsulation {
            description
              "Data encapsulation method";
            presence "true";
            leaf mpls {
              description
                "Use MPLS encapsulation";
              type empty;
            }
          }
          container template {
            description
              "Template to use for encapsulation and protocol configuration";
            presence "true";
            leaf template {
              description
                "<WORD>;;template name (Max size 32)";
              type string;
            }
          }
        }
        container encapsulation {
          description
            "Data encapsulation method";
          leaf mpls {
            description
              "Use MPLS encapsulation";
            type empty;
          }
        }
        leaf template {
          description
            "Template to use for encapsulation and protocol configuration";
          type string;
        }
      }
      list ACR {
        key "acr-int";
        leaf acr-int {
          description
            "<WORD>;;Virtual ACR interface";
          type string;
        }
        container service-instance {
          description
            "ethernet service instance";
          list id {
            key "id";
            leaf id {
              description
                "<1..8000>;;Service Instance Identifier";
              type uint16 {
                range "1..8000";
              }
            }
            leaf split-horizon {
              description
                "Configure this port as a member of a split horizon group";
              type empty;
            }
          }
        }
      }
      leaf Analysis-Module {
        description
          "Cisco network analysis service module";
        type uint8;
      }
      leaf Fcpa {
        description
          "Fiber Channel";
        type uint8;
      }
      leaf SBC {
        description
          "Session Border Controller";
        type uint32 {
          range "0..2147483647";
        }
      }
      leaf SONET_ACR {
        description
          "Virtual SONET-ACR controller";
        type uint8;
      }
      leaf _controller {
        status obsolete;
        type string {
          pattern '(OBSOLETED)';
        }
      }
      leaf Service-Engine {
        description
          "Cisco service engine module";
        type uint8;
      }
      leaf Tunnel-tp {
        description
          "MPLS Transport Profile interface";
        type uint16 {
          range "0..65535";
        }
      }
      leaf VPN {
        description
          "VPN interface";
        type uint32 {
          range "0..2147483647";
        }
      }
      leaf Virtual-TokenRing {
        description
          "Virtual TokenRing";
        type uint32 {
          range "0..2147483647";
        }
      }
      leaf ucse {
        description
          "Cisco ucse server";
        type uint8;
      }
      leaf vasileft {
        description
          "VasiLeft interface";
        type uint16 {
          range "1..2000";
        }
      }
      leaf vasiright {
        description
          "VasiRight interface";
        type uint16 {
          range "1..2000";
        }
      }
      leaf vfi {
        description
          "Enter VFI name";
        must '/ios:native/ios:l2vpn/ios-l2vpn:vfi/ios-l2vpn:context[ios-l2vpn:vfi-nm = current()]/ios-l2vpn:vpn/ios-l2vpn:id' {
          error-message "A VFI context must be configured with a valid vpn id first";
        }
        type string;
      }
      leaf vni {
        type uint32 {
          range "4096..16777215";
        }
      }
      list member-interface {
        key "interface";
        leaf interface {
          type bdomain-member-interface;
        }
        leaf interface-id {
          status obsolete;
          type union {
            type string;
            type uint32;
          }
        }
        list service-instance-list {
          description
            "ethernet service instance";
          key "instance-id";
          leaf instance-id {
            type uint32 {
              range "1..8000";
            }
          }
          container split-horizon {
            description
              "Configure this port as a member of a split horizon group";
            leaf group {
              description
                "Split-horizon group";
              type uint8;
            }
          }
          container remote {
            description
              "remote peer configuration commands";
            container circuit {
              description
                "Remote peer circuit configuration";
              leaf id {
                description
                  "Remote peer circuit ID";
                type uint16;
              }
            }
          }
        }
        leaf service-instance {
          description
            "ethernet service instance, Obsolete and replaced by service-instance-list";
          status obsolete;
          type uint32 {
            range "1..8000";
          }
        }
        container split-horizon {
          description
            "Configure this port as a member of a split horizon group, Obsolete and replaced by service-instance-list/split-horizon";
          status obsolete;
          leaf group {
            description
              "Split-horizon group, Obsolete and replaced by service-instance-list/split-horizon/group";
            status obsolete;
            type uint8;
          }
        }
        container remote {
          description
            "remote peer configuration commands, Obsolete and replaced by service-instance-list/remote";
          status obsolete;
          container circuit {
            description
              "Remote peer circuit configuration, Obsolete and replaced by service-instance-list/remote/circuit";
            status obsolete;
            leaf id {
              description
                "Remote peer circuit ID, Obsolete and replaced by service-instance-list/remote/circuit/id";
              status obsolete;
              type uint16;
            }
          }
        }
      }
      container evpn-instance-v2 {
        presence "true";
        choice evpn-instance-choice {
          case profile-case {
            list profile {
              key "profile-name";
              leaf profile-name {
                type string;
                must '(/ios:native/ios:l2vpn/ios-l2vpn:evpn_cont/ios-l2vpn:l2-profile/ios-l2vpn:evpn/ios-l2vpn:profile/ios-l2vpn:profile-name-list/ios-l2vpn:name = current()) or(/ios:native/ios:l2vpn/ios-l2vpn:evpn_cont/ios-l2vpn:l2-profile-service-type/ios-l2vpn:evpn/ios-l2vpn:profile/ios-l2vpn:profile-name-list/ios-l2vpn:name = current())' {
                  error-message "EVPN L2 Profile must created first";
                }
                must 'not(/ios:native/ios:l2vpn/ios-l2vpn:evpn_cont/ios-l2vpn:l2-profile-service-type/ios-l2vpn:evpn/ios-l2vpn:profile/ios-l2vpn:profile-name-list[ios-l2vpn:name = current()]/ios-l2vpn:vlan-aware/ios-l2vpn:evi-id = 0)' {
                  error-message "EVPN L2 Vlan-Aware Profile must configure evi-id first";
                }
              }
            }
          }
          case instance-case {
            list instance {
              description
                "Ethernet Virtual Private Network (EVPN) instance";
              max-elements 1;
              key "instance-num";
              leaf instance-num {
                description
                  "EVPN instance number.";
                must "not(/ios:native/ios:l2vpn/ios-l2vpn:evpn_cont/ios-l2vpn:evpn-instance/ios-l2vpn:evpn/ios-l2vpn:instance/ios-l2vpn:instance[ios-l2vpn:evpn-instance-num = current()]) or (../vni or ../ethernet-tag) or ((/ios:native/ios:l2vpn/ios-l2vpn:evpn_cont/ios-l2vpn:evpn-instance/ios-l2vpn:evpn/ios-l2vpn:instance/ios-l2vpn:instance[ios-l2vpn:evpn-instance-num = current()]/ios-l2vpn:vlan-based) and not(/ios:native/ios:l2vpn/ios-l2vpn:evpn_cont/ios-l2vpn:evpn-instance/ios-l2vpn:evpn/ios-l2vpn:instance/ios-l2vpn:instance[ios-l2vpn:evpn-instance-num = current()]/ios-l2vpn:vlan-based/ios-l2vpn:encapsulation = 'vxlan') and not(../vni or ../ethernet-tag)) or ((/ios:native/ios:l2vpn/ios-l2vpn:evpn_cont/ios-l2vpn:evpn-instance/ios-l2vpn:evpn/ios-l2vpn:instance/ios-l2vpn:instance[ios-l2vpn:evpn-instance-num = current()]/ios-l2vpn:vlan-bundle) and not(/ios:native/ios:l2vpn/ios-l2vpn:evpn_cont/ios-l2vpn:evpn-instance/ios-l2vpn:evpn/ios-l2vpn:instance/ios-l2vpn:instance[ios-l2vpn:evpn-instance-num = current()]/ios-l2vpn:vlan-bundle/ios-l2vpn:encapsulation = 'vxlan') and not(../vni or ../ethernet-tag))" {
                  error-message "Configuration is only supported for MPLS Vlan-Based or Vlan-Bundle EVPN instances";
                }
                type uint16 {
                  range "1..65535";
                }
              }
              choice evpn-service-type {
                description
                  "Evpn Service type.";
                case ethernet-tag-case {
                  leaf ethernet-tag {
                    description
                      "Ethernet tag value.";
                    must "(/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware) and not(/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation = 'vxlan')" {
                      error-message "Ethernet-Tag configuration is only supported for MPLS Vlan-Aware EVPN instances";
                    }
                    type uint16 {
                      range "1..4094";
                    }
                  }
                }
                case vni-case {
                  leaf vni {
                    description
                      "VxLAN VNI.";
                    must "(../ethernet-tag-vxlan) or (/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-based/ios-l2vpn:encapsulation = 'vxlan') or (/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-bundle/ios-l2vpn:encapsulation = 'vxlan') or not(/ios:native/ios:l2vpn/ios-l2vpn:evpn_cont/ios-l2vpn:evpn-instance/ios-l2vpn:evpn/ios-l2vpn:instance/ios-l2vpn:instance[ios-l2vpn:evpn-instance-num = current()/../instance-num])" {
                      error-message
                        "VNI configuration is only supported for Vxlan EVPN instances,
                         Ethernet-Tag configuration is mandatory for Vxlan Vlan-Aware EVPN instances";
                    }
                    type uint32 {
                      range "4096..16777215";
                    }
                  }
                  leaf ethernet-tag-vxlan {
                    description
                      "Ethernet tag value.";
                    must "/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation = 'vxlan' " {
                      error-message "Ethernet-tag configuration is only supported for Vxlan Vlan-Aware EVPN instances";
                    }
                    type uint32 {
                      range "1..16777215";
                    }
                  }
                }
              }
            }
          }
        }
      }
      list evpn-instance {
        status obsolete;
        description
          "Ethernet Virtual Private Network (EVPN) instance, OBSOLETE";
        key "instance-num";
        leaf instance-num {
          status obsolete;
          description
            "EVPN instance number, OBSOLETE";
          type uint16 {
            range "1..65535";
          }
        }
        choice evpn-service-type {
          description
            "Evpn Service type, OBSOLETE";
          leaf ethernet-tag {
            status obsolete;
            when "/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware and (/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation = 'mpls' or not(/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation))";
            description
              "Ethernet tag value, OBSOLETE";
            type uint16 {
              range "1..4094";
            }
          }
          leaf vni {
            status obsolete;
            when "/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation = 'vxlan' or (/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-based/ios-l2vpn:encapsulation = 'vxlan') or (/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-bundle/ios-l2vpn:encapsulation = 'vxlan')";
            description
              "VxLAN VNI, OBSOLETE";
            type uint32 {
              range "4096..16777215";
            }
          }
        }
      }
      list pseudowire {
        description
          "Pseudowire Interface";
        must 'current()/../ios-bd:vfi' {
          error-message "A VFI member must be configured first";
        }
        key "name";
        leaf name {
          type uint32 {
            range "1..231072";
          }
        }
        leaf peer-addr {
          description
            "IP address of the peer";
          type inet:ipv4-address;
        }
        leaf vc-id {
          description
            "VC ID value";
          type uint32;
        }
        choice pw-encap-templ {
          leaf encapsulation {
            description
              "Data encapsulation method";
            type enumeration {
              enum mpls;
            }
          }
          leaf template {
            description
              "Template to use for encapsulation and protocol configuration";
            type string;
          }
        }
      }
      list sdwan-instance {
        if-feature "ios-features:sdwan-l2vpn";
        description
          "L2VPN SDWAN instance";
        when "local-name(../..) = 'brd-id'";
        max-elements 1;
        key "sdwan-instance-num";
        leaf sdwan-instance-num {
          description
            "Sdwan instance number, value is in <1..511 | 513..65527>.";
          type uint32 {
            range "1..511 | 513..65527";
          }
        }
        choice service-type-choice {
          case point-to-point-case {
            container point-to-point-container {
              description
                "The point-to-point choice for sdwan instance with point-to-point type";
              must '/ios:native/ios:l2vpn/ios-l2vpn:sdwan-l2vpn/ios-l2vpn:sdwan-instance/ios-l2vpn:sdwan/ios-l2vpn:instance[ios-l2vpn:sdwan-instance-num = current()/../sdwan-instance-num]/ios-l2vpn:point-to-point' {
                error-message "%Error: Case 1 - Failed to add the SDWAN instance member to a bridge domain because the L2VPN SDWAN instance either does not exist or is not of point-to-point type; Case 2 - Failed to delete the L2VPN SDWAN instance as the SDWAN instance member is attached to a bridge domain.";
              }
              leaf remote-site-id {
                description
                  "The remote site-id of this sdwan instance member";
                must '../vc-id and (../single-homing or ../dual-homing)' {
                  error-message "%Error: Must fully configure remote-site-id, vc-id and homing-choice.";
                }
                type uint32 {
                  range "0..4294967295";
                }
              }
              leaf vc-id {
                description
                  "Virtual circuit id";
                must '../remote-site-id and (../single-homing or ../dual-homing)' {
                  error-message "%Error: Must fully configure remote-site-id, vc-id and homing-choice.";
                }
                type uint32 {
                  range "1..4294967295";
                }
              }
              choice homing-choice {
                description
                  "The choice of homing type";
                case single-homing-case {
                  leaf single-homing {
                    description
                      "Homing type as single homing";
                    must '../remote-site-id and ../vc-id' {
                      error-message "%Error: Must fully configure remote-site-id, vc-id and homing-choice.";
                    }
                    type empty;
                  }
                }
                case dual-homing-case {
                  leaf dual-homing {
                    description
                      "Homing type as dual-homing";
                    must '../remote-site-id and ../vc-id' {
                      error-message "%Error: Must fully configure remote-site-id, vc-id and homing-choice.";
                    }
                    type empty;
                  }
                }
              }
            }
          }
          case multipoint-case {
            container multipoint-container {
              description
                "The multipoint choice for sdwan instance with multipoint type";
              must '/ios:native/ios:l2vpn/ios-l2vpn:sdwan-l2vpn/ios-l2vpn:sdwan-instance/ios-l2vpn:sdwan/ios-l2vpn:instance[ios-l2vpn:sdwan-instance-num = current()/../sdwan-instance-num]/ios-l2vpn:multipoint' {
                error-message "%Error: Case 1 - Failed to add the SDWAN instance member to a bridge domain because the L2VPN SDWAN instance either does not exist or is not of multipoint type; Case 2 - Failed to delete the L2VPN SDWAN instance as the SDWAN instance member is attached to a bridge domain.";
              }
              leaf vc-id {
                description
                  "Virtual circuit id";
                must '../single-homing or ../dual-homing' {
                  error-message "%Error: Must both configure vc-id and homing-choice.";
                }
                type uint32 {
                  range "1..4294967295";
                }
              }
              choice homing-choice {
                description
                  "The choice of homing type";
                case single-homing-case {
                  leaf single-homing {
                    description
                      "Homing type as single homing";
                    must '../vc-id' {
                      error-message "%Error: Must both configure vc-id and homing-choice.";
                    }
                    type empty;
                  }
                }
                case dual-homing-case {
                  leaf dual-homing {
                    description
                      "Homing type as dual homing";
                    must '../vc-id' {
                      error-message "%Error: Must both configure vc-id and homing-choice.";
                    }
                    type empty;
                  }
                }
              }
            }
          }
        }
      }
      list BD-VIF {
        description
          "Bridge-Domain Virtual IP interface";
        key "name";
        leaf name {
          type uint16;
        }
      }
    }
    container flooding-suppression {
      description
        "Suppress flooding";
      leaf unknown-unicast {
        description
          "Suppress unknown unicast flooding";
        type empty;
      }
    }
    leaf shutdown {
      description
        "Take the bridge domain admin down";
      type empty;
    }
  }

  grouping config-bridge-domain-grouping {
    list brd-id {
      key "bridge-domain-id";
      leaf bridge-domain-id {
        description
          "<1..16000>;;bridge-domain ID";
        type uint16 {
          range "1..16000";
        }
      }
      uses config-bdomain-mode-grouping;
    }
    container c-mac {
      description
        "Configure c-mac global commands";
      leaf aging-time {
        description
          "Configure aging time for c-mac bridge domains";
        type uint16 {
          range "30..21600";
        }
      }
    }
    container otv {
      description
        "Configure overlay bridge domains";
      container default {
        description
          "Change default setting of overlay bridge domains";
        leaf age-time {
          description
            "Configure default mac aging time of overlay bridge domains";
          type uint16 {
            range "30..21600";
          }
        }
      }
    }
    container parameterized {
      description
        "bridge-domain is derived from parameters";
      container vlan {
        description
          "bridge-domain from service instance vlan";
        presence "true";
        uses config-bdomain-mode-grouping;
      }
    }
  }

  augment "/ios:native/ios:bridge-domain" {
    uses config-bridge-domain-grouping;
  }
}
