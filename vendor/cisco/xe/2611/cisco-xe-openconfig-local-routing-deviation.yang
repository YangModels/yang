module cisco-xe-openconfig-local-routing-deviation {
  namespace "http://cisco.com/ns/yang/cisco-xe-openconfig-local-routing-deviation";
  prefix oc-loc-rt-devs;

  import openconfig-local-routing {
    prefix oc-loc-rt;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-local-routing module.
     Copyright (c) 2020 by Cisco Systems, Inc.
     All rights reserved.";

  revision 2020-09-20 {
    description
      "Initial Revision";
    reference
      "RFC 6020: YANG - A Data Modeling Language for the
       Network Configuration Protocol (NETCONF)";
  }

  deviation "/oc-loc-rt:local-routes" {
    deviate not-supported;
    description
      "oc-loc-rt model is supported under openconfig-network-instance";
  }
}
