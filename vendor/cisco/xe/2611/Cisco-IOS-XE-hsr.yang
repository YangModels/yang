module Cisco-IOS-XE-hsr {
  yang-version 1.1;
  namespace "http://cisco.com/ns/yang/Cisco-IOS-XE-hsr";
  prefix hsr;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE HSR(High-availability Seamless Redundancy) model";

  revision 2026-02-01 {
    description
      "- Initially created
       - Added Multicast filter group support
       - Added padding CLI";
    cisco-semver:module-version "1.0.0";
  }

  typedef int-vlan {
    description
      "custom int data type for vlan with required range";
    type uint16 {
      range "0..4095";
    }
  }

  typedef mac-address {
    description
      "The mac-address type represents an IEEE 802 MAC address.";
    type string {
      pattern '[0-9a-fA-F]{4}(.[0-9a-fA-F]{4}){2}';
    }
  }

  grouping config-hsr-grouping {
    list hsr-ring {
      key "id";
      leaf id {
        description
          "Denotes channel number";
        type uint8 {
          range "1..2";
        }
      }
      leaf padding {
        description
          "Enable padding for the HSR frames";
        type empty;
      }
      leaf entryForgetTime {
        description
          "Time to clear an entry from duplicate";
        type uint16 {
          range "0..65535";
        }
        units "seconds";
      }
      leaf nodeForgetTime {
        description
          "Time to clear node entry from node table";
        type uint16 {
          range "0..65535";
        }
        units "seconds";
      }
      leaf nodeRebootInterval {
        description
          "Time to remain silent after reboot";
        type uint16 {
          range "0..65535";
        }
        units "seconds";
      }
      leaf pauseFrameTime {
        description
          "HSR pause frame time";
        type uint16 {
          range "0..65535";
        }
        units "seconds";
      }
      leaf proxyNodeTableForgetTime {
        description
          "Time to clear node entry from vdan table";
        type uint16 {
          range "0..65535";
        }
        units "seconds";
      }
      container supervisionFrameOption {
        description
          "Enables VLAN-tagged supervision frames";
        leaf vlan-id {
          description
            "vlan-id";
          type int-vlan;
        }
        leaf vlan-cos {
          description
            "vlan class of service value";
          type uint8 {
            range "1..7";
          }
        }
        leaf vlan-cfi {
          description
            "Enable CFI for the VLAN tagged frame";
          type empty;
        }
        leaf vlan-tagged {
          description
            "vlan-tagged enable/disable";
          type empty;
        }
        leaf mac-da {
          description
            "MAC DA last two bit option value";
          type uint8 {
            range "1..255";
          }
        }
      }
      leaf supervisionFrameRedboxMacaddress {
        description
          "MAC address";
        type mac-address;
      }
      leaf supervisionFrameLifeCheckInterval {
        description
          "Interval time";
        type uint16 {
          range "0..65535";
        }
        units "seconds";
      }
      leaf supervisionFrameTime {
        description
          "Frame life time";
        type uint16 {
          range "0..65535";
        }
        units "seconds";
        default "3";
      }
      container multicast_filter_deny_group {
        description
          "HSR HSR Multicast Filter Configuration";
        list unique_multicast_filter_group {
          description
            "Unique Multicast Filter Group";
          key "group-number";
          leaf group-number {
            description
              "Unique Multicast Filter Group Number";
            type uint16 {
              range "5..260";
            }
          }
          leaf mac-address {
            description
              "H.H.H 48 bit mac address";
            type mac-address;
          }
        }
        list multicast_filter_group {
          description
            "Multicast Filter Group";
          key "group-number";
          leaf group-number {
            description
              "Multicast Filter Group Number";
            type uint8 {
              range "1..4";
            }
          }
          leaf mac-address {
            description
              "H.H.H 48 bit mac address";
            type mac-address;
          }
          leaf mac-address-mask {
            description
              "H.H.H 48 bit mac address mask";
            type mac-address;
          }
        }
      }
    }
  }

  grouping config-hsr-prp-grouping {
    container hsr-prp-mode {
      container enable {
        description
          "Enable HSR PRP redbox configuration";
        container prp-lan-a {
          leaf prp-lan-a {
            type uint8 {
              range "1..6";
            }
          }
        }
        container prp-lan-b {
          leaf prp-lan-b {
            type uint8 {
              range "1..6";
            }
          }
        }
      }
    }
    container hsr-hsr-mode {
      description
        "HSR-HSR Quad box config";
      container enable {
        description
          "Enable HSR-HSR dual box";
        leaf pair {
          type enumeration {
            enum sfp;
            enum copper;
            enum mixed;
          }
        }
      }
    }
  }

  grouping config-interface-GigE-prp-grouping {
    container hsr-ring {
      leaf id {
        description
          "Denotes ring number";
        type leafref {
          path "/ios:native/ios:interface/ios:HSR-ring/ios:name";
        }
      }
    }
  }

  augment "/ios:native" {
    uses config-hsr-grouping;
  }

  augment "/ios:native" {
    uses config-hsr-prp-grouping;
  }

  augment "/ios:native/ios:interface/ios:GigabitEthernet" {
    uses config-interface-GigE-prp-grouping;
  }
}
