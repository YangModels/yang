module Cisco-IOS-XE-route-map {
  yang-version 1.1;
  namespace "http://cisco.com/ns/yang/Cisco-IOS-XE-route-map";
  prefix ios-route-map;

  import cisco-semver {
    prefix cisco-semver;
  }
  import ietf-inet-types {
    prefix inet;
  }
  import Cisco-IOS-XE-types {
    prefix ios-types;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Route Map Yang model.
     Copyright (c) 2016-2021, 2024 by Cisco Systems, Inc.
     All rights reserved.";

  revision 2026-02-01 {
    description
      "- Obsolete route-map nodes deprecated in 17.12 to 17.14
       - Added model for ipv6 recursive vrf next-hop
       - Added model for ip recursive default next-hop
       - Added switching platform restriction for default recursive next-hop";
    cisco-semver:module-version "8.0.0";
  }
  revision 2025-03-01 {
    description
      "- Removed drop node name for access-list
       - Added alt-name to prefix-list deprecated node
       - Added model for set ip global next-hop verify-availability
       - Added default value of 10 for sequence number
       - Added model for set ip default next-hop verify-availability";
    cisco-semver:module-version "7.1.0";
  }
  revision 2024-11-01 {
    description
      "- Added reset-container for match ipv6 address clauses
       - Obsolete route-map nodes deprecated in 17.11 or earlier
       - Added model for set ip next-hop verify-availability
       - Increased Track id range to 1..32767";
    cisco-semver:module-version "7.0.0";
  }
  revision 2024-07-01 {
    description
      "- Changed deprecated nodes under route-map interface and route-map set interface models to obsolete, removed relevant entries
       - Changed deprecated nodes under set ipv6 next-hop model to obsolete, removed relevant entries
       - Changed deprecated nodes under set ipv6 default next-hop model to obsolete, removed relevant entries
       - Obsolete BGP route-map nodes deprecated in 17.9.1
       - Added model for set ip next-hop unchanged";
    cisco-semver:module-version "6.0.0";
  }
  revision 2024-03-01 {
    description
      "- Deprecated access-list and added access-list-ordered with ordered-by-user
       - adding must condition for match ipv6 address
       - Deprecated access-list and added access-list-ordered with ordered-by-user
       - Added description for match ipv6 address prefix list
       - added Null interface";
    cisco-semver:module-version "5.0.0";
  }
  revision 2023-11-01 {
    description
      "- Added description for operation and sequence number
       - setting default value for operation as permit
       - Deprecated prefix-list and added prefix-list-ordered with ordered-by-user";
    cisco-semver:module-version "4.2.0";
  }
  revision 2023-07-01 {
    description
      "- Hardened for match metric and external ";
    cisco-semver:module-version "4.1.0";
  }
  revision 2023-03-01 {
    description
      "- Hardened CLIs set ipv6 vrf next-hop , set ipv6 default vrf next-hop, set ipv6 vrf next-hop verify availability, set ipv6 vrf next-hop verify availability sequence track
       - Hardened set ipv6 next-hop verify-availability
       - Hardened CLI set tag
       - Hardened CLI match tag
       - Added new tos without presence container and deprecating tos container
       - Added new external number container and deprecating external container
       - Added a new descriptions list and deprecating description leaf";
    cisco-semver:module-version "4.0.0";
  }
  revision 2022-11-01 {
    description
      "- Update yang-version to 1.1
       - Hardened CLIs set ipv6 default global next-hop, set ipv6 default next-hop, set ipv6 global next-hop, set ipv6 global next-hop verify-availability";
    cisco-semver:module-version "3.0.0";
  }
  revision 2022-07-01 {
    description
      "- Migrate BGP-owned route-map nodes to BGP model
       - Deprecated set/ipv6/address/prefix-list from leaf-list to leaf
       - Moved deprecate annotations to annotation file";
    cisco-semver:module-version "2.5.0";
  }
  revision 2022-03-01 {
    description
      "- Add ordered-by user in match community and match extcommunity ";
    cisco-semver:module-version "2.4.0";
  }
  revision 2021-11-01 {
    description
      "- added additive option for set extended community color";
    cisco-semver:module-version "2.3.0";
  }
  revision 2021-03-01 {
    description
      "- Removed the tailf cli-diff-dependency";
    cisco-semver:module-version "2.2.1";
  }
  revision 2020-11-01 {
    description
      "Add large-community configurations";
    cisco-semver:module-version "2.2.0";
  }
  revision 2020-07-01 {
    description
      "Model change for match/length/max( and min), set/ipv6/default/next-hop
        and set/ipv6/next-hop";
    cisco-semver:module-version "2.1.0";
  }
  revision 2020-03-01 {
    description
      "Update set community-list configuration
       Add route-map continue configuration";
    cisco-semver:module-version "2.0.0";
  }
  revision 2019-11-01 {
    description
      "Changed address data type";
    cisco-semver:module-version "1.1.0";
  }
  revision 2019-07-01 {
    description
      "Establish semantic version baseline";
    cisco-semver:module-version "1.0.0";
  }
  revision 2019-03-06 {
    description
      "Fixed route-map set community configuration";
  }
  revision 2018-12-06 {
    description
      "Added Support of color extended community";
  }
  revision 2018-12-01 {
    description
      "Removed choice option from set ip nexthop so that multiple
       options can be configured at same time";
  }
  revision 2018-11-13 {
    description
      "Change to use + in multi-line descriptions to avoid NSO compile error";
  }
  revision 2018-08-30 {
    description
      "Added support for set nlri and set attribute-set";
  }
  revision 2018-08-10 {
    description
      "Added support for multiple IPv4 next-hop (set ip next-hop)";
  }
  revision 2018-05-02 {
    description
      "Add omp and nat-route to source-protocol matching";
  }
  revision 2018-03-08 {
    description
      "Add tailf:cli-flat-list-syntax to route-map/match-preference";
  }
  revision 2018-01-08 {
    description
      "Revise modeling for set metric";
  }
  revision 2017-10-20 {
    description
      "Add model omp-tag for set and match";
  }
  revision 2017-07-27 {
    description
      "Add model for set ip next-hop verify-availability<ipaddr> <range> track <range>";
  }
  revision 2017-06-07 {
    description
      "Add model for named ordering route-map enable";
  }
  revision 2017-02-07 {
    description
      "Initial revision";
  }

  grouping rt_map_interface-deprecated-grouping {
    choice interface-choice {
      leaf AppNav-Compress {
        status obsolete;
        description
          "Service-Context Virtual Interface Compress (OBSOLETE)";
        type uint16;
      }
      leaf AppNav-UnCompress {
        status obsolete;
        description
          "Service-Context Virtual Interface UnCompress (OBSOLETE)";
        type uint16;
      }
      leaf ATM {
        status obsolete;
        description
          "ATM interface (OBSOLETE)";
        type string;
      }
      container ATM-subinterface {
        status obsolete;
        leaf ATM {
          status obsolete;
          type string;
        }
      }
      leaf ATM-ACR {
        status obsolete;
        description
          "ATM-ACR interface (OBSOLETE)";
        type string {
          pattern '[0-9]';
        }
      }
      container ATM-ACRsubinterface {
        status obsolete;
        leaf ATM-ACR {
          status obsolete;
          type string {
            pattern '[0-9]\.([0-9]/){3}[0-9]';
          }
        }
      }
      leaf BDI {
        status obsolete;
        description
          "Bridge-Domain interface (OBSOLETE)";
        type string;
      }
      leaf CEM {
        status obsolete;
        description
          "CEM interface (OBSOLETE)";
        type string {
          pattern '([0-9]/){2}[0-9]';
        }
      }
      leaf CEM-ACR {
        status obsolete;
        description
          "CEM-ACR interface (OBSOLETE)";
        type uint8 {
          range "0..255";
        }
      }
      leaf Embedded-Service-Engine {
        status obsolete;
        description
          "cisco embedded service engine module (OBSOLETE)";
        type string;
      }
      leaf Ethernet {
        status obsolete;
        description
          "IEEE 802.3 (OBSOLETE)";
        type string;
      }
      leaf FastEthernet {
        status obsolete;
        description
          "FastEthernet IEEE 802.3 (OBSOLETE)";
        type string;
      }
      leaf GigabitEthernet {
        status obsolete;
        description
          "GigabitEthernet IEEE 802.3z (OBSOLETE)";
        type string;
      }
      leaf FiveGigabitEthernet {
        status obsolete;
        description
          "Five GigabitEthernet (OBSOLETE)";
        type string;
      }
      leaf AppGigabitEthernet {
        status obsolete;
        description
          "App-hosting Gigabit Ethernet IEEE 802.3z (OBSOLETE)";
        type string;
      }
      leaf TwentyFiveGigabitEthernet {
        status obsolete;
        description
          "Twenty Five GigabitEthernet (OBSOLETE)";
        type string;
      }
      leaf TwentyFiveGigE {
        status obsolete;
        description
          "Twenty Five GigabitEthernet (OBSOLETE)";
        type string;
      }
      leaf TwoGigabitEthernet {
        status obsolete;
        description
          "Two GigabitEthernet (OBSOLETE)";
        type string;
      }
      leaf FortyGigabitEthernet {
        status obsolete;
        description
          "Forty GigabitEthernet (OBSOLETE)";
        type string;
      }
      leaf HundredGigE {
        status obsolete;
        description
          "Hundred GigabitEthernet (OBSOLETE)";
        type string;
      }
      leaf LISP {
        status obsolete;
        description
          "Locator/ID Separation Protocol Virtual Interface (OBSOLETE)";
        type string;
      }
      container LISP-subinterface {
        status obsolete;
        description
          "Locator/ID Separation Protocol Virtual Interface (OBSOLETE)";
        leaf LISP {
          status obsolete;
          type string {
            pattern '[0-9]*(. ?[1-9][0-9]*)*';
          }
        }
      }
      leaf Loopback {
        status obsolete;
        description
          "Loopback interface (OBSOLETE)";
        type uint32;
      }
      leaf Multilink {
        status obsolete;
        description
          "Multilink-group interface (OBSOLETE)";
        type uint16;
      }
      leaf nve {
        status obsolete;
        description
          "Network virtualization endpoint interface (OBSOLETE)";
        type uint16;
      }
      leaf overlay {
        status obsolete;
        description
          "Overlay interface (OBSOLETE)";
        type uint16;
      }
      leaf Port-channel {
        status obsolete;
        description
          "Ethernet Channel of interfaces (OBSOLETE)";
        type uint32;
      }
      container Port-channel-subinterface {
        status obsolete;
        leaf Port-channel {
          status obsolete;
          type string;
        }
      }
      leaf pseudowire {
        status obsolete;
        description
          "Pseudowire Interface (OBSOLETE)";
        type uint32;
      }
      leaf SM {
        status obsolete;
        description
          "SM Interface (OBSOLETE)";
        type string;
      }
      leaf Cellular {
        status obsolete;
        description
          "Cellular Interface (OBSOLETE)";
        type string;
      }
      leaf Dialer {
        status obsolete;
        description
          "Dialer Interface (OBSOLETE)";
        type string;
      }
      leaf Serial {
        status obsolete;
        description
          "Serial interface (OBSOLETE)";
        type string;
      }
      leaf Async {
        status obsolete;
        description
          "Async serial interface (OBSOLETE)";
        type string;
      }
      leaf TenGigabitEthernet {
        status obsolete;
        description
          "Ten Gigabit Ethernet (OBSOLETE)";
        type string;
      }
      leaf Tunnel {
        status obsolete;
        description
          "Tunnel interface (OBSOLETE)";
        type uint32;
      }
      leaf Virtual-Template {
        status obsolete;
        description
          "Virtual Template interface (OBSOLETE)";
        type uint16;
      }
      leaf Vlan {
        status obsolete;
        description
          "Iosxr Vlans (OBSOLETE)";
        type uint16;
      }
      leaf VirtualPortGroup {
        status obsolete;
        description
          "Virtual Port Group (OBSOLETE)";
        type uint16;
      }
      leaf vasileft {
        status obsolete;
        description
          "vasileft (OBSOLETE)";
        type uint16;
      }
      leaf vasiright {
        status obsolete;
        description
          "vasiright (OBSOLETE)";
        type uint16;
      }
      leaf BD-VIF {
        status obsolete;
        description
          "Bridge-Domain Virtual IP interface (OBSOLETE)";
        type string;
      }
      leaf Null {
        status obsolete;
        description
          "Null interface (OBSOLETE)";
        type string;
      }
    }
  }

  grouping config-named-ordering-route-map-grouping {
    container named-ordering-route-map {
      description
        "named ordering route-map enable";
      leaf enable {
        description
          "named ordering enable";
        type empty;
      }
    }
  }

  grouping next-hop-address-grouping {
    container next-hop {
      description
        "Next hop along path";
      leaf-list address {
        type inet:ipv4-address;
      }
    }
  }

  grouping next-hop-address-default-grouping {
    container next-hop {
      description
        "Next hop along path";
      leaf-list address {
        type inet:ipv4-address;
      }
      leaf verify-availability {
        description
          "Verify if default nexthop is a CDP neighbor";
        type empty;
      }
      container recursive {
        description
          "Default Recursive next-hop";
        if-feature "ios-features:pbr-switching";
        choice recursive-ip-choice {
          leaf ipv4 {
            description
              "IP address of default recursive next hop";
            type inet:ipv4-address;
          }
          leaf global {
            description
              "IP address of default global recursive next hop";
            type inet:ipv4-address;
          }
          container vrf {
            description
              "VRF name";
            list vrfs {
              key "vrf";
              leaf vrf {
                description
                  "VRF name";
                type leafref {
                  path "/ios:native/ios:vrf/ios:definition/ios:name";
                }
              }
              leaf ipv4 {
                description
                  "IP address of default vrf recursive next hop";
                type inet:ipv4-address;
              }
            }
          }
        }
      }
    }
  }

  grouping ip-access-list-grouping {
    leaf-list access-list-ordered {
      description
        "Match entries of access-lists";
      ordered-by user;
      type ios-types:exp-acl-type;
    }
    leaf-list access-list {
      status obsolete;
      type ios-types:exp-acl-type;
    }
    leaf-list prefix-list-ordered {
      description
        "Match entries of prefix-lists";
      ordered-by user;
      type string;
    }
    leaf-list prefix-list {
      status obsolete;
      description
        "Match entries of prefix-lists (OBSOLETE)";
      type string;
    }
  }

  grouping ipv6-access-list-grouping {
    leaf access-list {
      description
        "IPv6 access-list name";
      must ' not (../prefix-list)' {
        error-message "prefix-list and access-list can not co-exist in one route-map sequence";
      }
      type string {
        pattern '[a-zA-Z].*';
      }
    }
    leaf prefix-list {
      description
        "IPv6 prefix-list name";
      type string;
    }
  }

  grouping route-map-community-grouping {
    list community-id {
      status obsolete;
      key "community-id cost-value";
      leaf community-id {
        status obsolete;
        description
          "Community ID";
        type uint8 {
          range "0..255";
        }
      }
      leaf cost-value {
        status obsolete;
        description
          "Cost Value (No-preference Cost = 2147483647)";
        type uint32 {
          range "0..4294967295";
        }
      }
    }
  }

  grouping config-route-map-common-grouping {
    list descriptions {
      description
        "list of Route-map comments";
      key "description-leaf";
      leaf description-leaf {
        description
          "Route-map comment";
        type string;
      }
    }
    leaf description {
      description
        "Route-map comment (OBSOLETE)";
      status obsolete;
      type string;
    }
    container set {
      description
        "Set values in destination routing protocol";
      container aigp-metric {
        description
          "accumulated metric value";
        leaf value {
          description
            "manual value";
          type uint32 {
            range "0..4294967295";
          }
        }
        leaf igp-metric {
          description
            "metric value from rib";
          type empty;
        }
      }
      container as-path {
        status obsolete;
        description
          "Modify BGP AS-path attribute (OBSOLETE - please use route-map configuration in Cisco-IOS-XE-bgp.yang)";
        container prepend {
          status obsolete;
          description
            "Prepend to the as-path (OBSOLETE - please use route-map configuration in Cisco-IOS-XE-bgp.yang)";
          container as-container {
            status obsolete;
            leaf as-number {
              status obsolete;
              description
                "<1-65535>;;AS number (OBSOLETE - please use route-map configuration in Cisco-IOS-XE-bgp.yang)";
              type string;
            }
          }
          container last-as-cont {
            status obsolete;
            leaf last-as {
              status obsolete;
              type uint16 {
                range "1..10";
              }
            }
          }
        }
        container tag {
          status obsolete;
          description
            "Set the tag as an AS-path attribute (OBSOLETE - please use route-map configuration in Cisco-IOS-XE-bgp.yang)";
          presence "tag";
        }
        container replace {
          status obsolete;
          description
            "Replace AS numbers in the AS-path with the local AS (OBSOLETE - please use route-map configuration in Cisco-IOS-XE-bgp.yang)";
          list as-container {
            status obsolete;
            ordered-by user;
            key "as-number";
            leaf as-number {
              status obsolete;
              description
                "<1-65535>;;AS number (OBSOLETE - please use route-map configuration in Cisco-IOS-XE-bgp.yang)";
              type string;
            }
          }
          leaf any {
            status obsolete;
            description
              "Replace each AS number in the AS-path with the local AS (OBSOLETE - please use route-map configuration in Cisco-IOS-XE-bgp.yang)";
            type empty;
          }
        }
      }
      leaf attribute-set {
        status obsolete;
        description
          "TE Profile name (OBSOLETE - please use route-map configuration in Cisco-IOS-XE-bgp.yang)";
        type string;
      }
      leaf automatic-tag {
        description
          "Automatically compute TAG value";
        type empty;
      }
      container clns {
        description
          "OSI summary address";
        uses next-hop-address-grouping;
      }
      container community {
        status obsolete;
        description
          "BGP community attribute (OBSOLETE - please use route-map configuration in Cisco-IOS-XE-bgp.yang)";
        choice community-well-known-choice {
          status obsolete;
          leaf none {
            status obsolete;
            description
              "No community attribute (OBSOLETE - please use route-map configuration in Cisco-IOS-XE-bgp.yang)";
            type empty;
          }
          container community-well-known {
            status obsolete;
            leaf-list community-list {
              status obsolete;
              ordered-by user;
              type union {
                type ios-types:community-number-type;
                type ios-types:community-well-known-type;
              }
            }
            leaf additive {
              status obsolete;
              type empty;
            }
          }
        }
      }
      container comm-list {
        status obsolete;
        description
          "set BGP community list (for deletion) (OBSOLETE - please use route-map configuration in Cisco-IOS-XE-bgp.yang)";
        choice comm-list-choice {
          status obsolete;
          leaf comm-list-standard {
            status obsolete;
            type uint16 {
              range "1..99";
            }
          }
          leaf comm-list-expanded {
            status obsolete;
            type uint16 {
              range "100..500";
            }
          }
          leaf comm-list-name {
            status obsolete;
            type string;
          }
        }
        leaf delete {
          status obsolete;
          description
            "Delete matching communities (OBSOLETE - please use route-map configuration in Cisco-IOS-XE-bgp.yang)";
          type empty;
        }
      }
      container dampening {
        status obsolete;
        description
          "Set BGP route flap dampening parameters (OBSOLETE - please use route-map configuration in Cisco-IOS-XE-bgp.yang)";
        list dampening-list {
          status obsolete;
          key "half-life-penalty restart-penalty suppress-penalty max-suppress-penalty";
          leaf half-life-penalty {
            status obsolete;
            description
              "half-life time for the penalty (OBSOLETE - please use route-map configuration in Cisco-IOS-XE-bgp.yang)";
            type uint8 {
              range "1..45";
            }
          }
          leaf restart-penalty {
            status obsolete;
            description
              "penalty to start reusing a route (OBSOLETE - please use route-map configuration in Cisco-IOS-XE-bgp.yang)";
            type uint16 {
              range "1..20000";
            }
          }
          leaf suppress-penalty {
            status obsolete;
            description
              "penalty to start suppressing a route (OBSOLETE - please use route-map configuration in Cisco-IOS-XE-bgp.yang)";
            type uint16 {
              range "1..20000";
            }
          }
          leaf max-suppress-penalty {
            status obsolete;
            description
              "Maximum duration to suppress a stable route (OBSOLETE - please use route-map configuration in Cisco-IOS-XE-bgp.yang)";
            type uint8 {
              range "1..255";
            }
          }
        }
      }
      container default {
        leaf-list interface-list {
          ordered-by user;
          description
            "SPAN source interface";
          must "not (starts-with(., 'AppNav-Compress')) or /ios:native/ios:interface/*[concat(local-name(), ios:name) = current()]" {
            error-message "AppNav-Compress interface must be created first and deleted last.";
          }
          must "not (starts-with(., 'AppNav-UnCompress')) or /ios:native/ios:interface/*[concat(local-name(), ios:name) = current()]" {
            error-message "AppNav-UnCompress interface must be created first and deleted last.";
          }
          must "not (starts-with(., 'ATM')) or /ios:native/ios:interface/*[concat(local-name(), ios:name) = current()]or /ios:native/ios:interface/ios:ATM-subinterface/*[concat(local-name(), ios:name) = current()]" {
            error-message "ATM interface must be created first and deleted last.";
          }
          must "not (starts-with(., 'ATM-ACR')) or /ios:native/ios:interface/*[concat(local-name(), ios:name) = current()]or /ios:native/ios:interface/ios:ATM-ACRsubinterface/*[concat(local-name(), ios:name) = current()]" {
            error-message "ATM-ACR interface must be created first and deleted last.";
          }
          must "not (starts-with(., 'BDI')) or /ios:native/ios:interface/*[concat(local-name(), ios:name) = current()]" {
            error-message "BDI interface must be created first and deleted last.";
          }
          must "not (starts-with(., 'CEM')) or /ios:native/ios:interface/*[concat(local-name(), ios:name) = current()]" {
            error-message "CEM interface must be created first and deleted last.";
          }
          must "not (starts-with(., 'CEM-ACR')) or /ios:native/ios:interface/*[concat(local-name(), ios:name) = current()]" {
            error-message "CEM-ACR interface must be created first and deleted last.";
          }
          must "not (starts-with(., 'Embedded-Service-Engine')) or /ios:native/ios:interface/*[concat(local-name(), ios:name) = current()]" {
            error-message "Embedded-Service-Engine interface must be created first and deleted last.";
          }
          must "not (starts-with(., 'Ethernet')) or /ios:native/ios:interface/*[concat(local-name(), ios:name) = current()]" {
            error-message "Ethernet interface must be created first and deleted last.";
          }
          must "not (starts-with(., 'FastEthernet')) or /ios:native/ios:interface/*[concat(local-name(), ios:name) = current()]" {
            error-message "FastEthernet interface must be created first and deleted last.";
          }
          must "not (starts-with(., 'GigabitEthernet')) or /ios:native/ios:interface/*[concat(local-name(), ios:name) = current()]" {
            error-message "GigabitEthernet interface must be created first and deleted last.";
          }
          must "not (starts-with(., 'FiveGigabitEthernet')) or /ios:native/ios:interface/*[concat(local-name(), ios:name) = current()]" {
            error-message "FiveGigabitEthernet interface must be created first and deleted last.";
          }
          must "not (starts-with(., 'AppGigabitEthernet')) or /ios:native/ios:interface/*[concat(local-name(), ios:name) = current()]" {
            error-message "AppGigabitEthernet interface must be created first and deleted last.";
          }
          must "not (starts-with(., 'TwentyFiveGigE')) or /ios:native/ios:interface/*[concat(local-name(), ios:name) = current()]" {
            error-message "TwentyFiveGigE interface must be created first and deleted last.";
          }
          must "not (starts-with(., 'TwoGigabitEthernet')) or /ios:native/ios:interface/*[concat(local-name(), ios:name) = current()]" {
            error-message "TwoGigabitEthernet interface must be created first and deleted last.";
          }
          must "not (starts-with(., 'FortyGigabitEthernet')) or /ios:native/ios:interface/*[concat(local-name(), ios:name) = current()]" {
            error-message "FortyGigabitEthernet interface must be created first and deleted last.";
          }
          must "not (starts-with(., 'HundredGigE')) or /ios:native/ios:interface/*[concat(local-name(), ios:name) = current()]" {
            error-message "HundredGigE interface must be created first and deleted last.";
          }
          must "not (starts-with(., 'LISP')) or /ios:native/ios:interface/*[concat(local-name(), ios:name) = current()]or /ios:native/ios:interface/ios:LISP-subinterface/*[concat(local-name(), ios:name) = current()]" {
            error-message "LISP interface must be created first and deleted last.";
          }
          must "not (starts-with(., 'Loopback')) or /ios:native/ios:interface/*[concat(local-name(), ios:name) = current()]" {
            error-message "Loopback interface must be created first and deleted last.";
          }
          must "not (starts-with(., 'Multilink')) or /ios:native/ios:interface/*[concat(local-name(), ios:name) = current()]" {
            error-message "Multilink interface must be created first and deleted last.";
          }
          must "not (starts-with(., 'nve')) or /ios:native/ios:interface/*[concat(local-name(), ios:name) = current()]" {
            error-message "nve interface must be created first and deleted last.";
          }
          must "not (starts-with(., 'overlay')) or /ios:native/ios:interface/*[concat(local-name(), ios:name) = current()]" {
            error-message "overlay interface must be created first and deleted last.";
          }
          must "not (starts-with(., 'Port-channel')) or /ios:native/ios:interface/*[concat(local-name(), ios:name) = current()]or /ios:native/ios:interface/ios:Port-channel-subinterface/*[concat(local-name(), ios:name) = current()]" {
            error-message "Port-channel interface must be created first and deleted last.";
          }
          must "not (starts-with(., 'pseudowire')) or /ios:native/ios:interface/*[concat(local-name(), ios:name) = current()]" {
            error-message "pseudowire interface must be created first and deleted last.";
          }
          must "not (starts-with(., 'SM')) or /ios:native/ios:interface/*[concat(local-name(), ios:name) = current()]" {
            error-message "SM interface must be created first and deleted last.";
          }
          must "not (starts-with(., 'Cellular')) or /ios:native/ios:interface/*[concat(local-name(), ios:name) = current()]" {
            error-message "Cellular interface must be created first and deleted last.";
          }
          must "not (starts-with(., 'Dialer')) or /ios:native/ios:interface/*[concat(local-name(), ios:name) = current()]" {
            error-message "Dialer interface must be created first and deleted last.";
          }
          must "not (starts-with(., 'Serial')) or /ios:native/ios:interface/*[concat(local-name(), ios:name) = current()]" {
            error-message "Serial interface must be created first and deleted last.";
          }
          must "not (starts-with(., 'Async')) or /ios:native/ios:interface/*[concat(local-name(), ios:name) = current()]" {
            error-message "Async interface must be created first and deleted last.";
          }
          must "not (starts-with(., 'TenGigabitEthernet')) or /ios:native/ios:interface/*[concat(local-name(), ios:name) = current()]" {
            error-message "TenGigabitEthernet interface must be created first and deleted last.";
          }
          must "not (starts-with(., 'Tunnel')) or /ios:native/ios:interface/*[concat(local-name(), ios:name) = current()]" {
            error-message "Tunnel interface must be created first and deleted last.";
          }
          must "not (starts-with(., 'Virtual-Template')) or /ios:native/ios:interface/*[concat(local-name(), ios:name) = current()]" {
            error-message "Virtual-Template interface must be created first and deleted last.";
          }
          must "not (starts-with(., 'Vlan')) or /ios:native/ios:interface/*[concat(local-name(), ios:name) = current()]" {
            error-message "Vlan interface must be created first and deleted last.";
          }
          must "not (starts-with(., 'VirtualPortGroup')) or /ios:native/ios:interface/*[concat(local-name(), ios:name) = current()]" {
            error-message "VirtualPortGroup interface must be created first and deleted last.";
          }
          must "not (starts-with(., 'vasileft')) or /ios:native/ios:interface/*[concat(local-name(), ios:name) = current()]" {
            error-message "vasileft interface must be created first and deleted last.";
          }
          must "not (starts-with(., 'vasiright')) or /ios:native/ios:interface/*[concat(local-name(), ios:name) = current()]" {
            error-message "vasiright interface must be created first and deleted last.";
          }
          must "not (starts-with(., 'BD-VIF')) or /ios:native/ios:interface/*[concat(local-name(), ios:name) = current()]" {
            error-message "BD-VIF interface must be created first and deleted last.";
          }
          type string;
        }
        container interface {
          status obsolete;
          description
            "SPAN source interface (OBSOLETE)";
          uses rt_map_interface-deprecated-grouping;
        }
      }
      container extcomm-list {
        status obsolete;
        description
          "Set BGP/VPN extended community list (for deletion) (OBSOLETE - please use route-map configuration in Cisco-IOS-XE-bgp.yang)";
        list ext-range {
          status obsolete;
          key "comm-list-num";
          leaf comm-list-num {
            status obsolete;
            description
              "Extended community-list number (expanded) (OBSOLETE - please use route-map configuration in Cisco-IOS-XE-bgp.yang)";
            type uint16 {
              range "1..500";
            }
          }
          leaf delete {
            status obsolete;
            description
              "Delete matching extended communities (OBSOLETE - please use route-map configuration in Cisco-IOS-XE-bgp.yang)";
            type empty;
          }
        }
        list excomm-list-name {
          status obsolete;
          key "name";
          leaf name {
            status obsolete;
            description
              "extcommunity-list name (OBSOLETE - please use route-map configuration in Cisco-IOS-XE-bgp.yang)";
            type string;
          }
          leaf delete {
            status obsolete;
            type empty;
          }
        }
      }
      container extcommunity {
        status obsolete;
        description
          "BGP extended community attribute (OBSOLETE - please use route-map configuration in Cisco-IOS-XE-bgp.yang)";
        container color-additive {
          status obsolete;
          leaf color {
            status obsolete;
            description
              "Color Extended Community (OBSOLETE - please use route-map configuration in Cisco-IOS-XE-bgp.yang)";
            type uint32 {
              range "1..4294967295";
            }
          }
          leaf additive {
            status obsolete;
            when '../color';
            description
              "additive (OBSOLETE - please use route-map configuration in Cisco-IOS-XE-bgp.yang)";
            type empty;
          }
        }
        leaf color {
          status obsolete;
          description
            "Color Extended Community (OBSOLETE - use color-additive/color in Cisco-IOS-XE-bgp.yang instead)";
          type uint32 {
            range "1..4294967295";
          }
        }
        container cost {
          status obsolete;
          description
            "Cost extended community (OBSOLETE - please use route-map configuration in Cisco-IOS-XE-bgp.yang)";
          uses route-map-community-grouping;
          container igp {
            status obsolete;
            description
              "Compare following IGP cost comparison (OBSOLETE - please use route-map configuration in Cisco-IOS-XE-bgp.yang)";
            uses route-map-community-grouping;
          }
          container pre-bestpath {
            status obsolete;
            description
              "Compare before all other steps in bestpath calculation (OBSOLETE - please use route-map configuration in Cisco-IOS-XE-bgp.yang)";
            uses route-map-community-grouping;
          }
        }
        container rt {
          status obsolete;
          description
            "Route Target extended community (OBSOLETE - please use route-map configuration in Cisco-IOS-XE-bgp.yang)";
          leaf-list asn-nn {
            status obsolete;
            ordered-by user;
            type union {
              type ios-types:asn-ip-type;
              type enumeration {
                enum additive;
              }
            }
          }
          container range {
            status obsolete;
            description
              "Specify a range of extended community (OBSOLETE - please use route-map configuration in Cisco-IOS-XE-bgp.yang)";
            leaf lower-limit {
              status obsolete;
              description
                "VPN extended community lower limit (OBSOLETE - please use route-map configuration in Cisco-IOS-XE-bgp.yang)";
              type ios-types:asn-ip-type;
            }
            leaf high-limit {
              status obsolete;
              description
                "VPN extended community high limit (OBSOLETE - please use route-map configuration in Cisco-IOS-XE-bgp.yang)";
              type ios-types:asn-ip-type;
            }
            leaf additive {
              status obsolete;
              description
                "Add to the existing extcommunity (OBSOLETE - please use route-map configuration in Cisco-IOS-XE-bgp.yang)";
              type empty;
            }
          }
        }
        container soo {
          status obsolete;
          description
            "Site-of-Origin extended community (OBSOLETE - please use route-map configuration in Cisco-IOS-XE-bgp.yang)";
          leaf asn-nn {
            status obsolete;
            type ios-types:asn-ip-type;
          }
        }
        container vpn-distinguisher {
          status obsolete;
          description
            "VPN Distinguisher (OBSOLETE - please use route-map configuration in Cisco-IOS-XE-bgp.yang)";
          leaf asn-nn {
            status obsolete;
            type ios-types:asn-ip-type;
          }
          container range {
            status obsolete;
            description
              "Specify a range of extended community (OBSOLETE - please use route-map configuration in Cisco-IOS-XE-bgp.yang)";
            leaf lower-limit {
              status obsolete;
              description
                "VPN extended community lower limit (OBSOLETE - please use route-map configuration in Cisco-IOS-XE-bgp.yang)";
              type ios-types:asn-ip-type;
            }
            leaf high-limit {
              status obsolete;
              description
                "VPN extended community high limit (OBSOLETE - please use route-map configuration in Cisco-IOS-XE-bgp.yang)";
              type ios-types:asn-ip-type;
            }
            leaf additive {
              status obsolete;
              description
                "Add to the existing extcommunity (OBSOLETE - please use route-map configuration in Cisco-IOS-XE-bgp.yang)";
              type empty;
            }
          }
        }
      }
      leaf global {
        type empty;
      }
      leaf-list interface-list {
        ordered-by user;
        description
          "Interface specific information";
        must "not (starts-with(., 'AppNav-Compress')) or /ios:native/ios:interface/*[concat(local-name(), ios:name) = current()]" {
          error-message "AppNav-Compress interface must be created first and deleted last.";
        }
        must "not (starts-with(., 'AppNav-UnCompress')) or /ios:native/ios:interface/*[concat(local-name(), ios:name) = current()]" {
          error-message "AppNav-UnCompress interface must be created first and deleted last.";
        }
        must "not (starts-with(., 'ATM')) or /ios:native/ios:interface/ios:ATM-subinterface/*[concat(local-name(), ios:name) = current()] or /ios:native/ios:interface/*[concat(local-name(), ios:name) = current()]" {
          error-message "ATM interface must be created first and deleted last.";
        }
        must "not (starts-with(., 'ATM-ACR')) or /ios:native/ios:interface/ios:ATM-ACRsubinterface/*[concat(local-name(), ios:name) = current()]or /ios:native/ios:interface/*[concat(local-name(), ios:name) = current()]" {
          error-message "ATM-ACR interface must be created first and deleted last.";
        }
        must "not (starts-with(., 'BDI')) or /ios:native/ios:interface/*[concat(local-name(), ios:name) = current()]" {
          error-message "BDI interface must be created first and deleted last.";
        }
        must "not (starts-with(., 'CEM')) or /ios:native/ios:interface/*[concat(local-name(), ios:name) = current()]" {
          error-message "CEM interface must be created first and deleted last.";
        }
        must "not (starts-with(., 'CEM-ACR')) or /ios:native/ios:interface/*[concat(local-name(), ios:name) = current()]" {
          error-message "CEM-ACR interface must be created first and deleted last.";
        }
        must "not (starts-with(., 'Embedded-Service-Engine')) or /ios:native/ios:interface/*[concat(local-name(), ios:name) = current()]" {
          error-message "Embedded-Service-Engine interface must be created first and deleted last.";
        }
        must "not (starts-with(., 'Ethernet')) or /ios:native/ios:interface/*[concat(local-name(), ios:name) = current()]" {
          error-message "Ethernet interface must be created first and deleted last.";
        }
        must "not (starts-with(., 'FastEthernet')) or /ios:native/ios:interface/*[concat(local-name(), ios:name) = current()]" {
          error-message "FastEthernet interface must be created first and deleted last.";
        }
        must "not (starts-with(., 'GigabitEthernet')) or /ios:native/ios:interface/*[concat(local-name(), ios:name) = current()]" {
          error-message "GigabitEthernet interface must be created first and deleted last.";
        }
        must "not (starts-with(., 'FiveGigabitEthernet')) or /ios:native/ios:interface/*[concat(local-name(), ios:name) = current()]" {
          error-message "FiveGigabitEthernet interface must be created first and deleted last.";
        }
        must "not (starts-with(., 'AppGigabitEthernet')) or /ios:native/ios:interface/*[concat(local-name(), ios:name) = current()]" {
          error-message "AppGigabitEthernet interface must be created first and deleted last.";
        }
        must "not (starts-with(., 'TwentyFiveGigE')) or /ios:native/ios:interface/*[concat(local-name(), ios:name) = current()]" {
          error-message "TwentyFiveGigE interface must be created first and deleted last.";
        }
        must "not (starts-with(., 'TwoGigabitEthernet')) or /ios:native/ios:interface/*[concat(local-name(), ios:name) = current()]" {
          error-message "TwoGigabitEthernet interface must be created first and deleted last.";
        }
        must "not (starts-with(., 'FortyGigabitEthernet')) or /ios:native/ios:interface/*[concat(local-name(), ios:name) = current()]" {
          error-message "FortyGigabitEthernet interface must be created first and deleted last.";
        }
        must "not (starts-with(., 'HundredGigE')) or /ios:native/ios:interface/*[concat(local-name(), ios:name) = current()]" {
          error-message "HundredGigE interface must be created first and deleted last.";
        }
        must "not (starts-with(., 'LISP')) or /ios:native/ios:interface/*[concat(local-name(), ios:name) = current()]or /ios:native/ios:interface/ios:LISP-subinterface/*[concat(local-name(), ios:name) = current()]" {
          error-message "LISP interface must be created first and deleted last.";
        }
        must "not (starts-with(., 'Loopback')) or /ios:native/ios:interface/*[concat(local-name(), ios:name) = current()]" {
          error-message "Loopback interface must be created first and deleted last.";
        }
        must "not (starts-with(., 'Multilink')) or /ios:native/ios:interface/*[concat(local-name(), ios:name) = current()]" {
          error-message "Multilink interface must be created first and deleted last.";
        }
        must "not (starts-with(., 'nve')) or /ios:native/ios:interface/*[concat(local-name(), ios:name) = current()]" {
          error-message "nve interface must be created first and deleted last.";
        }
        must "not (starts-with(., 'overlay')) or /ios:native/ios:interface/*[concat(local-name(), ios:name) = current()]" {
          error-message "overlay interface must be created first and deleted last.";
        }
        must "not (starts-with(., 'Port-channel')) or /ios:native/ios:interface/*[concat(local-name(), ios:name) = current()]or /ios:native/ios:interface/ios:Port-channel-subinterface/*[concat(local-name(), ios:name) = current()]" {
          error-message "Port-channel interface must be created first and deleted last.";
        }
        must "not (starts-with(., 'pseudowire')) or /ios:native/ios:interface/*[concat(local-name(), ios:name) = current()]" {
          error-message "pseudowire interface must be created first and deleted last.";
        }
        must "not (starts-with(., 'SM')) or /ios:native/ios:interface/*[concat(local-name(), ios:name) = current()]" {
          error-message "SM interface must be created first and deleted last.";
        }
        must "not (starts-with(., 'Cellular')) or /ios:native/ios:interface/*[concat(local-name(), ios:name) = current()]" {
          error-message "Cellular interface must be created first and deleted last.";
        }
        must "not (starts-with(., 'Dialer')) or /ios:native/ios:interface/*[concat(local-name(), ios:name) = current()]" {
          error-message "Dialer interface must be created first and deleted last.";
        }
        must "not (starts-with(., 'Serial')) or /ios:native/ios:interface/*[concat(local-name(), ios:name) = current()]" {
          error-message "Serial interface must be created first and deleted last.";
        }
        must "not (starts-with(., 'Async')) or /ios:native/ios:interface/*[concat(local-name(), ios:name) = current()]" {
          error-message "Async interface must be created first and deleted last.";
        }
        must "not (starts-with(., 'TenGigabitEthernet')) or /ios:native/ios:interface/*[concat(local-name(), ios:name) = current()]" {
          error-message "TenGigabitEthernet interface must be created first and deleted last.";
        }
        must "not (starts-with(., 'Tunnel')) or /ios:native/ios:interface/*[concat(local-name(), ios:name) = current()]" {
          error-message "Tunnel interface must be created first and deleted last.";
        }
        must "not (starts-with(., 'Virtual-Template')) or /ios:native/ios:interface/*[concat(local-name(), ios:name) = current()]" {
          error-message "Virtual-Template interface must be created first and deleted last.";
        }
        must "not (starts-with(., 'Vlan')) or /ios:native/ios:interface/*[concat(local-name(), ios:name) = current()]" {
          error-message "Vlan interface must be created first and deleted last.";
        }
        must "not (starts-with(., 'VirtualPortGroup')) or /ios:native/ios:interface/*[concat(local-name(), ios:name) = current()]" {
          error-message "VirtualPortGroup interface must be created first and deleted last.";
        }
        must "not (starts-with(., 'vasileft')) or /ios:native/ios:interface/*[concat(local-name(), ios:name) = current()]" {
          error-message "vasileft interface must be created first and deleted last.";
        }
        must "not (starts-with(., 'vasiright')) or /ios:native/ios:interface/*[concat(local-name(), ios:name) = current()]" {
          error-message "vasiright interface must be created first and deleted last.";
        }
        must "not (starts-with(., 'BD-VIF')) or /ios:native/ios:interface/*[concat(local-name(), ios:name) = current()]" {
          error-message "BD-VIF interface must be created first and deleted last.";
        }
        type string;
      }
      container interface {
        status obsolete;
        uses rt_map_interface-deprecated-grouping;
      }
      container ip {
        description
          "IP specific information";
        container address {
          description
            "Specify IP address";
          leaf prefix-list {
            description
              "Specify prefix-list";
            type string;
          }
        }
        container default {
          description
            "Set default information";
          container global {
            description
              "global routing table";
            uses next-hop-address-grouping;
          }
          uses next-hop-address-default-grouping;
          container vrf {
            description
              "VRF name";
            list vrfs {
              key "vrf";
              leaf vrf {
                description
                  "WORD;;VRF name";
                type string;
              }
              uses next-hop-address-grouping;
            }
          }
        }
        leaf df {
          type uint8 {
            range "0..1";
          }
        }
        container global {
          description
            "global routing table";
          container next-hop {
            description
              "Next hop along path";
            leaf-list address {
              type inet:ipv4-address;
            }
            container verify-availability {
              description
                "Verify if nexthop is reachable";
              list sequence-id {
                key "seq-id";
                leaf seq-id {
                  description
                    "Sequence to insert into next-hop list";
                  type uint16 {
                    range "1..65535";
                  }
                }
                leaf ipv4-address {
                  description
                    "Next hop address";
                  type inet:ipv4-address;
                }
                leaf track {
                  description
                    "tracked object number";
                  type uint16 {
                    range "1..32767";
                  }
                }
              }
            }
          }
        }
        container next-hop {
          description
            "Next hop address";
          leaf-list address-ordered {
            description
              "IP address of next hop";
            ordered-by user;
            type union {
              type inet:ipv4-address;
              type enumeration {
                enum force;
              }
            }
          }
          leaf-list address {
            description
              "IP address of next hop (OBSOLETE)";
            status obsolete;
            type union {
              type inet:ipv4-address;
              type enumeration {
                enum force;
              }
            }
          }
          container dynamic {
            description
              "application dynamically sets next hop";
            leaf dhcp {
              description
                "DHCP learned next hop";
              type empty;
            }
          }
          container encapsulate {
            description
              "Encapsulation profile for VPN nexthop";
            leaf l3vpn {
              description
                "L3VPN";
              type string;
            }
          }
          leaf peer-address {
            description
              "Use peer address (for BGP only)";
            type empty;
          }
          container recursive {
            description
              "Recursive next-hop";
            leaf ipv4 {
              description
                "IP address of recursive next hop";
              type inet:ipv4-address;
            }
            leaf global {
              description
                "IP address of recursive next hop";
              type inet:ipv4-address;
            }
            container vrf {
              description
                "VRF name";
              list vrfs {
                key "vrf";
                leaf vrf {
                  description
                    "VRF name";
                  type string;
                }
                leaf ipv4 {
                  description
                    "IP address of recursive next hop";
                  type inet:ipv4-address;
                }
              }
            }
          }
          leaf self {
            description
              "Use self address (for BGP only)";
            type empty;
          }
          leaf unchanged {
            description
              "Propagate next hop unchanged";
            type empty;
          }
          container verify-availability {
            description
              "Verify if nexthop is reachable";
            presence "true";
            list ipv4 {
              key "ipv4";
              leaf ipv4 {
                description
                  "IP address of next hop";
                type inet:ipv4-address;
              }
              leaf range {
                type uint16 {
                  range "1..65535";
                }
              }
              leaf track {
                description
                  "set the next hop depending on the state of a tracked object";
                type uint16 {
                  range "1..32767";
                }
              }
            }
          }
        }
        container precedence {
          description
            "Set precedence field";
          presence "true";
          leaf precedence-value {
            type uint8 {
              range "0..7";
            }
          }
          leaf precedence-fields {
            type enumeration {
              enum critical;
              enum flash;
              enum flash-override;
              enum immediate;
              enum internet;
              enum network;
              enum priority;
              enum routine;
            }
          }
        }
        container qos-group {
          description
            "Set QOS Group ID";
          presence "true";
          leaf qos-id {
            type uint8 {
              range "0..99";
            }
          }
        }
        container tos_without_presence {
          description
            "Set type of service field without presence";
          leaf service-values {
            type uint8 {
              range "0..15";
            }
          }
          leaf tos-field {
            type enumeration {
              enum max-reliability;
              enum max-throughput;
              enum min-delay;
              enum min-monetary-cost;
              enum normal;
            }
          }
        }
        container tos {
          description
            "Set type of service field (OBSOLETE)";
          presence "true";
          status obsolete;
          leaf service-value {
            status obsolete;
            type uint8 {
              range "0..15";
            }
          }
          leaf tos-fields {
            status obsolete;
            type enumeration {
              enum max-reliability;
              enum max-throughput;
              enum min-delay;
              enum min-monetary-cost;
              enum normal;
            }
          }
        }
        container vrf {
          description
            "VRF name";
          list vrfs {
            key "vrf";
            leaf vrf {
              description
                "WORD;;VRF name";
              type string;
            }
            container next-hop {
              description
                "Next hop along path";
              leaf-list address {
                type inet:ipv4-address;
              }
              container verify-availability {
                description
                  "Verify if nexthop is reachable";
                presence "true";
                list ipv4 {
                  key "ipv4";
                  leaf ipv4 {
                    description
                      "IP address of next hop";
                    type inet:ipv4-address;
                  }
                  leaf range {
                    type uint16 {
                      range "1..65535";
                    }
                  }
                  leaf track {
                    description
                      "set the next hop depending on the state of a tracked object";
                    type uint16 {
                      range "1..32767";
                    }
                  }
                }
              }
            }
          }
        }
      }
      container ipv6 {
        description
          "IPv6 specific information";
        container address {
          description
            "IPv6 address";
          leaf plist {
            description
              "IPv6 prefix-list";
            type string;
          }
          leaf-list prefix-list {
            status obsolete;
            description
              "IPv6 prefix-list (OBSOLETE)";
            type string;
          }
        }
        container default {
          description
            "Set default information";
          container global {
            description
              "global routing table";
            leaf-list next-hop-address {
              ordered-by user;
              description
                "Default Next hop IPv6 address";
              type inet:ipv6-address;
            }
            leaf next-hop {
              status obsolete;
              description
                "Next hop along path (OBSOLETE)";
              type inet:ipv6-address;
            }
          }
          container next-hop {
            description
              "Next hop along path";
            leaf-list ipv6 {
              ordered-by user;
              description
                "Default next hop IPv6 address";
              type inet:ipv6-address;
            }
            list ipv6s {
              status obsolete;
              key "ipv6";
              leaf ipv6 {
                description
                  "Default next hop IPv6 address";
                type inet:ipv6-address;
                status obsolete;
              }
            }
            leaf next-hop-address {
              type inet:ipv6-address;
              status obsolete;
            }
          }
          list vrf {
            key "vrf";
            leaf vrf {
              description
                "VRF name";
              type string;
            }
            leaf-list next-hop {
              description
                "List entries of next-hop ipv6 addresses";
              type inet:ipv6-address;
            }
          }
          list dvrf {
            status obsolete;
            key "dvrf";
            leaf dvrf {
              status obsolete;
              description
                "VRF name";
              type string;
            }
            list dvrf0 {
              status obsolete;
              key "dvrf0";
              leaf dvrf0 {
                status obsolete;
                description
                  "VRF name";
                type string;
              }
              leaf next-hop {
                status obsolete;
                description
                  "Next hop along path";
                type empty;
              }
            }
          }
        }
        container global {
          description
            "global routing table";
          container next-hop {
            description
              "IPv6 Next hop";
            status obsolete;
            list nh-ipv6 {
              status obsolete;
              key "nh-ipv6";
              leaf nh-ipv6 {
                description
                  "Next hop address";
                status obsolete;
                type inet:ipv6-address;
              }
              leaf nh-ipv60 {
                description
                  "Next hop address";
                status obsolete;
                type inet:ipv6-address;
              }
            }
            leaf verify-availability {
              description
                "Next hop address";
              type inet:ipv6-address;
              status obsolete;
            }
          }
          container next-hop-conf {
            description
              "IPv6 Next hop";
            leaf-list ipv6-address {
              ordered-by user;
              description
                "Next hop address";
              type inet:ipv6-address;
            }
            container verify-availability {
              description
                "Verify if nexthop is reachable";
              list sequence-id {
                key "seq-id";
                leaf seq-id {
                  description
                    "Sequence to insert into next-hop list";
                  type uint16 {
                    range "1..65535";
                  }
                }
                leaf ipv6-address {
                  description
                    "Next hop address";
                  type inet:ipv6-address;
                }
                leaf track {
                  description
                    "tracked object number";
                  type uint16 {
                    range "1..32767";
                  }
                }
              }
            }
          }
        }
        container next-hop {
          description
            "IPv6 Next hop";
          leaf-list ipv6 {
            ordered-by user;
            description
              "Next hop IPv6 address";
            type inet:ipv6-address;
          }
          list nha-ipv6 {
            status obsolete;
            key "nha-ipv6";
            leaf nha-ipv6 {
              description
                "Next hop address";
              type inet:ipv6-address;
              status obsolete;
            }
            list nha-ipv60 {
              status obsolete;
              key "nha-ipv60";
              leaf nha-ipv60 {
                description
                  "Next hop address";
                type inet:ipv6-address;
                status obsolete;
              }
              leaf nh-ipv6 {
                description
                  "Next hop address";
                type inet:ipv6-address;
                status obsolete;
              }
            }
          }
          container encapsulate {
            description
              "Encapsulation profile for VPN nexthop";
            leaf l3vpn {
              description
                "Encapsulation profile name";
              type string;
            }
          }
          leaf peer-address {
            description
              "Use peer address (for BGP only)";
            type empty;
          }
          leaf recursive {
            description
              "IPv6 address of recursive next-hop (Deprecated)";
            status deprecated;
            type inet:ipv6-address;
          }
          container recursive_conf {
            description
              "IPv6 address of recursive next-hop";
            leaf ipv6 {
              description
                "IPv6 address of recursive next hop";
              type inet:ipv6-address;
            }
            container vrf {
              description
                "VRF name";
              list vrfs {
                key "vrf";
                leaf vrf {
                  description
                    "VRF name";
                  type leafref {
                    path "/ios:native/ios:vrf/ios:definition/ios:name";
                  }
                }
                leaf ipv6 {
                  description
                    "IPV6 address of recursive next hop";
                  type inet:ipv6-address;
                }
              }
            }
          }
          container verify-availability {
            description
              "Verify if nexthop is reachable";
            status obsolete;
            list va-ipv6 {
              status obsolete;
              key "va-ipv6";
              leaf va-ipv6 {
                status obsolete;
                description
                  "Next hop address";
                type inet:ipv6-address;
              }
              leaf seq-nh {
                status obsolete;
                description
                  "Sequence to insert into next-hop list";
                type uint16 {
                  range "1..65535";
                }
              }
            }
          }
          container verify-availability-conf {
            description
              "Verify if nexthop is reachable";
            list sequence-id {
              key "seq-id";
              leaf seq-id {
                description
                  "Sequence to insert into next-hop list";
                type uint16 {
                  range "1..65535";
                }
              }
              leaf ipv6-address {
                description
                  "Next hop address";
                type inet:ipv6-address;
              }
              leaf track {
                description
                  "tracked object number";
                type uint16 {
                  range "1..32767";
                }
              }
            }
          }
        }
        leaf precedence {
          description
            "Precedence value";
          type uint8 {
            range "0..7";
          }
        }
        list vrf {
          key "vrf";
          leaf vrf {
            description
              "VRF name";
            type string;
          }
          container next-hop {
            description
              "IPv6 Next hop";
            leaf-list ipv6 {
              description
                "List entries of next-hop ipv6 addresses";
              type inet:ipv6-address;
            }
            list verify-availability {
              description
                "Verify if nexthop is reachable";
              key "ipv6";
              leaf ipv6 {
                description
                  "IP address of next hop";
                type inet:ipv6-address;
              }
              leaf sequence {
                type uint16 {
                  range "1..65535";
                }
              }
              leaf track {
                description
                  "Set the next hop depending on the state
                   of a tracked object";
                must '../sequence';
                type uint16 {
                  range "1..32767";
                }
              }
            }
          }
        }
        list bvrf {
          status obsolete;
          key "bvrf";
          leaf bvrf {
            description
              "VRF name";
            type string;
            status obsolete;
          }
          list bvrf0 {
            status obsolete;
            key "bvrf0";
            leaf bvrf0 {
              status obsolete;
              description
                "VRF name";
              type string;
            }
            container next-hop {
              status obsolete;
              description
                "IPv6 Next hop";
              leaf bipv6 {
                status obsolete;
                description
                  "Next hop address";
                type inet:ipv6-address;
              }
              leaf verify-availability {
                status obsolete;
                description
                  "Verify if nexthop is reachable";
                type empty;
              }
            }
          }
        }
      }
      container large-community {
        status obsolete;
        description
          "BGP large community attribute (OBSOLETE - please use route-map configuration in Cisco-IOS-XE-bgp.yang)";
        choice large-community-choice {
          status obsolete;
          leaf none {
            status obsolete;
            description
              "No large community attribute (OBSOLETE - please use route-map configuration in Cisco-IOS-XE-bgp.yang)";
            type empty;
          }
          container large-community-value {
            status obsolete;
            description
              "large-community-format (OBSOLETE - please use route-map configuration in Cisco-IOS-XE-bgp.yang)";
            leaf-list large-community-list {
              status obsolete;
              description
                "large community number in aa:bb:cc format (OBSOLETE - please use route-map configuration in Cisco-IOS-XE-bgp.yang)";
              ordered-by user;
              type ios-types:large-community-number-type;
            }
            leaf additive {
              status obsolete;
              description
                "Add to the existing community (OBSOLETE - please use route-map configuration in Cisco-IOS-XE-bgp.yang)";
              when '../large-community-list';
              type empty;
            }
          }
        }
      }
      container largecomm-list {
        status obsolete;
        description
          "set BGP large community list (for deletion) (OBSOLETE - please use route-map configuration in Cisco-IOS-XE-bgp.yang)";
        presence "true";
        choice largecomm-list-choice {
          status obsolete;
          mandatory true;
          leaf largecomm-list-standard {
            status obsolete;
            description
              "Community-list number (standard) (OBSOLETE - please use route-map configuration in Cisco-IOS-XE-bgp.yang)";
            type uint16 {
              range "1..99";
            }
          }
          leaf largecomm-list-expanded {
            status obsolete;
            description
              "Community-list number (expanded) (OBSOLETE - please use route-map configuration in Cisco-IOS-XE-bgp.yang)";
            type uint16 {
              range "100..500";
            }
          }
          leaf largecomm-list-name {
            status obsolete;
            description
              "Large-Community-list name (OBSOLETE - please use route-map configuration in Cisco-IOS-XE-bgp.yang)";
            type string;
          }
        }
        leaf delete {
          status obsolete;
          description
            "Delete matching communities (OBSOLETE - please use route-map configuration in Cisco-IOS-XE-bgp.yang)";
          mandatory true;
          type empty;
        }
      }
      container level {
        description
          "Where to import route";
        leaf level-1 {
          description
            "Import into a level-1 area";
          type empty;
        }
        leaf level-1-2 {
          description
            "Import into level-1 and level-2";
          type empty;
        }
        leaf level-2 {
          description
            "Import into level-2 sub-domain";
          type empty;
        }
        leaf nssa-only {
          description
            "Import only into OSPF NSSA areas and don't propagate";
          type empty;
        }
      }
      container lisp {
        description
          "Locator ID Separation Protocol specific information";
        leaf locator-set {
          description
            "The name of the locator set";
          type string;
        }
      }
      leaf local-preference {
        status obsolete;
        description
          "Preference value (OBSOLETE - please use route-map configuration in Cisco-IOS-XE-bgp.yang)";
        type uint32 {
          range "0..4294967295";
        }
      }
      container metric {
        description
          "Metric value for destination routing protocol";
        choice metric-choice {
          case relative-value {
            leaf metric-change {
              description
                "+/-<metric>;;Add or subtract metric";
              type string {
                pattern '(\+|-)\d{1,10}';
              }
            }
          }
          case absolute-values {
            container values {
              leaf value {
                description
                  "Metric value or Bandwidth in Kbits per second";
                type uint32;
              }
              leaf delay {
                description
                  "EIGRP delay metric, in 10 microsecond units";
                when '../value';
                type string {
                  pattern '(\+|-)?\d{1,10}';
                }
              }
              leaf reliability {
                description
                  "EIGRP reliability metric where 255 is 100% reliable";
                when '../delay';
                must '../loading and ../MTU';
                type uint8;
              }
              leaf loading {
                description
                  "EIGRP Effective bandwidth metric (Loading) where 255 is 100% loaded";
                when '../delay';
                must '../reliability and ../MTU';
                type uint8 {
                  range "1..255";
                }
              }
              leaf MTU {
                description
                  "EIGRP MTU of the path";
                when '../delay';
                must '../reliability and ../loading';
                type uint32 {
                  range "1..4294967295";
                }
              }
            }
          }
        }
      }
      leaf metric-type {
        description
          "Type of metric for destination routing protocol";
        type enumeration {
          enum external;
          enum internal;
          enum type-1;
          enum type-2;
        }
      }
      leaf mpls-label {
        description
          "Set MPLS label for prefix";
        type empty;
      }
      container nlri {
        status obsolete;
        description
          "BGP NLRI type (OBSOLETE - please use route-map configuration in Cisco-IOS-XE-bgp.yang)";
        leaf unicast {
          status obsolete;
          description
            "Used in unicast RIB (OBSOLETE - please use route-map configuration in Cisco-IOS-XE-bgp.yang)";
          type empty;
        }
        leaf multicast {
          status obsolete;
          description
            "Used in multicast RIB (OBSOLETE - please use route-map configuration in Cisco-IOS-XE-bgp.yang)";
          type empty;
        }
      }
      leaf weight {
        status obsolete;
        description
          "BGP weight for routing table (OBSOLETE - please use route-map configuration in Cisco-IOS-XE-bgp.yang)";
        type uint32 {
          range "0..65535";
        }
      }
      leaf omp-tag {
        if-feature "ios-features:omp";
        description
          "OMP tag value for destination routing protocol";
        type uint32;
      }
      container origin {
        status obsolete;
        description
          "BGP origin code (OBSOLETE - please use route-map configuration in Cisco-IOS-XE-bgp.yang)";
        leaf origin-value {
          status obsolete;
          type enumeration {
            enum igp;
            enum incomplete;
          }
        }
        leaf egp {
          status obsolete;
          description
            "remote EGP (OBSOLETE - please use route-map configuration in Cisco-IOS-XE-bgp.yang)";
          type uint32 {
            range "0..65535";
          }
        }
      }
      leaf tag-val {
        description
          "Tag value for destination routing protocol";
        type union {
          type uint32 {
            range "0..4294967295";
          }
          type inet:ipv4-address;
        }
      }
      container tag {
        status obsolete;
        description
          "Tag value for destination routing protocol (OBSOLETE - please use tag-val)";
        leaf tag-val {
          status obsolete;
          description
            "Tag value (OBSOLETE - please use tag-val)";
          type uint32 {
            range "0..4294967295";
          }
        }
        leaf tag-ipv4 {
          status obsolete;
          description
            "Tag value(dotted decimal format) (OBSOLETE - please use tag-val)";
          type inet:ipv4-address;
        }
      }
      leaf traffic-index {
        description
          "Bucket number";
        type uint8 {
          range "1..64";
        }
      }
      leaf vrf {
        description
          "VPN Routing/Forwarding instance name";
        type string;
      }
    }
    container match {
      description
        "Match values from routing table";
      container additional-paths {
        status obsolete;
        description
          "BGP Add-Path match policies (OBSOLETE - please use route-map configuration in Cisco-IOS-XE-bgp.yang)";
        container advertise-set {
          status obsolete;
          description
            "BGP Add-Path advertise-set policy (OBSOLETE - please use route-map configuration in Cisco-IOS-XE-bgp.yang)";
          container all {
            status obsolete;
            description
              "BGP Add-Path advertise all paths (OBSOLETE - please use route-map configuration in Cisco-IOS-XE-bgp.yang)";
            presence "true";
            leaf best {
              status obsolete;
              description
                "BGP Add-Path best n paths to advertise (OBSOLETE - please use route-map configuration in Cisco-IOS-XE-bgp.yang)";
              type uint8 {
                range "1..3";
              }
            }
            leaf best-range {
              status obsolete;
              description
                "BGP Add-Path best paths to advertise (lower limit) (OBSOLETE - please use route-map configuration in Cisco-IOS-XE-bgp.yang)";
              type uint8 {
                range "1..3";
              }
            }
            container group-best {
              status obsolete;
              description
                "BGP Add-Path advertise group-best path (OBSOLETE - please use route-map configuration in Cisco-IOS-XE-bgp.yang)";
              presence "true";
              leaf best {
                status obsolete;
                description
                  "BGP Add-Path advertise best n paths (OBSOLETE - please use route-map configuration in Cisco-IOS-XE-bgp.yang)";
                type empty;
              }
              leaf best-range {
                status obsolete;
                description
                  "BGP Add-Path advertise best paths (range m to n) (OBSOLETE - please use route-map configuration in Cisco-IOS-XE-bgp.yang)";
                type empty;
              }
            }
          }
          container best {
            status obsolete;
            description
              "BGP Add-Path advertise best n paths (OBSOLETE - please use route-map configuration in Cisco-IOS-XE-bgp.yang)";
            list best-range {
              status obsolete;
              key "best-range";
              leaf best-range {
                status obsolete;
                description
                  "BGP Add-Path best n paths to advertise (OBSOLETE - please use route-map configuration in Cisco-IOS-XE-bgp.yang)";
                type uint8 {
                  range "1..3";
                }
              }
              leaf all {
                status obsolete;
                description
                  "BGP Add-Path advertise all paths (OBSOLETE - please use route-map configuration in Cisco-IOS-XE-bgp.yang)";
                type empty;
              }
              leaf group-best {
                status obsolete;
                description
                  "BGP Add-Path advertise group-best path (OBSOLETE - please use route-map configuration in Cisco-IOS-XE-bgp.yang)";
                type empty;
              }
            }
          }
          container best-range {
            status obsolete;
            description
              "BGP Add-Path advertise best paths (range m to n) (OBSOLETE - please use route-map configuration in Cisco-IOS-XE-bgp.yang)";
            list adv-path {
              status obsolete;
              key "adv-path";
              leaf adv-path {
                status obsolete;
                description
                  "BGP Add-Path best paths to advertise (lower limit) (OBSOLETE - please use route-map configuration in Cisco-IOS-XE-bgp.yang)";
                type uint8 {
                  range "1..3";
                }
              }
              leaf adv-path0 {
                status obsolete;
                description
                  "BGP Add-Path best paths to advertise (upper limit) (OBSOLETE - please use route-map configuration in Cisco-IOS-XE-bgp.yang)";
                type uint8 {
                  range "1..3";
                }
              }
            }
          }
          container group-best {
            status obsolete;
            description
              "BGP Add-Path advertise group-best path (OBSOLETE - please use route-map configuration in Cisco-IOS-XE-bgp.yang)";
            presence "true";
            leaf all {
              status obsolete;
              description
                "BGP Add-Path advertise all paths (OBSOLETE - please use route-map configuration in Cisco-IOS-XE-bgp.yang)";
              type empty;
            }
            leaf best {
              status obsolete;
              description
                "BGP Add-Path best n paths to advertise (OBSOLETE - please use route-map configuration in Cisco-IOS-XE-bgp.yang)";
              type uint8 {
                range "1..3";
              }
            }
            leaf best-range {
              status obsolete;
              description
                "BGP Add-Path best paths to advertise (lower limit) (OBSOLETE - please use route-map configuration in Cisco-IOS-XE-bgp.yang)";
              type uint8 {
                range "1..3";
              }
            }
          }
        }
      }
      container as-path {
        status obsolete;
        description
          "Match BGP AS path list (OBSOLETE - please use route-map configuration in Cisco-IOS-XE-bgp.yang)";
        leaf-list access-list {
          status obsolete;
          description
            "AS path access-list (OBSOLETE - please use route-map configuration in Cisco-IOS-XE-bgp.yang)";
          type uint16 {
            range "1..500";
          }
        }
      }
      container clns {
        description
          "CLNS information";
        leaf-list name {
          description
            "Named clna list";
          type string;
        }
      }
      container community {
        status obsolete;
        description
          "Match BGP community list (OBSOLETE - please use route-map configuration in Cisco-IOS-XE-bgp.yang)";
        leaf-list community-list {
          status obsolete;
          description
            "Named Access List (OBSOLETE - please use route-map configuration in Cisco-IOS-XE-bgp.yang)";
          ordered-by user;
          type string;
        }
        leaf-list name {
          description
            "Named Access List (OBSOLETE- please use community-list in Cisco-IOS-XE-bgp.yang)";
          status obsolete;
          type string;
        }
      }
      container extcommunity {
        status obsolete;
        description
          "Match BGP/VPN extended community list (OBSOLETE - please use route-map configuration in Cisco-IOS-XE-bgp.yang)";
        leaf-list extcommunity-list {
          status obsolete;
          description
            "Named Access List (OBSOLETE - please use route-map configuration in Cisco-IOS-XE-bgp.yang)";
          ordered-by user;
          type string;
        }
        leaf-list name {
          description
            "Named Access List (OBSOLETE- please use extcommunity-list in Cisco-IOS-XE-bgp.yang)";
          status obsolete;
          type string;
        }
      }
      container interface {
        description
          "SPAN source interface";
        leaf-list interface {
          type string;
        }
      }
      container ip {
        description
          "IP specific information";
        container address {
          description
            "Match address of route or match packet";
          uses ip-access-list-grouping;
        }
        container flowspec {
          description
            "Match address of route";
          container dest-pfx {
            description
              "Match dest prefix component of flowspec prefix";
            uses ip-access-list-grouping;
          }
          container src-pfx {
            description
              "Match source prefix component of flowspec prefix";
            uses ip-access-list-grouping;
          }
        }
        container next-hop {
          description
            "Match next-hop address of route";
          uses ip-access-list-grouping;
        }
        container redistribution-source {
          description
            "route redistribution source (EIGRP only)";
          uses ip-access-list-grouping;
        }
        container route-source {
          description
            "Match advertising source address of route";
          uses ip-access-list-grouping;
        }
      }
      container ipv6 {
        description
          "IPv6 specific information";
        container address {
          description
            "Match address of route";
          uses ipv6-access-list-grouping;
        }
        container flowspec {
          description
            "Match address of route";
          container dest-pfx {
            description
              "Match dest prefix component of flowspec prefix";
            uses ipv6-access-list-grouping;
          }
          container src-pfx {
            description
              "Match source prefix component of flowspec prefix";
            uses ipv6-access-list-grouping;
          }
        }
        container next-hop {
          description
            "Match next-hop address of route";
          uses ipv6-access-list-grouping;
        }
        container route-source {
          description
            "Match advertising source address of route";
          uses ipv6-access-list-grouping;
        }
      }
      container large-community {
        status obsolete;
        description
          "Match BGP large-community list (OBSOLETE - please use route-map configuration in Cisco-IOS-XE-bgp.yang)";
        leaf-list name {
          status obsolete;
          description
            "Large community-list name or number (OBSOLETE - please use route-map configuration in Cisco-IOS-XE-bgp.yang)";
          ordered-by user;
          type string;
        }
        leaf exact-match {
          status obsolete;
          description
            "Do exact matching of large communities (OBSOLETE - please use route-map configuration in Cisco-IOS-XE-bgp.yang)";
          when '../name';
          type empty;
        }
      }
      container length {
        description
          "Packet length";
        list lengths {
          max-elements 1;
          key "min-len max-len";
          leaf min-len {
            description
              "Minimum packet length";
            type uint32 {
              range "0..2147483647";
            }
          }
          leaf max-len {
            description
              "Maximum packet length";
            type uint32 {
              range "0..2147483647";
            }
          }
        }
      }
      container traffic-steering {
        if-feature "ios-features:pbr-sbit-switching";
        description
          "traffic-steering selection";
        leaf service-selector {
          description
            "Service selector value";
          type uint8 {
            range "1..255";
          }
        }
      }
      container local-preference {
        status obsolete;
        description
          "Local preference for route (OBSOLETE - please use route-map configuration in Cisco-IOS-XE-bgp.yang)";
        leaf-list values {
          status obsolete;
          type uint32 {
            range "0..4294967295";
          }
        }
      }
      container mdt-group {
        description
          "Match routes corresponding to MDT group";
        leaf-list name {
          description
            "IP Access List";
          type string;
        }
      }
      container metric {
        description
          "Match metric of route";
        leaf-list metric-value-number-list {
          ordered-by user;
          description
            "Match Metric Value";
          type uint32 {
            range "1..4294967295";
          }
        }
        leaf metric-value-number {
          status obsolete;
          type uint32 {
            range "1..4294967295";
          }
        }
        leaf metric-value {
          status obsolete;
          type string;
        }
        leaf-list external-number-list {
          ordered-by user;
          description
            "Match External Metric Value";
          type uint32 {
            range "1..4294967295";
          }
        }
        leaf external-number {
          status obsolete;
          description
            "match route using external protocol metric (OBSOLETE)";
          type uint32 {
            range "1..4294967295";
          }
        }
        leaf external {
          status obsolete;
          description
            "match route using external protocol metric (OBSOLETE)";
          type string;
        }
      }
      leaf mpls-label {
        description
          "Match routes which have MPLS labels";
        type empty;
      }
      container policy-list {
        description
          "Match IP policy list";
        leaf-list policy-map-names {
          description
            "IP Policy map name";
          type string;
        }
      }
      leaf omp-tag {
        if-feature "ios-features:omp";
        description
          "OMP Tag value for route match";
        type uint32;
      }
      container route-type {
        description
          "Match route-type of route";
        container external {
          description
            "external route (BGP, EIGRP and OSPF type 1/2)";
          presence "true";
          leaf type-1 {
            description
              "OSPF external type 1 route";
            type empty;
          }
          leaf type-2 {
            description
              "OSPF external type 2 route";
            type empty;
          }
        }
        leaf internal {
          description
            "internal route (including OSPF intra/inter area)";
          type empty;
        }
        leaf level-1 {
          description
            "IS-IS level-1 route";
          type empty;
        }
        leaf level-2 {
          description
            "IS-IS level-2 route";
          type empty;
        }
        leaf local {
          status obsolete;
          description
            "locally generated route (OBSOLETE - please use route-map configuration in Cisco-IOS-XE-bgp.yang)";
          type empty;
        }
        container nssa-external {
          description
            "nssa-external route (OSPF type 1/2)";
          presence "true";
          leaf type-1 {
            description
              "OSPF external type 1 route";
            type empty;
          }
          leaf type-2 {
            description
              "OSPF external type 2 route";
            type empty;
          }
        }
      }
      container rpki {
        description
          "Match RPKI state of route";
        leaf invalid {
          description
            "RPKI Invalid State";
          type empty;
        }
        leaf not-found {
          description
            "RPKI Not Found State";
          type empty;
        }
        leaf valid {
          description
            "RPKI Valid State";
          type empty;
        }
      }
      container source-protocol {
        description
          "Match source-protocol of route";
        presence "true";
        leaf-list bgp {
          description
            "Border Gateway Protocol (BGP)";
          type ios-types:bgp-as-number-type;
        }
        leaf connected {
          description
            "Connected";
          type empty;
        }
        leaf-list eigrp {
          description
            "Border Gateway Protocol (BGP)";
          type string;
        }
        leaf isis {
          description
            "ISO IS-IS";
          type empty;
        }
        leaf lisp {
          description
            "Locator ID Separation Protocol (LISP)";
          type empty;
        }
        leaf mobile {
          description
            "Mobile routes";
          type empty;
        }
        leaf-list ospf {
          description
            "Open Shortest Path First (OSPF)";
          type string;
        }
        leaf-list ospfv3 {
          description
            "OSPFv3";
          type string;
        }
        leaf rip {
          description
            "Routing Information Protocol (RIP)";
          type empty;
        }
        leaf static {
          description
            "Static routes";
          type empty;
        }
        leaf omp {
          if-feature "ios-features:omp";
          description
            "Overlay Management Protocol (OMP)";
          type empty;
        }
        leaf nat-route {
          if-feature "ios-features:sdwan";
          description
            "NAT Route Protocol";
          type empty;
        }
      }
      container tag {
        description
          "Match tag of route";
        leaf-list tag-val {
          description
            "Tag value for destination routing protocol";
          type union {
            type uint32 {
              range "0..4294967295";
            }
            type inet:ipv4-address;
          }
        }
        leaf-list tag_value {
          status obsolete;
          description
            "Tag value (OBSOLETE- please use tag-val)";
          type uint32 {
            range "0..4294967295";
          }
        }
        leaf-list ipv4-address {
          status obsolete;
          description
            "<A.B.C.D>;;Tag value(dotted decimal format) (OBSOLETE - please use tag-val)";
          type inet:ipv4-address;
        }
        container list {
          description
            "Route Tag List";
          leaf-list tag-names {
            description
              "Tag list name";
            type string;
          }
        }
      }
      leaf track {
        description
          "tracking object";
        type uint16 {
          range "1..32767";
        }
      }
    }
    container continue {
      description
        "Continue on a different entry within the route-map";
      presence "true";
      leaf sequence-number {
        description
          "Route-map entry sequence number";
        type uint16 {
          range "0..65535";
        }
      }
    }
  }

  grouping config-route-map-grouping {
    list route-map-seq {
      key "ordering-seq";
      leaf ordering-seq {
        description
          "Ordering seq tag";
        type string;
      }
      leaf operation {
        description
          "Route map permit/deny set operations";
        default "permit";
        type enumeration {
          enum deny;
          enum permit;
        }
      }
      leaf sequence {
        default "10";
        type uint16 {
          range "0..65535";
        }
      }
      uses config-route-map-common-grouping;
    }
    list route-map-without-order-seq {
      description
        "Sequence to insert to/delete from existing route-map entry";
      key "seq_no";
      leaf seq_no {
        type uint16 {
          range "0..65535";
        }
      }
      leaf operation {
        description
          "Route map permit/deny set operations";
        default "permit";
        type enumeration {
          enum deny;
          enum permit;
        }
      }
      uses config-route-map-common-grouping;
    }
  }

  augment "/ios:native" {
    uses config-named-ordering-route-map-grouping;
  }

  augment "/ios:native/ios:route-map" {
    uses config-route-map-grouping;
  }
}
