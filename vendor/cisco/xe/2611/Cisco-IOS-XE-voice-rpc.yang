module Cisco-IOS-XE-voice-rpc {
  yang-version 1.1;
  namespace "http://cisco.com/ns/yang/Cisco-IOS-XE-voice-rpc";
  prefix voice-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Voice RPC.
     Copyright (c) 2022 by Cisco Systems, Inc.
     All rights reserved.";

  revision 2022-11-01 {
    description
      "- Update yang-version to 1.1
       - Adding SGW sync start support.";
    reference
      "1.1.0";
    cisco-semver:module-version "1.1.0";
  }
  revision 2022-07-01 {
    description
      "Initial revision";
    reference
      "1.0.0";
    cisco-semver:module-version "1.0.0";
  }

  typedef enm-voice-register-webex-sgw {
    type enumeration {
      enum sync-done {
        value 2;
        description
          "Data sync completed in Webex-SGW mode";
      }
      enum sync-start {
        value 3;
        description
          "Start data sync in Webex-SGW mode";
      }
    }
    description
      "Webex SGW grouping";
  }

  grouping voice-register {
    description
      "Voice register grouping";
    leaf webex-sgw {
      type voice-rpc:enm-voice-register-webex-sgw;
      mandatory true;
      description
        "Voice register webex survivability gateway mode";
    }
  }

  rpc voice-register {
    description
      "Voice register RPC to indicate Webex-SGW data sync completion event";
    input {
      uses voice-rpc:voice-register;
    }
  }
}
