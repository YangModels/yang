module Cisco-IOS-XE-red-app-events {
  yang-version 1.1;
  namespace "http://cisco.com/ns/yang/Cisco-IOS-XE-red-app-events";
  prefix red-app-events;

  import Cisco-IOS-XE-red-app-common-types {
    prefix red-app-comm-ios-xe-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for redundancy application notification data.
     Copyright (c) 2024 by Cisco Systems, Inc.
     All rights reserved.";

  revision 2024-07-01 {
    description
      "Initial revision";
    reference
      "1.0.0";
    cisco-semver:module-version "1.0.0";
  }

  grouping red-app-events {
    description
      "Redundancy group information";
    leaf rg-id {
      type uint32;
      description
        "Key for application group";
    }
    leaf sys-time {
      type yang:date-and-time;
      description
        "Time when the last role change occurred";
    }
    leaf site-id {
      type uint32;
      description
        "Site identifier";
    }
    leaf sys-ip-addr {
      type inet:ip-address;
      description
        "Local system address";
    }
    leaf role {
      type red-app-comm-ios-xe-types:rg-app-role;
      description
        "Redundancy application role";
    }
  }

  notification red-event {
    description
      "Redundancy application group role notification";
    uses red-app-events:red-app-events;
  }
}
