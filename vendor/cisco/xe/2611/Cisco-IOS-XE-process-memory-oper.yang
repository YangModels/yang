module Cisco-IOS-XE-process-memory-oper {
  yang-version 1.1;
  namespace "http://cisco.com/ns/yang/Cisco-IOS-XE-process-memory-oper";
  prefix process-memory-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring memory usage of processes in a Network Element.
     Copyright (c) 2016-2017, 2019, 2022 by Cisco Systems, Inc.
     All rights reserved.";

  revision 2022-11-01 {
    description
      "Update yang-version to 1.1";
    reference
      "1.2.0";
    cisco-semver:module-version "1.2.0";
  }
  revision 2019-05-01 {
    description
      "Added semantic version";
    reference
      "1.1.0";
    cisco-semver:module-version "1.1.0";
  }
  revision 2017-02-07 {
    description
      "Initial revision";
    reference
      "1.0.0";
    cisco-semver:module-version "1.0.0";
  }

  grouping process-memory-key {
    description
      "Unique process identifier";
    leaf pid {
      type uint32;
      description
        "Process-ID of the process.";
    }
    leaf name {
      type string;
      description
        "The name of the process.";
    }
  }

  grouping process-memory-usage {
    description
      "Memory usage information for a given process";
    leaf tty {
      type uint16;
      description
        "TTY bound to by the process.";
    }
    leaf allocated-memory {
      type uint64;
      units "bytes";
      description
        "Total memory allocated to this process (bytes)";
    }
    leaf freed-memory {
      type uint64;
      units "bytes";
      description
        "Total memory freed by this process (bytes)";
    }
    leaf holding-memory {
      type uint64;
      units "bytes";
      description
        "Total memory currently held by this process (bytes)";
    }
    leaf get-buffers {
      type uint32;
      description
        "Get Buffers of this process (bytes)";
    }
    leaf ret-buffers {
      type uint32;
      description
        "Return Buffers of this process (bytes)";
    }
  }

  container memory-usage-processes {
    config false;
    description
      "Data nodes for System wide Process Memory Statistics.";
    list memory-usage-process {
      key "pid name";
      description
        "The list of software processes on the device.";
      uses process-memory-ios-xe-oper:process-memory-key;
      uses process-memory-ios-xe-oper:process-memory-usage;
    }
  }
}
