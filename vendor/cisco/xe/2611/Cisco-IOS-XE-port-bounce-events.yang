module Cisco-IOS-XE-port-bounce-events {
  yang-version 1.1;
  namespace "http://cisco.com/ns/yang/Cisco-IOS-XE-port-bounce-events";
  prefix port-bounce-ios-xe-events;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2024 by Cisco Systems, Inc.
     All rights reserved.";

  revision 2024-07-01 {
    description
      "Initial revision";
    reference
      "1.0.0";
    cisco-semver:module-version "1.0.0";
  }

  typedef port-bounce-status {
    type enumeration {
      enum pb-st-in-prog {
        value 0;
        description
          "Port bounce has been initiated.";
      }
      enum pb-st-success {
        value 1;
        description
          "Interface has successfully finished bouncing.";
      }
      enum pb-st-fail {
        value 2;
        description
          "Interface has failed to complete bounce and
           the operation has been stopped.";
      }
    }
    description
      "Status of port bounce operation";
  }

  typedef port-bounce-error-types {
    type enumeration {
      enum pb-err-no-err {
        value 0;
        description
          "No error seen during port bounce.";
      }
      enum pb-err-if-shut-config {
        value 1;
        description
          "The user has shutdown the interface via configuration.
           This has caused port bounce operation to stop as
           configuration takes priority.";
      }
      enum pb-err-dev-err {
        value 2;
        description
          "There is an unknown error on device which caused the
           port bounce operation to fail.";
      }
    }
    description
      "Error codes for port bounce";
  }

  grouping port-bounce-notif-fields {
    description
      "Notification field for port bounce";
    leaf if-name {
      type string;
      description
        "Name of the interface";
    }
    leaf status {
      type port-bounce-ios-xe-events:port-bounce-status;
      description
        "Status of the port bounce operation";
    }
    leaf err-code {
      type port-bounce-ios-xe-events:port-bounce-error-types;
      description
        "Reason for port bounce to fail";
    }
  }

  notification port-bounce-event {
    description
      "Notification for port bounce event";
    uses port-bounce-ios-xe-events:port-bounce-notif-fields;
  }
}
