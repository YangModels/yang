module Cisco-IOS-XE-object-group {
  yang-version 1.1;
  namespace "http://cisco.com/ns/yang/Cisco-IOS-XE-object-group";
  prefix ios-og;

  import cisco-semver {
    prefix cisco-semver;
  }
  import Cisco-IOS-XE-types {
    prefix ios-types;
  }
  import Cisco-IOS-XE-native {
    prefix ios;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Object Group Yang model.
     Copyright (c) 2016-2019 by Cisco Systems, Inc.
     All rights reserved.";

  revision 2026-02-01 {
    description
      "- Added support for eq for source and range for destination under ipv6 OG";
    cisco-semver:module-version "4.2.0";
  }
  revision 2025-07-01 {
    description
      "- Added new containers under object group v6 service grouping model";
    cisco-semver:module-version "4.1.0";
  }
  revision 2025-03-01 {
    description
      "- Moved deprecated nodes to obsolete ";
    cisco-semver:module-version "4.0.0";
  }
  revision 2024-07-01 {
    description
      "- Added knob option and enable leaf";
    cisco-semver:module-version "3.4.0";
  }
  revision 2024-03-01 {
    description
      "- Added udp ipv6 and tcp leaves to v6 service og model";
    cisco-semver:module-version "3.3.0";
  }
  revision 2023-11-01 {
    description
      "- New v6 service OG model";
    cisco-semver:module-version "3.2.0";
  }
  revision 2022-11-01 {
    description
      "- Update yang-version to 1.1
       - Deprecated tag and introduced tags as leaf-list for SGT (object-group security)";
    cisco-semver:module-version "3.1.0";
  }
  revision 2021-11-01 {
    description
      "-Added new containers for udp-src-dst-port-list with operators";
    cisco-semver:module-version "3.0.1";
  }
  revision 2021-03-01 {
    description
      "- Added new containers for TCP port list
       - Added support for tcp source port and range list
       - Added new containers for UDP port list, source port list and range list
       - Added new containers for TCP-UDP port list
       - Added support for tcp-udp source port list and range list configuration without operator";
    cisco-semver:module-version "2.3.0";
  }
  revision 2020-11-01 {
    description
      "- Added support of Geolocation Object Group for 17.4.1";
    cisco-semver:module-version "2.2.0";
  }
  revision 2020-03-01 {
    description
      "- Added support for FQDN ACL";
    cisco-semver:module-version "2.1.0";
  }
  revision 2019-11-01 {
    description
      "- Added must constraint for object-group v4 network
       - Changes for object-group v6-network";
    cisco-semver:module-version "2.0.0";
  }
  revision 2019-07-01 {
    description
      "Establish semantic version baseline";
    cisco-semver:module-version "1.0.0";
  }
  revision 2018-11-07 {
    description
      "Cleanup spelling errors in description statements";
  }
  revision 2018-10-03 {
    description
      "Fix protocol icmp, tcp and udp able to standalone";
  }
  revision 2018-10-01 {
    description
      "Fix not being able to configure multiple protocol numbers and names";
  }
  revision 2018-06-24 {
    description
      "Refactor source port service object-group support";
  }
  revision 2018-06-20 {
    description
      "Add source port support to service object-group";
  }
  revision 2017-07-31 {
    description
      "Support multiple-host under object group network";
  }
  revision 2017-02-07 {
    description
      "Initial revision";
  }

  typedef object-group-port-operator {
    type enumeration {
      enum eq;
      enum gt;
      enum lt;
    }
  }

  typedef alpha-3-country-code-type {
    type enumeration {
      enum ABW;
      enum AFG;
      enum AGO;
      enum AIA;
      enum ALA;
      enum ALB;
      enum AND;
      enum ANT;
      enum ARE;
      enum ARG;
      enum ARM;
      enum ASM;
      enum ATA;
      enum ATF;
      enum ATG;
      enum AUS;
      enum AUT;
      enum AZE;
      enum BDI;
      enum BEL;
      enum BEN;
      enum BES;
      enum BFA;
      enum BGD;
      enum BGR;
      enum BHR;
      enum BHS;
      enum BIH;
      enum BLM;
      enum BLR;
      enum BLZ;
      enum BMU;
      enum BOL;
      enum BRA;
      enum BRB;
      enum BRN;
      enum BTN;
      enum BVT;
      enum BWA;
      enum CAF;
      enum CAN;
      enum CCK;
      enum CHE;
      enum CHL;
      enum CHN;
      enum CIV;
      enum CMR;
      enum COD;
      enum COG;
      enum COK;
      enum COL;
      enum COM;
      enum CPV;
      enum CRI;
      enum CUB;
      enum CUW;
      enum CXR;
      enum CYM;
      enum CYP;
      enum CZE;
      enum DEU;
      enum DJI;
      enum DMA;
      enum DNK;
      enum DOM;
      enum DZA;
      enum ECU;
      enum EGY;
      enum ERI;
      enum ESH;
      enum ESP;
      enum EST;
      enum ETH;
      enum FIN;
      enum FJI;
      enum FLK;
      enum FRA;
      enum FRO;
      enum FSM;
      enum GAB;
      enum GBR;
      enum GEO;
      enum GGY;
      enum GHA;
      enum GIB;
      enum GIN;
      enum GLP;
      enum GMB;
      enum GNB;
      enum GNQ;
      enum GRC;
      enum GRD;
      enum GRL;
      enum GTM;
      enum GUF;
      enum GUM;
      enum GUY;
      enum HKG;
      enum HMD;
      enum HND;
      enum HRV;
      enum HTI;
      enum HUN;
      enum IDN;
      enum IMN;
      enum IND;
      enum IOT;
      enum IRL;
      enum IRN;
      enum IRQ;
      enum ISL;
      enum ISR;
      enum ITA;
      enum JAM;
      enum JEY;
      enum JOR;
      enum JPN;
      enum KAZ;
      enum KEN;
      enum KGZ;
      enum KHM;
      enum KIR;
      enum KNA;
      enum KOR;
      enum KWT;
      enum LAO;
      enum LBN;
      enum LBR;
      enum LBY;
      enum LCA;
      enum LIE;
      enum LKA;
      enum LSO;
      enum LTU;
      enum LUX;
      enum LVA;
      enum MAC;
      enum MAF;
      enum MAR;
      enum MCO;
      enum MDA;
      enum MDG;
      enum MDV;
      enum MEX;
      enum MHL;
      enum MKD;
      enum MLI;
      enum MLT;
      enum MMR;
      enum MNE;
      enum MNG;
      enum MNP;
      enum MOZ;
      enum MRT;
      enum MSR;
      enum MTQ;
      enum MUS;
      enum MWI;
      enum MYS;
      enum MYT;
      enum NAM;
      enum NCL;
      enum NER;
      enum NFK;
      enum NGA;
      enum NIC;
      enum NIU;
      enum NLD;
      enum NOR;
      enum NPL;
      enum NRU;
      enum NZL;
      enum OMN;
      enum PAK;
      enum PAN;
      enum PCN;
      enum PER;
      enum PHL;
      enum PLW;
      enum PNG;
      enum POL;
      enum PRI;
      enum PRK;
      enum PRT;
      enum PRY;
      enum PSE;
      enum PYF;
      enum QAT;
      enum REU;
      enum ROU;
      enum RUS;
      enum RWA;
      enum SAU;
      enum SDN;
      enum SEN;
      enum SGP;
      enum SGS;
      enum SHN;
      enum SJM;
      enum SLB;
      enum SLE;
      enum SLV;
      enum SMR;
      enum SOM;
      enum SPM;
      enum SRB;
      enum SSD;
      enum STP;
      enum SUR;
      enum SVK;
      enum SVN;
      enum SWE;
      enum SWZ;
      enum SXM;
      enum SYC;
      enum SYR;
      enum TCA;
      enum TCD;
      enum TGO;
      enum THA;
      enum TJK;
      enum TKL;
      enum TKM;
      enum TLS;
      enum TON;
      enum TTO;
      enum TUN;
      enum TUR;
      enum TUV;
      enum TWN;
      enum TZA;
      enum UGA;
      enum UKR;
      enum UMI;
      enum URY;
      enum USA;
      enum UZB;
      enum VAT;
      enum VCT;
      enum VEN;
      enum VGB;
      enum VIR;
      enum VNM;
      enum VUT;
      enum WLF;
      enum WSM;
      enum YEM;
      enum ZAF;
      enum ZMB;
      enum ZWE;
    }
  }

  typedef alpha-continent-code-type {
    type enumeration {
      enum AF;
      enum AN;
      enum AS;
      enum EU;
      enum NA;
      enum OC;
      enum SA;
    }
  }

  grouping udp-src-dst-range-port-list-op-grouping {
    container udp-src-dst-range-port-list-op {
      description
        "List of udp source, destination range ports with operators";
      list source {
        description
          "Source port number";
        key "operator udp-src-port udp-dst-min-port udp-dst-max-port";
        leaf operator {
          type object-group-port-operator;
        }
        leaf udp-src-port {
          type ios-types:acl-udp-port-type;
        }
        leaf udp-dst-min-port {
          type ios-types:acl-udp-port-type;
        }
        leaf udp-dst-max-port {
          type ios-types:acl-udp-port-type;
        }
      }
    }
  }

  grouping tcp-src-dst-range-port-list-op-grouping {
    container tcp-src-dst-range-port-list-op {
      description
        "List of TCP source, destination range ports with operators";
      list source {
        description
          "Source port number";
        key "operator tcp-src-port tcp-dst-min-port tcp-dst-max-port";
        leaf operator {
          type object-group-port-operator;
        }
        leaf tcp-src-port {
          type ios-types:acl-tcp-port-type;
        }
        leaf tcp-dst-min-port {
          type ios-types:acl-tcp-port-type;
        }
        leaf tcp-dst-max-port {
          type ios-types:acl-tcp-port-type;
        }
      }
    }
  }

  grouping tcp-udp-src-dst-range-port-list-op-grouping {
    container tcp-udp-src-dst-range-port-list-op {
      description
        "List of tcp-udp source, destination range ports with operators";
      list source {
        description
          "Source port number";
        key "operator tcp-udp-src-port tcp-udp-dst-min-port tcp-udp-dst-max-port";
        leaf operator {
          type object-group-port-operator;
        }
        leaf tcp-udp-src-port {
          type ios-types:acl-tcp-udp-port-type;
        }
        leaf tcp-udp-dst-min-port {
          type ios-types:acl-tcp-udp-port-type;
        }
        leaf tcp-udp-dst-max-port {
          type ios-types:acl-tcp-udp-port-type;
        }
      }
    }
  }

  grouping object-group-service-grouping {
    leaf description {
      description
        "Service object group description";
      type string {
        length "1..200";
      }
    }
    list group-objects {
      description
        "List of nested IPv4 service object groups";
      key "service-group";
      leaf service-group {
        description
          "Nested service object group name";
        type leafref {
          path "/ios:native/ios:object-group/ios-og:service/ios-og:name";
        }
      }
    }
    leaf group-object {
      status obsolete;
      description
        "Nested object group (OBSOLETE - use group-objects)";
      type string;
    }
    leaf-list protocal-number {
      description
        "An IP protocol number";
      type uint8;
    }
    leaf ahp {
      description
        "Authentication Header Protocol";
      type empty;
    }
    leaf eigrp {
      description
        "Cisco's EIGRP routing protocol";
      type empty;
    }
    leaf esp {
      description
        "Encapsulation Security Payload";
      type empty;
    }
    leaf gre {
      description
        "Cisco's GRE tunneling";
      type empty;
    }
    leaf icmp {
      description
        "Internet Control Message Protocol";
      type empty;
    }
    container icmp-conf {
      container icmp {
        description
          "Internet Control Message Protocol";
        leaf port-number {
          type uint8;
        }
        leaf alternate-address {
          description
            "Alternate address";
          type empty;
        }
        leaf conversion-error {
          description
            "Datagram conversion";
          type empty;
        }
        leaf echo {
          description
            "Echo (ping)";
          type empty;
        }
        leaf echo-reply {
          description
            "Echo reply";
          type empty;
        }
        leaf information-reply {
          description
            "Information replies";
          type empty;
        }
        leaf information-request {
          description
            "Information requests";
          type empty;
        }
        leaf mask-reply {
          description
            "Mask replies";
          type empty;
        }
        leaf mask-request {
          description
            "Mask requests";
          type empty;
        }
        leaf mobile-redirect {
          description
            "Mobile host redirect";
          type empty;
        }
        leaf parameter-problem {
          description
            "All parameter problems";
          type empty;
        }
        leaf redirect {
          description
            "All redirects";
          type empty;
        }
        leaf router-advertisement {
          description
            "Router discovery advertisements";
          type empty;
        }
        leaf router-solicitation {
          description
            "Router discovery solicitations";
          type empty;
        }
        leaf source-quench {
          description
            "Source quenches";
          type empty;
        }
        leaf time-exceeded {
          description
            "All time exceeded";
          type empty;
        }
        leaf timestamp-reply {
          description
            "Timestamp replies";
          type empty;
        }
        leaf timestamp-request {
          description
            "Timestamp requests";
          type empty;
        }
        leaf traceroute {
          description
            "Traceroute";
          type empty;
        }
        leaf unreachable {
          description
            "All unreachables";
          type empty;
        }
      }
    }
    leaf igmp {
      description
        "Internet Gateway Message Protocol";
      type empty;
    }
    leaf ip {
      description
        "Any Internet Protocol";
      type empty;
    }
    leaf ipinip {
      description
        "IP in IP tunneling";
      type empty;
    }
    leaf nos {
      description
        "KA9Q NOS compatible IP over IP tunneling";
      type empty;
    }
    leaf ospf {
      description
        "OSPF routing protocol";
      type empty;
    }
    leaf pcp {
      description
        "Payload Compression Protocol";
      type empty;
    }
    leaf pim {
      description
        "Protocol Independent Multicast";
      type empty;
    }
    leaf tcp {
      description
        "Transmission Control Protocol";
      type empty;
    }
    container tcp-conf {
      container tcp {
        description
          "Transmission Control Protocol";
        list tcp-port-list-op {
          description
            "List of Destination TCP ports with port operator";
          key "operator tcp-port";
          leaf operator {
            description
              "Port operator - equal to/lesser than/greater than";
            type object-group-port-operator;
          }
          leaf tcp-port {
            description
              "Destination TCP port number";
            type ios-types:acl-tcp-port-type;
          }
        }
        list tcp-port-list-no-op {
          description
            "List of Destination TCP ports without port operator";
          key "tcp-port";
          leaf tcp-port {
            description
              "Destination TCP port number";
            type ios-types:acl-tcp-port-type;
          }
        }
        list tcp-port-list {
          status obsolete;
          description
            "( OBSOLETE ) : Use tcp-port-list-op if operator is specified and tcp-port-list-no-op if not.";
          key "tcp-port";
          leaf tcp-port {
            status obsolete;
            type ios-types:acl-tcp-port-type;
          }
          leaf operator {
            status obsolete;
            type object-group-port-operator;
          }
        }
        container tcp-range-port-list {
          list range {
            description
              "Match only packets in the range of port numbers";
            key "tcp-min-port tcp-max-port";
            leaf tcp-min-port {
              type ios-types:acl-tcp-port-type;
            }
            leaf tcp-max-port {
              type ios-types:acl-tcp-port-type;
            }
          }
        }
        container tcp-src-port-list-op {
          description
            "List of TCP source ports with port operator";
          list source {
            description
              "Source port number";
            key "operator tcp-port";
            leaf tcp-port {
              type ios-types:acl-tcp-port-type;
            }
            leaf operator {
              type object-group-port-operator;
            }
          }
        }
        container tcp-src-port-list-no-op {
          description
            "List of TCP source ports without port operator";
          list source {
            description
              "Source port number";
            key "tcp-port";
            leaf tcp-port {
              type ios-types:acl-tcp-port-type;
            }
          }
        }
        container tcp-src-port-list {
          status obsolete;
          list source {
            description
              "(OBSOLETE) Source port number";
            status obsolete;
            key "tcp-port";
            leaf tcp-port {
              status obsolete;
              type ios-types:acl-tcp-port-type;
            }
            leaf operator {
              status obsolete;
              type object-group-port-operator;
            }
          }
        }
        container tcp-src-range-port-list {
          container source {
            description
              "Source port number";
            list range {
              description
                "Match only packets in the range of port numbers";
              key "tcp-min-port tcp-max-port";
              leaf tcp-min-port {
                type ios-types:acl-tcp-port-type;
              }
              leaf tcp-max-port {
                type ios-types:acl-tcp-port-type;
              }
            }
          }
        }
        container tcp-src-dst-port-list-op {
          description
            "List of TCP source and destination ports with port operator";
          list source {
            description
              "Source port number";
            key "src-operator tcp-src-port dst-operator tcp-dst-port";
            leaf src-operator {
              type object-group-port-operator;
            }
            leaf tcp-src-port {
              type ios-types:acl-tcp-port-type;
            }
            leaf dst-operator {
              type object-group-port-operator;
            }
            leaf tcp-dst-port {
              type ios-types:acl-tcp-port-type;
            }
          }
        }
        container tcp-src-dst-port-list-no-op {
          description
            "List of TCP source and destination ports without port operator";
          list source {
            description
              "Source port number";
            key "tcp-src-port  tcp-dst-port";
            leaf tcp-src-port {
              type ios-types:acl-tcp-port-type;
            }
            leaf tcp-dst-port {
              type ios-types:acl-tcp-port-type;
            }
          }
        }
        container tcp-src-dst-port-list-src-op {
          description
            "List of TCP source and destination ports with source port operator";
          list source {
            description
              "Source port number";
            key "src-operator tcp-src-port tcp-dst-port";
            leaf src-operator {
              type object-group-port-operator;
            }
            leaf tcp-src-port {
              type ios-types:acl-tcp-port-type;
            }
            leaf tcp-dst-port {
              type ios-types:acl-tcp-port-type;
            }
          }
        }
        container tcp-src-dst-port-list-dst-op {
          description
            "List of TCP source and destination ports with destination port operator";
          list source {
            description
              "Source port number";
            key "tcp-src-port dst-operator tcp-dst-port";
            leaf tcp-src-port {
              type ios-types:acl-tcp-port-type;
            }
            leaf dst-operator {
              type object-group-port-operator;
            }
            leaf tcp-dst-port {
              type ios-types:acl-tcp-port-type;
            }
          }
        }
        container tcp-src-dst-port-list {
          description
            "(OBSOLETE): List of TCP source and destination ports";
          status obsolete;
          list source {
            description
              "(OBSOLETE) Source port number";
            status obsolete;
            key "tcp-src-port tcp-dst-port";
            leaf src-operator {
              status obsolete;
              type object-group-port-operator;
            }
            leaf tcp-src-port {
              status obsolete;
              type ios-types:acl-tcp-port-type;
            }
            leaf dst-operator {
              status obsolete;
              type object-group-port-operator;
            }
            leaf tcp-dst-port {
              status obsolete;
              type ios-types:acl-tcp-port-type;
            }
          }
        }
        container tcp-src-range-dst-port-list-op {
          description
            "List of TCP source range, destination ports with port operator";
          list source {
            description
              "Source port number";
            key "tcp-src-min-port tcp-src-max-port operator tcp-dst-port";
            leaf tcp-src-min-port {
              type ios-types:acl-tcp-port-type;
            }
            leaf tcp-src-max-port {
              type ios-types:acl-tcp-port-type;
            }
            leaf operator {
              type object-group-port-operator;
            }
            leaf tcp-dst-port {
              type ios-types:acl-tcp-port-type;
            }
          }
        }
        container tcp-src-range-dst-port-list-no-op {
          description
            "List of TCP source range, destination ports without port operator";
          list source {
            description
              "Source port number";
            key "tcp-src-min-port tcp-src-max-port tcp-dst-port";
            leaf tcp-src-min-port {
              type ios-types:acl-tcp-port-type;
            }
            leaf tcp-src-max-port {
              type ios-types:acl-tcp-port-type;
            }
            leaf tcp-dst-port {
              type ios-types:acl-tcp-port-type;
            }
          }
        }
        container tcp-src-range-dst-port-list {
          description
            "(OBSOLETE): List of TCP source range, destination ports";
          status obsolete;
          list source {
            status obsolete;
            description
              "(OBSOLETE) Source port number";
            key "tcp-src-min-port tcp-src-max-port tcp-dst-port";
            leaf tcp-src-min-port {
              status obsolete;
              type ios-types:acl-tcp-port-type;
            }
            leaf tcp-src-max-port {
              status obsolete;
              type ios-types:acl-tcp-port-type;
            }
            leaf operator {
              status obsolete;
              type object-group-port-operator;
            }
            leaf tcp-dst-port {
              status obsolete;
              type ios-types:acl-tcp-port-type;
            }
          }
        }
        uses tcp-src-dst-range-port-list-op-grouping;
        container tcp-src-dst-range-port-list-no-op {
          description
            "List of TCP source, destination range ports without operators";
          list source {
            description
              "Source port number";
            key "tcp-src-port tcp-dst-min-port tcp-dst-max-port";
            leaf tcp-src-port {
              type ios-types:acl-tcp-port-type;
            }
            leaf tcp-dst-min-port {
              type ios-types:acl-tcp-port-type;
            }
            leaf tcp-dst-max-port {
              type ios-types:acl-tcp-port-type;
            }
          }
        }
        container tcp-src-dst-range-port-list {
          description
            "(OBSOLETE): List of TCP source, destination range ports";
          status obsolete;
          list source {
            status obsolete;
            description
              "(OBSOLETE) Source port number";
            key "tcp-src-port tcp-dst-min-port tcp-dst-max-port";
            leaf operator {
              status obsolete;
              type object-group-port-operator;
            }
            leaf tcp-src-port {
              status obsolete;
              type ios-types:acl-tcp-port-type;
            }
            leaf tcp-dst-min-port {
              status obsolete;
              type ios-types:acl-tcp-port-type;
            }
            leaf tcp-dst-max-port {
              status obsolete;
              type ios-types:acl-tcp-port-type;
            }
          }
        }
        container tcp-src-range-dst-range-port-list {
          list source {
            description
              "Source port number";
            key "tcp-src-min-port tcp-src-max-port tcp-dst-min-port tcp-dst-max-port";
            leaf tcp-src-min-port {
              type ios-types:acl-tcp-port-type;
            }
            leaf tcp-src-max-port {
              type ios-types:acl-tcp-port-type;
            }
            leaf tcp-dst-min-port {
              type ios-types:acl-tcp-port-type;
            }
            leaf tcp-dst-max-port {
              type ios-types:acl-tcp-port-type;
            }
          }
        }
      }
    }
    container tcp-udp {
      description
        "TCP or UDP protocol";
      list tcp-udp-port-list-op {
        description
          "List of Destination tcp-udp ports with port operator";
        key "operator tcp-udp-port";
        leaf operator {
          description
            "Port operator - equal to/lesser than/greater than";
          type object-group-port-operator;
        }
        leaf tcp-udp-port {
          description
            "Destination tcp-udp port number";
          type ios-types:acl-tcp-udp-port-type;
        }
      }
      list tcp-udp-port-list-no-op {
        description
          "List of Destination tcp-udp ports without port operator";
        key "tcp-udp-port";
        leaf tcp-udp-port {
          description
            "Destination tcp-udp port number";
          type ios-types:acl-tcp-udp-port-type;
        }
      }
      list tcp-udp-port-list {
        status obsolete;
        description
          "(OBSOLETE): Use tcp-udp-port-list-op if operator is specified and tcp-udp-port-list-no-op if not.";
        key "tcp-udp-port";
        leaf tcp-udp-port {
          status obsolete;
          type ios-types:acl-tcp-udp-port-type;
        }
        leaf operator {
          status obsolete;
          type object-group-port-operator;
        }
      }
      container tcp-udp-range-port-list {
        list range {
          description
            "Match only packets in the range of port numbers";
          key "tcp-udp-min-port tcp-udp-max-port";
          leaf tcp-udp-min-port {
            type ios-types:acl-tcp-udp-port-type;
          }
          leaf tcp-udp-max-port {
            type ios-types:acl-tcp-udp-port-type;
          }
        }
      }
      container tcp-udp-src-port-list-op {
        description
          "List of tcp-udp source ports with port operator";
        list source {
          description
            "Source port number";
          key "operator tcp-udp-port";
          leaf tcp-udp-port {
            type ios-types:acl-tcp-udp-port-type;
          }
          leaf operator {
            type object-group-port-operator;
          }
        }
      }
      container tcp-udp-src-port-list-no-op {
        description
          "List of tcp-udp source ports without port operator";
        list source {
          description
            "Source port number";
          key "tcp-udp-port";
          leaf tcp-udp-port {
            type ios-types:acl-tcp-udp-port-type;
          }
        }
      }
      container tcp-udp-src-port-list {
        status obsolete;
        list source {
          description
            "(OBSOLETE) Source port number";
          status obsolete;
          key "tcp-udp-port";
          leaf tcp-udp-port {
            status obsolete;
            type ios-types:acl-tcp-udp-port-type;
          }
          leaf operator {
            status obsolete;
            type object-group-port-operator;
          }
        }
      }
      container tcp-udp-src-range-port-list {
        container source {
          description
            "Source port number";
          list range {
            description
              "Match only packets in the range of port numbers";
            key "tcp-udp-min-port tcp-udp-max-port";
            leaf tcp-udp-min-port {
              type ios-types:acl-tcp-udp-port-type;
            }
            leaf tcp-udp-max-port {
              type ios-types:acl-tcp-udp-port-type;
            }
          }
        }
      }
      container tcp-udp-src-dst-port-list-op {
        description
          "List of tcp-udp source and destination ports with port operator";
        list source {
          description
            "Source port number";
          key "src-operator tcp-udp-src-port dst-operator tcp-udp-dst-port";
          leaf src-operator {
            description
              "Source port operator";
            type object-group-port-operator;
          }
          leaf tcp-udp-src-port {
            description
              "Source port value";
            type ios-types:acl-tcp-udp-port-type;
          }
          leaf dst-operator {
            description
              "Destination port operator";
            type object-group-port-operator;
          }
          leaf tcp-udp-dst-port {
            description
              "Destination port value";
            type ios-types:acl-tcp-udp-port-type;
          }
        }
      }
      container tcp-udp-src-dst-port-list-no-op {
        description
          "List of tcp-udp source and destination ports without port operator";
        list source {
          description
            "Source port number";
          key "tcp-udp-src-port  tcp-udp-dst-port";
          leaf tcp-udp-src-port {
            description
              "Source port value";
            type ios-types:acl-tcp-udp-port-type;
          }
          leaf tcp-udp-dst-port {
            description
              "Destination port value";
            type ios-types:acl-tcp-udp-port-type;
          }
        }
      }
      container tcp-udp-src-dst-port-list-src-op {
        description
          "List of tcp-udp source and destination ports with source port operator";
        list source {
          description
            "Source port number";
          key "src-operator tcp-udp-src-port tcp-udp-dst-port";
          leaf src-operator {
            description
              "Source port operator";
            type object-group-port-operator;
          }
          leaf tcp-udp-src-port {
            description
              "Source port value";
            type ios-types:acl-tcp-udp-port-type;
          }
          leaf tcp-udp-dst-port {
            description
              "Destination port value";
            type ios-types:acl-tcp-udp-port-type;
          }
        }
      }
      container tcp-udp-src-dst-port-list-dst-op {
        description
          "List of tcp-udp source and destination ports with destination port operator";
        list source {
          description
            "Source port number";
          key "tcp-udp-src-port dst-operator tcp-udp-dst-port";
          leaf tcp-udp-src-port {
            description
              "Source port operator";
            type ios-types:acl-tcp-udp-port-type;
          }
          leaf dst-operator {
            description
              "Destination port operator";
            type object-group-port-operator;
          }
          leaf tcp-udp-dst-port {
            description
              "Destination port value";
            type ios-types:acl-tcp-udp-port-type;
          }
        }
      }
      container tcp-udp-src-dst-port-list {
        description
          "(OBSOLETE): List of tcp-udp source and destination ports";
        status obsolete;
        list source {
          description
            "(OBSOLETE) Source port number";
          status obsolete;
          key "tcp-udp-src-port tcp-udp-dst-port";
          leaf src-operator {
            status obsolete;
            type object-group-port-operator;
          }
          leaf tcp-udp-src-port {
            status obsolete;
            type ios-types:acl-tcp-udp-port-type;
          }
          leaf dst-operator {
            status obsolete;
            type object-group-port-operator;
          }
          leaf tcp-udp-dst-port {
            status obsolete;
            type ios-types:acl-tcp-udp-port-type;
          }
        }
      }
      container tcp-udp-src-range-dst-port-list-op {
        description
          "List of tcp-udp source range, destination ports with port operator";
        list source {
          description
            "Source port number";
          key "tcp-udp-src-min-port tcp-udp-src-max-port operator tcp-udp-dst-port";
          leaf tcp-udp-src-min-port {
            type ios-types:acl-tcp-udp-port-type;
          }
          leaf tcp-udp-src-max-port {
            type ios-types:acl-tcp-udp-port-type;
          }
          leaf operator {
            type object-group-port-operator;
          }
          leaf tcp-udp-dst-port {
            type ios-types:acl-tcp-udp-port-type;
          }
        }
      }
      container tcp-udp-src-range-dst-port-list-no-op {
        description
          "List of tcp-udp source range, destination ports without port operator";
        list source {
          description
            "Source port number";
          key "tcp-udp-src-min-port tcp-udp-src-max-port tcp-udp-dst-port";
          leaf tcp-udp-src-min-port {
            type ios-types:acl-tcp-udp-port-type;
          }
          leaf tcp-udp-src-max-port {
            type ios-types:acl-tcp-udp-port-type;
          }
          leaf tcp-udp-dst-port {
            type ios-types:acl-tcp-udp-port-type;
          }
        }
      }
      container tcp-udp-src-range-dst-port-list {
        description
          "(OBSOLETE): List of tcp-udp source range, destination ports";
        status obsolete;
        list source {
          status obsolete;
          description
            "(OBSOLETE) Source port number";
          key "tcp-udp-src-min-port tcp-udp-src-max-port tcp-udp-dst-port";
          leaf tcp-udp-src-min-port {
            status obsolete;
            type ios-types:acl-tcp-udp-port-type;
          }
          leaf tcp-udp-src-max-port {
            status obsolete;
            type ios-types:acl-tcp-udp-port-type;
          }
          leaf operator {
            status obsolete;
            type object-group-port-operator;
          }
          leaf tcp-udp-dst-port {
            status obsolete;
            type ios-types:acl-tcp-udp-port-type;
          }
        }
      }
      uses tcp-udp-src-dst-range-port-list-op-grouping;
      container tcp-udp-src-dst-range-port-list-no-op {
        description
          "List of tcp-udp source, destination range ports without operators";
        list source {
          description
            "Source port number";
          key "tcp-udp-src-port tcp-udp-dst-min-port tcp-udp-dst-max-port";
          leaf tcp-udp-src-port {
            type ios-types:acl-tcp-udp-port-type;
          }
          leaf tcp-udp-dst-min-port {
            type ios-types:acl-tcp-udp-port-type;
          }
          leaf tcp-udp-dst-max-port {
            type ios-types:acl-tcp-udp-port-type;
          }
        }
      }
      container tcp-udp-src-dst-range-port-list {
        description
          "(OBSOLETE): List of tcp-udp source, destination range ports";
        status obsolete;
        list source {
          status obsolete;
          description
            "(OBSOLETE) Source port number";
          key "tcp-udp-src-port tcp-udp-dst-min-port tcp-udp-dst-max-port";
          leaf operator {
            status obsolete;
            type object-group-port-operator;
          }
          leaf tcp-udp-src-port {
            status obsolete;
            type ios-types:acl-tcp-udp-port-type;
          }
          leaf tcp-udp-dst-min-port {
            status obsolete;
            type ios-types:acl-tcp-udp-port-type;
          }
          leaf tcp-udp-dst-max-port {
            status obsolete;
            type ios-types:acl-tcp-udp-port-type;
          }
        }
      }
      container tcp-udp-src-range-dst-range-port-list {
        list source {
          description
            "Source port number";
          key "tcp-udp-src-min-port tcp-udp-src-max-port tcp-udp-dst-min-port tcp-udp-dst-max-port";
          leaf tcp-udp-src-min-port {
            type ios-types:acl-tcp-udp-port-type;
          }
          leaf tcp-udp-src-max-port {
            type ios-types:acl-tcp-udp-port-type;
          }
          leaf tcp-udp-dst-min-port {
            type ios-types:acl-tcp-udp-port-type;
          }
          leaf tcp-udp-dst-max-port {
            type ios-types:acl-tcp-udp-port-type;
          }
        }
      }
    }
    leaf udp {
      description
        "User Datagram Protocol";
      type empty;
    }
    container udp-conf {
      container udp {
        description
          "User Datagram Protocol";
        list udp-port-list-op {
          description
            "List of Destination udp ports with port operator";
          key "operator udp-port";
          leaf operator {
            description
              "Port operator - equal to/lesser than/greater than";
            type object-group-port-operator;
          }
          leaf udp-port {
            description
              "Destination udp port number";
            type ios-types:acl-udp-port-type;
          }
        }
        list udp-port-list-no-op {
          description
            "List of Destination udp ports without port operator";
          key "udp-port";
          leaf udp-port {
            description
              "Destination udp port number";
            type ios-types:acl-udp-port-type;
          }
        }
        list udp-port-list {
          status obsolete;
          description
            "(OBSOLETE): Use udp-port-list-op if operator is specified and udp-port-list-no-op if not.";
          key "udp-port";
          leaf udp-port {
            status obsolete;
            type ios-types:acl-udp-port-type;
          }
          leaf operator {
            status obsolete;
            type object-group-port-operator;
          }
        }
        container udp-range-port-list {
          list range {
            description
              "Match only packets in the range of port numbers";
            key "udp-min-port udp-max-port";
            leaf udp-min-port {
              type ios-types:acl-udp-port-type;
            }
            leaf udp-max-port {
              type ios-types:acl-udp-port-type;
            }
          }
        }
        container udp-src-port-list-op {
          description
            "List of udp source ports with port operator";
          list source {
            description
              "Source port number";
            key "operator udp-port";
            leaf udp-port {
              type ios-types:acl-udp-port-type;
            }
            leaf operator {
              type object-group-port-operator;
            }
          }
        }
        container udp-src-port-list-no-op {
          description
            "List of udp source ports without port operator";
          list source {
            description
              "Source port number";
            key "udp-port";
            leaf udp-port {
              type ios-types:acl-udp-port-type;
            }
          }
        }
        container udp-src-port-list {
          status obsolete;
          list source {
            description
              "Source port number";
            status obsolete;
            key "udp-port";
            leaf udp-port {
              status obsolete;
              type ios-types:acl-udp-port-type;
            }
            leaf operator {
              status obsolete;
              type object-group-port-operator;
            }
          }
        }
        container udp-src-range-port-list {
          container source {
            description
              "Source port number";
            list range {
              description
                "Match only packets in the range of port numbers";
              key "udp-min-port udp-max-port";
              leaf udp-min-port {
                type ios-types:acl-udp-port-type;
              }
              leaf udp-max-port {
                type ios-types:acl-udp-port-type;
              }
            }
          }
        }
        container udp-src-dst-port-list-op {
          list source {
            description
              "Source port number";
            key "src-operator udp-src-port dst-operator udp-dst-port";
            leaf src-operator {
              description
                "Source port operator";
              type object-group-port-operator;
            }
            leaf udp-src-port {
              description
                "Source port value";
              type ios-types:acl-udp-port-type;
            }
            leaf dst-operator {
              description
                "Destination port operator";
              type object-group-port-operator;
            }
            leaf udp-dst-port {
              description
                "Destination port value";
              type ios-types:acl-udp-port-type;
            }
          }
        }
        container udp-src-dst-port-list-no-op {
          list source {
            description
              "Source port number";
            key "udp-src-port udp-dst-port";
            leaf udp-src-port {
              description
                "Source port value";
              type ios-types:acl-udp-port-type;
            }
            leaf udp-dst-port {
              description
                "Destination port value";
              type ios-types:acl-udp-port-type;
            }
          }
        }
        container udp-src-dst-port-list-src-op {
          list source {
            description
              "Source port number";
            key "src-operator udp-src-port udp-dst-port";
            leaf src-operator {
              description
                "Source port operator";
              type object-group-port-operator;
            }
            leaf udp-src-port {
              description
                "Source port value";
              type ios-types:acl-udp-port-type;
            }
            leaf udp-dst-port {
              description
                "Destination port value";
              type ios-types:acl-udp-port-type;
            }
          }
        }
        container udp-src-dst-port-list-dst-op {
          list source {
            description
              "Source port number";
            key "udp-src-port dst-operator udp-dst-port";
            leaf udp-src-port {
              description
                "Source port value";
              type ios-types:acl-udp-port-type;
            }
            leaf dst-operator {
              description
                "Destination port operator";
              type object-group-port-operator;
            }
            leaf udp-dst-port {
              description
                "Destination port value";
              type ios-types:acl-udp-port-type;
            }
          }
        }
        container udp-src-dst-port-list {
          status obsolete;
          list source {
            description
              "(OBSOLETE) Source port number";
            status obsolete;
            key "udp-src-port udp-dst-port";
            leaf src-operator {
              status obsolete;
              description
                "(OBSOLETE) Source operator";
              type object-group-port-operator;
            }
            leaf udp-src-port {
              status obsolete;
              description
                " (OBSOLETE) Source port number";
              type ios-types:acl-udp-port-type;
            }
            leaf dst-operator {
              status obsolete;
              description
                "(OBSOLETE) Destination operator";
              type object-group-port-operator;
            }
            leaf udp-dst-port {
              status obsolete;
              description
                "(OBSOLETE) Destination port number";
              type ios-types:acl-udp-port-type;
            }
          }
        }
        container udp-src-range-dst-port-list-op {
          description
            "List of udp source range, destination ports with port operator";
          list source {
            description
              "Source port number";
            key "udp-src-min-port udp-src-max-port operator udp-dst-port";
            leaf udp-src-min-port {
              type ios-types:acl-udp-port-type;
            }
            leaf udp-src-max-port {
              type ios-types:acl-udp-port-type;
            }
            leaf operator {
              type object-group-port-operator;
            }
            leaf udp-dst-port {
              type ios-types:acl-udp-port-type;
            }
          }
        }
        container udp-src-range-dst-port-list-no-op {
          description
            "List of udp source range, destination ports without port operator";
          list source {
            description
              "Source port number";
            key "udp-src-min-port udp-src-max-port udp-dst-port";
            leaf udp-src-min-port {
              type ios-types:acl-udp-port-type;
            }
            leaf udp-src-max-port {
              type ios-types:acl-udp-port-type;
            }
            leaf udp-dst-port {
              type ios-types:acl-udp-port-type;
            }
          }
        }
        container udp-src-range-dst-port-list {
          description
            "(OBSOLETE): List of udp source range, destination ports";
          status obsolete;
          list source {
            status obsolete;
            description
              "(OBSOLETE) Source port number";
            key "udp-src-min-port udp-src-max-port udp-dst-port";
            leaf udp-src-min-port {
              status obsolete;
              type ios-types:acl-udp-port-type;
            }
            leaf udp-src-max-port {
              status obsolete;
              type ios-types:acl-udp-port-type;
            }
            leaf operator {
              status obsolete;
              type object-group-port-operator;
            }
            leaf udp-dst-port {
              status obsolete;
              type ios-types:acl-udp-port-type;
            }
          }
        }
        uses udp-src-dst-range-port-list-op-grouping;
        container udp-src-dst-range-port-list-no-op {
          description
            "List of udp source, destination range ports without operators";
          list source {
            description
              "Source port number";
            key "udp-src-port udp-dst-min-port udp-dst-max-port";
            leaf udp-src-port {
              type ios-types:acl-udp-port-type;
            }
            leaf udp-dst-min-port {
              type ios-types:acl-udp-port-type;
            }
            leaf udp-dst-max-port {
              type ios-types:acl-udp-port-type;
            }
          }
        }
        container udp-src-dst-range-port-list {
          description
            "(OBSOLETE): List of udp source, destination range ports";
          status obsolete;
          list source {
            status obsolete;
            description
              "(OBSOLETE) Source port number";
            key "udp-src-port udp-dst-min-port udp-dst-max-port";
            leaf operator {
              status obsolete;
              type object-group-port-operator;
            }
            leaf udp-src-port {
              status obsolete;
              type ios-types:acl-udp-port-type;
            }
            leaf udp-dst-min-port {
              status obsolete;
              type ios-types:acl-udp-port-type;
            }
            leaf udp-dst-max-port {
              status obsolete;
              type ios-types:acl-udp-port-type;
            }
          }
        }
        container udp-src-range-dst-range-port-list {
          list source {
            description
              "Source port number";
            key "udp-src-min-port udp-src-max-port udp-dst-min-port udp-dst-max-port";
            leaf udp-src-min-port {
              type ios-types:acl-udp-port-type;
            }
            leaf udp-src-max-port {
              type ios-types:acl-udp-port-type;
            }
            leaf udp-dst-min-port {
              type ios-types:acl-udp-port-type;
            }
            leaf udp-dst-max-port {
              type ios-types:acl-udp-port-type;
            }
          }
        }
      }
    }
  }

  grouping object-group-v6service-grouping {
    leaf ipv6 {
      description
        "Internet v6 Protocol";
      type empty;
    }
    leaf icmp {
      description
        "Internet Control Message Protocol";
      type empty;
    }
    leaf udp {
      description
        "User Datagram Protocol";
      type empty;
    }
    container udp-conf {
      container udp {
        description
          "User Datagram Protocol";
        container udp-src-port-list-op {
          description
            "List of udp source ports with port operator";
          list source {
            description
              "Source port number";
            key "operator udp-port";
            leaf operator {
              description
                "Port operator";
              type object-group-port-operator;
            }
            leaf udp-port {
              description
                "Port number";
              type ios-types:acl-udp-port-type;
            }
          }
        }
        container udp-src-range-port-list {
          container source {
            description
              "Source port number";
            list range {
              description
                "Match only packets in the range of port numbers";
              key "udp-min-port udp-max-port";
              leaf udp-min-port {
                description
                  "Port number";
                type ios-types:acl-udp-port-type;
              }
              leaf udp-max-port {
                description
                  "Port number";
                type ios-types:acl-udp-port-type;
              }
            }
          }
        }
        container udp-src-range-dst-port-list-op {
          description
            "List of udp source range, destination ports with port operator";
          list source {
            description
              "Source port number";
            key "udp-src-min-port udp-src-max-port operator udp-dst-port";
            leaf udp-src-min-port {
              description
                "Port number";
              type ios-types:acl-udp-port-type;
            }
            leaf udp-src-max-port {
              description
                "Port number";
              type ios-types:acl-udp-port-type;
            }
            leaf operator {
              description
                "Port operator";
              type object-group-port-operator;
            }
            leaf udp-dst-port {
              description
                "Port number";
              type ios-types:acl-udp-port-type;
            }
          }
        }
        container udp-src-dst-port-list-op {
          list source {
            description
              "Source port number";
            key "src-operator udp-src-port dst-operator udp-dst-port";
            leaf src-operator {
              description
                "Source port operator";
              type object-group-port-operator;
            }
            leaf udp-src-port {
              description
                "Source port value";
              type ios-types:acl-udp-port-type;
            }
            leaf dst-operator {
              description
                "Destination port operator";
              type object-group-port-operator;
            }
            leaf udp-dst-port {
              description
                "Destination port value";
              type ios-types:acl-udp-port-type;
            }
          }
        }
        container udp-src-range-dst-range-port-list {
          list source {
            description
              "Source port number";
            key "udp-src-min-port udp-src-max-port udp-dst-min-port udp-dst-max-port";
            leaf udp-src-min-port {
              type ios-types:acl-udp-port-type;
            }
            leaf udp-src-max-port {
              type ios-types:acl-udp-port-type;
            }
            leaf udp-dst-min-port {
              type ios-types:acl-udp-port-type;
            }
            leaf udp-dst-max-port {
              type ios-types:acl-udp-port-type;
            }
          }
        }
        uses udp-src-dst-range-port-list-op-grouping;
      }
    }
    leaf tcp {
      description
        "Transmission Control Protocol";
      type empty;
    }
    container tcp-conf {
      container tcp {
        description
          "Transmission Control Protocol";
        container tcp-src-port-list-op {
          description
            "List of TCP source ports with port operator";
          list source {
            description
              "Source port number";
            key "operator tcp-port";
            leaf operator {
              description
                "Port operator";
              type object-group-port-operator;
            }
            leaf tcp-port {
              description
                "Port number";
              type ios-types:acl-tcp-port-type;
            }
          }
        }
        container tcp-src-range-port-list {
          container source {
            description
              "Source port number";
            list range {
              description
                "Match only packets in the range of port numbers";
              key "tcp-min-port tcp-max-port";
              leaf tcp-min-port {
                description
                  "Port number";
                type ios-types:acl-tcp-port-type;
              }
              leaf tcp-max-port {
                description
                  "Port number";
                type ios-types:acl-tcp-port-type;
              }
            }
          }
        }
        container tcp-src-range-dst-port-list-op {
          description
            "List of TCP source range, destination ports with port operator";
          list source {
            description
              "Source port number";
            key "tcp-src-min-port tcp-src-max-port operator tcp-dst-port";
            leaf tcp-src-min-port {
              description
                "Port number";
              type ios-types:acl-tcp-port-type;
            }
            leaf tcp-src-max-port {
              description
                "Port number";
              type ios-types:acl-tcp-port-type;
            }
            leaf operator {
              description
                "Port operator";
              type object-group-port-operator;
            }
            leaf tcp-dst-port {
              description
                "Port number";
              type ios-types:acl-tcp-port-type;
            }
          }
        }
        container tcp-src-dst-port-list-op {
          description
            "List of TCP source and destination ports with port operator";
          list source {
            description
              "Source port number";
            key "src-operator tcp-src-port dst-operator tcp-dst-port";
            leaf src-operator {
              type object-group-port-operator;
            }
            leaf tcp-src-port {
              type ios-types:acl-tcp-port-type;
            }
            leaf dst-operator {
              type object-group-port-operator;
            }
            leaf tcp-dst-port {
              type ios-types:acl-tcp-port-type;
            }
          }
        }
        container tcp-src-range-dst-range-port-list {
          list source {
            description
              "Source port number";
            key "tcp-src-min-port tcp-src-max-port tcp-dst-min-port tcp-dst-max-port";
            leaf tcp-src-min-port {
              type ios-types:acl-tcp-port-type;
            }
            leaf tcp-src-max-port {
              type ios-types:acl-tcp-port-type;
            }
            leaf tcp-dst-min-port {
              type ios-types:acl-tcp-port-type;
            }
            leaf tcp-dst-max-port {
              type ios-types:acl-tcp-port-type;
            }
          }
        }
        uses tcp-src-dst-range-port-list-op-grouping;
      }
    }
    container tcp-udp {
      description
        "TCP or UDP protocol";
      container tcp-udp-src-port-list-op {
        description
          "List of tcp-udp source ports with port operator";
        list source {
          description
            "Source port number";
          key "operator tcp-udp-port";
          leaf operator {
            description
              "Port operator";
            type object-group-port-operator;
          }
          leaf tcp-udp-port {
            description
              "Port number";
            type ios-types:acl-tcp-udp-port-type;
          }
        }
      }
      container tcp-udp-src-range-port-list {
        container source {
          description
            "Source port number";
          list range {
            description
              "Match only packets in the range of port numbers";
            key "tcp-udp-min-port tcp-udp-max-port";
            leaf tcp-udp-min-port {
              description
                "Port number";
              type ios-types:acl-tcp-udp-port-type;
            }
            leaf tcp-udp-max-port {
              description
                "Port number";
              type ios-types:acl-tcp-udp-port-type;
            }
          }
        }
      }
      container tcp-udp-src-range-dst-port-list-op {
        description
          "List of tcp-udp source range, destination ports with port operator";
        list source {
          description
            "Source port number";
          key "tcp-udp-src-min-port tcp-udp-src-max-port operator tcp-udp-dst-port";
          leaf tcp-udp-src-min-port {
            description
              "Port number";
            type ios-types:acl-tcp-udp-port-type;
          }
          leaf tcp-udp-src-max-port {
            description
              "Port number";
            type ios-types:acl-tcp-udp-port-type;
          }
          leaf operator {
            description
              "Port operator";
            type object-group-port-operator;
          }
          leaf tcp-udp-dst-port {
            description
              "Port number";
            type ios-types:acl-tcp-udp-port-type;
          }
        }
      }
      container tcp-udp-src-dst-port-list-op {
        description
          "List of tcp-udp source and destination ports with port operator";
        list source {
          description
            "Source port number";
          key "src-operator tcp-udp-src-port dst-operator tcp-udp-dst-port";
          leaf src-operator {
            description
              "Source port operator";
            type object-group-port-operator;
          }
          leaf tcp-udp-src-port {
            description
              "Source port value";
            type ios-types:acl-tcp-udp-port-type;
          }
          leaf dst-operator {
            description
              "Destination port operator";
            type object-group-port-operator;
          }
          leaf tcp-udp-dst-port {
            description
              "Destination port value";
            type ios-types:acl-tcp-udp-port-type;
          }
        }
      }
      container tcp-udp-src-range-dst-range-port-list {
        list source {
          description
            "Source port number";
          key "tcp-udp-src-min-port tcp-udp-src-max-port tcp-udp-dst-min-port tcp-udp-dst-max-port";
          leaf tcp-udp-src-min-port {
            type ios-types:acl-tcp-udp-port-type;
          }
          leaf tcp-udp-src-max-port {
            type ios-types:acl-tcp-udp-port-type;
          }
          leaf tcp-udp-dst-min-port {
            type ios-types:acl-tcp-udp-port-type;
          }
          leaf tcp-udp-dst-max-port {
            type ios-types:acl-tcp-udp-port-type;
          }
        }
      }
      uses tcp-udp-src-dst-range-port-list-op-grouping;
    }
  }

  grouping config-object-group-grouping {
    list network {
      description
        "network group";
      key "name";
      leaf name {
        description
          "WORD;;object-group name";
        type string {
          length "1..64";
        }
      }
      container obj-Mode-config-network-group {
        list network_address {
          key "ipv4_addr ipv4_mask";
          leaf ipv4_addr {
            description
              "A.B.C.D;;Network address of the group members";
            type inet:ipv4-address;
          }
          leaf ipv4_mask {
            description
              "A.B.C.D;;Network mask";
            type inet:ipv4-address;
          }
        }
        leaf description {
          description
            "Network object group description";
          type string {
            length "1..200";
          }
        }
        list group-objects {
          description
            "List of nested IPv4 network groups";
          key "network-group";
          leaf network-group {
            description
              "Nested network object group name";
            type leafref {
              path "/ios:native/ios:object-group/ios-og:network/ios-og:name";
            }
          }
        }
        leaf group-object {
          status obsolete;
          description
            "Nested object group ((OBSOLETE) - use group-objects)";
          type string;
        }
        list host {
          description
            "Host address of the object-group member";
          key "ipv4-host";
          leaf ipv4-host {
            description
              "Host address of the object-group member";
            type inet:host;
          }
        }
        list addr-ranges {
          description
            "List of IPv4 address ranges";
          key "addr-range-start addr-range-end";
          leaf addr-range-start {
            description
              "Starting IPv4 Address";
            type inet:ipv4-address;
          }
          leaf addr-range-end {
            description
              "Ending IPv4 Address";
            type inet:ipv4-address;
          }
        }
        container range {
          status obsolete;
          leaf ip-addr-min {
            status obsolete;
            description
              "Starting IPv4 Address ((OBSOLETE) - use addr-range/addr-range-start";
            type inet:ipv4-address;
          }
          leaf ip-addr-max {
            status obsolete;
            description
              "Ending IPv4 Address ((OBSOLETE) - use addr-range/addr-range-end";
            type inet:ipv4-address;
          }
        }
      }
    }
    list security {
      description
        "security group";
      key "name";
      leaf name {
        type string {
          length "1..64";
        }
      }
      container security-group {
        leaf description {
          description
            "Network object group description";
          type string {
            length "1..200";
          }
        }
        leaf group-object {
          description
            "Nested object group";
          type string;
        }
        container security-group {
          description
            "Security Group Tag";
          leaf-list tags {
            description
              "Security Group Tag value";
            type uint16 {
              range "1..65535";
            }
          }
          leaf tag {
            status obsolete;
            description
              "Tags ((OBSOLETE) - use tags instead)";
            type uint16 {
              range "1..65535";
            }
          }
        }
      }
    }
    list fqdn {
      description
        "FQDN object-group type";
      key "name";
      leaf name {
        description
          "Name of FQDN OG";
        type string {
          length "1..64";
        }
      }
      leaf description {
        description
          "Description for FQDN OG";
        type string {
          length "1..200";
        }
      }
      list group-object {
        description
          "List of nested FQDN Groups";
        key "fqdn-group";
        leaf fqdn-group {
          description
            "FQDN group name";
          type leafref {
            path "/ios:native/ios:object-group/ios-og:fqdn/ios-og:name";
          }
        }
      }
      list pattern {
        description
          "List of reg exp FQDN patterns";
        key "fqdn-pattern";
        leaf fqdn-pattern {
          description
            "FQDN pattern";
          type string {
            length "1..240";
          }
        }
      }
    }
    list geo {
      description
        "Geolocation object groups";
      key "name";
      leaf name {
        description
          "Name of geolocation object group";
        type string {
          length "1..64";
        }
      }
      leaf description {
        description
          "Geolocation group description";
        type string {
          length "1..200";
        }
      }
      list group-object {
        description
          "Nested geolocation groups";
        key "geo-group";
        leaf geo-group {
          description
            "Nested geolocation group";
          type leafref {
            path "/ios:native/ios:object-group/ios-og:geo/ios-og:name";
          }
        }
      }
      list countries {
        description
          "List of countries, identified by ISO-3661-1 alpha-3 codes";
        key "country";
        leaf country {
          description
            "ISO-3166 alpha-3 country code";
          type alpha-3-country-code-type;
        }
      }
      list continents {
        description
          "List of continents";
        key "continent";
        leaf continent {
          description
            "2-letter continent code";
          type alpha-continent-code-type;
        }
      }
    }
    list service {
      description
        "service group";
      key "name";
      leaf name {
        type string {
          length "1..64";
        }
      }
      uses object-group-service-grouping;
    }
    list v6-service {
      description
        "V6 service group";
      key "name";
      leaf name {
        type string {
          length "1..64";
        }
      }
      uses object-group-v6service-grouping;
    }
    list v6-network {
      description
        "IPv6 network group";
      key "name";
      leaf name {
        description
          "WORD;;object-group name";
        type string {
          length "1..64";
        }
      }
      leaf description {
        description
          "STRING;;Network object group description";
        type string {
          length "1..200";
        }
      }
      list network-address {
        key "ipv6-addr-prefix";
        leaf ipv6-addr-prefix {
          description
            "X:X:X:X::X/<0-128>;;IPv6 network address/prefix length";
          type ios-types:ipv6-prefix;
        }
      }
      list host {
        key "ipv6-host";
        leaf ipv6-host {
          description
            "X:X:X:X::X;;Host address of group member";
          type ios-types:ipv6-host;
        }
      }
      list group-object {
        key "v6-network-object-group";
        leaf v6-network-object-group {
          description
            "WORD;;Nested object group";
          type leafref {
            path "/ios:native/ios:object-group/ios-og:v6-network/ios-og:name";
          }
        }
      }
    }
    list knob {
      key "knob_option";
      leaf knob_option {
        description
          "Different knob options";
        type enumeration {
          enum check-nested-entry-dup;
          enum check-normal-entry-dup;
          enum expand-v6-ace-for-pd;
        }
      }
      leaf enable {
        description
          "enable knob option";
        type empty;
      }
    }
  }

  augment "/ios:native/ios:object-group" {
    uses config-object-group-grouping;
  }
}
