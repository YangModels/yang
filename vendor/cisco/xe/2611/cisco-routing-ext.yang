module cisco-routing-ext {
  namespace "urn:cisco:params:xml:ns:yang:cisco-routing-ext";
  prefix rt-ext;

  import cisco-semver {
    prefix cisco-semver;
  }
  import ietf-routing {
    prefix rt;
  }

  organization
    "Cisco Systems, Inc.";
  contact
    "Cisco Systems, Inc.
     Customer Service

     Postal: 170 W Tasman Drive
     San Jose, CA 95134

     Tel: +1 1800 553-NETS

     E-mail: cs-yang@cisco.com";
  description
    "This YANG module is an extention to 'ietf-routing'
     module and describes addtional operational
     data for route list.
     Copyright (c) 2016, 2019 by Cisco Systems, Inc.
     All rights reserved.";

  revision 2019-11-01 {
    description
      "-Added missing IPv6 ND identity as a routing protocol";
  }
  revision 2019-07-01 {
    description
      "Establish semantic version baseline";
    cisco-semver:module-version "1.0.0";
  }
  revision 2016-07-09 {
    description
      "Removed deviation for last-updated and added it to ietf-routing-devs.yang.";
  }
  revision 2015-05-27 {
    description
      "Proposed";
    reference
      "TODO";
  }

  identity rip {
    base rt:routing-protocol;
    description
      "RIP.";
  }

  identity is-is {
    base rt:routing-protocol;
    description
      "IS-IS.";
  }

  identity bgp {
    base rt:routing-protocol;
    description
      "BGP.";
  }

  identity eigrp {
    base rt:routing-protocol;
    description
      "Eigrp.";
  }

  identity igrp {
    base rt:routing-protocol;
    description
      "IGRP";
  }

  identity nhrp {
    base rt:routing-protocol;
    description
      "NHRP";
  }

  identity hsrp {
    base rt:routing-protocol;
    description
      "HSRP";
  }

  identity lisp {
    base rt:routing-protocol;
    description
      "LISP";
  }

  identity omp {
    base rt:routing-protocol;
    description
      "OMP";
  }

  identity nat-route {
    base rt:routing-protocol;
    description
      "NAT-ROUTE";
  }

  identity nd {
    base rt:routing-protocol;
    description
      "ND";
  }
}
