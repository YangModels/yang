module Cisco-IOS-XE-dialer-deviation {
  yang-version 1.1;
  namespace "http://cisco.com/ns/yang/Cisco-IOS-XE-dialer-deviation";
  prefix ios-dialer-d;

  import Cisco-IOS-XE-native {
    prefix ios;
  }
  import cisco-semver {
    prefix cisco-semver;
  }

  organization
    "Cisco Systems";
  description
    "Cisco XE Native Deviation YANG module for IOS
     Copyright (c) 2020 by Cisco Systems, Inc.
     All rights reserved.";

  revision 2022-11-01 {
    description
      "- Update yang-version to 1.1";
    cisco-semver:module-version "1.2.0";
  }
  revision 2020-07-01 {
    description
      "Added dialer mtu deviation";
    cisco-semver:module-version "1.0.0";
  }

  deviation "/ios:native/ios:interface/ios:Dialer/ios:mtu" {
    deviate replace {
      type uint16 {
        range "64..9216";
      }
    }
  }
}
