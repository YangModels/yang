module Cisco-IOS-XE-perf-measure-deviation {
  yang-version 1.1;
  namespace "http://cisco.com/ns/yang/Cisco-IOS-XE-perf-measure-deviation";
  prefix ios-performance-measurement-d;

  import Cisco-IOS-XE-native {
    prefix ios;
  }
  import Cisco-IOS-XE-perf-measure {
    prefix ios-performance-measurement;
  }

  organization
    "Cisco Systems, Inc.";
  description
    "Cisco XE Native Performance-Measurement Deviation Yang model.
     Copyright (c) 2023 by Cisco Systems, Inc.
     All rights reserved.";

  revision 2024-03-01 {
    description
      " - Add deviation for delay-profile probe measurement-mode";
  }

  deviation "/ios:native/ios:performance-measurement/ios-performance-measurement:delay-profile/ios-performance-measurement:interfaces/ios-performance-measurement:probe/ios-performance-measurement:measurement-mode-v2" {
    deviate replace {
      type enumeration {
        enum two-way;
      }
    }
  }

  deviation "/ios:native/ios:performance-measurement/ios-performance-measurement:delay-profile/ios-performance-measurement:named-interfaces/ios-performance-measurement:interfaces/ios-performance-measurement:name/ios-performance-measurement:probe/ios-performance-measurement:measurement-mode-v2" {
    deviate replace {
      type enumeration {
        enum two-way;
      }
    }
  }

  deviation "/ios:native/ios:performance-measurement/ios-performance-measurement:delay-profile/ios-performance-measurement:sr-policy/ios-performance-measurement:probe/ios-performance-measurement:measurement-mode-v2" {
    deviate replace {
      type enumeration {
        enum two-way;
        enum loopback;
      }
    }
  }

  deviation "/ios:native/ios:performance-measurement/ios-performance-measurement:delay-profile/ios-performance-measurement:named-sr-policy/ios-performance-measurement:sr-policy/ios-performance-measurement:name/ios-performance-measurement:probe/ios-performance-measurement:measurement-mode-v2" {
    deviate replace {
      type enumeration {
        enum two-way;
        enum loopback;
      }
    }
  }

  deviation "/ios:native/ios:performance-measurement/ios-performance-measurement:delay-profile/ios-performance-measurement:interfaces/ios-performance-measurement:probe/ios-performance-measurement:measurement-mode/ios-performance-measurement:mode-choice/ios-performance-measurement:one-way/ios-performance-measurement:one-way" {
    deviate not-supported;
  }

  deviation "/ios:native/ios:performance-measurement/ios-performance-measurement:delay-profile/ios-performance-measurement:named-interfaces/ios-performance-measurement:interfaces/ios-performance-measurement:name/ios-performance-measurement:probe/ios-performance-measurement:measurement-mode/ios-performance-measurement:mode-choice/ios-performance-measurement:one-way/ios-performance-measurement:one-way" {
    deviate not-supported;
  }

  deviation "/ios:native/ios:performance-measurement/ios-performance-measurement:delay-profile/ios-performance-measurement:sr-policy/ios-performance-measurement:probe/ios-performance-measurement:measurement-mode/ios-performance-measurement:mode-choice/ios-performance-measurement:one-way/ios-performance-measurement:one-way" {
    deviate not-supported;
  }

  deviation "/ios:native/ios:performance-measurement/ios-performance-measurement:delay-profile/ios-performance-measurement:named-sr-policy/ios-performance-measurement:sr-policy/ios-performance-measurement:name/ios-performance-measurement:probe/ios-performance-measurement:measurement-mode/ios-performance-measurement:mode-choice/ios-performance-measurement:one-way/ios-performance-measurement:one-way" {
    deviate not-supported;
  }
}
