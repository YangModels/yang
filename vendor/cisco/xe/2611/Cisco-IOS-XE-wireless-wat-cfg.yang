module Cisco-IOS-XE-wireless-wat-cfg {
  yang-version 1.1;
  namespace "http://cisco.com/ns/yang/Cisco-IOS-XE-wireless-wat-cfg";
  prefix ios-xe-wat-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     global Wireless Active Testing (WAT) configurational data.
     Copyright (c) 2025 by Cisco Systems, Inc.
     All rights reserved.";

  revision 2025-07-01 {
    description
      "Initial revision";
    reference
      "1.0.0";
    cisco-semver:module-version "1.0.0";
  }

  grouping wat-config {
    description
      "Wireless Active Testing Configuration";
    leaf wat-enable {
      type boolean;
      default "true";
      description
        "Enable WAT at global level";
    }
    leaf te-conn-str {
      type string {
        length "0..196" {
          error-message "ThousandEyes connection string must not be greater than 196 characters";
          error-app-tag "must-violation";
        }
        pattern '[A-Za-z0-9/+-_=.]*' {
          error-message "ThousandEyes connection string can only have Base64 characters";
          error-app-tag "pattern-violation";
        }
      }
      default "";
      description
        "Represents the connection string used by the ThousandEyes agent for
         for communication with the ThousandEyes cloud";
    }
    leaf te-download-url {
      type string {
        length "0..196" {
          error-message "ThousandEyes Download URL must not be greater than 196 characters";
          error-app-tag "must-violation";
        }
        pattern '(((https?)://[A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*' {
          error-message "ThousandEyes download URL must be a valid https or http URL";
          error-app-tag "pattern-violation";
        }
      }
      default "https://downloads.thousandeyes.com/endpointagent/iox/arm64/latest.tar";
      description
        "ThousandEyes endpoint URL from which the WAT manager download the
         ThousandEyes agent IOx container";
    }
  }

  container wat-cfg-data {
    description
      "WAT configurational data";
    container wat-config {
      presence "wat-config";
      description
        "Wireless Active Testing (WAT) ThousandEyes configurations";
      uses ios-xe-wat-cfg:wat-config;
    }
  }
}
