module Cisco-IOS-XE-dns-oper {
  yang-version 1.1;
  namespace "http://cisco.com/ns/yang/Cisco-IOS-XE-dns-oper";
  prefix dns-ios-xe-oper;

  import Cisco-IOS-XE-common-types {
    prefix common-types-ios-xe;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of Cisco DNS operational information.
     Copyright (c) 2023 by Cisco Systems, Inc.
     All rights reserved.";

  revision 2023-11-01 {
    description
      "Initial revision";
    reference
      "1.0.0";
    cisco-semver:module-version "1.0.0";
  }

  typedef dns-source-type {
    type enumeration {
      enum source-type-static {
        value 0;
        description
          "IPv4/IPv6 address configured by user";
      }
      enum source-type-dhcp {
        value 1;
        description
          "IPv4/IPv6 address learned via DHCP";
      }
    }
    description
      "Source type of the DNS IPv4/IPv6 address";
  }

  grouping dns-name-server-data {
    description
      "DNS IPv4/IPv6 name server data";
    leaf ip-addr {
      type inet:ip-address;
      description
        "DNS IPv4/IPv6 address";
    }
    leaf source {
      type dns-ios-xe-oper:dns-source-type;
      description
        "DNS IPv4/IPv6 address source";
    }
  }

  grouping dns-name-server {
    description
      "DNS IPv4/IPv6 name server information";
    list name-server {
      description
        "DNS IPv4/IPv6 name server data";
      uses dns-ios-xe-oper:dns-name-server-data;
    }
  }

  grouping dns-name-server-key {
    description
      "DNS IPv4/IPv6 name server key information";
    leaf ni-name {
      type string {
        length "0..32";
      }
      description
        "Network instance name. If the Network instance type is net-inst-default, then name is not meaningful";
    }
    leaf ni-type {
      type common-types-ios-xe:net-inst-type;
      description
        "Network instance type. Differentiates between the default routing instance and VRFs";
    }
  }

  container dns-oper-data {
    config false;
    description
      "Cisco DNS IPv4/IPv6 name server data";
    list dns-name-server {
      key "ni-name ni-type";
      description
        "List of IPv4/IPv6 name server data";
      uses dns-ios-xe-oper:dns-name-server;
      uses dns-ios-xe-oper:dns-name-server-key;
    }
  }
}
