module Cisco-IOS-XE-cellular {
  yang-version 1.1;
  namespace "http://cisco.com/ns/yang/Cisco-IOS-XE-cellular";
  prefix ios-cell;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Cellular Interfaces.
     Copyright (c) 2017, 2018 by Cisco Systems, Inc.
     All rights reserved.";

  revision 2022-11-01 {
    description
      "- Update yang-version to 1.1";
    cisco-semver:module-version "1.1.0";
  }
  revision 2019-07-01 {
    description
      "Establish semantic version baseline";
    cisco-semver:module-version "1.0.0";
  }
  revision 2018-05-01 {
    description
      "Move dialer related model to dialer yang file";
  }
  revision 2017-12-20 {
    description
      "Add dialer and dialer-list";
  }
  revision 2017-12-13 {
    description
      "Add interface cellular / dialer-group and pulse-time";
  }
  revision 2017-02-07 {
    description
      "Initial revision";
  }

  grouping config-interface-cellular-grouping {
    leaf pulse-time {
      description
        "Assign interface to dialer-list";
      type uint8 {
        range "0..60";
      }
    }
    container async {
      leaf mode {
        type enumeration {
          enum interactive;
        }
      }
    }
  }

  augment "/ios:native/ios:interface/ios:Cellular" {
    uses config-interface-cellular-grouping;
  }
}
