module cisco-xe-openconfig-network-instance-l2-deviation {
  namespace "http://cisco.com/ns/cisco-xe-openconfig-network-instance-l2-deviation";
  prefix oc-netinst-l2-devs;

  import openconfig-network-instance {
    prefix oc-netinst;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-network-instance-l2 module.";

  revision 2023-11-01 {
    description
      "Initial Revision";
  }

  deviation "/oc-netinst:network-instances/oc-netinst:network-instance/oc-netinst:fdb/oc-netinst:l2rib" {
    deviate not-supported;
    description
      "Currently not supported";
  }
}
