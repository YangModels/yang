module Cisco-IOS-XE-fwd-oper {
  yang-version 1.1;
  namespace "http://cisco.com/ns/yang/Cisco-IOS-XE-fwd-oper";
  prefix fwd-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE Forwarding operational data.
     Copyright (c) 2025 by Cisco Systems, Inc.
     All rights reserved.";

  revision 2025-07-01 {
    description
      "Initial revision";
    reference
      "1.0.0";
    cisco-semver:module-version "1.0.0";
  }

  typedef fib-origin-proto {
    type enumeration {
      enum fib-origin-proto-none {
        value 0;
        description
          "Origin Protocol: NONE";
      }
      enum fib-origin-proto-bgp {
        value 1;
        description
          "Origin Protocol: BGP";
      }
      enum fib-origin-proto-igp {
        value 2;
        description
          "Origin Protocol: IGP";
      }
      enum fib-origin-proto-pnni {
        value 3;
        description
          "Origin Protocol: Private Network-to-Network Interface";
      }
      enum fib-origin-proto-static {
        value 4;
        description
          "Origin Protocol: STATIC";
      }
      enum fib-origin-proto-mobile {
        value 5;
        description
          "Origin Protocol: MOBILE";
      }
      enum fib-origin-proto-rip {
        value 6;
        description
          "Origin Protocol: RIP";
      }
      enum fib-origin-proto-nhrp {
        value 7;
        description
          "Origin Protocol: NHRP";
      }
      enum fib-origin-proto-connected {
        value 8;
        description
          "Origin Protocol: CONNECTED";
      }
      enum fib-origin-proto-igrp {
        value 9;
        description
          "Origin Protocol: Interior Gateway Routing Protocol";
      }
      enum fib-origin-proto-piro {
        value 10;
        description
          "Origin Protocol: Protocol Independent Routing Optimization";
      }
      enum fib-origin-proto-ospf {
        value 11;
        description
          "Origin Protocol: OSPF";
      }
      enum fib-origin-proto-isis {
        value 12;
        description
          "Origin Protocol: ISIS";
      }
      enum fib-origin-proto-igrp2 {
        value 13;
        description
          "Origin Protocol: EIGRP";
      }
      enum fib-origin-proto-iso-igrp {
        value 14;
        description
          "Origin Protocol: ISO Interior Gateway Routing Protocol";
      }
      enum fib-origin-proto-nlsp {
        value 15;
        description
          "Origin Protocol: NLSP";
      }
      enum fib-origin-proto-other {
        value 16;
        description
          "Origin Protocol: OTHER";
      }
      enum fib-origin-proto-fstatic {
        value 17;
        description
          "Origin Protocol: Floating STATIC";
      }
      enum fib-origin-proto-odr {
        value 18;
        description
          "Origin Protocol: On-Demand Routing";
      }
      enum fib-origin-proto-iso-atm-static {
        value 19;
        description
          "Origin Protocol: ATM STATIC";
      }
      enum fib-origin-proto-dnet-conv {
        value 20;
        description
          "Origin Protocol: DECNET";
      }
      enum fib-origin-proto-esis {
        value 21;
        description
          "Origin Protocol: End System-to-Intermediate System Routing";
      }
      enum fib-origin-proto-clns-ebgp {
        value 22;
        description
          "Origin Protocol: CLNS EBGP";
      }
      enum fib-origin-proto-ospfv3 {
        value 23;
        description
          "Origin Protocol: OSPFV3";
      }
      enum fib-origin-proto-hsrp {
        value 24;
        description
          "Origin Protocol: HSRP";
      }
      enum fib-origin-proto-app {
        value 25;
        description
          "Origin Protocol: APP";
      }
      enum fib-origin-proto-omp-agent {
        value 26;
        description
          "Origin Protocol: OMP AGENT";
      }
      enum fib-origin-proto-nat-route {
        value 27;
        description
          "Origin Protocol: NAT ROUTE";
      }
      enum fib-origin-proto-lisp {
        value 28;
        description
          "Origin Protocol: LISP";
      }
      enum fib-origin-proto-lisp-dyn-eid {
        value 29;
        description
          "Origin Protocol: LISP Dynamic EID";
      }
      enum fib-origin-proto-lisp-other {
        value 30;
        description
          "Origin Protocol: LISP OTHER";
      }
      enum fib-origin-proto-fib-local {
        value 31;
        description
          "Origin Protocol: FIB LOCAL";
      }
      enum fib-origin-proto-fib-local-nexthop {
        value 32;
        description
          "Origin Protocol: FIB LOCAL NEXTHOP";
      }
      enum fib-origin-proto-fib-receive {
        value 33;
        description
          "Origin Protocol: FIB RECEIVE";
      }
      enum fib-origin-proto-fib-other {
        value 34;
        description
          "Origin Protocol: FIB OTHER";
      }
    }
    description
      "FIB Origin Protocol Types";
  }

  grouping fib-ipv4-entry {
    description
      "IPv4 FIB Entry";
    leaf prefix {
      type inet:ipv4-prefix;
      description
        "IPv4 Prefix";
    }
    leaf packets-fwd {
      type uint64;
      description
        "Packets Forwarded";
    }
    leaf octets-fwd {
      type uint64;
      description
        "Octets Forwarded";
    }
    leaf nhg-id {
      type uint64;
      description
        "Next-Hop-Group ID";
    }
    leaf origin-proto {
      type fwd-ios-xe-oper:fib-origin-proto;
      description
        "Origin Protocol";
    }
  }

  grouping fib-ipv4-ni-entry {
    description
      "IPv4 FIB Network Instance";
    leaf ni-name {
      type string;
      description
        "Network Instance name";
    }
    leaf num-entries {
      type uint32;
      description
        "Number of IPv4 forwarding entries in the Network Instance";
    }
    list fib-ipv4-entry {
      key "prefix";
      description
        "Forwarding entries in the Network Instance";
      uses fwd-ios-xe-oper:fib-ipv4-entry;
    }
  }

  grouping fib-ipv6-entry {
    description
      "IPv6 FIB Entry";
    leaf prefix {
      type inet:ipv6-prefix;
      description
        "IPv6 Prefix";
    }
    leaf packets-fwd {
      type uint64;
      description
        "Packets Forwarded";
    }
    leaf octets-fwd {
      type uint64;
      description
        "Octets Forwarded";
    }
    leaf nhg-id {
      type uint64;
      description
        "Next-Hop-Group ID";
    }
    leaf origin-proto {
      type fwd-ios-xe-oper:fib-origin-proto;
      description
        "Origin Protocol";
    }
  }

  grouping fib-ipv6-ni-entry {
    description
      "IPv6 FIB Network Instance";
    leaf ni-name {
      type string;
      description
        "Network Instance name";
    }
    leaf num-entries {
      type uint32;
      description
        "Number of IPv6 forwarding entries in the Network Instance";
    }
    list fib-ipv6-entry {
      key "prefix";
      description
        "Forwarding entries in the Network Instance";
      uses fwd-ios-xe-oper:fib-ipv6-entry;
    }
  }

  grouping nhg-nh-entry {
    description
      "Next-hop-group Next-hop Entry";
    leaf nh-id {
      type uint64;
      description
        "Next-hop ID";
    }
    leaf weight {
      type uint64;
      description
        "weight";
    }
  }

  grouping nhg-entry {
    description
      "Next-hop Group Entry";
    leaf nhg-id {
      type uint64;
      description
        "Next-hop Group ID";
    }
    leaf refcount {
      type uint32;
      description
        "Reference count for this entry";
    }
    list nhg-nh-entry {
      key "nh-id";
      description
        "Next-hops in the Next-hop Group";
      uses fwd-ios-xe-oper:nhg-nh-entry;
    }
  }

  grouping nhg-ni-entry {
    description
      "Next-hop Group Network Instance Table";
    leaf ni-name {
      type string;
      description
        "The name of the Network Instance";
    }
    leaf num-entries {
      type uint32;
      description
        "Number of entries in the Next-Hop Group Table";
    }
    list nhg-entry {
      key "nhg-id";
      description
        "Next-Hop Group entries in the Network Instance";
      uses fwd-ios-xe-oper:nhg-entry;
    }
  }

  grouping nh-entry {
    description
      "Next-hop Entry";
    leaf nh-id {
      type uint64;
      description
        "Next-hop ID";
    }
    leaf addr {
      type inet:ip-address;
      description
        "Next-hop Address";
    }
    leaf mac {
      type yang:mac-address;
      description
        "Next-hop MAC Address";
    }
    leaf pak-fwd {
      type uint64;
      description
        "Packets Forwarded";
    }
    leaf oct-fwd {
      type uint64;
      description
        "Octets Forwarded";
    }
    leaf vni-lbl {
      type uint32;
      description
        "VNI Label";
    }
    leaf tun-src-ip {
      type inet:ip-address;
      description
        "Tunnel Source IP";
    }
    leaf if-name {
      type string;
      description
        "Interface Name";
    }
    leaf sub-if-name {
      type string;
      description
        "Sub-Interface Name";
    }
  }

  grouping nh-ni-entry {
    description
      "Next-hop Network Instance Table";
    leaf ni-name {
      type string;
      description
        "The name of the Network Instance";
    }
    leaf num-entries {
      type uint32;
      description
        "Number of entries in the Next-hop Table";
    }
    list nh-entry {
      key "nh-id";
      description
        "Next-hop entries in the Network Instance";
      uses fwd-ios-xe-oper:nh-entry;
    }
  }

  container fwd-oper-data {
    config false;
    description
      "IOS Forwarding operational data";
    list fib-ipv4-ni {
      key "ni-name";
      description
        "FIB IPv4 Network Instance Table";
      uses fwd-ios-xe-oper:fib-ipv4-ni-entry;
    }
    list fib-ipv6-ni {
      key "ni-name";
      description
        "FIB IPv6 Network Instance Table";
      uses fwd-ios-xe-oper:fib-ipv6-ni-entry;
    }
    list nhg-ni {
      key "ni-name";
      description
        "Nexthop-Group Network Instance Table";
      uses fwd-ios-xe-oper:nhg-ni-entry;
    }
    list nh-ni {
      key "ni-name";
      description
        "Nexthop Network Instance Table";
      uses fwd-ios-xe-oper:nh-ni-entry;
    }
  }
}
