module Cisco-IOS-XE-buffers {
  yang-version 1.1;
  namespace "http://cisco.com/ns/yang/Cisco-IOS-XE-buffers";
  prefix ios-buffers;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE buffers YANG model.
     Copyright (c) 2023 by Cisco Systems, Inc.
     All rights reserved.";

  revision 2024-07-01 {
    description
      "-Added support for buffers YANG model";
  }
  revision 2023-11-01 {
    description
      "-Establish semantic version baseline";
    cisco-semver:module-version "1.0.0";
  }

  grouping buffers-type-grouping {
    leaf initial {
      description
        "Number of temporary buffers allocated at system reload";
      type uint32 {
        range "0..65536";
      }
      default "0";
    }
    leaf max-free {
      description
        "Maximum number of free buffers";
      type uint32 {
        range "0..65536";
      }
      default "300";
    }
    leaf min-free {
      description
        "Minimum number of free buffers";
      must 'current() <= ../max-free' {
        error-message "Min-free must be less than or equal to Max-free";
      }
      type uint32 {
        range "0..65536";
      }
      default "0";
    }
    leaf permanent {
      description
        "Number of permanent buffers";
      type uint32 {
        range "0..65536";
      }
      default "100";
    }
  }

  grouping config-buffers-grouping {
    container buffers {
      description
        "Configuration to adjust system buffer pool parameters";
      container big {
        description
          "Big buffer configuration";
        uses buffers-type-grouping {
          refine "max-free" {
            default "1800";
          }
          refine "min-free" {
            default "50";
          }
          refine "permanent" {
            default "900";
          }
        }
      }
      container verybig {
        description
          "Very Big buffer configuration";
        uses buffers-type-grouping;
      }
      container large {
        description
          "Large buffer configuration";
        uses buffers-type-grouping;
      }
      container huge {
        description
          "Huge buffer configuration";
        uses buffers-type-grouping {
          refine "max-free" {
            default "33";
          }
          refine "permanent" {
            default "20";
          }
        }
        leaf size {
          description
            "Size of huge buffers";
          type uint32 {
            range "18024..65535";
          }
          default "18024";
        }
      }
      container VeryLarge {
        description
          "Very Large buffer configuration";
        uses buffers-type-grouping;
      }
      container fastswitching {
        description
          "Fast switching particle pool";
        leaf initial {
          description
            "Number of temporary buffers allocated at system reload";
          type uint32 {
            range "0|512..65535";
          }
          default "0";
        }
        leaf max-free {
          description
            "Maximum number of free buffers";
          type uint32 {
            range "512..65535";
          }
          default "1024";
        }
        leaf min-free {
          description
            "Minimum number of free buffers";
          must 'current() <= ../max-free' {
            error-message "Min-free must be less than or equal to Max-free";
          }
          type uint32 {
            range "128|512..65535";
          }
          default "128";
        }
        leaf permanent {
          description
            "Number of permanent buffers";
          type uint32 {
            range "384|512..65535";
          }
          default "384";
        }
      }
    }
  }

  augment "/ios:native" {
    uses config-buffers-grouping;
  }
}
