module Cisco-IOS-XE-geo {
  yang-version 1.1;
  namespace "http://cisco.com/ns/yang/Cisco-IOS-XE-geo";
  prefix ios-geo;

  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Geo-location Database Yang model.
     Copyright (c) 2020 by Cisco Systems, Inc.
     All rights reserved.";

  revision 2022-11-01 {
    description
      "- Update yang-version to 1.1";
  }
  revision 2020-11-01 {
    description
      "Initial revision";
  }

  grouping config-geo-grouping {
    container geo {
      description
        "Configure Geo-Location Database";
      leaf database {
        description
          "Configure Geo-Location Database";
        type empty;
      }
    }
  }

  augment "/ios:native" {
    uses config-geo-grouping;
  }
}
