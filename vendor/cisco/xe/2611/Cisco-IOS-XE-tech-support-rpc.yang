module Cisco-IOS-XE-tech-support-rpc {
  yang-version 1.1;
  namespace "http://cisco.com/ns/yang/Cisco-IOS-XE-tech-support-rpc";
  prefix tech-support-ios-xe-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2023, 2025 by Cisco Systems, Inc.
     All rights reserved.";

  revision 2026-02-01 {
    description
      "Added a new parameter to the tech-support-archive RPC";
    reference
      "1.1.0";
    cisco-semver:module-version "1.1.0";
  }
  revision 2023-11-01 {
    description
      "Initial revision";
    reference
      "1.0.0";
    cisco-semver:module-version "1.0.0";
  }

  typedef file-info-list {
    type enumeration {
      enum default {
        value 0;
        description
          "This is the default option for tech-support file,
           which will generate a file containing all system
           information for technical support";
      }
    }
    description
      "Options for tech-support file.";
  }

  grouping archive-options {
    description
      "Options for tech-support archive generation. Tech-support
       archive is an archive of the tech-support file and system
       report.";
    leaf archive {
      type boolean;
      default "true";
      description
        "Tech-support archive generate option.
         If this option is marked as 'true',
         tech-support archive will be generated.
         The tech-support file included in the archive will be equivalent
         to the output generated by 'show tech-support'.";
    }
    leaf archive-wireless {
      type empty;
      description
        "Tech-support wireless archive generate option.
         If this option is present, tech-support wireless file will be generated.
         The tech-support wireless file included in the archive will be equivalent
         to the output generated by 'show tech-support wireless'.";
    }
  }

  grouping file-options {
    description
      "Choose one of these options, only if the tech-support file is needed.
       Tech-support file refers to the output generated by 'show tech-support'
       and the options associated with it.";
    choice info-type-choice {
      mandatory true;
      description
        "Options for technical support";
      case default {
        leaf default-option {
          type boolean;
          default "true";
          description
            "This is option will gather all tech-support information, except for
             protocol-specific tech-support information. Selecting this option
             will generate tech-support file which contains data collected by
             the basic version of show-tech support CLI - 'show tech-support'.";
        }
      }
    }
  }

  grouping tech-support-response {
    description
      "Response to tech-support actions";
    leaf file-name {
      type string {
        pattern '(flash:|bootflash:|crashinfo:|harddisk:)[A-Za-z_0-9]*';
      }
      description
        "File name of the tech-support archive/file that will be generated. If
         the file-name is empty, it indicates that there was failure in the
         operation, possibly an internal error or another operation was being
         processed. In such cases, the reason for failure will also be
         attached to the response message. The arrival of response does not
         indicate that the operation is complete because the tech-support
         operation takes a huge amount of time to complete and notifications
         related to the execution can be consumed by subscribing to the tech-support
         event notification model which will contain the same file-name found in this
         response message.";
    }
  }

  rpc tech-support-archive {
    description
      "RPC message for tech-support archive generation";
    input {
      uses tech-support-ios-xe-rpc:archive-options;
    }
    output {
      uses tech-support-ios-xe-rpc:tech-support-response;
    }
  }

  rpc tech-support-file {
    description
      "RPC message for tech-support file generation";
    input {
      uses tech-support-ios-xe-rpc:file-options;
    }
    output {
      uses tech-support-ios-xe-rpc:tech-support-response;
    }
  }
}
