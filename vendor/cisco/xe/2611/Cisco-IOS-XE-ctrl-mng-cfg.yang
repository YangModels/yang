module Cisco-IOS-XE-ctrl-mng-cfg {
  yang-version 1.1;
  namespace "http://cisco.com/ns/yang/Cisco-IOS-XE-ctrl-mng-cfg";
  prefix ctrl-mng-ios-xe-cfg;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for configuration data to allow management of devices by vmanage.
     Copyright (c) 2023-2025 by Cisco Systems, Inc.
     All rights reserved.";

  revision 2026-02-01 {
    description
      "- Updated constraints for WAN and tunnel interfaces to fix typo for supporting Five Gigabit Ethernet interfaces";
    reference
      "4.0.0";
    cisco-semver:module-version "4.0.0";
  }
  revision 2025-07-01 {
    description
      "- Updated constraints for WAN and tunnel interfaces to add support for Five Gigabit Ethernet interfaces";
    reference
      "3.0.0";
    cisco-semver:module-version "3.0.0";
  }
  revision 2025-03-01 {
    description
      "- Added length and pattern constraint to WAN interface name
       - Added pattern constraint to bind interface name
       - Added length and pattern constraint to config template name";
    reference
      "2.0.0";
    cisco-semver:module-version "2.0.0";
  }
  revision 2023-11-01 {
    description
      "- Added preference for using the WAN interface to exchange
         control traffic with vManage
       - Added a leaf to indicate that the device
         is managed by vManage
       - Added a leaf to display the config template name";
    reference
      "1.1.0";
    cisco-semver:module-version "1.1.0";
  }
  revision 2023-07-01 {
    description
      "Initial revision";
    reference
      "1.0.0";
    cisco-semver:module-version "1.0.0";
  }

  typedef persn-enum {
    type enumeration {
      enum personality-enum-vedge {
        value 0;
        description
          "System personality vedge";
      }
      enum personality-enum-vsmart {
        value 1;
        description
          "System personality vsmart";
      }
      enum personality-enum-vmanage {
        value 2;
        description
          "System personality vmanage";
      }
    }
    description
      "System personality type";
  }

  typedef ud-remote {
    type enumeration {
      enum ud-remote-unset {
        value 0;
        description
          "vbond unset";
      }
      enum ud-remote-inet-ip-address {
        value 1;
        description
          "Configure local IPv4 vbond address";
      }
      enum ud-remote-domain-name {
        value 2;
        description
          "Configure remote vbond";
      }
    }
    description
      "Configure remote vBond or local IPv4 vbond address";
  }

  grouping ctrl-mng-if {
    description
      "Configure interface parameters for connection to vmanage";
    leaf name {
      type string {
        length "1..127";
        pattern '(((Two|Five|Ten|Forty)?GigabitEthernet)|((TwentyFive|Hundred)GigE)|Port\-channel|Cellular|Dialer|Loopback)[0-9]+.*';
      }
      description
        "WAN interface name";
    }
    leaf tunnel-if-enabled {
      type boolean;
      default "true";
      description
        "Enable interface as a secure WAN transport connection";
    }
    leaf hello-interval {
      type uint32 {
        range "100 .. 600000";
      }
      units "seconds";
      default "1000";
      description
        "Interval between hello packets sent on a WAN connection, in seconds";
    }
    leaf bind {
      type string {
        length "1..32";
        pattern '(((Two|Five|Ten|Forty)?GigabitEthernet)|((TwentyFive|Hundred)GigE)|Port\-channel|Cellular|Dialer)[0-9]+.*';
      }
      description
        "Bind loopback tunnel interface to a physical interface";
    }
    leaf hello-tolr {
      type uint32 {
        range "12 .. 6000";
      }
      must '((2000 * .) >= (../hello-interval))' {
        error-message "hello-tolerance should be at least twice the hello-interval";
        error-app-tag "must-violation";
      }
      default "12";
      description
        "Interval to wait since the last hello packet was sent on a WAN connection before declaring it to be down";
    }
    leaf vmanage-con-pref {
      type uint8 {
        range "0 .. 8";
      }
      default "5";
      description
        "Preference for using the WAN interface to exchange control traffic with vManage";
    }
  }

  grouping vbond-info {
    description
      "configure vbond parameters";
    leaf port {
      type uint16 {
        range "1 .. 65335";
      }
      description
        "Port number to connect to vbond orchestrator";
    }
    choice vbond-remote-discrim-choice {
      description
        "Configure remote vBond or local IPv4 vbond address";
      case ud-remote-inet-ip-address {
        leaf ip {
          type inet:ip-address;
          description
            "IPv4 or IPv6 address of vbond orchestrator";
        }
      }
      case ud-remote-domain-name {
        leaf name {
          type string {
            length "1..253";
            pattern '((([a-zA-Z0-9_]([a-zA-Z0-9\-_]){0,61})?[a-zA-Z0-9]\.)*([a-zA-Z0-9_]([a-zA-Z0-9\-_]){0,61})?[a-zA-Z0-9]\.?)|\.';
          }
          description
            "Name that point to vbond orchestrator";
        }
      }
    }
  }

  grouping ctrl-mng-config {
    description
      "Configuration info  to allow management by vmanage";
    leaf ctrl-mng-enable {
      type boolean;
      default "false";
      description
        "Knob to enable management by vmanage";
    }
    leaf persn {
      type ctrl-mng-ios-xe-cfg:persn-enum;
      description
        "System type";
    }
    leaf auto-sys-ip {
      type inet:ipv4-address;
      description
        "System-IP automatically generated by vManage for device";
    }
    leaf sys-ip {
      type inet:ipv4-address;
      description
        "System IP address of a device";
    }
    leaf site-id {
      type uint32;
      description
        "Numeric identifier of the site in the network";
    }
    leaf ipv6-strict-control {
      type boolean;
      default "false";
      description
        "Establish IPv6 control connection in a dual stack IP";
    }
    leaf org-name {
      type string {
        length "1..128";
        pattern '[^#$]*';
      }
      description
        "Name of the organization";
    }
    leaf sp-org-name {
      type string {
        length "1..128";
        pattern '[^#$]*';
      }
      description
        "Name of the SP organization";
    }
    container vbond {
      description
        "Specifies the IP address and other information related to vbond orchestrator";
      uses ctrl-mng-ios-xe-cfg:vbond-info;
    }
    leaf descr {
      type string {
        length "1..32";
        pattern '[^<>]*';
      }
      description
        "System description";
    }
    leaf sys-tunnel-mtu {
      type uint16 {
        range "500 .. 2000";
      }
      default "1024";
      description
        "Control tunnel MTU";
    }
    leaf upgrade-confirm {
      type uint8 {
        range "5 .. 60";
      }
      units "minutes";
      default "15";
      description
        "Software upgrade confirmation timeout";
    }
    container ctrl-mng-ifs {
      description
        "Interface list for control connection to vmanage";
      list ctrl-mng-if {
        key "name";
        description
          "Interface for control connection to vmanage";
        uses ctrl-mng-ios-xe-cfg:ctrl-mng-if;
      }
    }
    leaf is-vmanaged {
      type boolean;
      description
        "Device is managed by vManage";
    }
    leaf config-template-name {
      type string {
        length "1..128";
        pattern '[^&<>!"]*';
      }
      description
        "Configuration template assigned by the vManage";
    }
  }

  container ctrl-mng-cfg-data {
    description
      "Configuration data to allow device to be managed by vmanage";
    container ctrl-mng-config {
      presence "ctrl-mng-config";
      description
        "Configuration data to allow device management by vmanage";
      uses ctrl-mng-ios-xe-cfg:ctrl-mng-config {
        refine "vbond/port" {
          default "12346";
        }
      }
    }
  }
}
