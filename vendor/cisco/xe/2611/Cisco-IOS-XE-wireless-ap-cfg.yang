module Cisco-IOS-XE-wireless-ap-cfg {
  yang-version 1.1;
  namespace "http://cisco.com/ns/yang/Cisco-IOS-XE-wireless-ap-cfg";
  prefix wireless-ap-cfg;

  import Cisco-IOS-XE-wireless-ap-types {
    prefix wireless-ap-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AP configuration.
     Copyright (c) 2016-2020, 2022 by Cisco Systems, Inc.
     All rights reserved.";

  revision 2026-02-01 {
    description
      "Added AP name under static AP configuration";
    reference
      "9.0.0";
    cisco-semver:module-version "9.0.0";
  }
  revision 2025-03-01 {
    description
      "Range of AP rule priority modified";
    reference
      "8.0.0";
    cisco-semver:module-version "8.0.0";
  }
  revision 2024-11-01 {
    description
      "Removing length constraint for location description";
    reference
      "7.1.0";
    cisco-semver:module-version "7.1.0";
  }
  revision 2024-07-01 {
    description
      "Added constraints for filter and rule priority.";
    reference
      "7.0.0";
    cisco-semver:module-version "7.0.0";
  }
  revision 2022-11-01 {
    description
      "- Update yang-version to 1.1
       - Added AP priming filter and AP MAC configuration.";
    reference
      "6.2.0";
    cisco-semver:module-version "6.2.0";
  }
  revision 2022-07-01 {
    description
      "- Added AAA Location attributes support";
    reference
      "6.1.0";
    cisco-semver:module-version "6.1.0";
  }
  revision 2021-03-01 {
    description
      "-Add ASCII 32-126 and leading/trailing spaces restriction for AP location name";
    reference
      "6.0.0";
    cisco-semver:module-version "6.0.0";
  }
  revision 2020-07-01 {
    description
      "- Updated site-tag description";
    reference
      "5.0.1";
    cisco-semver:module-version "5.0.1";
  }
  revision 2019-06-25 {
    description
      "- Deprecating filter priority, replacing filter priority with
         rule priority with range [0-1023].
       - Added semantic version.
       - Fix constraint for tag source priority.";
    reference
      "5.0.0";
    cisco-semver:module-version "5.0.0";
  }
  revision 2018-10-29 {
    description
      "- Removing default empty strings from filter-name and tag-info
       - Cleaned up spelling errors in descriptions.";
    reference
      "4.0.0";
    cisco-semver:module-version "4.0.0";
  }
  revision 2018-05-10 {
    description
      "- Added new range constraints in grouping st-tag-source-priority-config
       - Added new length constraints in grouping st-tag-list-config
       - Added location-entries";
    reference
      "3.0.0";
    cisco-semver:module-version "3.0.0";
  }
  revision 2018-03-08 {
    description
      "Add AP filter priority list";
    reference
      "2.1.0";
    cisco-semver:module-version "2.1.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping ap-tag {
    description
      "Configuration of ap tag";
    leaf ap-mac {
      type yang:mac-address;
      description
        "mac address of Access point";
    }
    leaf policy-tag {
      type string;
      default "";
      description
        "Configuration of policy tag";
    }
    leaf site-tag {
      type string;
      default "";
      description
        "Site Tag configuration for an AP.
         APs with same named Site Tag form a site.
         Cisco recommendations for number of APs in a site vary by platform and deployment model.
         Please follow these recommendation for your platform and deployment model";
    }
    leaf rf-tag {
      type string;
      default "";
      description
        "Configuration of rf tag";
    }
    leaf priming-profile {
      type string;
      description
        "Configuration of AP priming profile";
    }
    leaf ap-name {
      type string {
        length "0..32";
        pattern '[!-~]*';
      }
      description
        "Configuration of AP name";
    }
  }

  grouping st-tag-source-priority-config {
    description
      "Priority for tag source";
    leaf priority {
      type uint8 {
        range "0 .. 4";
      }
      description
        "Priority for tag source";
    }
    leaf tag-src {
      type wireless-ap-types:enm-ap-tag-source;
      must "(../tag-src != 'tag-source-static' and ../tag-src != 'tag-source-default') or
            (../tag-src = 'tag-source-static' and ../priority = 0) or
            (../tag-src = 'tag-source-default' and ../priority = 4)" {
        error-message "Static and Default tag sources must have priorities 0 and 4 respectively";
        error-app-tag "must-violation";
      }
      description
        "tag source";
    }
  }

  grouping st-tag-list-config {
    description
      "ap tag list";
    leaf policy-tag {
      type string {
        length "0..32";
      }
      description
        "policy tag";
    }
    leaf site-tag {
      type string {
        length "0..32";
      }
      description
        "site tag";
    }
    leaf rf-tag {
      type string {
        length "0..32";
      }
      description
        "rf tag";
    }
  }

  grouping ap-filter-priority-config {
    description
      "Priority for AP filter";
    leaf priority {
      type uint8 {
        range "0 .. 127";
      }
      must "(../filter-name != '')" {
        error-message "Priority cannot be assigned to filter with no name";
        error-app-tag "must-violation";
      }
      description
        "Priority of filter";
    }
    leaf filter-name {
      type string;
      must "../../../ap-filter-configs/ap-filter-config[filter-name = current()]/filter-string != ''" {
        error-message "Priority cannot be assigned to filter with no regular expression";
        error-app-tag "must-violation";
      }
      description
        "Name of the filter.";
    }
  }

  grouping st-ap-rule-priority-config {
    description
      "Priority for AP filter rule";
    leaf priority {
      type uint32 {
        range "0 .. 1023";
      }
      must "(../filter-name != '')" {
        error-message "Priority cannot be assigned to filter with no name";
        error-app-tag "must-violation";
      }
      description
        "Priority of filter rule";
    }
    leaf filter-name {
      type string;
      must "../../../ap-filter-configs/ap-filter-config[filter-name = current()]/filter-string != ''" {
        error-message "Priority cannot be assigned to filter with no regular expression";
        error-app-tag "must-violation";
      }
      description
        "Name of the filter rule";
    }
  }

  grouping st-ap-filter-config {
    description
      "ap filter structure";
    leaf filter-name {
      type string;
      description
        "filter name";
    }
    leaf filter-string {
      type string;
      description
        "regular expression string";
    }
    leaf filter-priority {
      type uint8;
      description
        "filter priority";
    }
    container apply-tag-list {
      description
        "applying tag list";
      uses wireless-ap-cfg:st-tag-list-config;
    }
    leaf filter-type {
      type wireless-ap-types:enm-ap-filter-type;
      description
        "AP filter type";
    }
    leaf priming-profile {
      type string;
      default "";
      description
        "Applied AP priming profile name";
    }
  }

  grouping associated-aps {
    description
      "Structure have location configuration information.";
    leaf ap-mac {
      type yang:mac-address;
      description
        "AP MAC address.";
    }
  }

  grouping st-location-tags {
    description
      "AP location's tag information";
    leaf policy-tag {
      type string {
        length "0..32";
      }
      default "default-policy-tag";
      description
        "Policy tag for AP location";
    }
    leaf site-tag {
      type string {
        length "0..32";
      }
      default "default-site-tag";
      description
        "Site tag for AP location";
    }
    leaf rf-tag {
      type string {
        length "0..32";
      }
      default "default-rf-tag";
      description
        "RF tag for AP location";
    }
  }

  grouping st-location-attributes {
    description
      "AAA Location attribute identifiers";
    leaf civic-id {
      type string {
        length "0..215";
      }
      default "";
      description
        "Civic profile identifier for AAA Location information";
    }
    leaf geo-id {
      type string {
        length "0..215";
      }
      default "";
      description
        "Geo profile identifier for AAA Location information";
    }
    leaf oper-id {
      type string {
        length "0..215";
      }
      default "";
      description
        "Operator identifier for AAA Location information";
    }
  }

  grouping location-config {
    description
      "Location configuration information for AP";
    leaf location-name {
      type string {
        length "1..32";
        pattern '[!-~]([ -~]*[!-~])?';
      }
      description
        "Name of the AP location";
    }
    leaf description {
      type string;
      description
        "Description for location of AP";
    }
    container tag-info {
      description
        "Tag information for AP location";
      uses wireless-ap-cfg:st-location-tags;
    }
    container associated-aps {
      description
        "Container of associated APs";
      list associated-ap {
        key "ap-mac";
        description
          "Associated AP information";
        uses wireless-ap-cfg:associated-aps;
      }
    }
    container location-attributes {
      description
        "Location Attribute information for APs";
      uses wireless-ap-cfg:st-location-attributes;
    }
  }

  container ap-cfg-data {
    description
      "AP tag configuration";
    container location-entries {
      description
        "Structure has location configuration information.";
      list location-entry {
        key "location-name";
        description
          "Structure has location configuration information.";
        uses wireless-ap-cfg:location-config;
      }
    }
    container tag-source-priority-configs {
      description
        "Priority for tag source";
      list tag-source-priority-config {
        key "priority";
        description
          "Priority for tag source";
        uses wireless-ap-cfg:st-tag-source-priority-config;
      }
    }
    container ap-filter-configs {
      description
        "ap filter";
      list ap-filter-config {
        key "filter-name";
        description
          "ap filter";
        uses wireless-ap-cfg:st-ap-filter-config;
      }
    }
    container ap-filter-priority-cfg-entries {
      status obsolete;
      description
        "Priority for AP filter";
      list ap-filter-priority-cfg-entry {
        key "priority";
        description
          "Priority for AP filter";
        uses wireless-ap-cfg:ap-filter-priority-config;
      }
    }
    container ap-rule-priority-cfg-entries {
      description
        "Priority for AP filter rule";
      list ap-rule-priority-cfg-entry {
        key "priority";
        description
          "Priority for AP filter rule";
        uses wireless-ap-cfg:st-ap-rule-priority-config;
      }
    }
    container ap-tags {
      description
        "Configuration of AP tags";
      list ap-tag {
        key "ap-mac";
        description
          "List of AP tags";
        uses wireless-ap-cfg:ap-tag;
      }
    }
  }
}
