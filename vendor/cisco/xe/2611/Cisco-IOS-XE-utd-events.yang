module Cisco-IOS-XE-utd-events {
  yang-version 1.1;
  namespace "http://cisco.com/ns/yang/Cisco-IOS-XE-utd-events";
  prefix utd-ios-xe-events;

  import Cisco-IOS-XE-ios-common-oper {
    prefix ios-common-ios-xe-oper;
  }
  import Cisco-IOS-XE-utd-common-oper {
    prefix utd-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG Definitions
     for UTD event notification.
     Copyright (c) 2024 by Cisco Systems, Inc.
     All rights reserved.";

  revision 2024-03-01 {
    description
      "Initial revision";
    reference
      "1.0.0";
    cisco-semver:module-version "1.0.0";
  }

  typedef utd-connectivity-type-val {
    type enumeration {
      enum utd-conn-type-none {
        value 0;
        description
          "Unified Threat Defense (UTD) connectivity type is none";
      }
      enum utd-conn-type-urlf {
        value 1;
        description
          "Unified Threat Defense (UTD) connectivity type is URL-Filtering";
      }
    }
    description
      "Unified Threat Defense (UTD) connectivity type";
  }

  grouping utd-connectivity {
    description
      "Unified Threat Defense (UTD) connectivity";
    leaf severity {
      type ios-common-ios-xe-oper:notification-severity;
      description
        "Event severity";
    }
    leaf host-name {
      type string;
      description
        "Host name";
    }
    leaf system-ip {
      type inet:ip-address;
      description
        "System IP address";
    }
    leaf type {
      type utd-ios-xe-events:utd-connectivity-type-val;
      description
        "connectivity type";
    }
    leaf timestamp {
      type yang:date-and-time;
      description
        "connectivity timestamp";
    }
    leaf status {
      type utd-common-ios-xe-oper:utd-con-state;
      description
        "connectivity status";
    }
    leaf reason {
      type utd-common-ios-xe-oper:utd-con-reason;
      description
        "connectivity down reason";
    }
  }

  notification utd-con {
    description
      "Unified Threat Defense (UTD) connectivity notification";
    uses utd-ios-xe-events:utd-connectivity;
  }
}
