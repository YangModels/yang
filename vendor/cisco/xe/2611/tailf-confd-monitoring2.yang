module tailf-confd-monitoring2 {
  namespace "http://tail-f.com/yang/confd-monitoring2";
  prefix tfcm2;

  import tailf-confd-monitoring {
    prefix tfcm;
  }

  import tailf-common-monitoring2 {
    prefix tfcg2;
    revision-date 2022-09-29;
  }

  organization "Tail-f Systems";

  description
    "This module defines status objects for monitoring of ConfD.

     Copyright 2022 Cisco Systems, Inc.
     All rights reserved.
     Permission is hereby granted to redistribute this file without
     modification.";

  revision 2022-10-03 {
      description
          "Released as part of ConfD-8.0.";
  }

  augment /tfcm:confd-state {
    uses tfcg2:common-monitoring-objects;
  }
}
