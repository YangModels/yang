module Cisco-IOS-XE-wireless-afc-cloud-oper {
  yang-version 1.1;
  namespace "http://cisco.com/ns/yang/Cisco-IOS-XE-wireless-afc-cloud-oper";
  prefix wireless-afc-cloud-oper;

  import Cisco-IOS-XE-wireless-afc-types {
    prefix wireless-afc-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AFC cloud stats
     Copyright (c) 2022-2023 by Cisco Systems, Inc.
     All rights reserved.";

  revision 2023-11-01 {
    description
      "Initial revision";
    reference
      "1.0.0";
    cisco-semver:module-version "1.0.0";
  }

  grouping st-afc-msg-info {
    description
      "AFC message information";
    leaf request-id {
      type uint64;
      description
        "Request ID";
    }
    leaf ap-mac {
      type yang:mac-address;
      description
        "AP MAC address";
    }
    leaf msg-timestamp {
      type yang:date-and-time;
      description
        "Timestamp";
    }
  }

  grouping st-afc-cloud-stats {
    description
      "AFC statistics";
    leaf num-afc-ap {
      type uint32;
      description
        "Number of APs requiring AFC service";
    }
    leaf afc-msg-sent {
      type uint64;
      description
        "Messages sent to AFC";
    }
    leaf afc-msg-rcvd {
      type uint64;
      description
        "Successful messages received from AFC";
    }
    leaf afc-msg-err {
      type uint64;
      description
        "Errored AFC messages";
    }
    leaf afc-msg-pending {
      type uint32;
      description
        "Pending AFC messages";
    }
    container last-msg-sent {
      description
        "Last inquired channel message sent";
      uses wireless-afc-cloud-oper:st-afc-msg-info;
    }
    container last-msg-rcvd {
      description
        "Last inquired channel message received";
      uses wireless-afc-cloud-oper:st-afc-msg-info;
    }
    leaf min-msg-rtt {
      type uint64;
      units "milliseconds";
      description
        "Minimum response time";
    }
    leaf max-msg-rtt {
      type uint64;
      units "milliseconds";
      description
        "Maximum response time";
    }
    leaf avg-rtt {
      type uint64;
      units "milliseconds";
      description
        "Average response time";
    }
    container healthcheck {
      description
        "AFC cloud health check";
      uses wireless-afc-types:afc-healthcheck;
    }
    leaf num-6ghz-ap {
      type uint32;
      description
        "Number of APs with 6GHz radio";
    }
  }

  container afc-cloud-oper-data {
    config false;
    description
      "AFC Cloud Operational Data Model";
    container afc-cloud-stats {
      presence "afc-cloud-stats";
      description
        "AFC cloud statistics";
      uses wireless-afc-cloud-oper:st-afc-cloud-stats;
    }
  }
}
