module Cisco-IOS-XE-aaa-deviation {
  yang-version 1.1;
  namespace "http://cisco.com/ns/yang/Cisco-IOS-XE-aaa-deviation";
  prefix ios-aaa-d;

  import Cisco-IOS-XE-native {
    prefix ios;
  }
  import Cisco-IOS-XE-aaa {
    prefix ios-aaa;
  }
  import cisco-semver {
    prefix cisco-semver;
  }

  organization
    "Cisco Systems";
  description
    "Cisco XE Native AAA Deviation YANG module for IOS
     Copyright (c) 2020 by Cisco Systems, Inc.
     All rights reserved.";

  revision 2025-07-01 {
    description
      "Added range for different interface types";
    cisco-semver:module-version "1.2.0";
  }
  revision 2024-11-01 {
    description
      "Added ip radius source-interface Vlan range deviation";
    cisco-semver:module-version "1.0.0";
  }

  deviation "/ios:native/ios:aaa/ios-aaa:group/ios-aaa:server/ios-aaa:radius/ios-aaa:ip/ios-aaa:radius/ios-aaa:source-interface/ios-aaa:interface-choice/ios-aaa:Vlan/ios-aaa:Vlan" {
    deviate replace {
      type uint16 {
        range "1..4094";
      }
    }
  }

  deviation "/ios:native/ios:aaa/ios-aaa:group/ios-aaa:server/ios-aaa:radius/ios-aaa:ipv6/ios-aaa:radius/ios-aaa:source-interface/ios-aaa:interface-choice/ios-aaa:Vlan/ios-aaa:Vlan" {
    deviate replace {
      type uint16 {
        range "1..4094";
      }
    }
  }

  deviation "/ios:native/ios:aaa/ios-aaa:group/ios-aaa:server/ios-aaa:radius/ios-aaa:ipv6/ios-aaa:radius/ios-aaa:source-interface/ios-aaa:interface-choice/ios-aaa:Tunnel/ios-aaa:Tunnel" {
    deviate replace {
      type uint32 {
        range "0..2147483647";
      }
    }
  }

  deviation "/ios:native/ios:aaa/ios-aaa:group/ios-aaa:server/ios-aaa:radius/ios-aaa:ipv6/ios-aaa:radius/ios-aaa:source-interface/ios-aaa:interface-choice/ios-aaa:Port-channel/ios-aaa:Port-channel" {
    deviate replace {
      type uint8 {
        range "1..64";
      }
    }
  }

  deviation "/ios:native/ios:aaa/ios-aaa:group/ios-aaa:server/ios-aaa:tacacsplus/ios-aaa:ip/ios-aaa:tacacs/ios-aaa:source-interface/ios-aaa:interface-choice/ios-aaa:Port-channel/ios-aaa:Port-channel" {
    deviate replace {
      type uint8 {
        range "1..64";
      }
    }
  }

  deviation "/ios:native/ios:aaa/ios-aaa:group/ios-aaa:server/ios-aaa:tacacsplus/ios-aaa:ip/ios-aaa:tacacs/ios-aaa:source-interface/ios-aaa:interface-choice/ios-aaa:Tunnel/ios-aaa:Tunnel" {
    deviate replace {
      type uint32 {
        range "0..2147483647";
      }
    }
  }

  deviation "/ios:native/ios:aaa/ios-aaa:group/ios-aaa:server/ios-aaa:tacacsplus/ios-aaa:ip/ios-aaa:tacacs/ios-aaa:source-interface/ios-aaa:interface-choice/ios-aaa:Vlan/ios-aaa:Vlan" {
    deviate replace {
      type uint16 {
        range "1..4094";
      }
    }
  }

  deviation "/ios:native/ios:aaa/ios-aaa:group/ios-aaa:server/ios-aaa:tacacsplus/ios-aaa:ipv6/ios-aaa:tacacs/ios-aaa:source-interface/ios-aaa:interface-choice/ios-aaa:Port-channel/ios-aaa:Port-channel" {
    deviate replace {
      type uint8 {
        range "1..64";
      }
    }
  }

  deviation "/ios:native/ios:aaa/ios-aaa:group/ios-aaa:server/ios-aaa:tacacsplus/ios-aaa:ipv6/ios-aaa:tacacs/ios-aaa:source-interface/ios-aaa:interface-choice/ios-aaa:Tunnel/ios-aaa:Tunnel" {
    deviate replace {
      type uint32 {
        range "0..2147483647";
      }
    }
  }

  deviation "/ios:native/ios:aaa/ios-aaa:group/ios-aaa:server/ios-aaa:tacacsplus/ios-aaa:ipv6/ios-aaa:tacacs/ios-aaa:source-interface/ios-aaa:interface-choice/ios-aaa:Vlan/ios-aaa:Vlan" {
    deviate replace {
      type uint16 {
        range "1..4094";
      }
    }
  }

  deviation "/ios:native/ios:ip/ios-aaa:tacacs/ios-aaa:source-interface/ios-aaa:interface-choice/ios-aaa:Tunnel/ios-aaa:Tunnel" {
    deviate replace {
      type uint32 {
        range "0..2147483647";
      }
    }
  }

  deviation "/ios:native/ios:ip/ios-aaa:radius/ios-aaa:source-interface/ios-aaa:interface-choice/ios-aaa:Vlan/ios-aaa:Vlan" {
    deviate replace {
      type uint16 {
        range "1..4094";
      }
    }
  }
}
