module Cisco-IOS-XE-system-security-events {
  yang-version 1.1;
  namespace "http://cisco.com/ns/yang/Cisco-IOS-XE-system-security-events";
  prefix system-security-ios-xe-events;

  import Cisco-IOS-XE-ios-common-oper {
    prefix ios-common-ios-xe-oper;
  }
  import Cisco-IOS-XE-system-security-types {
    prefix system-security-types-ios-xe-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for events data related to system security.
     Copyright (c) 2025 by Cisco Systems, Inc.
     All rights reserved.";

  revision 2026-02-01 {
    description
      "Initial revision";
    reference
      "1.0.0";
    cisco-semver:module-version "1.0.0";
  }

  grouping sys-insec-dyn-conf-details {
    description
      "System's insecure configuration CLI details";
    leaf severity {
      type ios-common-ios-xe-oper:notification-severity;
      description
        "Indicates the severity level of the system security event notification.";
    }
    leaf type {
      type system-security-types-ios-xe-oper:sys-insec-evt-type;
      description
        "Specifies the type of system security event being reported.";
    }
    container insec-data {
      description
        "Contains detailed information about the insecure configuration that triggered the event notification.";
      uses system-security-types-ios-xe-oper:sys-insec-info;
    }
  }

  grouping sys-aicdb-upd-evt {
    description
      "Indicates that a new insecure configuration has been added to the system";
    leaf severity {
      type ios-common-ios-xe-oper:notification-severity;
      description
        "Indicates the severity level of the system security event notification.";
    }
  }

  notification sys-insec-evt {
    description
      "Notification event triggered when a specific feature detects
       an insecure configuration during runtime, instead of through
       CLI-based insecure configuration detection";
    uses system-security-ios-xe-events:sys-insec-dyn-conf-details;
  }

  notification sys-aicdb-evt {
    description
      "Notification event triggered when new insecure configurations
       are added to the system, enabling monitoring systems to stay
       updated and fetch the complete insecure configuration information";
    uses system-security-ios-xe-events:sys-aicdb-upd-evt;
  }
}
