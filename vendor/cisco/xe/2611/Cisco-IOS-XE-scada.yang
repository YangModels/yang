module Cisco-IOS-XE-scada {
  yang-version 1.1;
  namespace "http://cisco.com/ns/yang/Cisco-IOS-XE-scada";
  prefix ios-scada;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Modbus Yang Model.
     Copyright (c) 2025 by Cisco Systems, Inc.
     All rights reserved.";

  revision 2026-02-01 {
    description
      "Yang model for modbus";
    cisco-semver:module-version "1.0.0";
  }

  grouping config-scada-grouping {
    container scada {
      description
        "SCADA configuration container";
      container modbus {
        description
          "Modbus protocol configuration";
        container tcp {
          description
            "TCP protocol configuration";
          container server {
            description
              "Modbus TCP server configuration";
            leaf enable {
              type empty;
              description
                "Enable/disable Modbus TCP server";
            }
            leaf port {
              type uint16 {
                range "1..65535";
              }
              default "502";
              description
                "TCP port number for Modbus server (Default is 502)";
            }
            leaf connections {
              type uint8 {
                range "1..5";
              }
              default "1";
              description
                "Maximum number of concurrent Modbus TCP connections (Default is 1)";
            }
          }
        }
      }
    }
  }

  augment "/ios:native" {
    uses config-scada-grouping;
  }
}
