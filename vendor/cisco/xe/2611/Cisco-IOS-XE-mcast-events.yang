module Cisco-IOS-XE-mcast-events {
  yang-version 1.1;
  namespace "http://cisco.com/ns/yang/Cisco-IOS-XE-mcast-events";
  prefix mcast-ios-xe-events;

  import Cisco-IOS-XE-common-types {
    prefix common-types-ios-xe;
  }
  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for multicast events data.
     Copyright (c) 2024 by Cisco Systems, Inc.
     All rights reserved.";

  revision 2024-07-01 {
    description
      "Initial revision";
    reference
      "1.0.0";
    cisco-semver:module-version "1.0.0";
  }

  typedef pim-nbr-state {
    type enumeration {
      enum pim-nbr-up {
        value 0;
        description
          "PIM neighbor state is up";
      }
      enum pim-nbr-down {
        value 1;
        description
          "PIM neighbor state is down";
      }
    }
    description
      "PIM neighbor state";
  }

  grouping pim-nbr-state-event {
    description
      "PIM neighbor state change event";
    leaf severity {
      type ios-common-ios-xe-oper:notification-severity;
      description
        "Event severity";
    }
    leaf host-name {
      type string;
      description
        "Host name of the device";
    }
    leaf system-ip {
      type inet:ip-address;
      description
        "System IP of the device";
    }
    leaf if-name {
      type string;
      description
        "Interface name";
    }
    leaf nbr-addr {
      type inet:ip-address;
      description
        "Neighbor address";
    }
    leaf ni-type {
      type common-types-ios-xe:net-inst-type;
      description
        "Network instance type. Differentiates between the
         default routing instance and VRFs";
    }
    leaf ni-name {
      type string;
      description
        "Network instance name. If the type is
         net-inst-default, the name is not meaningful";
    }
    leaf state {
      type mcast-ios-xe-events:pim-nbr-state;
      description
        "Neighbor state";
    }
  }

  notification pim-nbr-state-event {
    description
      "PIM neighbor state change notification";
    uses mcast-ios-xe-events:pim-nbr-state-event;
  }
}
