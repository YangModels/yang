module Cisco-IOS-XE-pnp {
  yang-version 1.1;
  namespace "http://cisco.com/ns/yang/Cisco-IOS-XE-pnp";
  prefix ios-pnp;

  import cisco-semver {
    prefix cisco-semver;
  }
  import Cisco-IOS-XE-native {
    prefix ios;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE PnP Yang model.
     Copyright (c) 2018-2019 by Cisco Systems, Inc.
     All rights reserved.";

  revision 2025-07-01 {
    description
      "- Added FiftyGigabitEthernet interface support";
    cisco-semver:module-version "1.4.0";
  }
  revision 2024-03-01 {
    description
      "Added tailf annotation for config-pnp-transport-grouping";
    cisco-semver:module-version "1.3.1";
  }
  revision 2022-11-01 {
    description
      "- Update yang-version to 1.1";
    cisco-semver:module-version "1.3.0";
  }
  revision 2021-11-01 {
    description
      "Added model for PnP under interface";
    cisco-semver:module-version "1.2.0";
  }
  revision 2019-11-01 {
    description
      "Added model for PnP transport http";
    cisco-semver:module-version "1.1.0";
  }
  revision 2019-07-01 {
    description
      "Establish semantic version baseline";
    cisco-semver:module-version "1.0.0";
  }
  revision 2018-08-13 {
    description
      "Added model for PnP transport https";
  }
  revision 2018-07-10 {
    description
      "Initial revision";
  }

  grouping config-pnp-transport-port-grouping {
    leaf port {
      description
        "port number";
      type uint16 {
        range "1..65535";
      }
    }
  }

  grouping config-pnp-transport-localcert-grouping {
    leaf localcert {
      description
        "Local certificate";
      type string;
    }
  }

  grouping config-pnp-transport-remotecert-grouping {
    leaf remotecert {
      description
        "Remote certificate validation";
      type string;
    }
  }

  grouping config-pnp-transport-grouping {
    container host {
      description
        "hostname of the server";
      leaf host-name {
        description
          "Hostname of the server";
        type string;
      }
      uses config-pnp-transport-port-grouping;
      uses config-pnp-transport-localcert-grouping;
      uses config-pnp-transport-remotecert-grouping;
    }
    container ipv4 {
      description
        "ipv4 address";
      leaf ipv4-address {
        description
          "IPv4 address of the server";
        type inet:ipv4-address;
      }
      uses config-pnp-transport-port-grouping;
      uses config-pnp-transport-localcert-grouping;
      uses config-pnp-transport-remotecert-grouping;
    }
    container ipv6 {
      description
        "IPv6 address of the server";
      leaf ipv6-address {
        description
          "IPv6 address of the server";
        type inet:ipv6-address;
      }
      uses config-pnp-transport-port-grouping;
      uses config-pnp-transport-localcert-grouping;
      uses config-pnp-transport-remotecert-grouping;
    }
  }

  grouping config-pnp-interface-grouping {
    container pnp {
      description
        "Configure PNP";
      leaf startup-vlan {
        description
          "PNP startup-vlan";
        type uint16 {
          range "2..4094";
        }
      }
    }
  }

  grouping config-pnp-grouping {
    container pnp {
      description
        "Configure PNP";
      leaf startup-vlan {
        description
          "PNP startup-vlan";
        type uint16 {
          range "2..4094";
        }
      }
      list profile {
        description
          "PNP profile";
        key "name";
        leaf name {
          type string;
        }
        container transport {
          description
            "The transport to use";
          container https {
            description
              "Use https (encrypted) transport";
            uses config-pnp-transport-grouping;
          }
          container http {
            description
              "Use http (plain text) transport";
            uses config-pnp-transport-grouping;
          }
        }
      }
    }
  }

  augment "/ios:native" {
    uses config-pnp-grouping;
  }

  augment "/ios:native/ios:interface/ios:FastEthernet" {
    uses config-pnp-interface-grouping;
  }

  augment "/ios:native/ios:interface/ios:GigabitEthernet" {
    uses config-pnp-interface-grouping;
  }

  augment "/ios:native/ios:interface/ios:TenGigabitEthernet" {
    uses config-pnp-interface-grouping;
  }

  augment "/ios:native/ios:interface/ios:FiveGigabitEthernet" {
    uses config-pnp-interface-grouping;
  }

  augment "/ios:native/ios:interface/ios:AppGigabitEthernet" {
    uses config-pnp-interface-grouping;
  }

  augment "/ios:native/ios:interface/ios:TwentyFiveGigE" {
    uses config-pnp-interface-grouping;
  }

  augment "/ios:native/ios:interface/ios:TwoGigabitEthernet" {
    uses config-pnp-interface-grouping;
  }

  augment "/ios:native/ios:interface/ios:FortyGigabitEthernet" {
    uses config-pnp-interface-grouping;
  }

  augment "/ios:native/ios:interface/ios:FiftyGigabitEthernet" {
    uses config-pnp-interface-grouping;
  }

  augment "/ios:native/ios:interface/ios:HundredGigE" {
    uses config-pnp-interface-grouping;
  }
}
