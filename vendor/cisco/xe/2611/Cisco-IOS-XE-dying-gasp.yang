module Cisco-IOS-XE-dying-gasp {
  yang-version 1.1;
  namespace "http://cisco.com/ns/yang/Cisco-IOS-XE-dying-gasp";
  prefix ios-dying-gasp;

  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Dying-gasp Yang Model.
     Copyright (c) 2023  by Cisco Systems, Inc.
     All rights reserved.";

  revision 2024-07-01 {
    description
      "Added ethernet-oam in dying-gasp sources";
  }
  revision 2023-07-01 {
    description
      "- Initial Revision ";
  }

  grouping config-dying-gasp-grouping {
    container dying-gasp {
      leaf primary {
        description
          "Enable primary dying gasp notification";
        type enumeration {
          enum snmp-trap {
            description
              "Enable trap notification sent to SNMP server";
          }
          enum syslog {
            description
              "Enable system logger";
          }
          enum ethernet-oam {
            description
              "Enable Ethernet OAM notification";
          }
        }
      }
      leaf secondary {
        description
          "Enable secondary dying gasp notification";
        must '../primary' {
          error-message "Primary dying-gasp notification not enabled";
        }
        must 'not(. = ../primary)' {
          error-message "Secondary option cannot have the same value as the primary option.";
        }
        type enumeration {
          enum ethernet-oam {
            description
              "Enable Ethernet OAM notification";
          }
          enum syslog {
            description
              "Enable system logger";
          }
          enum snmp-trap {
            description
              "Enable trap notification sent to SNMP server";
          }
        }
      }
    }
  }

  augment "/ios:native" {
    uses config-dying-gasp-grouping;
  }
}
