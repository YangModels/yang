module Cisco-IOS-XE-loop-detect {
  yang-version 1.1;
  namespace "http://cisco.com/ns/yang/Cisco-IOS-XE-loop-detect";
  prefix ios-loop-detect;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Cisco Smart Install (LOOP DETECT) Yang model.
     Copyright (c) 2022 by Cisco Systems, Inc.
     All rights reserved.";

  revision 2025-07-01 {
    description
      "- Added FiftyGigabitEthernet interface support";
    cisco-semver:module-version "1.2.0";
  }
  revision 2022-11-01 {
    description
      "Update yang-version to 1.1";
    cisco-semver:module-version "1.1.0";
  }
  revision 2022-07-01 {
    description
      "Enable model support for loop detect feature";
    cisco-semver:module-version "1.0.0";
  }

  grouping config-interface-loop-detect-grouping {
    container loopdetect-enable {
      leaf loopdetect {
        description
          "Enable loop detection on the port";
        type empty;
      }
    }
    container loopdetect-param {
      container loopdetect {
        description
          "Configure loop detect feature setting";
        leaf interval {
          description
            "Time in seconds between sending of
             loop detect frames";
          type uint32 {
            range "1..10";
          }
          default "5";
        }
        container action {
          description
            "Select the action to be performed upon loop detection";
          leaf syslog {
            description
              "Syslog will display upon loop detection";
            type empty;
          }
        }
        leaf source-port {
          description
            "Source Port will be error disabled upon loop detection";
          type empty;
        }
      }
    }
  }

  augment "/ios:native/ios:interface/ios:FastEthernet" {
    uses config-interface-loop-detect-grouping;
  }

  augment "/ios:native/ios:interface/ios:GigabitEthernet" {
    uses config-interface-loop-detect-grouping;
  }

  augment "/ios:native/ios:interface/ios:TwoGigabitEthernet" {
    uses config-interface-loop-detect-grouping;
  }

  augment "/ios:native/ios:interface/ios:FiveGigabitEthernet" {
    uses config-interface-loop-detect-grouping;
  }

  augment "/ios:native/ios:interface/ios:AppGigabitEthernet" {
    uses config-interface-loop-detect-grouping;
  }

  augment "/ios:native/ios:interface/ios:TenGigabitEthernet" {
    uses config-interface-loop-detect-grouping;
  }

  augment "/ios:native/ios:interface/ios:TwentyFiveGigE" {
    uses config-interface-loop-detect-grouping;
  }

  augment "/ios:native/ios:interface/ios:FortyGigabitEthernet" {
    uses config-interface-loop-detect-grouping;
  }

  augment "/ios:native/ios:interface/ios:FiftyGigabitEthernet" {
    uses config-interface-loop-detect-grouping;
  }

  augment "/ios:native/ios:interface/ios:HundredGigE" {
    uses config-interface-loop-detect-grouping;
  }
}
