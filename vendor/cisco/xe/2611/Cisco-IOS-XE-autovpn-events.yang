module Cisco-IOS-XE-autovpn-events {
  yang-version 1.1;
  namespace "http://cisco.com/ns/yang/Cisco-IOS-XE-autovpn-events";
  prefix autovpn-ios-xe-events;

  import Cisco-IOS-XE-crypto-types {
    prefix crypto-ios-xe-types;
  }
  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for autovpn events data.
     Copyright (c) 2025 by Cisco Systems, Inc.
     All rights reserved.";

  revision 2026-02-01 {
    description
      "Initial revision";
    reference
      "1.0.0";
    cisco-semver:module-version "1.0.0";
  }

  typedef vpn-reg-reachability-status {
    type enumeration {
      enum vpn-reg-reach {
        value 0;
        description
          "VPN registry is reachable from uplink interface";
      }
      enum vpn-reg-no-reach {
        value 1;
        description
          "VPN registry is unreachable from uplink interface";
      }
    }
    description
      "AutoVPN module VPN registry status identifiers";
  }

  typedef autovpn-session-status {
    type enumeration {
      enum autovpn-pub-con-in-prog {
        value 0;
        description
          "AutoVPN session establishing public connection";
      }
      enum autovpn-pub-con {
        value 1;
        description
          "AutoVPN session public connection established";
      }
      enum autovpn-priv-con-in-prog {
        value 2;
        description
          "AutoVPN session establishing private connection";
      }
      enum autovpn-priv-con {
        value 3;
        description
          "AutoVPN session private connection established";
      }
      enum autovpn-priv-no-con {
        value 4;
        description
          "AutoVPN session connection failed";
      }
    }
    description
      "AutoVPN session status identifiers";
  }

  grouping autovpn-vpn-registry-notification {
    description
      "VPN registry status event notification";
    leaf severity {
      type ios-common-ios-xe-oper:notification-severity;
      description
        "Notification severity level";
    }
    leaf if-ip {
      type inet:ip-address;
      description
        "Specifies the local IP address used for the AutoVPN session";
    }
    leaf port {
      type uint16;
      description
        "Specifies the local port number used for the AutoVPN session";
    }
    leaf status {
      type autovpn-ios-xe-events:vpn-reg-reachability-status;
      description
        "Indicates the VPN registry reachability status";
    }
  }

  grouping autovpn-session-notification {
    description
      "AutoVPN session notification";
    leaf severity {
      type ios-common-ios-xe-oper:notification-severity;
      description
        "Notification severity level";
    }
    leaf src-ip {
      type inet:ip-address;
      description
        "Specifies the source IP address of autovpn session";
    }
    leaf src-port {
      type uint16;
      description
        "Specifies the source port number of autovpn session";
    }
    leaf dst-ip {
      type inet:ip-address;
      description
        "Specifies the destination IP address of autovpn session";
    }
    leaf dst-port {
      type uint16;
      description
        "Specifies the destination port number of autovpn session";
    }
    leaf local-uplink {
      type string;
      description
        "Specifies the local uplink interface name";
    }
    leaf remote-uplink {
      type string;
      description
        "Specifies the remote uplink interface name";
    }
    leaf session-status {
      type autovpn-ios-xe-events:autovpn-session-status;
      description
        "Indicates the AutoVPN session status";
    }
  }

  grouping autovpn-symnat-notification {
    description
      "AutoVPN SYMNAT notification";
    leaf severity {
      type ios-common-ios-xe-oper:notification-severity;
      description
        "Notification severity level";
    }
    leaf wan-ip {
      type inet:ip-address;
      description
        "Specifies the local uplink IP address";
    }
    leaf status {
      type crypto-ios-xe-types:symnat-status;
      description
        "Indicates the status of interface behind SYMNAT";
    }
  }

  notification vpn-reg-event {
    description
      "VPN registry notification";
    uses autovpn-ios-xe-events:autovpn-vpn-registry-notification;
  }

  notification sess-event {
    description
      "AutoVPN session notification";
    uses autovpn-ios-xe-events:autovpn-session-notification;
  }

  notification symnat-event {
    description
      "AutoVPN SYMNAT notification";
    uses autovpn-ios-xe-events:autovpn-symnat-notification;
  }
}
