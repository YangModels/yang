module Cisco-IOS-XE-dapr {
  yang-version 1.1;
  namespace "http://cisco.com/ns/yang/Cisco-IOS-XE-dapr";
  prefix ios-dapr;

  import cisco-semver {
    prefix cisco-semver;
  }
  import ietf-inet-types {
    prefix inet;
  }
  import Cisco-IOS-XE-native {
    prefix ios;
  }

  organization
    "Cisco Systems, Inc.";
  contact
    "Cisco Systems, Inc.
      Customer Service

      Postal: 170 W Tasman Drive
      San Jose, CA 95134

      Tel: +1 1800 553-NETS

      E-mail: cs-yang@cisco.com";
  description
    "Cisco XE Native Dynamic Application Policy Routing(DAPR) Yang model.
     Copyright (c) 2018 by Cisco Systems, Inc.
     All rights reserved.";

  revision 2025-07-01 {
    description
      "- Enabling yang support of DAPR configuration for Tunnel interface";
    cisco-semver:module-version "1.2.0";
  }
  revision 2022-11-01 {
    description
      "- Update yang-version to 1.1";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2018-11-20 {
    description
      "Limit dapr instance to 1, Removed border-router vrf option,
       Kept restrictions on values, Moved shutdown leaf to last,
       Kept ingress and egress in choice";
  }
  revision 2018-09-24 {
    description
      "Initial revision";
  }

  grouping config-dapr-password-grouping {
    container password {
      description
        "Specify the password (Max 25 characters)";
      choice auth-key {
        case uncpwd {
          leaf unc-pwd {
            description
              "The UNENCRYPTED (cleartext) user password";
            type string {
              length "1..25";
            }
          }
        }
        case key0 {
          leaf key-0 {
            description
              "Specifies an UNENCRYPTED password will follow";
            type string {
              length "1..25";
            }
          }
        }
        case key4 {
          leaf key-4 {
            description
              "Specifies an SHA256 HASHED password will follow";
            type string;
          }
        }
      }
    }
  }

  grouping config-dapr-border-router-grouping {
    container authentication {
      description
        "Authentication parameters";
      uses config-dapr-password-grouping;
    }
    container route-manager {
      description
        "Route manager address";
      leaf ipv4 {
        description
          "IP address";
        type inet:ipv4-address;
      }
    }
    container source-interface {
      description
        "Border router address source";
      leaf Loopback {
        description
          "Loopback interface";
        type uint32;
      }
    }
    leaf shutdown {
      description
        "Disable border router instance";
      type empty;
    }
  }

  grouping config-dapr-grouping {
    list dapr {
      description
        "Dynamic Application Policy Routing(DAPR) configuration";
      key "name";
      max-elements 1;
      leaf name {
        description
          "Instance name";
        type string {
          length "1..20";
        }
      }
      container border-router {
        description
          "DAPR border router (BR) configuration";
        presence "true";
        uses config-dapr-border-router-grouping;
      }
      container route-manager {
        description
          "DAPR route manager (RM) configuration";
        presence "true";
        container authentication {
          description
            "Authentication parameters";
          uses config-dapr-password-grouping;
        }
        container border-routers {
          description
            "Authorized border routers";
          list br-ip {
            description
              "Border-routers address";
            key "ipv4";
            max-elements 20;
            leaf ipv4 {
              description
                "Border router address";
              type inet:ipv4-address;
            }
          }
        }
        list class {
          description
            "Application class parameters";
          key "name";
          unique "seq";
          leaf name {
            description
              "Application class name";
            type string {
              length "1..64";
            }
          }
          leaf seq {
            description
              "Application class processing sequence";
            type uint16 {
              range "1..255";
            }
          }
          container match {
            description
              "Match criteria";
            leaf access-list {
              description
                "IP Named Extended Access list name";
              type string {
                length "1..64";
              }
            }
          }
          container path-preference {
            description
              "Specify path preference";
            presence "true";
            list path-pref-list {
              description
                "List of path preferences";
              key "seq";
              max-elements 3;
              leaf seq {
                description
                  "Path preference sequence number";
                type uint16 {
                  range "1..255";
                }
              }
              leaf lg-name {
                description
                  "Link Group Name";
                type string {
                  length "1..50";
                }
              }
            }
          }
        }
        container link-thresholds {
          description
            "BR egress link thresholds";
          leaf max-utilization {
            description
              "Maximum % utilization";
            default "50";
            type uint8 {
              range "1..100";
            }
          }
          leaf min-bandwidth {
            description
              "Minimum bandwidth (kbps) for viability";
            default "500";
            type uint32 {
              range "1..10000000";
            }
          }
        }
        container source-interface {
          description
            "Route manager address source";
          leaf Loopback {
            description
              "Loopback interface";
            type uint32;
          }
        }
        leaf shutdown {
          description
            "Disable route manager instance";
          type empty;
        }
      }
    }
  }

  grouping config-interface-dapr-grouping {
    container dapr {
      choice mode {
        container ingress {
          description
            "DAPR ingress interface";
          presence "true";
        }
        container egress {
          description
            "DAPR egress interface";
          presence "true";
          leaf link-group {
            description
              "Specify link group name (max 50 characters)";
            type string {
              length "1..50";
            }
          }
        }
      }
    }
  }

  augment "/ios:native" {
    uses config-dapr-grouping;
  }

  augment "/ios:native/ios:interface/ios:Ethernet" {
    uses config-interface-dapr-grouping;
  }

  augment "/ios:native/ios:interface/ios:FastEthernet" {
    uses config-interface-dapr-grouping;
  }

  augment "/ios:native/ios:interface/ios:GigabitEthernet" {
    uses config-interface-dapr-grouping;
  }

  augment "/ios:native/ios:interface/ios:TenGigabitEthernet" {
    uses config-interface-dapr-grouping;
  }

  augment "/ios:native/ios:interface/ios:FiveGigabitEthernet" {
    uses config-interface-dapr-grouping;
  }

  augment "/ios:native/ios:interface/ios:AppGigabitEthernet" {
    uses config-interface-dapr-grouping;
  }

  augment "/ios:native/ios:interface/ios:TwentyFiveGigE" {
    uses config-interface-dapr-grouping;
  }

  augment "/ios:native/ios:interface/ios:FortyGigabitEthernet" {
    uses config-interface-dapr-grouping;
  }

  augment "/ios:native/ios:interface/ios:HundredGigE" {
    uses config-interface-dapr-grouping;
  }

  augment "/ios:native/ios:interface/ios:TwoGigabitEthernet" {
    uses config-interface-dapr-grouping;
  }

  augment "/ios:native/ios:interface/ios:Serial" {
    uses config-interface-dapr-grouping;
  }

  augment "/ios:native/ios:interface/ios:Virtual-Template" {
    uses config-interface-dapr-grouping;
  }

  augment "/ios:native/ios:interface/ios:Tunnel" {
    uses config-interface-dapr-grouping;
  }
}
