module Cisco-IOS-XE-perf-measure {
  yang-version 1.1;
  namespace "http://cisco.com/ns/yang/Cisco-IOS-XE-perf-measure";
  prefix ios-performance-measurement;

  import cisco-semver {
    prefix cisco-semver;
  }
  import ietf-inet-types {
    prefix inet;
  }
  import Cisco-IOS-XE-native {
    prefix ios;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Performance-Measurement Yang model.
     Copyright (c) 2016, 2018-2023 by Cisco Systems, Inc.
     All rights reserved.";

  revision 2024-07-01 {
    description
      "- Added new leaf measurement-mode-v2 and deprecated measurement-mode";
    cisco-semver:module-version "2.4.0";
  }
  revision 2024-03-01 {
    description
      "- Update endpoint and delay-profile endpoint";
    cisco-semver:module-version "2.3.0";
  }
  revision 2023-11-01 {
    description
      "- Added leaf for interface delay profile name";
    cisco-semver:module-version "2.2.0";
  }
  revision 2022-11-01 {
    description
      "- Update yang-version to 1.1
       - Updated loss measurement
       - Updated leaf name for advertise-loss profile";
    cisco-semver:module-version "2.1.0";
  }
  revision 2021-07-01 {
    description
      "- Updated range for leaf querier-dst-port and querier-src-port";
    cisco-semver:module-version "2.0.1";
  }
  revision 2020-11-01 {
    description
      "- Added named profile for both interface and sr-policy
       - Added liveness config";
    cisco-semver:module-version "2.0.0";
  }
  revision 2020-03-01 {
    description
      "- Added next-hop config";
    cisco-semver:module-version "2.1.0";
  }
  revision 2019-11-01 {
    description
      "Initial revision";
    cisco-semver:module-version "1.0.0";
  }

  typedef ipv4-address-sweep-range {
    type string {
      pattern '((127)\.)(([0-9]|[1-9][0-9]|1[0-9][0-9]|2[0-4][0-9]|25[0-5])\.){2}([0-9]|[1-9][0-9]|11[0-9]|12[0-7])';
    }
  }

  grouping config-perf-measure-advertisement-grouping {
    description
      "Common node for delay profile advertisment";
    container advertisement {
      description
        "Advertisement Profile";
      container accelerated {
        description
          "Accelerated Advertisement Profile";
        presence "true";
        leaf threshold {
          description
            "Accelerated advertisement threshold percentage";
          type ios-types:percentage;
          units "percentage";
          default "20";
        }
        leaf minimum-change {
          description
            "Accelerated advertisement minimum value in
             microseconds (uSec)";
          type uint32 {
            range "0..1000000";
          }
          units "microseconds";
          default "500";
        }
      }
      container periodic {
        description
          "Periodic Advertisement Profile";
        leaf interval {
          description
            "Periodic advertisement interval in seconds";
          type uint32 {
            range "30..3600";
          }
          units "second";
          default "120";
        }
        leaf threshold {
          description
            "Periodic advertisement threshold percentage";
          type ios-types:percentage;
          units "percentage";
          default "10";
        }
        leaf minimum-change {
          description
            "Periodic advertisement minimum value in microseconds (uSec)";
          type uint32 {
            range "0..1000000";
          }
          units "microsecond";
        }
        leaf disable {
          description
            "Disable Performance Measurement Periodic Advertisement";
          type empty;
        }
      }
    }
  }

  grouping config-perf-measure-advertisement-grouping-endpoint {
    description
      "Common node for delay profile advertisment";
    container advertisement {
      description
        "Advertisement Profile";
      container accelerated {
        description
          "Accelerated Advertisement Profile";
        presence "true";
        leaf threshold {
          description
            "Accelerated advertisement threshold percentage";
          type ios-types:percentage;
          units "percentage";
          default "20";
        }
        leaf minimum-change {
          description
            "Accelerated advertisement minimum value in microseconds (uSec)";
          type uint32 {
            range "0..1000000";
          }
          units "microseconds";
          default "500";
        }
      }
      container periodic {
        description
          "Periodic Advertisement Profile";
        leaf interval {
          description
            "Periodic advertisement interval in seconds";
          type uint32 {
            range "30..3600";
          }
          units "seconds";
          default "120";
        }
        leaf threshold {
          description
            "Periodic advertisement threshold percentage";
          type ios-types:percentage;
          units "percentage";
          default "10";
        }
        leaf minimum-change {
          description
            "Periodic advertisement minimum value in microseconds (uSec)";
          type uint32 {
            range "0..1000000";
          }
          units "microseconds";
          default "500";
        }
        leaf disabled {
          description
            "Disable Performance Measurement Periodic Advertisement";
          type empty;
        }
      }
      container threshold-check {
        description
          "Threshold Check";
        leaf threshold-check-value {
          type enumeration {
            enum average-delay;
            enum maximum-delay;
            enum minimum-delay;
          }
          default "average-delay";
        }
      }
    }
  }

  grouping config-perf-measure-advertisement-grouping-srpolicy {
    description
      "Common node for delay profile advertisment";
    container advertisement {
      description
        "Advertisement Profile";
      container accelerated {
        description
          "Accelerated Advertisement Profile";
        presence "true";
        leaf threshold {
          description
            "Accelerated advertisement threshold percentage";
          type ios-types:percentage;
          units "percentage";
          default "20";
        }
        leaf minimum-change {
          description
            "Accelerated advertisement minimum value in
             microseconds (uSec)";
          type uint32 {
            range "0..1000000";
          }
          units "microseconds";
          default "500";
        }
      }
      container periodic {
        description
          "Periodic Advertisement Profile";
        leaf interval {
          description
            "Periodic advertisement interval in seconds";
          type uint32 {
            range "30..3600";
          }
          units "second";
          default "120";
        }
        leaf threshold {
          description
            "Periodic advertisement threshold percentage";
          type ios-types:percentage;
          units "percentage";
          default "10";
        }
        leaf minimum-change {
          description
            "Periodic advertisement minimum value in microseconds (uSec)";
          type uint32 {
            range "0..1000000";
          }
          units "microsecond";
        }
        leaf disable {
          description
            "Disable Performance Measurement Periodic Advertisement";
          type empty;
        }
      }
      container threshold-check {
        description
          "Threshold Check";
        choice mode-choice {
          default "average-delay";
          case average-delay {
            leaf average-delay {
              description
                "Enable average-delay threshold check";
              type empty;
            }
          }
          case minimum-delay {
            leaf minimum-delay {
              description
                "Enable minimum-delay threshold check";
              type empty;
            }
          }
          case maximum-delay {
            leaf maximum-delay {
              description
                "Enable maximum-delay threshold check";
              type empty;
            }
          }
        }
      }
    }
  }

  grouping config-perf-measure-loss-advertisement-grouping {
    description
      "Common node for loss profile advertisement";
    container advertisement {
      description
        "Advertisement Profile";
      container anomaly-check {
        description
          "Configure anomaly range, if exceeds set anomaly bit";
        leaf lower-bound {
          description
            "Lower bound for anomaly";
          must '. < ../upper-bound' {
            error-message "lower-bound must be less than upper-bound";
          }
          type decimal64 {
            fraction-digits 6;
            range "0.000000..50.331642";
          }
          units "percentage";
          default "0.500000";
        }
        leaf upper-bound {
          description
            "Upper bound for anomaly";
          must '. > ../lower-bound' {
            error-message "upper-bound must be greater than lower-bound";
          }
          type decimal64 {
            fraction-digits 6;
            range "0.000000..50.331642";
          }
          units "percentage";
          default "1.000000";
        }
      }
      container periodic {
        description
          "Periodic Advertisement Profile";
        leaf interval {
          description
            "Periodic advertisement interval in seconds";
          type uint32 {
            range "30..3600";
          }
          units "second";
          default "120";
        }
        leaf minimum-change {
          description
            "Periodic advertisement minimum value in microseconds (uSec)";
          type decimal64 {
            fraction-digits 6;
            range "0.000000..50.331642";
          }
          units "percentage";
          default "0.100000";
        }
        leaf threshold {
          description
            "Periodic advertisement threshold percentage";
          type decimal64 {
            fraction-digits 6;
            range "0.000003..100.000000";
          }
          units "percentage";
          default "10.000000";
        }
      }
    }
  }

  grouping config-perf-measure-probe-grouping {
    container probe {
      description
        "PM Delay Profile Probe";
      leaf computation-interval {
        description
          "The value for delay profile probe interval in seconds";
        type uint32 {
          range "3..3600";
        }
        units "second";
        default "30";
      }
      leaf measurement-mode-v2 {
        description
          "Delay measurement mode";
        type enumeration {
          enum two-way {
            description
              "Enable two-way delay measurement";
          }
          enum one-way {
            description
              "Enable one-way delay measurement";
          }
        }
        default "two-way";
      }
      container measurement-mode {
        status deprecated;
        description
          "Delay measurement mode";
        choice mode-choice {
          status deprecated;
          default "two-way";
          case two-way {
            status deprecated;
            leaf two-way {
              status deprecated;
              description
                "Enable two-way delay measurement";
              type empty;
            }
          }
          case one-way {
            status deprecated;
            leaf one-way {
              status deprecated;
              type empty;
              description
                "Enable one-way delay measurement";
            }
          }
        }
      }
      leaf burst-interval {
        description
          "The value for delay profile probe burst
           interval in milliseconds";
        type uint32 {
          range "30..15000";
        }
        units "millisecond";
        default "3000";
      }
      container protocol {
        description
          "Protocol used to send probes";
        choice protocol-choice {
          default "pm-mpls";
          case pm-mpls {
            leaf pm-mpls {
              description
                "Interface delay measurement using RFC 6374 with MPLS encap";
              type empty;
            }
          }
          case twamp-light {
            leaf twamp-light {
              description
                "Interface delay measurement using RFC 5357";
              type empty;
            }
          }
        }
      }
    }
  }

  grouping config-perf-measure-loss-probe-grouping {
    container probe {
      description
        "PM Loss Profile Probe";
      container color-type {
        description
          "Loss profile probe color-type submode";
        choice color-type-choice {
          default "single-color";
          case dual-color {
            leaf dual-color {
              description
                "Configure dual-color protocol";
              type enumeration {
                enum gre;
              }
              default "gre";
            }
          }
          case single-color {
            container single-color {
              description
                "Loss profile probe color-type single-color submode";
              presence "true";
              leaf accuracy {
                description
                  "Configure accuracy";
                type decimal64 {
                  fraction-digits 6;
                  range "0.100000..10.000000";
                }
                units "percentage";
                default "0.100000";
              }
              leaf max-reordering {
                description
                  "Configure maximum expected reordering
                   value in milliseconds";
                type uint32 {
                  range "100..2000";
                }
                units "millisecond";
                default "250";
              }
            }
          }
        }
      }
      leaf tx-interval {
        description
          "Transmit interval value in seconds";
        type uint32 {
          range "10..1000";
        }
        units "second";
        default "30";
      }
    }
  }

  grouping config-perf-measure-liveness-grouping-endpoint {
    container liveness-detection {
      description
        "Liveness-detection";
      leaf multiplier {
        description
          "Detect multiplier";
        type uint32 {
          range "2..10";
        }
        units "packets lost";
        default "3";
      }
    }
  }

  grouping config-perf-measure-liveness-grouping-policy {
    container liveness-detection {
      description
        "Liveness-detection";
      leaf multiplier {
        description
          "Detect multiplier";
        type uint32 {
          range "2..10";
        }
        units "packets lost";
        default "3";
      }
    }
  }

  grouping config-perf-measure-probe-grouping-endpoint {
    container probe {
      description
        "PM Delay Profile Probe";
      leaf computation-interval {
        description
          "Delay profile probe computation interval in seconds";
        type uint32 {
          range "3..3600";
        }
        units "seconds";
        default "30";
      }
      leaf measurement-mode {
        description
          "Delay measurement mode";
        type enumeration {
          enum two-way;
          enum one-way;
          enum loopback;
        }
        default "two-way";
      }
      leaf burst-interval {
        description
          "Delay profile probe burst interval in milliseconds";
        type uint32 {
          range "30..15000";
        }
        units "milliseconds";
        default "3000";
      }
      leaf padding-size {
        description
          "Packet padding size (added to minimum packet size)";
        type uint32 {
          range "0..8000";
        }
        units "bytes";
        default "0";
      }
      leaf tos-dscp {
        description
          "TOS DSCP 6-leftmost bits of TOS byte (0-63)";
        type uint16 {
          range "0..63";
        }
        default "48";
      }
    }
  }

  grouping config-perf-measure-probe-grouping-srpolicy {
    container probe {
      description
        "PM Delay Profile Probe";
      leaf computation-interval {
        description
          "The value for delay profile probe interval in seconds";
        type uint32 {
          range "3..3600";
        }
        units "second";
        default "30";
      }
      leaf measurement-mode-v2 {
        description
          "Delay measurement mode";
        type enumeration {
          enum two-way {
            description
              "Enable two-way delay measurement";
          }
          enum loopback {
            description
              "Enable loopback delay measurement";
          }
          enum one-way {
            description
              "Enable one-way delay measurement";
          }
        }
        default "two-way";
      }
      container measurement-mode {
        status deprecated;
        description
          "Delay measurement mode";
        choice mode-choice {
          status deprecated;
          default "one-way";
          case two-way {
            status deprecated;
            leaf two-way {
              status deprecated;
              description
                "Enable two-way delay measurement";
              type empty;
            }
          }
          case one-way {
            status deprecated;
            leaf one-way {
              status deprecated;
              description
                "Enable one-way delay measurement";
              type empty;
            }
          }
          case loopback {
            status deprecated;
            leaf loopback {
              status deprecated;
              description
                "Enable loopback delay measurement";
              type empty;
            }
          }
        }
      }
      leaf burst-interval {
        description
          "The value for delay profile probe burst
           interval in milliseconds";
        type uint32 {
          range "30..15000";
        }
        units "millisecond";
        default "3000";
      }
      container protocol {
        description
          "Protocol used to send probes";
        choice protocol-choice {
          default "pm-mpls";
          case pm-mpls {
            leaf pm-mpls {
              description
                "SR Policy delay measurement using RFC 6374 with MPLS encap";
              type empty;
            }
          }
          case twamp-light {
            leaf twamp-light {
              description
                "SR Policy delay measurement using RFC 5357";
              type empty;
            }
          }
        }
      }
      container sweep {
        description
          "Enable ECMP hashing by sweeping a field in the probe";
        container destination {
          description
            "Sweep a range of IP destination addresses";
          leaf ipv4 {
            description
              "IPv4 address";
            type ipv4-address-sweep-range;
          }
          leaf range {
            description
              " Start of the IPv4 address range";
            type uint16 {
              range "0..128";
            }
          }
        }
      }
    }
  }

  grouping config-perf-measure-grouping {
    list interface {
      description
        "Configure a performance-measurement interface";
      key "interface-name";
      leaf interface-name {
        type string;
      }
      container delay-measurement {
        description
          "Interface delay measurement";
        presence "true";
        leaf advertise-delay {
          description
            "The value for interface delay measurement
             advertisement delay in uSec";
          type uint32 {
            range "0..16777215";
          }
          units "microsecond";
        }
        leaf profile {
          description
            "Profile name";
          type string;
        }
      }
      container loss-measurement {
        description
          "Interface loss measurement";
        presence "true";
        container advertise-loss {
          leaf advertise-loss {
            description
              "The value for interface loss measurement
               advertisement loss in percentage";
            type decimal64 {
              fraction-digits 6;
              range "0.000000..50.331642";
            }
            units "percentage";
          }
          leaf anomaly-set {
            description
              "Set anomaly bit";
            type empty;
          }
        }
        leaf profile {
          description
            "Profile name";
          type string;
        }
      }
      container next-hop {
        description
          "next-hop address";
        choice nexthop-address-choice {
          case nexthop-ipv4-address {
            leaf ipv4 {
              description
                "IPv4 address";
              type inet:ipv4-address;
            }
          }
          case nexthop-ipv6-address {
            leaf ipv6 {
              description
                "IPv6 address";
              type inet:ipv6-address;
            }
          }
        }
      }
    }
    list endpoint {
      description
        "Configure a performance-measurement endpoint";
      key "endpoint-name";
      leaf endpoint-name {
        type string;
      }
      container delay-measurement {
        description
          "Endpoint delay measurement";
        presence "true";
        leaf profile {
          description
            "Profile name";
          type string;
        }
      }
      container destination-address {
        description
          "Endpoint destination address";
        choice destination-address-choice {
          case destination-ipv4-address {
            leaf ipv4 {
              description
                "IPv4 address";
              type inet:ipv4-address;
            }
          }
          case destination-ipv6-address {
            leaf ipv6 {
              description
                "IPv6 address";
              type inet:ipv6-address;
            }
          }
        }
      }
      leaf shutdown {
        description
          "Shutdown the selected endpoint querier";
        type empty;
      }
      container source-address {
        description
          "Endpoint source address";
        choice source-address-choice {
          case source-ipv4-address {
            leaf ipv4 {
              description
                "IPv4 address";
              type inet:ipv4-address;
            }
          }
          case source-ipv6-address {
            leaf ipv6 {
              description
                "IPv6 address";
              type inet:ipv6-address;
            }
          }
        }
      }
      container segment-list {
        description
          "Configure a segment-list for the endpoint";
        leaf forward-path {
          description
            "Configure forward path on segment-list";
          type string;
        }
        leaf reverse-path {
          description
            "Configure reverse path on segment-list";
          type string;
        }
      }
      leaf vrf {
        description
          "Set VRF for the endpoint";
        type string;
      }
    }
    container delay-profile {
      description
        "Performance-measurement delay profile";
      container interfaces {
        description
          "Performance-measurement interface default delay profile";
        uses config-perf-measure-advertisement-grouping;
        uses config-perf-measure-probe-grouping;
      }
      container named-interfaces {
        container interfaces {
          description
            "Performance-measurement interface named delay profile";
          list name {
            key "profile-name";
            leaf profile-name {
              type string;
            }
            uses config-perf-measure-advertisement-grouping;
            uses config-perf-measure-probe-grouping;
          }
        }
      }
      container endpoint {
        description
          "Performance-measurement endpoint default delay profile";
        uses config-perf-measure-advertisement-grouping-endpoint;
        uses config-perf-measure-probe-grouping-endpoint;
        uses config-perf-measure-liveness-grouping-endpoint;
      }
      container named-endpoint {
        container endpoint {
          description
            "Performance-measurement endpoint named delay profile";
          list name {
            key "profile-name";
            leaf profile-name {
              type string;
            }
            uses config-perf-measure-advertisement-grouping-endpoint;
            uses config-perf-measure-probe-grouping-endpoint;
            uses config-perf-measure-liveness-grouping-endpoint;
          }
        }
      }
      container sr-policy {
        description
          "Performance-measurement sr-policy default delay profile";
        uses config-perf-measure-advertisement-grouping-srpolicy;
        uses config-perf-measure-probe-grouping-srpolicy;
        uses config-perf-measure-liveness-grouping-policy;
      }
      container named-sr-policy {
        container sr-policy {
          description
            "Performance-measurement sr-policy named delay profile";
          list name {
            key "profile-name";
            leaf profile-name {
              type string;
            }
            uses config-perf-measure-advertisement-grouping-srpolicy;
            uses config-perf-measure-probe-grouping-srpolicy;
            uses config-perf-measure-liveness-grouping-policy;
          }
        }
      }
    }
    container loss-profile {
      description
        "Performance-measurement loss profile";
      container interfaces {
        description
          "Performance-measurement interface default loss profile";
        uses config-perf-measure-loss-advertisement-grouping;
        uses config-perf-measure-loss-probe-grouping;
      }
      container named-interfaces {
        container interfaces {
          description
            "Performance-measurement interface named loss profile";
          list name {
            key "profile-name";
            leaf profile-name {
              type string;
            }
            uses config-perf-measure-loss-advertisement-grouping;
            uses config-perf-measure-loss-probe-grouping;
          }
        }
      }
    }
    container protocol {
      description
        "Supported Protocol";
      container sdlm-light {
        description
          "Enter sdlm-light protocol submode";
        container measurement {
          description
            "Supported measurement types";
          container loss {
            description
              "Enter loss measurement submode";
            container unauthenticated {
              description
                "Enter unauthenticated mode";
              leaf querier-dst-port {
                description
                  "<862,1024-14999>  Port number";
                type uint16 {
                  range "862 | 1024..14999";
                }
              }
              leaf querier-src-port {
                description
                  "<1024-14999>  Port number";
                must 'not (. = ../querier-dst-port)' {
                  error-message "querier-dst-port and querier-src-port cannot be configured equal";
                }
                type uint16 {
                  range "1024..14999";
                }
              }
            }
          }
        }
      }
      container twamp-light {
        description
          "Enter twamp-light protocol submode";
        container measurement {
          description
            "Supported measurement types";
          container delay {
            description
              "Enter delay measurement submode";
            container unauthenticated {
              description
                "Enter unauthenticated mode";
              leaf querier-dst-port {
                description
                  "<862,1024-14999>  Port number";
                type uint16 {
                  range "862 | 1024..14999";
                }
              }
              leaf querier-src-port {
                description
                  "<1024-14999>  Port number";
                must 'not (. = ../querier-dst-port)' {
                  error-message "querier-dst-port and querier-src-port cannot be configured equal";
                }
                type uint16 {
                  range "1024..14999";
                }
              }
            }
          }
        }
      }
    }
    container dual-color {
      description
        "Configure parameters for a protocol using dual-coloring";
      container gre {
        description
          "Configure GRE protocol";
        leaf bit-position {
          description
            "Configure bit-position for GRE";
          type uint16 {
            range "9..12";
          }
          default "9";
        }
      }
    }
    leaf max-pps {
      description
        "Configure maximum packets per second allowed";
      type uint16 {
        range "0..2000";
      }
    }
  }

  augment "/ios:native/ios:performance-measurement" {
    uses config-perf-measure-grouping;
  }
}
