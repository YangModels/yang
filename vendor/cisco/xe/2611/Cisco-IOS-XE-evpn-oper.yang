module Cisco-IOS-XE-evpn-oper {
  yang-version 1.1;
  namespace "http://cisco.com/ns/yang/Cisco-IOS-XE-evpn-oper";
  prefix evpn-ios-xe-oper;

  import Cisco-IOS-XE-common-types {
    prefix common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for EVPN operational data.
     Copyright (c) 2024 by Cisco Systems, Inc.
     All rights reserved.";

  revision 2025-03-01 {
    description
      "Initial revision";
    reference
      "1.0.0";
    cisco-semver:module-version "1.0.0";
  }

  typedef evpn-type {
    type enumeration {
      enum evpn-unknown {
        value 0;
        description
          "EVPN Type unknown";
      }
      enum evpn-vpws {
        value 1;
        description
          "EVPN point-to-point";
      }
      enum evpn-vlan-based {
        value 2;
        description
          "VLAN Based EVPN";
      }
      enum evpn-vlan-bundle {
        value 3;
        description
          "VLAN Bundle EVPN";
      }
      enum evpn-vlan-aware {
        value 4;
        description
          "VLAN Aware EVPN";
      }
    }
    description
      "EVPN Type";
  }

  typedef evpn-encapsulation-type {
    type enumeration {
      enum evpn-encap-type-none {
        value 0;
        description
          "EVPN encapsulation unknown";
      }
      enum evpn-encap-type-mpls {
        value 1;
        description
          "EVPN MPLS encapsulation";
      }
      enum evpn-encap-type-vxlan {
        value 2;
        description
          "EVPN VxLAN encapsulation";
      }
      enum evpn-encap-type-max {
        value 3;
        description
          "EVPN encapsulation maximum value";
      }
    }
    description
      "EVPN Encapsulation Type";
  }

  typedef evpn-replication-type {
    type enumeration {
      enum evpn-replication-undefined {
        value 0;
        description
          "EVPN replication type unknown";
      }
      enum evpn-replication-ingress {
        value 1;
        description
          "EVPN Ingress replication";
      }
      enum evpn-replication-p2mp {
        value 2;
        description
          "EVPN Point to multipoint replication";
      }
      enum evpn-replication-mp2mp {
        value 3;
        description
          "EVPN Multipoint to multipoint replication";
      }
      enum evpn-replication-static {
        value 4;
        description
          "EVPN Static replication";
      }
      enum evpn-replication-none {
        value 5;
        description
          "No EVPN replication";
      }
    }
    description
      "EVPN Replication Type";
  }

  typedef evpn-ip-local-learn {
    type enumeration {
      enum evpn-ip-local-learn-undefined {
        value 0;
        description
          "EVPN IP local learn undefined";
      }
      enum evpn-ip-local-learn-enabled {
        value 1;
        description
          "EVPN IP local learn enabled";
      }
      enum evpn-ip-local-learn-disabled {
        value 2;
        description
          "EVPN IP local learn disabled";
      }
    }
    description
      "EVPN IP local learn";
  }

  typedef evpn-dg-type {
    type enumeration {
      enum evpn-dg-advertise-undefined {
        value 0;
        description
          "undefined";
      }
      enum evpn-dg-advertise-enabled {
        value 1;
        description
          "EVPN Distributed Gateway Advertising Enabled";
      }
      enum evpn-dg-advertise-disabled {
        value 2;
        description
          "EVPN Distributed Gateway Advertising Disabled";
      }
    }
    description
      "EVPN Distributed Gateway Advertising";
  }

  typedef evpn-route-re-originate {
    type enumeration {
      enum evpn-re-orig-route-undefined {
        value 0;
        description
          "EVPN Route Re-Originate Undefined";
      }
      enum evpn-re-orig-route-enabled {
        value 1;
        description
          "EVPN Route Re-Originate Enabled";
      }
      enum evpn-re-orig-route-disabled {
        value 2;
        description
          "EVPN Route Re-Originate Disabled";
      }
    }
    description
      "EVPN Route Re-Originate";
  }

  typedef evpn-mcast-adv {
    type enumeration {
      enum evpn-multicast-advertise-undefined {
        value 0;
        description
          "EVPN Multicast Advertising Undefined";
      }
      enum evpn-multicast-advertise-enabled {
        value 1;
        description
          "EVPN Multicast Advertising Enabled";
      }
      enum evpn-multicast-advertise-disabled {
        value 2;
        description
          "EVPN Multicast Advertising Disabled";
      }
    }
    description
      "EVPN Multicast Advertising";
  }

  typedef evpn-flooding-suppression-flag {
    type enumeration {
      enum evpn-flood-suppress-undefined {
        value 0;
        description
          "EVPN Flood Suppression not defined";
      }
      enum evpn-flood-suppress-enabled {
        value 1;
        description
          "EVPN Flood Suppression Enabled";
      }
      enum evpn-flood-suppress-disabled {
        value 2;
        description
          "EVPN Flood Suppression Disabled";
      }
    }
    description
      "EVPN Flood Suppression Flag";
  }

  typedef evpn-irb-type {
    type enumeration {
      enum evpn-irb-asymmetric {
        value 0;
        description
          "EVPN Integrated Routing and Bridging Asymmetric";
      }
      enum evpn-irb-local-routing {
        value 1;
        description
          "EVPN Integrated Routing and Bridging Local Routing";
      }
    }
    description
      "EVPN Integrated Routing and Bridging Type";
  }

  typedef evpn-evi-state {
    type enumeration {
      enum evi-state-no-bgp-incomplete {
        value 0;
        description
          "No BGP, Incomplete";
      }
      enum evi-state-no-bgp-complete {
        value 1;
        description
          "No BGP, Complete";
      }
      enum evi-state-incomplete {
        value 2;
        description
          "Incomplete";
      }
      enum evi-state-delete-pending {
        value 3;
        description
          "Delete Pending";
      }
      enum evi-state-incomplete-pending {
        value 4;
        description
          "Incomplete Pending";
      }
      enum evi-state-complete-pending {
        value 5;
        description
          "Complete Pending";
      }
      enum evi-state-established {
        value 6;
        description
          "Established";
      }
    }
    description
      "EVPN Instance State";
  }

  typedef evpn-efi-state {
    type enumeration {
      enum efi-state-evi-down-bd-adown {
        value 0;
        description
          "EVPN Instance Down, BD Admin Down";
      }
      enum efi-state-evi-up-bd-adown {
        value 1;
        description
          "EVPN Instance Up, BD Admin Down";
      }
      enum efi-state-evi-down-bd-down {
        value 2;
        description
          "EVPN Instance Down, BD Oper Down";
      }
      enum efi-state-evi-up-bd-down {
        value 3;
        description
          "EVPN Instance Up, BD Oper Down";
      }
      enum efi-state-evi-down-bd-up {
        value 4;
        description
          "EVPN Instance Down, BD Up";
      }
      enum efi-state-established {
        value 5;
        description
          "Established";
      }
      enum efi-state-evi-down-bd-adown-delpend {
        value 6;
        description
          "EVPN Instance Down, BD Admin Down, Delete Pending";
      }
      enum efi-state-evi-up-bd-adown-delpend {
        value 7;
        description
          "EVPN Instance Up, BD Admin Down, Delete Pending";
      }
      enum efi-state-evi-down-bd-down-delpend {
        value 8;
        description
          "EVPN Instance Down, BD Oper Down, Delete Pending";
      }
      enum efi-state-evi-up-bd-down-delpend {
        value 9;
        description
          "EVPN Instance Up, BD Oper Down, Delete Pending";
      }
      enum efi-state-evi-down-bd-up-delpend {
        value 10;
        description
          "EVPN Instance Down, BD Up, Delete Pending";
      }
      enum efi-state-evi-up-bd-up-delpend {
        value 11;
        description
          "EVPN Instance Up, BD Up, Delete Pending";
      }
      enum efi-state-evi-down-bd-adown-crepend {
        value 12;
        description
          "EVPN Instance Down, BD Admin Down, Create Pending";
      }
      enum efi-state-evi-up-bd-adown-crepend {
        value 13;
        description
          "EVPN Instance Up, BD Admin Down, Create Pending";
      }
      enum efi-state-evi-down-bd-down-crepend {
        value 14;
        description
          "EVPN Instance Down, BD Oper Down, Create Pending";
      }
      enum efi-state-evi-up-bd-down-crepend {
        value 15;
        description
          "EVPN Instance Up, BD Oper Down, Create Pending";
      }
      enum efi-state-evi-down-bd-up-crepend {
        value 16;
        description
          "EVPN Instance Down, BD Up, Create Pending";
      }
      enum efi-state-evi-up-bd-up-crepend {
        value 17;
        description
          "Established Pending";
      }
    }
    description
      "EVPN Ethernet State";
  }

  typedef evpn-efp-state {
    type enumeration {
      enum evpn-efp-state-up {
        value 1;
        description
          "EVPN EFP State Up";
      }
      enum evpn-efp-state-admindown {
        value 2;
        description
          "EVPN EFP Admin Down State";
      }
      enum evpn-efp-state-efp-admindown {
        value 3;
        description
          "EVPN EFP Admin Down EFP State";
      }
      enum evpn-efp-state-down {
        value 4;
        description
          "EVPN EFP Down State";
      }
      enum evpn-efp-state-errdisabled {
        value 5;
        description
          "EVPN EFP Error Disabled State";
      }
      enum evpn-efp-state-unknown {
        value 6;
        description
          "EVPN EFP Unknown State";
      }
      enum evpn-efp-state-deleted {
        value 7;
        description
          "EVPN EFP Deleted State";
      }
      enum evpn-efp-state-bd-admindown {
        value 8;
        description
          "EVPN EFP BD Admin Down State";
      }
      enum evpn-efp-red-state-active {
        value 99;
        description
          "EVPN EFP Redundancy Active State";
      }
      enum evpn-efp-red-state-standby {
        value 100;
        description
          "EVPN EFP Redundancy Standby State";
      }
    }
    description
      "EVPN EFP State";
  }

  typedef network-instance-type {
    type enumeration {
      enum default-instance {
        value 0;
        description
          "Default Network Instance";
      }
      enum l3vrf {
        value 1;
        description
          "Layer 3 only routing instance";
      }
      enum l2vsi {
        value 2;
        description
          "Layer 2 only forwarding instance";
      }
      enum l2p2p {
        value 3;
        description
          "Layer 2 point to point forwarding instance";
      }
      enum l2l3 {
        value 4;
        description
          "Layer 2 and Layer 3 forwarding instance";
      }
    }
    description
      "Network Instance Type";
  }

  grouping evpn-pseudo-port-table-key {
    description
      "EVPN Port key";
    leaf if-id {
      type uint64;
      description
        "Interface index";
    }
    leaf svc-inst {
      type uint32;
      description
        "Service instance";
    }
  }

  grouping evpn-pseudo-port {
    description
      "EVPN Port operational data";
    leaf if-name {
      type string;
      description
        "Interface Name";
    }
    leaf efp-state {
      type evpn-ios-xe-oper:evpn-efp-state;
      description
        "EFP State";
    }
  }

  grouping evpn-peer-table-key {
    description
      "EVPN Peer key";
    leaf peer-ip-addr {
      type inet:ip-address;
      description
        "Peer IP address";
    }
  }

  grouping evpn-peer {
    description
      "EVPN Peer operational data";
    leaf peer-up-time {
      type yang:date-and-time;
      description
        "Peer Up Time";
    }
    leaf local-vni-id {
      when "../../../evpn-encap-type = 'evpn-encap-type-vxlan'";
      type uint32;
      description
        "Local VNI id";
    }
    leaf remote-vni-id {
      when "../../../evpn-encap-type = 'evpn-encap-type-vxlan'";
      type uint32;
      description
        "Remote VNI id";
    }
  }

  grouping evpn-vlan-table-key {
    description
      "EVPN VLAN key";
    leaf vlan-id {
      type uint16;
      description
        "BD VLAN id";
    }
  }

  grouping evpn-vlan {
    description
      "EVPN VLAN operational data";
    leaf evpn-inst-id {
      type uint16;
      description
        "EVPN Instance Id";
    }
    leaf vlan-if {
      type string;
      description
        "VLAN interface name";
    }
    leaf vlan-protected {
      type boolean;
      description
        "VLAN protected";
    }
    leaf efi-state {
      type evpn-ios-xe-oper:evpn-efi-state;
      description
        "EVPN Ethernet State";
    }
    leaf flood-suppr-attached {
      type boolean;
      description
        "Flood suppression status";
    }
    leaf core-if {
      when "../../evpn-encap-type = 'evpn-encap-type-vxlan'";
      type string;
      description
        "Core Interface";
    }
    leaf access-if {
      type string;
      description
        "Access Interface";
    }
    leaf nve-if {
      when "../../evpn-encap-type = 'evpn-encap-type-vxlan'";
      type string;
      description
        "Network Virtual Endpoint Interface";
    }
    leaf host-reach-bgp {
      when "../../evpn-encap-type = 'evpn-encap-type-vxlan'";
      type boolean;
      description
        "Host Reachability BGP";
    }
    leaf rmac {
      when "../../evpn-encap-type = 'evpn-encap-type-vxlan'";
      type yang:mac-address;
      description
        "Router MAC";
    }
    leaf core-vlan {
      when "../../evpn-encap-type = 'evpn-encap-type-vxlan'";
      type uint32;
      description
        "Core VLAN";
    }
    leaf l2-vni {
      when "../../evpn-encap-type = 'evpn-encap-type-vxlan'";
      type uint32;
      description
        "L2 VNI";
    }
    leaf l3-vni {
      when "../../evpn-encap-type = 'evpn-encap-type-vxlan'";
      type uint32;
      description
        "L3 VNI";
    }
    leaf vtep-ip {
      when "../../evpn-encap-type = 'evpn-encap-type-vxlan'";
      type inet:ip-address;
      description
        "VTEP IP Address";
    }
    leaf sec-vtep-ip {
      when "../../evpn-encap-type = 'evpn-encap-type-vxlan'";
      type inet:ip-address;
      description
        "Secondary VTEP IP Address";
    }
    leaf mcast-ip {
      type inet:ip-address;
      description
        "Multicast IP Address";
    }
    leaf ni-type {
      type common-types-ios-xe:net-inst-type;
      description
        "Network instance type. Differentiates between the
         default routing instance and VRFs";
    }
    leaf ni-name {
      type string;
      description
        "Network Instance or VRF name. If the type is
         net-inst-default, the name is not meaningful";
    }
    leaf irb-type {
      when "../../evpn-encap-type = 'evpn-encap-type-vxlan'";
      type evpn-ios-xe-oper:evpn-irb-type;
      description
        "IRB Type";
    }
    leaf ipv4-irb {
      type boolean;
      description
        "IPv4 IRB enabled";
    }
    leaf ipv6-irb {
      type boolean;
      description
        "IPv6 IRB enabled";
    }
    list evpn-pseudo-port {
      key "if-id svc-inst";
      description
        "Table EVPN Ports";
      uses evpn-ios-xe-oper:evpn-pseudo-port;
      uses evpn-ios-xe-oper:evpn-pseudo-port-table-key;
    }
    list evpn-peer {
      key "peer-ip-addr";
      description
        "Table EVPN Peers";
      uses evpn-ios-xe-oper:evpn-peer;
      uses evpn-ios-xe-oper:evpn-peer-table-key;
    }
  }

  grouping evpn-inst-table-key {
    description
      "EVPN Table key";
    leaf evpn-inst-id {
      type uint16;
      description
        "EVPN Instance Id";
    }
  }

  grouping evpn-inst {
    description
      "EVPN Instance operational data";
    leaf evpn-type {
      type evpn-ios-xe-oper:evpn-type;
      description
        "EVPN Type";
    }
    leaf evi-state {
      type evpn-ios-xe-oper:evpn-evi-state;
      description
        "EVPN Instance State";
    }
    leaf evpn-repl-type {
      type evpn-ios-xe-oper:evpn-replication-type;
      description
        "EVPN Replication Type";
    }
    leaf evpn-encap-type {
      type evpn-ios-xe-oper:evpn-encapsulation-type;
      description
        "EVPN Encapsulation Type";
    }
    leaf evpn-ip-local-learn {
      type evpn-ios-xe-oper:evpn-ip-local-learn;
      description
        "EVPN IP Local learn";
    }
    leaf evpn-dg-adv {
      type evpn-ios-xe-oper:evpn-dg-type;
      description
        "EVPN Distributed Gateway Advertising";
    }
    leaf evi-re-orig-rt5 {
      type evpn-ios-xe-oper:evpn-route-re-originate;
      description
        "EVPN Route Re-origination";
    }
    leaf evpn-ip-mcast-adv {
      type evpn-ios-xe-oper:evpn-mcast-adv;
      description
        "EVPN Multicast Advertising";
    }
    leaf evpn-ar-flood-suppr {
      type evpn-ios-xe-oper:evpn-flooding-suppression-flag;
      description
        "EVPN Flood Suppression";
    }
    leaf rd {
      type string;
      description
        "Route Distinguisher";
    }
    leaf-list import-rts {
      type string;
      ordered-by user;
      description
        "Import Route Targets";
    }
    leaf-list export-rts {
      type string;
      ordered-by user;
      description
        "Export Route Targets";
    }
    list evpn-vlan {
      key "vlan-id";
      description
        "Table VLANs";
      uses evpn-ios-xe-oper:evpn-vlan;
      uses evpn-ios-xe-oper:evpn-vlan-table-key;
    }
  }

  grouping evpn-id-map-info {
    description
      "VLAN EVPN Mapping";
    leaf evpn-inst-id {
      type uint16;
      description
        "EVPN Instance Id";
    }
  }

  grouping ni-evpn-map {
    description
      "Network Instance EVPN Mapping";
    leaf ni-name {
      type string;
      description
        "Network Instance Name";
    }
    leaf oc-ni-type {
      type evpn-ios-xe-oper:network-instance-type;
      description
        "Network Instance Type";
    }
    list evpn-id-map-info {
      key "evpn-inst-id";
      description
        "EVPN Instance Ids";
      uses evpn-ios-xe-oper:evpn-id-map-info;
    }
  }

  container evpn-oper-data {
    config false;
    description
      "EVPN operational data";
    list evpn-inst {
      key "evpn-inst-id";
      description
        "EVPN operational data";
      uses evpn-ios-xe-oper:evpn-inst;
      uses evpn-ios-xe-oper:evpn-inst-table-key;
    }
    list ni-evpn-map {
      key "ni-name";
      description
        "Network Instance EVPN Mapping";
      uses evpn-ios-xe-oper:ni-evpn-map;
    }
  }
}
