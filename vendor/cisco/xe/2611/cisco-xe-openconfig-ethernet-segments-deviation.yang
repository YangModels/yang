module cisco-xe-openconfig-ethernet-segments-deviation {
  namespace "http://cisco.com/ns/cisco-xe-openconfig-ethernet-segments-deviation";
  prefix oc-es-devs;

  import openconfig-ethernet-segments {
    prefix oc-es;
  }

  organization
    "Cisco Systems, Inc.";
  contact
    "Cisco Systems, Inc.
     Customer Service

     Postal: 170 W Tasman Drive
     San Jose, CA 95134

     Tel: +1 1800 553-NETS

     E-mail: cs-yang@cisco.com";
  description
    "This module defines deviation statements for openconfig-ethernet-segments module.
     Copyright (c) 2024 by Cisco Systems, Inc.
     All rights reserved.";

  revision 2025-07-01 {
    description
      "Initial version";
  }

  deviation "/oc-es:ethernet-segments/oc-es:ethernet-segment" {
    deviate not-supported;
    description
      "Currently not supported";
  }
}
