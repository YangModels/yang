module Cisco-IOS-XE-port-channel-crankshaft-deviation {
  yang-version 1.1;
  namespace "http://cisco.com/ns/yang/Cisco-IOS-XE-port-channel-crankshaft-deviation";
  prefix ios-ethernet-pcrank;

  import Cisco-IOS-XE-native {
    prefix ios;
  }
  import Cisco-IOS-XE-ethernet {
    prefix ios-eth;
  }

  organization
    "Cisco Systems";
  description
    "Cisco XE Native Deviation YANG module for IOS
     Copyright (c) 2024 by Cisco Systems, Inc.
     All rights reserved.";

  revision 2024-07-01 {
    description
      "Added port-channel deviation for crankshaft";
  }

  deviation "/ios:native/ios:interface/ios:Port-channel/ios:name" {
    deviate replace {
      type uint32 {
        range "1..32";
      }
    }
  }

  deviation "/ios:native/ios:interface/ios:GigabitEthernet/ios-eth:channel-group/ios-eth:number" {
    deviate replace {
      type uint16 {
        range "1..32";
      }
    }
  }

  deviation "/ios:native/ios:interface/ios:AppGigabitEthernet/ios-eth:channel-group/ios-eth:number" {
    deviate replace {
      type uint16 {
        range "1..32";
      }
    }
  }

  deviation "/ios:native/ios:interface/ios:FastEthernet/ios-eth:channel-group/ios-eth:number" {
    deviate replace {
      type uint16 {
        range "1..32";
      }
    }
  }

  deviation "/ios:native/ios:interface/ios:FiveGigabitEthernet/ios-eth:channel-group/ios-eth:number" {
    deviate replace {
      type uint16 {
        range "1..32";
      }
    }
  }

  deviation "/ios:native/ios:interface/ios:FortyGigabitEthernet/ios-eth:channel-group/ios-eth:number" {
    deviate replace {
      type uint16 {
        range "1..32";
      }
    }
  }

  deviation "/ios:native/ios:interface/ios:GigabitEthernet/ios-eth:channel-group/ios-eth:number" {
    deviate replace {
      type uint16 {
        range "1..32";
      }
    }
  }

  deviation "/ios:native/ios:interface/ios:TenGigabitEthernet/ios-eth:channel-group/ios-eth:number" {
    deviate replace {
      type uint16 {
        range "1..32";
      }
    }
  }

  deviation "/ios:native/ios:interface/ios:TwentyFiveGigE/ios-eth:channel-group/ios-eth:number" {
    deviate replace {
      type uint16 {
        range "1..32";
      }
    }
  }

  deviation "/ios:native/ios:interface/ios:TwoGigabitEthernet/ios-eth:channel-group/ios-eth:number" {
    deviate replace {
      type uint16 {
        range "1..32";
      }
    }
  }
}
