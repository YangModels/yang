module Cisco-IOS-XE-ipmux {
  yang-version 1.1;
  namespace "http://cisco.com/ns/yang/Cisco-IOS-XE-ipmux";
  prefix ios-ipmux;

  import cisco-semver {
    prefix cisco-semver;
  }
  import ietf-inet-types {
    prefix inet;
  }
  import Cisco-IOS-XE-types {
    prefix ios-types;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native IP Multiplexing Yang model.
     Copyright (c) 2019 by Cisco Systems, Inc.
     All rights reserved.";

  revision 2022-11-01 {
    description
      "- Update yang-version to 1.1";
    cisco-semver:module-version "1.1.0";
  }
  revision 2019-10-01 {
    description
      "Initial revision";
    cisco-semver:module-version "1.0.0";
  }

  grouping ipmux-interface-grouping {
    choice interface-choice {
      leaf Ethernet {
        description
          "IEEE 802.3";
        type string;
      }
      leaf FastEthernet {
        description
          "FastEthernet IEEE 802.3";
        type string;
      }
      leaf GigabitEthernet {
        description
          "GigabitEthernet IEEE 802.3z";
        type string;
      }
      leaf FiveGigabitEthernet {
        description
          "Five Gigabit Ethernet ";
        type string;
      }
      leaf AppGigabitEthernet {
        description
          "App-hosting Gigabit Ethernet IEEE 802.3z";
        type string;
      }
      leaf TenGigabitEthernet {
        description
          "Ten Gigabit Ethernet";
        type string;
      }
      leaf TwentyFiveGigabitEthernet {
        status obsolete;
        description
          "Twenty Five Gigabit Ethernet ";
        type string;
      }
      leaf TwentyFiveGigE {
        description
          "Twenty Five Gigabit Ethernet ";
        type string;
      }
      leaf FortyGigabitEthernet {
        description
          "Forty Gigabit Ethernet";
        type string;
      }
      leaf TwoGigabitEthernet {
        description
          "Two Gigabit Ethernet ";
        type string;
      }
      leaf HundredGigE {
        description
          "Hundred Gigabit Ethernet";
        type string;
      }
      leaf Tunnel {
        description
          "Tunnel interface";
        type uint32;
      }
    }
  }

  grouping config-interface-ip-mux-grouping {
    leaf mux {
      description
        "Enable IP multiplexing for outgoing packets";
      type empty;
    }
  }

  grouping config-ip-mux-profile-comm-grouping {
    leaf shutdown {
      type boolean;
      default "true";
    }
    leaf holdtime {
      description
        "Specify maximum mux policy queue hold time";
      default "20";
      type uint16 {
        range "20..250";
      }
    }
    leaf maxlength {
      description
        "Specify maximum size of packets to be multiplexed";
      must '. < ../mtu' {
        error-message "maxlength must be less than mtu";
      }
      type uint16 {
        range "64..1472";
      }
    }
    leaf mtu {
      description
        "Specify maximum superframe size";
      default "1500";
      type uint16 {
        range "256..1500";
      }
    }
    leaf singlepacket {
      description
        "Send single packet superframes";
      type boolean;
      default "true";
    }
    leaf ttl {
      default "64";
      type uint8 {
        range "1..255";
      }
    }
  }

  grouping config-ip-mux-profile-v4-grouping {
    leaf access-list {
      description
        "Specify standard or extended access lists to classify traffic";
      type ios-types:exp-acl-type;
    }
    leaf destination {
      description
        "Destination address of multiplexed packets";
      type inet:ipv4-address;
    }
    container source {
      description
        "Source address to use on multiplexed packets";
      choice source-choice {
        case ip-case {
          leaf source-ip {
            type inet:ipv4-address;
          }
        }
        case intf-case {
          container interface {
            description
              "Interface for source IP address";
            uses ipmux-interface-grouping;
          }
        }
      }
    }
  }

  grouping config-ip-mux-profile-v6-grouping {
    leaf access-list {
      description
        "Specify standard or extended access lists to classify traffic";
      type string {
        pattern '[a-zA-Z].*';
      }
    }
    leaf destination {
      description
        "Destination address of multiplexed packets";
      type inet:ipv6-address;
    }
    container source {
      description
        "Source address to use on multiplexed packets";
      choice source-choice {
        case ip-case {
          leaf source-ip {
            type inet:ipv6-address;
          }
        }
        case intf-case {
          container interface {
            description
              "Interface for source IP address";
            uses ipmux-interface-grouping;
          }
        }
      }
    }
  }

  grouping config-ipv4-mux-profile-grouping {
    list profile {
      description
        "Create or edit IP Multiplex DSCP policy";
      key "id";
      leaf id {
        type string;
      }
      uses config-ip-mux-profile-v4-grouping;
      uses config-ip-mux-profile-comm-grouping;
    }
  }

  grouping config-ipv6-mux-profile-grouping {
    list profile {
      description
        "Create or edit IP Multiplex DSCP policy";
      key "id";
      leaf id {
        type string;
      }
      uses config-ip-mux-profile-v6-grouping;
      uses config-ip-mux-profile-comm-grouping;
    }
  }

  grouping config-ip-mux-comm-grouping {
    leaf udpport {
      description
        "Specify destination UDP port to use for multiplexed packets";
      default "6682";
      type inet:port-number {
        range "1024..49151";
      }
    }
    leaf cache {
      description
        "Set maximum IP Multiplex cache size in bytes";
      default "1000000";
      type uint32 {
        range "1000000..4294967295";
      }
    }
    list policy {
      description
        "Create or edit IP Multiplex DSCP policy";
      key "name";
      leaf name {
        type string;
      }
      leaf outdscp {
        description
          "Specify DSCP value used on multiplexed superframe";
        type ios-types:dscp-type;
      }
      list matchdscp {
        description
          "Specify DSCP value used to match packets for this policy";
        key "dscp";
        leaf dscp {
          type ios-types:dscp-type;
        }
      }
    }
  }

  grouping config-ipv4-mux-grouping {
    container mux {
      uses config-ip-mux-comm-grouping;
      uses config-ipv4-mux-profile-grouping;
    }
  }

  grouping config-ipv6-mux-grouping {
    container mux {
      uses config-ip-mux-comm-grouping;
      uses config-ipv6-mux-profile-grouping;
    }
  }

  augment "/ios:native/ios:ip" {
    uses config-ipv4-mux-grouping {
      refine "mux/policy";
      refine "mux/profile/shutdown" {
        description
          "Enable/Disable IP Multiplex profile";
      }
      refine "mux/profile/ttl" {
        description
          "Set the IP TTL for the superframe";
      }
    }
  }

  augment "/ios:native/ios:interface/ios:Ethernet/ios:ip" {
    uses config-interface-ip-mux-grouping;
  }

  augment "/ios:native/ios:interface/ios:FastEthernet/ios:ip" {
    uses config-interface-ip-mux-grouping;
  }

  augment "/ios:native/ios:interface/ios:GigabitEthernet/ios:ip" {
    uses config-interface-ip-mux-grouping;
  }

  augment "/ios:native/ios:interface/ios:TenGigabitEthernet/ios:ip" {
    uses config-interface-ip-mux-grouping;
  }

  augment "/ios:native/ios:interface/ios:FiveGigabitEthernet/ios:ip" {
    uses config-interface-ip-mux-grouping;
  }

  augment "/ios:native/ios:interface/ios:AppGigabitEthernet/ios:ip" {
    uses config-interface-ip-mux-grouping;
  }

  augment "/ios:native/ios:interface/ios:TwentyFiveGigE/ios:ip" {
    uses config-interface-ip-mux-grouping;
  }

  augment "/ios:native/ios:interface/ios:TwoGigabitEthernet/ios:ip" {
    uses config-interface-ip-mux-grouping;
  }

  augment "/ios:native/ios:interface/ios:FortyGigabitEthernet/ios:ip" {
    uses config-interface-ip-mux-grouping;
  }

  augment "/ios:native/ios:interface/ios:HundredGigE/ios:ip" {
    uses config-interface-ip-mux-grouping;
  }

  augment "/ios:native/ios:interface/ios:Tunnel/ios:ip" {
    uses config-interface-ip-mux-grouping;
  }

  augment "/ios:native/ios:ipv6" {
    uses config-ipv6-mux-grouping {
      refine "mux/policy";
      refine "mux/profile/shutdown" {
        description
          "Enable/Disable IPv6 Multiplex profile";
      }
      refine "mux/profile/ttl" {
        description
          "Set the IPv6 TTL for the superframe";
      }
    }
  }

  augment "/ios:native/ios:interface/ios:Ethernet/ios:ipv6" {
    uses config-interface-ip-mux-grouping;
  }

  augment "/ios:native/ios:interface/ios:FastEthernet/ios:ipv6" {
    uses config-interface-ip-mux-grouping;
  }

  augment "/ios:native/ios:interface/ios:GigabitEthernet/ios:ipv6" {
    uses config-interface-ip-mux-grouping;
  }

  augment "/ios:native/ios:interface/ios:TenGigabitEthernet/ios:ipv6" {
    uses config-interface-ip-mux-grouping;
  }

  augment "/ios:native/ios:interface/ios:FiveGigabitEthernet/ios:ipv6" {
    uses config-interface-ip-mux-grouping;
  }

  augment "/ios:native/ios:interface/ios:AppGigabitEthernet/ios:ipv6" {
    uses config-interface-ip-mux-grouping;
  }

  augment "/ios:native/ios:interface/ios:TwentyFiveGigE/ios:ipv6" {
    uses config-interface-ip-mux-grouping;
  }

  augment "/ios:native/ios:interface/ios:TwoGigabitEthernet/ios:ipv6" {
    uses config-interface-ip-mux-grouping;
  }

  augment "/ios:native/ios:interface/ios:FortyGigabitEthernet/ios:ipv6" {
    uses config-interface-ip-mux-grouping;
  }

  augment "/ios:native/ios:interface/ios:HundredGigE/ios:ipv6" {
    uses config-interface-ip-mux-grouping;
  }

  augment "/ios:native/ios:interface/ios:Tunnel/ios:ipv6" {
    uses config-interface-ip-mux-grouping;
  }
}
