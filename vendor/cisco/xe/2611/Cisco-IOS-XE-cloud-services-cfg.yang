module Cisco-IOS-XE-cloud-services-cfg {
  yang-version 1.1;
  namespace "http://cisco.com/ns/yang/Cisco-IOS-XE-cloud-services-cfg";
  prefix cloudm;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for configuration of cloud services
     parameters.
     Copyright (c) 2024-2025 by Cisco Systems, Inc.
     All rights reserved.";

  revision 2026-02-01 {
    description
      "- Added URL for Cisco Spaces cloud.
       - Added no-proxy list for proxy bypass.";
    reference
      "2.2.0";
    cisco-semver:module-version "2.2.0";
  }
  revision 2024-07-01 {
    description
      "- HTTP Proxy URL for cloud-services deprecated.";
    reference
      "2.1.0";
    cisco-semver:module-version "2.1.0";
  }
  revision 2023-07-01 {
    description
      "- Add HTTP validation for cloud proxy type";
    reference
      "2.0.0";
    cisco-semver:module-version "2.0.0";
  }
  revision 2023-03-01 {
    description
      "Initial revision";
    reference
      "1.0.0";
    cisco-semver:module-version "1.0.0";
  }

  typedef cloudm-config-db-proxy-type {
    type enumeration {
      enum cloud-services-proxy-type-https {
        value 0;
        description
          "HTTPS proxy type";
      }
      enum cloud-services-proxy-type-unknown {
        value 1;
        description
          "Unknown proxy type";
      }
      enum cloud-services-proxy-type-http {
        value 2;
        description
          "HTTP proxy";
      }
    }
    description
      "Type of proxy transport";
  }

  grouping cloudm-config-db-proxy {
    description
      "Proxy for cloud services access.";
    leaf host {
      type string {
        length "0..230";
        pattern '(([A-Za-z0-9]+[A-Za-z0-9.\-]*|([0-9]{1,3}\.){3}[0-9]{1,3}|\[[a-fA-F0-9:]+\])(:[0-9]{1,5})?)?';
      }
      default "";
      status deprecated;
      description
        "Proxy URL without scheme";
    }
    leaf proxy-type {
      type cloudm:cloudm-config-db-proxy-type;
      must "((../proxy-type = 'cloud-services-proxy-type-http') and (../host != '')) or ((../proxy-type = 'cloud-services-proxy-type-unknown') and (../host = ''))" {
        error-message "proxy type can only be HTTP, or empty and unknown";
        error-app-tag "must-violation";
      }
      default "cloud-services-proxy-type-unknown";
      status deprecated;
      description
        "Proxy transport";
    }
  }

  grouping st-cloudm-global-config {
    description
      "Parameters for cloud services access";
    container proxy {
      status deprecated;
      description
        "Configures cloud services proxy, This is deprecated. Please use /native/ip/http/proxy-server instead";
      uses cloudm:cloudm-config-db-proxy;
    }
    leaf cisco-spaces-url {
      type string {
        length "1..221";
        pattern '(((http|https)://[A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*';
      }
      default "https://spaces.cisco.com";
      description
        "URL for Cisco Spaces cloud";
    }
    leaf no-proxy-list {
      type string {
        length "0..224";
        pattern '((([A-Za-z0-9@.:/?=%,&-]+)|(((([0-1]?[0-9]{1,2})|([2]?[0-5]{1,2})|([2]?[0-4][0-9]))[.]){3}(([0-1]?[0-9]{1,2})|([2]?[0-5]{1,2})|([2]?[0-4][1-9]))))*)*';
      }
      default "";
      description
        "List of comma separated host-names or IP addresses to be excluded from proxy";
    }
  }

  container cloud-services-cfg-data {
    description
      "Cloud services configuration data";
    container cloudm-config {
      presence "cloudm-config";
      description
        "Cloud services configuration parameters";
      uses cloudm:st-cloudm-global-config;
    }
  }
}
