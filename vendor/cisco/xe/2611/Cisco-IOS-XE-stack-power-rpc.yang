module Cisco-IOS-XE-stack-power-rpc {
  yang-version 1.1;
  namespace "http://cisco.com/ns/yang/Cisco-IOS-XE-stack-power-rpc";
  prefix stack-power-rpc-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for stack-power port enable disable actions.
     Copyright (c) 2023 by Cisco Systems, Inc.
     All rights reserved.";

  revision 2023-11-01 {
    description
      "Initial revision";
    reference
      "1.0.0";
    cisco-semver:module-version "1.0.0";
  }

  typedef stkpwr-state {
    type enumeration {
      enum disable {
        value 0;
        description
          "Disable stack power port";
      }
      enum enable {
        value 1;
        description
          "Enable stack power port";
      }
    }
    description
      "Stack port status";
  }

  grouping stkpwr-change {
    description
      "Set the switch stack-port status";
    leaf switch-number {
      type uint8 {
        range "1..16";
      }
      mandatory true;
      description
        "Switch number";
    }
    leaf port-number {
      type uint8 {
        range "1..2";
      }
      mandatory true;
      description
        "Stack port number";
    }
    leaf stkpwr-state {
      type stack-power-rpc-ios-xe:stkpwr-state;
      mandatory true;
      description
        "Stack port state";
    }
  }

  rpc set-stkpwr-port-state {
    description
      "Set the stack port status for a switch.";
    input {
      uses stack-power-rpc-ios-xe:stkpwr-change;
    }
  }
}
