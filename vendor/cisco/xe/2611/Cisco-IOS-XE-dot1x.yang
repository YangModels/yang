module Cisco-IOS-XE-dot1x {
  yang-version 1.1;
  namespace "http://cisco.com/ns/yang/Cisco-IOS-XE-dot1x";
  prefix ios-dot1x;

  import cisco-semver {
    prefix cisco-semver;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native dot1x Yang model.
     Copyright (c) 2016-2019 by Cisco Systems, Inc.
     All rights reserved.";

  revision 2026-02-01 {
    description
      "- Added support for type 6 in DOT1x credentials
       - Added support for dot1x supplicant enable-macsec CLI";
    cisco-semver:module-version "3.2.0";
  }
  revision 2025-07-01 {
    description
      "- Added FiftyGigabitEthernet interface support";
    cisco-semver:module-version "3.1.0";
  }
  revision 2024-07-01 {
    description
      "- Moved deprecated node dot1x critical eapol to obsolete";
    cisco-semver:module-version "3.0.0";
  }
  revision 2022-11-01 {
    description
      "- Update yang-version to 1.1";
    cisco-semver:module-version "2.2.0";
  }
  revision 2020-03-01 {
    description
      "- Added default values for dot1x timeout";
    cisco-semver:module-version "2.1.0";
  }
  revision 2019-11-01 {
    description
      "- Added dot1x config for UCSE";
    cisco-semver:module-version "2.0.0";
  }
  revision 2019-07-01 {
    description
      "- Establish semantic version baseline
       - Added anonymous-id";
    cisco-semver:module-version "1.0.0";
  }
  revision 2019-02-26 {
    description
      "Added leaf for App-hosting Gigabit Ethernet interface";
  }
  revision 2018-01-30 {
    description
      "Added dot1x logging";
  }
  revision 2017-11-27 {
    description
      "Added Change 25GE name";
  }
  revision 2017-11-14 {
    description
      "This revision has changes for new 40 and 100GE interface addition";
  }
  revision 2017-09-14 {
    description
      "This revision has changes for new 2gig interface addition";
  }
  revision 2017-08-16 {
    description
      "This revision has changes for new 5gig and 25gig interfaces addition";
  }
  revision 2017-02-07 {
    description
      "Initial revision";
  }

  grouping mode-config-fallback-profile-grouping {
    leaf description {
      description
        "Any textual description";
      type string;
    }
    container ip {
      description
        "Internet Protocol configuration commands";
      list access-group {
        description
          "Specify access control for packets";
        key "name";
        leaf name {
          description
            "IP expanded access list (standard or extended)";
          type union {
            type uint16 {
              range "1300..2699";
            }
            type string;
          }
        }
        leaf in {
          description
            "inbound packets";
          type empty;
        }
      }
      leaf admission {
        description
          "Name of IP admission rule";
        type string;
      }
    }
  }

  grouping config-fallback-grouping {
    container profile {
      description
        "Create a Fallback profile";
      list fallback-list {
        description
          "Specify a policy name";
        key "name";
        leaf name {
          type string;
        }
        uses mode-config-fallback-profile-grouping;
      }
    }
  }

  grouping config-dot1x-grouping {
    container auth-fail {
      description
        "Set 802.1x Fail Authentication parameter";
      leaf eapol {
        description
          "Send EAPOL-Success on successful auth-fail Authorization";
        type empty;
      }
    }
    container guest-vlan {
      description
        "Configure Guest Vlan and 802.1x Supplicant behavior";
      leaf supplicant {
        description
          "Allow 802.1x capable supplicants to enter Guest Vlan";
        type empty;
      }
    }
    list credentials {
      description
        "Configure 802.1X credentials profiles";
      key "profile-name";
      leaf description {
        description
          "Provide a description for the credentials profile";
        type string;
      }
      leaf profile-name {
        description
          "Specify a profile name";
        type string;
      }
      leaf username {
        description
          "Set the authentication userid";
        type string;
      }
      container password {
        description
          "Set the authentication password";
        leaf type {
          type enumeration {
            enum 0;
            enum 7;
            enum 6;
          }
        }
        leaf secret {
          type string;
        }
      }
      leaf pki-trustpoint {
        description
          "Set the default pki trustpoint";
        type string;
      }
      leaf anonymous-id {
        description
          "Set the anonymous userid";
        type string;
      }
    }
    container critical {
      description
        "Set 802.1x Critical Authentication parameters";
      container eapol-config {
        description
          "Send EAPOL-Success on successful Critical Authentication";
        presence "true";
        leaf block {
          description
            "Block all EAPoL transaction on Critical Authentication";
          type empty;
        }
      }
      leaf eapol {
        status obsolete;
        description
          "Obsolete: Use eapol-config";
        type empty;
      }
      container recovery {
        description
          "Set 802.1x Critical Authentication Recovery parameters";
        leaf delay {
          description
            "Set 802.1x Critical Authentication Recovery Delay period";
          type uint16 {
            range "1..10000";
          }
        }
      }
    }
    container test {
      description
        "Configure dot1x test related parameters";
      leaf timeout {
        description
          "Timeout for device EAPOL capabilities test in seconds";
        type uint16 {
          range "1..65535";
        }
      }
    }
    container logging {
      description
        "Set logging parameters";
      leaf verbose {
        description
          "Show verbose messages in system logs";
        type empty;
      }
    }
    container supplicant {
      description
        "802.1X supplicant configuration";
      container controlled {
        description
          "Configure controlled access by 802.1X supplicant";
        leaf transient {
          description
            "Controlled access is only applied during authentication";
          type empty;
        }
      }
      leaf force-multicast {
        description
          "Force 802.1X supplicant to send multicast packets";
        type empty;
      }
    }
    leaf system-auth-control {
      description
        "Enable or Disable SysAuthControl";
      type empty;
    }
  }

  grouping config-interface-dot1x-grouping {
    container dot1x {
      description
        "Interface Config Commands for IEEE 802.1X";
      container authenticator {
        description
          "Configure authenticator parameters";
        container eap {
          description
            "Configure EAP authenticator parameters";
          leaf profile {
            description
              "EAP authenticator profile configuration";
            type string;
          }
        }
      }
      leaf pae {
        description
          "Set 802.1x interface pae type";
        type enumeration {
          enum authenticator;
          enum supplicant;
          enum both;
        }
      }
      leaf credentials {
        description
          "Credentials profile configuration";
        type string;
      }
      leaf max-reauth-req {
        description
          "Max No. of Reauthentication Attempts";
        type uint8 {
          range "1..10";
        }
      }
      leaf max-req {
        description
          "Max No. of Retries";
        type uint8 {
          range "1..10";
        }
      }
      leaf max-start {
        description
          "Max No. of EAPOL-Start requests";
        type uint8 {
          range "1..10";
        }
      }
      container supplicant {
        description
          "Configure supplicant parameters";
        container eap {
          description
            "Configure EAP supplicant parameters";
          leaf profile {
            description
              "EAP supplicant profile configuration";
            type string;
          }
        }
        leaf enable-macsec {
          description
            "Enable or Disable macsec";
          type empty;
        }
      }
      container timeout {
        description
          "Various Timeouts";
        leaf auth-period {
          description
            "Timeout for authenticator reply";
          type uint16 {
            range "1..65535" {
              error-message "The auth-period must be a positive number not larger than 65535";
            }
          }
          default "30";
        }
        leaf held-period {
          description
            "Timeout for authentication retries";
          type uint16 {
            range "1..65535" {
              error-message "The held-period must be a positive number not larger than 65535";
            }
          }
          default "60";
        }
        leaf quiet-period {
          description
            "QuietPeriod in Seconds";
          type uint16 {
            range "1..65535" {
              error-message "The quiet-period must be a positive number not larger than 65535";
            }
          }
          default "60";
        }
        leaf ratelimit-period {
          description
            "Ratelimit Period in seconds";
          type uint16 {
            range "1..65535" {
              error-message "The ratelimit-period must be a positive number not larger than 65535";
            }
          }
        }
        leaf server-timeout {
          description
            "Timeout for Radius Retries";
          type uint16 {
            range "1..65535" {
              error-message "The server-period must be a positive number not larger than 65535";
            }
          }
        }
        leaf start-period {
          description
            "Timeout for EAPOL-start retries";
          type uint16 {
            range "1..65535" {
              error-message "The start-period must be a positive number not larger than 65535";
            }
          }
          default "30";
        }
        leaf supp-timeout {
          description
            "Timeout for supplicant reply";
          type uint16 {
            range "1..65535" {
              error-message "The supp-timeout must be a positive number not larger than 65535";
            }
          }
          default "30";
        }
        leaf tx-period {
          description
            "Timeout for supplicant retries";
          type uint16 {
            range "1..65535" {
              error-message "The tx-timeout must be a positive number not larger than 65535";
            }
          }
          default "30";
        }
      }
    }
  }

  augment "/ios:native/ios:dot1x" {
    uses config-dot1x-grouping;
  }

  augment "/ios:native/ios:fallback" {
    uses config-fallback-grouping;
  }

  augment "/ios:native/ios:interface/ios:FastEthernet" {
    uses config-interface-dot1x-grouping {
      if-feature "ios-features:dot1x";
    }
  }

  augment "/ios:native/ios:interface/ios:GigabitEthernet" {
    uses config-interface-dot1x-grouping {
      if-feature "ios-features:dot1x";
    }
  }

  augment "/ios:native/ios:interface/ios:TenGigabitEthernet" {
    uses config-interface-dot1x-grouping {
      if-feature "ios-features:dot1x";
    }
  }

  augment "/ios:native/ios:interface/ios:FiveGigabitEthernet" {
    uses config-interface-dot1x-grouping {
      if-feature "ios-features:dot1x";
    }
  }

  augment "/ios:native/ios:interface/ios:AppGigabitEthernet" {
    uses config-interface-dot1x-grouping {
      if-feature "ios-features:dot1x";
    }
  }

  augment "/ios:native/ios:interface/ios:TwentyFiveGigE" {
    uses config-interface-dot1x-grouping {
      if-feature "ios-features:dot1x";
    }
  }

  augment "/ios:native/ios:interface/ios:TwoGigabitEthernet" {
    uses config-interface-dot1x-grouping {
      if-feature "ios-features:dot1x";
    }
  }

  augment "/ios:native/ios:interface/ios:FortyGigabitEthernet" {
    uses config-interface-dot1x-grouping {
      if-feature "ios-features:dot1x";
    }
  }

  augment "/ios:native/ios:interface/ios:FiftyGigabitEthernet" {
    uses config-interface-dot1x-grouping {
      if-feature "ios-features:dot1x";
    }
  }

  augment "/ios:native/ios:interface/ios:HundredGigE" {
    uses config-interface-dot1x-grouping {
      if-feature "ios-features:dot1x";
    }
  }

  augment "/ios:native/ios:interface/ios:Port-channel" {
    uses config-interface-dot1x-grouping {
      if-feature "ios-features:dot1x";
    }
  }

  augment "/ios:native/ios:interface/ios:ucse" {
    uses config-interface-dot1x-grouping {
      if-feature "ios-features:dot1x";
    }
  }
}
