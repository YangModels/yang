module cisco-semver-internal {
  namespace "http://cisco.com/ns/yang/cisco-semver-internal";
  prefix cisco-semver-internal;

  organization
    "Cisco Systems
     170 West Tasman Drive
     San Jose, CA 95134-1706
     USA";
  contact
    "Mailing list: <cs-yang@cisco.com>";
  description
    "This YANG module defines internal extensions for semantic versioning.
     Copyright (c) 2019 by Cisco Systems, Inc.
     All rights reserved.";

  revision 2019-03-20 {
    description
      "Initial Version.";
  }

  extension os-version {
    argument version;
    description
      "The OS release version that this revision is targeted for.
       Used as a substatement to the revision statement.";
  }
}
