module Cisco-IOS-XE-dpi-events {
  yang-version 1.1;
  namespace "http://cisco.com/ns/yang/Cisco-IOS-XE-dpi-events";
  prefix dpi-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for dpi events.
     Copyright (c) 2025 by Cisco Systems, Inc.
     All rights reserved.";

  revision 2026-02-01 {
    description
      "Initial revision";
    reference
      "1.0.0";
    cisco-semver:module-version "1.0.0";
  }

  typedef dpi-category {
    type enumeration {
      enum dpi-cat-nbar {
        value 0;
        description
          "DPI Category NBAR";
      }
      enum dpi-cat-sdavc {
        value 1;
        description
          "DPI Category SD-AVC";
      }
      enum dpi-cat-tc {
        value 2;
        description
          "DPI Category Traffic Category";
      }
      enum dpi-cat-proto {
        value 3;
        description
          "DPI Category Protocol";
      }
    }
    description
      "DPI Category";
  }

  typedef dpi-result {
    type enumeration {
      enum dpi-res-success {
        value 0;
        description
          "DPI success";
      }
      enum dpi-res-ac-fail {
        value 1;
        description
          "DPI Application Classification Failure";
      }
    }
    description
      "DPI result";
  }

  typedef dpi-operation {
    type enumeration {
      enum dpi-op-enable {
        value 0;
        description
          "DPI operation enable";
      }
      enum dpi-op-disable {
        value 1;
        description
          "DPI operation disable";
      }
      enum dpi-op-upd {
        value 2;
        description
          "DPI operation update";
      }
      enum dpi-op-sync {
        value 3;
        description
          "DPI operation sync";
      }
    }
    description
      "DPI Operation";
  }

  typedef dpi-action {
    type enumeration {
      enum dpi-act-none {
        value 0;
        description
          "No action";
      }
      enum dpi-act-admin-tech {
        value 1;
        description
          "Collect admin-tech";
      }
    }
    description
      "DPI Action";
  }

  typedef dpi-failure-reason {
    type enumeration {
      enum dpi-rc-none {
        value 0;
        description
          "No specific reason";
      }
      enum dpi-rc-proto {
        value 1;
        description
          "Protocol iteration failed";
      }
      enum dpi-rc-proc {
        value 2;
        description
          "Process create failed";
      }
    }
    description
      "DPI failure reason";
  }

  grouping dpi-status {
    description
      "DPI status event";
    leaf severity {
      type ios-common-ios-xe-oper:notification-severity;
      description
        "Event severity";
    }
    leaf host-name {
      type string;
      description
        "Host name of the device";
    }
    leaf system-ip {
      type inet:ip-address;
      description
        "System IP of the device";
    }
    leaf category {
      type dpi-ios-xe-events:dpi-category;
      description
        "DPI status category";
    }
    leaf status {
      type dpi-ios-xe-events:dpi-result;
      description
        "DPI operation status";
    }
    leaf message {
      type string;
      description
        "DPI operation status message";
    }
    leaf action {
      type dpi-ios-xe-events:dpi-action;
      description
        "User action";
    }
    leaf op {
      type dpi-ios-xe-events:dpi-operation;
      description
        "DPI operation";
    }
    leaf reason {
      type dpi-ios-xe-events:dpi-failure-reason;
      description
        "Failure reason";
    }
  }

  notification dpi-status {
    description
      "DPI status notification";
    uses dpi-ios-xe-events:dpi-status;
  }
}
