module Cisco-IOS-XE-sdwan-ipsec-oper {
  yang-version 1.1;
  namespace "http://cisco.com/ns/yang/Cisco-IOS-XE-sdwan-ipsec-oper";
  prefix sdwan-ipsec-xe-oper;

  import Cisco-IOS-XE-sdwan-types {
    prefix ios-xe-sdwan-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for SDWAN IPSec IOS operational data.
     Copyright (c) 2025 by Cisco Systems, Inc.
     All rights reserved.";

  revision 2026-02-01 {
    description
      "Initial revision";
    reference
      "1.0.0";
    cisco-semver:module-version "1.0.0";
  }

  typedef iosd-encr-algo-enum {
    type enumeration {
      enum enc-none {
        value 0;
        description
          "No encryption";
      }
      enum enc-aes-gcm-256 {
        value 1;
        description
          "Represents the AES-GCM-256 encryption algorithm.";
      }
    }
    description
      "SDWAN encryption algorithm";
  }

  typedef iosd-auth-algo-enum {
    type enumeration {
      enum ath-none {
        value 0;
        description
          "No authentication";
      }
      enum ath-sha1 {
        value 1;
        description
          "Represents the SHA1 authentication algorithm.";
      }
    }
    description
      "SDWAN authentication algorithm";
  }

  typedef iosd-int-algo-enum {
    type enumeration {
      enum int-none {
        value 0;
        description
          "No integrity";
      }
      enum int-esp {
        value 1;
        description
          "ESP integrity";
      }
      enum int-ip-udp-esp {
        value 2;
        description
          "IP, UDP and ESP integrity";
      }
      enum int-ip-udp-esp-no-id {
        value 3;
        description
          "IP, UDP and ESP without ID integrity";
      }
    }
    description
      "SDWAN integrity algorithm";
  }

  grouping local-sa-key {
    description
      "Display IPsec local SA key";
    leaf tloc-addr {
      type inet:ip-address;
      description
        "Specifies the TLOC address.";
    }
    leaf tloc-color {
      type ios-xe-sdwan-types:sdwan-color-enum;
      description
        "Indicates the color attribute of the TLOC";
    }
    leaf spi {
      type uint32;
      description
        "Specifies the Security Parameter Index used in the Security Association";
    }
    leaf tloc-idx {
      type uint32;
      description
        "Specifies the index of the TLOC in the local TLOC table";
    }
  }

  grouping local-sa-obj {
    description
      "Display IPsec local SA object";
    leaf ip {
      type inet:ip-address;
      description
        "Specifies the IPv4 address associated with the local SA";
    }
    leaf port {
      type uint16;
      description
        "Specifies the UDP port number used by the local SA";
    }
    leaf encrypt-key-hash {
      type string;
      description
        "Encryption key hash";
    }
    leaf auth-key-hash {
      type string;
      description
        "Authentication key hash";
    }
    leaf ipv6 {
      type inet:ipv6-address;
      description
        "Specifies the IPv6 address associated with the local SA";
    }
  }

  grouping inb-conn-key {
    description
      "Display IPsec inbound connections key";
    leaf local-tloc-addr {
      type inet:ip-address;
      description
        "Specifies the local TLOC address.";
    }
    leaf local-tloc-color {
      type ios-xe-sdwan-types:sdwan-color-enum;
      description
        "Indicates the color attribute of the local TLOC.";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping inb-conn-obj {
    description
      "Display IPsec inbound connections object";
    leaf local-tloc-idx {
      type uint32;
      description
        "Local SA flow id";
    }
    leaf remote-tloc-idx {
      type uint32;
      description
        "Remote SA flow id";
    }
    leaf src-ip {
      type inet:ip-address;
      description
        "Source IP address";
    }
    leaf src-port {
      type uint16;
      description
        "Source port number";
    }
    leaf dst-ip {
      type inet:ip-address;
      description
        "Destination IP address";
    }
    leaf dst-port {
      type uint16;
      description
        "Destination port number";
    }
    leaf neg-encr-algo {
      type sdwan-ipsec-xe-oper:iosd-encr-algo-enum;
      description
        "Negotiated encryption algorithm";
    }
    leaf spi-per-tun {
      type uint32;
      description
        "Number of Traffic Control Security Parameter Index per Tunnel";
    }
  }

  grouping outb-conn-key {
    description
      "Display IPsec outbound connections key";
    leaf local-tloc-addr {
      type inet:ip-address;
      description
        "Specifies the local TLOC address.";
    }
    leaf local-tloc-color {
      type ios-xe-sdwan-types:sdwan-color-enum;
      description
        "Indicates the color attribute of the local TLOC,";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping outb-conn-obj {
    description
      "Display IPsec outbound connections object";
    leaf src-ip {
      type inet:ip-address;
      description
        "Source IP address";
    }
    leaf src-port {
      type uint16;
      description
        "Source port number";
    }
    leaf dst-ip {
      type inet:ip-address;
      description
        "Destination IP address";
    }
    leaf dst-port {
      type uint16;
      description
        "Destination port number";
    }
    leaf spi {
      type uint32;
      description
        "Specifies the Security Parameter Index used in the Security Association";
    }
    leaf tunnel-mtu {
      type uint32;
      description
        "Tunnel MTU";
    }
    leaf auth-used {
      type sdwan-ipsec-xe-oper:iosd-auth-algo-enum;
      description
        "Authentication used";
    }
    leaf encrypt-key-hash {
      type string;
      description
        "Encryption key hash";
    }
    leaf auth-key-hash {
      type string;
      description
        "Authenticated key hash";
    }
    leaf neg-algo {
      type sdwan-ipsec-xe-oper:iosd-encr-algo-enum;
      description
        "Negotiated encryption algorithm";
    }
    leaf int-used {
      type sdwan-ipsec-xe-oper:iosd-int-algo-enum;
      description
        "Integrity method used";
    }
    leaf spi-per-tun {
      type uint32;
      description
        "Number of Traffic Control Security Parameter Index  per Tunnel";
    }
  }

  grouping pwk-local-sa-key {
    description
      "Display Pairwise Key IPsec local SA Key";
    leaf tloc-addr {
      type inet:ip-address;
      description
        "Specifies the TLOC address.";
    }
    leaf tloc-color {
      type ios-xe-sdwan-types:sdwan-color-enum;
      description
        "Indicates the color attribute of the TLOC,";
    }
    leaf spi {
      type uint32;
      description
        "Specifies the Security Parameter Index used in the Security Association";
    }
    leaf tloc-idx {
      type uint32;
      description
        "TLOC index to local TLOC table";
    }
  }

  grouping pwk-local-sa-obj {
    description
      "Display Pairwise Key IPsec local SA object";
    leaf ip {
      type inet:ip-address;
      description
        "IP address";
    }
    leaf port {
      type uint16;
      description
        "Port number";
    }
    leaf sa-idx {
      type uint32;
      description
        "Inbound-SA index";
    }
    leaf pkey-id {
      type uint32;
      description
        "Pairwise Key ID";
    }
    leaf nonce-hash {
      type string;
      description
        "Nonce Hash";
    }
    leaf pkey-hash {
      type string;
      description
        "Pairwise Key Public Key Hash";
    }
  }

  grouping pwk-inb-conn-key {
    description
      "Display Pairwise Key IPsec inbound connections key";
    leaf local-tloc-addr {
      type inet:ip-address;
      description
        "Specifies the local TLOC address.";
    }
    leaf local-tloc-color {
      type ios-xe-sdwan-types:sdwan-color-enum;
      description
        "Indicates the color attribute of the local TLOC,";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping pwk-inb-conn-obj {
    description
      "Display Pairwise Key IPsec inbound connections object";
    leaf local-tloc-idx {
      type uint32;
      description
        "Local SA flow id";
    }
    leaf remote-tloc-idx {
      type uint32;
      description
        "Remote SA flow id";
    }
    leaf src-ip {
      type inet:ip-address;
      description
        "Source IP address";
    }
    leaf src-port {
      type uint16;
      description
        "Source port number";
    }
    leaf dst-ip {
      type inet:ip-address;
      description
        "Destination IP address";
    }
    leaf dst-port {
      type uint16;
      description
        "Destination port number";
    }
    leaf pwk-spi {
      type uint32;
      description
        "Pairwise Key Inbound SPI";
    }
    leaf sa-idx {
      type uint32;
      description
        "Inbound-SA index";
    }
    leaf pkey-id {
      type uint32;
      description
        "Pairwise Key ID";
    }
    leaf nonce-hash {
      type string;
      description
        "Nonce Hash";
    }
    leaf pkey-hash {
      type string;
      description
        "Pairwise Key Public Key Hash";
    }
    leaf ss-hash {
      type string;
      description
        "Pairwise Key Shared Secret Hash";
    }
    leaf d-key-hash {
      type string;
      description
        "Pairwise Key IPsec Decryption Key Hash";
    }
    leaf is-ah-auth {
      type boolean;
      description
        "Pairwise Key IPsec Using AH-AUTH";
    }
  }

  grouping pwk-outb-conn-key {
    description
      "Display Pairwise Key IPsec outbound connections key";
    leaf local-tloc-addr {
      type inet:ip-address;
      description
        "Specifies the local TLOC address.";
    }
    leaf local-tloc-color {
      type ios-xe-sdwan-types:sdwan-color-enum;
      description
        "Indicates the color attribute of the local TLOC,";
    }
    leaf remote-tloc-addr {
      type inet:ip-address;
      description
        "Specifies the remote TLOC address.";
    }
    leaf remote-tloc-color {
      type ios-xe-sdwan-types:sdwan-color-enum;
      description
        "Indicates the color attribute of the remote TLOC,";
    }
  }

  grouping pwk-outb-conn-obj {
    description
      "Display Pairwise Key IPsec outbound connections object";
    leaf src-ip {
      type inet:ip-address;
      description
        "Source IP address";
    }
    leaf src-port {
      type uint16;
      description
        "Source port number";
    }
    leaf dst-ip {
      type inet:ip-address;
      description
        "Destination IP address";
    }
    leaf dst-port {
      type uint16;
      description
        "Destination port number";
    }
    leaf spi {
      type uint32;
      description
        "Specifies the Security Parameter Index used in the Security Association";
    }
    leaf tloc-idx {
      type uint32;
      description
        "TLOC index to local TLOC table";
    }
    leaf local-tloc-idx {
      type uint32;
      description
        "Local SA flow id";
    }
    leaf remote-tloc-idx {
      type uint32;
      description
        "Remote SA flow id";
    }
    leaf pwk-spi {
      type uint32;
      description
        "Pairwise Key Security Parameter Index";
    }
    leaf sa-idx {
      type uint32;
      description
        "Outbound-SA index";
    }
    leaf pkey-id {
      type uint32;
      description
        "Pairwise Key ID";
    }
    leaf nonce-hash {
      type string;
      description
        "Nonce hash";
    }
    leaf pkey-hash {
      type string;
      description
        "Pairwise Key Public Key Hash";
    }
    leaf ss-hash {
      type string;
      description
        "Pairwise Key Shared Secret Hash";
    }
    leaf e-key-hash {
      type string;
      description
        "Pairwise Key IPsec Encryption Key Hash";
    }
    leaf is-ah-auth {
      type boolean;
      description
        "Pairwise Key IPsec Using AH-AUTH";
    }
  }

  container sdwan-ipsec-oper-data {
    config false;
    description
      "SDWAN IPSec IOS operational data";
    list local-sa {
      key "tloc-addr tloc-color spi tloc-idx";
      description
        "Local SA list";
      uses sdwan-ipsec-xe-oper:local-sa-key;
      uses sdwan-ipsec-xe-oper:local-sa-obj;
    }
    list inbound-con {
      key "local-tloc-addr local-tloc-color remote-tloc-addr remote-tloc-color";
      description
        "Inbound connection list";
      uses sdwan-ipsec-xe-oper:inb-conn-key;
      uses sdwan-ipsec-xe-oper:inb-conn-obj;
    }
    list outbound-con {
      key "local-tloc-addr local-tloc-color remote-tloc-addr remote-tloc-color";
      description
        "Outbound connection list";
      uses sdwan-ipsec-xe-oper:outb-conn-key;
      uses sdwan-ipsec-xe-oper:outb-conn-obj;
    }
    list pwk-local-sa {
      key "tloc-addr tloc-color spi tloc-idx";
      description
        "Pairwise key Local SA list";
      uses sdwan-ipsec-xe-oper:pwk-local-sa-key;
      uses sdwan-ipsec-xe-oper:pwk-local-sa-obj;
    }
    list pwk-inbound-con {
      key "local-tloc-addr local-tloc-color remote-tloc-addr remote-tloc-color";
      description
        "Pairwise key inbound connection list";
      uses sdwan-ipsec-xe-oper:pwk-inb-conn-key;
      uses sdwan-ipsec-xe-oper:pwk-inb-conn-obj;
    }
    list pwk-outbound-con {
      key "local-tloc-addr local-tloc-color remote-tloc-addr remote-tloc-color";
      description
        "Pairwise key outbound connection list";
      uses sdwan-ipsec-xe-oper:pwk-outb-conn-key;
      uses sdwan-ipsec-xe-oper:pwk-outb-conn-obj;
    }
  }
}
