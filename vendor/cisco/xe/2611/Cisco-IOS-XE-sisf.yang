module Cisco-IOS-XE-sisf {
  yang-version 1.1;
  namespace "http://cisco.com/ns/yang/ios-xe/sisf";
  prefix ios-sisf;

  import cisco-semver {
    prefix cisco-semver;
  }
  import Cisco-IOS-XE-native {
    prefix ios;
  }
  import Cisco-IOS-XE-dhcp {
    prefix ios-dhcp;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE SISF Yang Model.
     Copyright (c) 2021 by Cisco Systems, Inc.
     All rights reserved.";

  revision 2026-02-01 {
    description
      "- Added tailf:cli-diff-delete-before to process none before vlan-range, add, all";
    cisco-semver:module-version "2.0.1";
  }
  revision 2024-07-01 {
    description
      "- Updated must constraint for sisf features to allow 'default' policy";
    cisco-semver:module-version "2.0.0";
  }
  revision 2023-07-01 {
    description
      "- Added DHCP guard grouping";
    cisco-semver:module-version "1.2.0";
  }
  revision 2022-11-01 {
    description
      "- Update yang-version to 1.1";
    cisco-semver:module-version "1.1.0";
  }
  revision 2021-07-01 {
    description
      "- Adding monitor leaf inside template/access-session container
       - Removing vlan-name leaf from the vlan-grouping";
    cisco-semver:module-version "1.0.0";
  }

  grouping vlanlist-grouping {
    container vlan {
      description
        "Vlan list for which this policy applies";
      leaf add {
        description
          "add VLANs to the current list";
        type string;
      }
      leaf except {
        description
          "all VLANs except the following";
        type string;
      }
      leaf remove {
        description
          "remove VLANs from the current list";
        type string;
      }
      leaf vlan-range {
        description
          "VLAN IDs of the VLANs for which this policy applies";
        type string;
      }
      leaf all {
        description
          "all VLANs";
        type empty;
      }
      leaf none {
        description
          "no VLANs";
        type empty;
      }
    }
  }

  grouping config-ipv6-nd-raguard-grouping {
    container raguard {
      presence "Attach default RA guard policy on interface";
      description
        "Configure RA guard on the interface";
      container attach-policy {
        description
          "Apply a policy for feature RA guard";
        list policy-name {
          description
            "policy name for feature RA guard";
          key "policy-name";
          leaf policy-name {
            type string;
          }
          uses vlanlist-grouping;
        }
      }
      uses vlanlist-grouping;
    }
  }

  grouping config-ipv6-dhcp-guard-grouping {
    container guard {
      if-feature "ios-features:dhcp-guard";
      presence "true";
      description
        "Configure DHCP guard on the interface";
      container attach-policy {
        description
          "Apply a policy for feature DHCP guard";
        list policy-list {
          description
            "policy name for feature DHCP guard";
          key "policy-name";
          leaf policy-name {
            type string;
            must "(/ios:native/ios:ipv6/ios:dhcp/ios-dhcp:guard/ios-dhcp:policy[ios-dhcp:dhcp-guard-policy-name=current()]) or .='default'" {
              error-message "Create dhcp guard policy first, then attach policy; Detach policy from interface before removing the policy";
            }
          }
          uses vlanlist-grouping;
        }
      }
      uses vlanlist-grouping;
    }
  }

  grouping config-device-tracking-grouping {
    container device-tracking {
      presence "Attach default device-tracking policy on interface";
      description
        "Configure device-tracking on the interface";
      container attach-policy {
        description
          "Apply a policy for feature device-tracking";
        list policy-name {
          description
            "policy name for device tracking";
          key "policy-name";
          leaf policy-name {
            type string;
          }
          uses vlanlist-grouping;
        }
      }
      uses vlanlist-grouping;
    }
  }

  grouping config-source-guard-grouping {
    container source-guard {
      description
        "Configure IPv6 sourceguard";
      list policy {
        description
          "Configure a policy for feature sourceguard";
        key "source-guard-policy-name";
        leaf source-guard-policy-name {
          type string;
        }
        container validate {
          description
            "Validate the src of the received data traffic";
          leaf address-config {
            description
              "Validate against addresses learned in NDP/DHCP traffic (default)";
            type boolean;
            default "true";
          }
          leaf address {
            status deprecated;
            description
              "DEPRECATED: deprecated and replaced by address-config";
            type empty;
          }
          leaf prefix {
            description
              "Validate against prefixes learned in RA or DHCP-PD traffic";
            type empty;
          }
        }
        container deny {
          description
            "Block data traffic";
          leaf global-autoconf {
            description
              "Drop data traffic from global autoconfigured addresses";
            type empty;
          }
        }
        container permit {
          description
            "Allow data traffic";
          leaf link-local {
            description
              "Allow data traffic from all Link-local addresses";
            type empty;
          }
        }
        leaf trusted {
          description
            "Bridge all data traffic";
          type empty;
        }
      }
    }
  }

  grouping config-destination-guard-grouping {
    container destination-guard {
      description
        "Configure Destination guard";
      list policy {
        description
          "Configure a policy for feature destguard";
        key "destination-guard-policy-name";
        leaf destination-guard-policy-name {
          type string;
        }
        container enforcement {
          description
            "Sets the enforcement level";
          leaf always {
            description
              "Enforced under all conditions (default)";
            type empty;
          }
          leaf stressed {
            description
              "Enforced when system is under stress";
            type empty;
          }
        }
      }
    }
  }
}
