module Cisco-IOS-XE-aws-cw-oper {
  yang-version 1.1;
  namespace "http://cisco.com/ns/yang/Cisco-IOS-XE-aws-cw-oper";
  prefix aws-cw-oper;

  import Cisco-IOS-XE-aws-common-oper {
    prefix aws-common-oper;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWS Cloudwatch operational data.
     Copyright (c) 2023-2025 by Cisco Systems, Inc.
     All rights reserved.";

  revision 2025-07-01 {
    description
      "Initial revision";
    reference
      "1.0.0";
    cisco-semver:module-version "1.0.0";
  }

  grouping aws-cw-log-oper {
    description
      "AWS cloudwatch log data";
    leaf cw-log-file-path {
      type string;
      description
        "Log file path";
    }
    leaf cw-log-group-name {
      type string;
      description
        "Log group name";
    }
    leaf cw-log-stream-name {
      type string;
      description
        "Log stream name";
    }
  }

  grouping cw-service-oper {
    description
      "AWS Cloudwatch service information";
    leaf cw-profile-name {
      type string;
      description
        "Profile name";
    }
    leaf cw-pid {
      type uint32;
      description
        "Cloudwatch agent process ID";
    }
    leaf cw-state {
      type aws-common-oper:aws-agent-state;
      description
        "Agent state";
    }
    leaf cw-vrf {
      type aws-common-oper:aws-vrf-name;
      description
        "Cloudwatch VRF";
    }
    leaf cw-trace {
      type aws-common-oper:aws-agent-trace;
      description
        "Cloudwatch trace level";
    }
    leaf cw-region {
      type string;
      description
        "Cloudwatch region";
    }
    leaf cw-profile-descr {
      type string;
      description
        "Cloudwatch profile description";
    }
    container cw-proxy {
      description
        "Cloudwatch proxy settings";
      uses aws-common-oper:aws-proxy-config;
    }
    leaf cw-shutdown {
      type boolean;
      description
        "Cloudwatch shutdown variable";
    }
    list aws-oper-log-cw {
      key "cw-log-stream-name";
      description
        "AWS cloudwatch log data";
      uses aws-cw-oper:aws-cw-log-oper;
    }
  }

  container aws-cw-oper-data {
    config false;
    description
      "AWS Cloudwatch oper data";
    list aws-oper-cw {
      key "cw-profile-name";
      description
        "AWS Cloudwatch profile oper data";
      uses aws-cw-oper:cw-service-oper;
    }
  }
}
