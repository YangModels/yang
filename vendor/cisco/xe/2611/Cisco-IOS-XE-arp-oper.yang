module Cisco-IOS-XE-arp-oper {
  yang-version 1.1;
  namespace "http://cisco.com/ns/yang/Cisco-IOS-XE-arp-oper";
  prefix arp-ios-xe-oper;

  import Cisco-IOS-XE-ios-common-oper {
    prefix ios-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for IOS-XE ARP operational data.";

  revision 2022-11-01 {
    description
      "Update yang-version to 1.1";
    reference
      "1.4.0";
    cisco-semver:module-version "1.4.0";
  }
  revision 2021-07-01 {
    description
      "Deprecated arp-oper list. New arp-entry list with support for multiple
       ARP entries with the same IP address replaces the deprecated list.";
    reference
      "1.3.0";
    cisco-semver:module-version "1.3.0";
  }
  revision 2019-05-01 {
    description
      "Added semantic version";
    reference
      "1.2.0";
    cisco-semver:module-version "1.2.0";
  }
  revision 2018-07-13 {
    description
      "change in description";
    reference
      "1.1.0";
    cisco-semver:module-version "1.1.0";
  }
  revision 2017-12-13 {
    description
      "Initial revision";
    reference
      "1.0.0";
    cisco-semver:module-version "1.0.0";
  }

  typedef ios-arp-mode {
    type enumeration {
      enum ios-arp-mode-null {
        value 0;
        description
          "Undefined - error";
      }
      enum ios-arp-mode-dynamic {
        value 1;
        description
          "Entry has been learned";
      }
      enum ios-arp-mode-incomplete {
        value 2;
        description
          "We've requested, but have no reply yet";
      }
      enum ios-arp-mode-interface {
        value 3;
        description
          "Interface entry";
      }
      enum ios-arp-mode-static {
        value 4;
        description
          "Static Entry";
      }
      enum ios-arp-mode-alias {
        value 5;
        description
          "Static - We're fronting this host";
      }
      enum ios-arp-mode-app-simple {
        value 6;
        description
          "Simple Application ARP";
      }
      enum ios-arp-mode-app-alias {
        value 7;
        description
          "Application Alias";
      }
      enum ios-arp-mode-app-timer {
        value 8;
        description
          "Application Timer";
      }
    }
    description
      "The mode that this entry is running in";
  }

  grouping arp-oper-key {
    description
      "Key for ARP entry";
    leaf address {
      type inet:ip-address;
      description
        "High level protocol address";
    }
    leaf interface {
      type string;
      description
        "Interface associated with this ARP entry";
    }
  }

  grouping arp-entry {
    description
      "ARP Operational Data Entry";
    leaf enctype {
      type ios-common-ios-xe-oper:ios-encaps-type;
      description
        "Protocol that produced the entry";
    }
    leaf type {
      type ios-common-ios-xe-oper:ios-linktype;
      description
        "Protocol type of the ARP entry";
    }
    leaf mode {
      type arp-ios-xe-oper:ios-arp-mode;
      description
        "Mode of the ARP entry";
    }
    leaf hwtype {
      type ios-common-ios-xe-oper:ios-snpa-type;
      description
        "Type of HW address";
    }
    leaf hardware {
      type yang:mac-address;
      description
        "Hardware address";
    }
    leaf time {
      type yang:date-and-time;
      description
        "Time of the last update";
    }
  }

  grouping arp-oper {
    description
      "ARP Operational Data Entry";
    leaf address {
      type inet:ip-address;
      description
        "High level protocol address";
    }
    leaf enctype {
      type ios-common-ios-xe-oper:ios-encaps-type;
      description
        "Protocol that produced the entry";
    }
    leaf interface {
      type string;
      description
        "Interface associated with this ARP entry";
    }
    leaf type {
      type ios-common-ios-xe-oper:ios-linktype;
      description
        "Protocol that this ARP entry belongs to";
    }
    leaf mode {
      type arp-ios-xe-oper:ios-arp-mode;
      description
        "The mode that this entry is running in";
    }
    leaf hwtype {
      type ios-common-ios-xe-oper:ios-snpa-type;
      description
        "Type of HW address";
    }
    leaf hardware {
      type yang:mac-address;
      description
        "hardware address";
    }
    leaf time {
      type yang:date-and-time;
      description
        "Time of the last update";
    }
  }

  grouping arp-vrf {
    description
      "ARP Table Parent VRF";
    leaf vrf {
      type string;
      description
        "VRF name that the ARP table entries are tied to";
    }
    list arp-oper {
      key "address";
      status deprecated;
      description
        "This list is deprecated because it does not support multiple ARP entries with
         the same IP address. Use arp-entry list instead. The new list supports multiple
         ARP entries with the same IP address across different interfaces.";
      uses arp-ios-xe-oper:arp-oper;
    }
    list arp-entry {
      key "address interface";
      description
        "List of ARP entries associated with this VRF";
      uses arp-ios-xe-oper:arp-oper-key;
      uses arp-ios-xe-oper:arp-entry;
    }
  }

  container arp-data {
    config false;
    description
      "This module contains a collection of YANG definitions for
       monitoring the operation of IOS-XE ARP.
       Copyright (c) 2018-2019, 2021-2022 by Cisco Systems, Inc.
       All rights reserved.";
    list arp-vrf {
      key "vrf";
      description
        "List of VRFs with ARP table entries";
      uses arp-ios-xe-oper:arp-vrf;
    }
  }
}
