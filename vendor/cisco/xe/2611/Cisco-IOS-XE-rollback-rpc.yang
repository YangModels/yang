module Cisco-IOS-XE-rollback-rpc {
  yang-version 1.1;
  namespace "http://cisco.com/ns/yang/Cisco-IOS-XE-rollback-rpc";
  prefix ios-xe-rollback-rpc;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for RPCs related to the rollback files.
     Copyright (c) 2024 by Cisco Systems, Inc.
     All rights reserved.";

  revision 2026-02-01 {
    description
      "Initial revision";
    reference
      "1.0.0";
    cisco-semver:module-version "1.0.0";
  }

  grouping config-history-resp {
    description
      "Configuration history information.";
    list config-history {
      key "seqno";
      description
        "Configuration history.";
      leaf seqno {
        type uint16;
        description
          "Sequence number.";
      }
      leaf timestamp {
        type yang:date-and-time;
        description
          "The time when the configuration was made.";
      }
      leaf username {
        type string;
        description
          "The user who performed the configuration.";
      }
      leaf trans-id {
        type uint16;
        description
          "transaction Id.";
      }
      leaf protocol {
        type string;
        description
          "Protocol used to perform this configuration.";
      }
      leaf label {
        type string;
        description
          "Label used in the configuration request.";
      }
      leaf comment {
        type string;
        description
          "Comment used in the configuration request.";
      }
    }
  }

  rpc get-configuration-history {
    description
      "Information of configuration history.";
    output {
      uses ios-xe-rollback-rpc:config-history-resp;
    }
  }
}
