module Cisco-IOS-XE-ntp {
  yang-version 1.1;
  namespace "http://cisco.com/ns/yang/Cisco-IOS-XE-ntp";
  prefix ios-ntp;

  import cisco-semver {
    prefix cisco-semver;
  }
  import ietf-inet-types {
    prefix inet;
  }
  import Cisco-IOS-XE-types {
    prefix ios-types;
  }
  import Cisco-IOS-XE-native {
    prefix ios;
  }
  import Cisco-IOS-XE-features {
    prefix ios-features;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Network Time Protocol (NTP) Yang model.
     Copyright (c) 2016-2021 by Cisco Systems, Inc.
     All rights reserved.";

  revision 2022-11-01 {
    description
      "- Update yang-version to 1.1";
    cisco-semver:module-version "3.4.0";
  }
  revision 2022-07-01 {
    description
      "- Added support for ntp refclock ptp";
    cisco-semver:module-version "3.3.0";
  }
  revision 2022-03-01 {
    description
      "- Added new model for ntp multicast list";
    cisco-semver:module-version "3.2.0";
  }
  revision 2021-11-01 {
    description
      "- Modified the model to conform to yang 1.1 standard";
    cisco-semver:module-version "3.1.1";
  }
  revision 2021-07-01 {
    description
      "- Add support for on board GPS and Cellular GPS source to NTP
       - Modified the type of burst leafs from boolean to empty";
    cisco-semver:module-version "3.1.0";
  }
  revision 2021-03-01 {
    description
      "- Restricted string length of ipaddress to 63 for 'ntp server ip-address'
       - leaf ipaddress string length is restricted in ntp-peer-server-grouping
       - Removed must constraint from 'ntp server vrf' and added side effect handling";
    cisco-semver:module-version "3.0.0";
  }
  revision 2020-11-01 {
    description
      "- Added new leafs sha1 and sha2 in ntp authentication-key";
    cisco-semver:module-version "2.3.0";
  }
  revision 2020-07-01 {
    description
      "- Augmented ntp disable for Dialer interface and added default value
         for 'ntp master stratum-number'
       - Added new leafs sha1 and sha2 in ntp authentication-key";
    cisco-semver:module-version "2.2.0";
  }
  revision 2020-03-01 {
    description
      "- Incorporated backward compatible changes for NTP auth md5 leaf
       - reverted ntp-access-group peer model. Added separate grouping for ipv4 container";
    cisco-semver:module-version "2.1.0";
  }
  revision 2019-11-01 {
    description
      "- Added new leaf periodic to ntp-peer-server-attr-grouping
       - Added choice node for 'auth type' in ntp authentication-key
       - deprecated acl and kod leafs from ntp access-group peer, query-only, serve,
         serve-only container. Preserved only single xPath with ipv4 option
       - Added new grouping ntp-access-group-grouping-revised to met above requirements";
    cisco-semver:module-version "2.0.0";
  }
  revision 2019-07-01 {
    description
      "- Establish semantic version baseline
       - Corrected encryption-type in ntp authentication-key
       - Corrected ntp trusted-key
       - Corrected ntp server source command to accept interfaces
       - Change the ntp server source to leaf
       - Added new grouping ntp-peer-server-grouping-vrf";
    cisco-semver:module-version "1.0.0";
  }
  revision 2019-01-22 {
    description
      "Added leaf for App-hosting Gigabit Ethernet interface";
  }
  revision 2018-10-25 {
    description
      "Update types for ipv6 acl to only support string";
  }
  revision 2018-10-22 {
    description
      "Add defaults for server and peer list grouping";
  }
  revision 2018-06-28 {
    description
      "Added must constraints for deleting vrf";
  }
  revision 2018-01-05 {
    description
      "ntp server-list union order changed to make string type last";
  }
  revision 2017-11-27 {
    description
      "Added Change 25GE name";
  }
  revision 2017-11-14 {
    description
      "Added Two and 40 GE support";
  }
  revision 2017-09-21 {
    description
      "Added interface ntp broadcast";
  }
  revision 2017-09-20 {
    description
      "Added interface ntp broadcast client";
  }
  revision 2017-02-07 {
    description
      "Initial revision";
  }

  grouping ntp-access-group-kod-grouping {
    leaf acl {
      type ios-types:std-acl-type;
    }
    leaf kod {
      description
        "Send a Kiss-o-Death packet for failing peers";
      type empty;
      must '../acl';
    }
  }

  grouping ntp-access-group-kod-grouping-ipv4 {
    leaf acl {
      type ios-types:std-acl-type;
    }
    leaf kod {
      description
        "Send a Kiss-o-Death packet for failing peers";
      type empty;
      must '../acl';
    }
  }

  grouping ntp-ipv6-access-group-kod-grouping {
    leaf acl {
      type string;
    }
    leaf kod {
      description
        "Send a Kiss-o-Death packet for failing peers";
      type empty;
      must '../acl';
    }
  }

  grouping ntp-access-group-grouping {
    container peer {
      description
        "Provide full access";
      uses ntp-access-group-kod-grouping;
    }
    container query-only {
      description
        "Provide server and query access";
      uses ntp-access-group-kod-grouping;
    }
    container serve {
      description
        "Provide server and query access";
      uses ntp-access-group-kod-grouping;
    }
    container serve-only {
      description
        "Provide only server access";
      uses ntp-access-group-kod-grouping;
    }
  }

  grouping ntp-access-group-grouping-ipv4 {
    container peer {
      description
        "Provide full access";
      uses ntp-access-group-kod-grouping-ipv4;
    }
    container query-only {
      description
        "Provide server and query access";
      uses ntp-access-group-kod-grouping-ipv4;
    }
    container serve {
      description
        "Provide server and query access";
      uses ntp-access-group-kod-grouping-ipv4;
    }
    container serve-only {
      description
        "Provide only server access";
      uses ntp-access-group-kod-grouping-ipv4;
    }
  }

  grouping ntp-ipv6-access-group-grouping {
    container peer {
      description
        "Provide full access";
      uses ntp-ipv6-access-group-kod-grouping;
    }
    container query-only {
      description
        "Provide server and query access";
      uses ntp-ipv6-access-group-kod-grouping;
    }
    container serve {
      description
        "Provide server and query access";
      uses ntp-ipv6-access-group-kod-grouping;
    }
    container serve-only {
      description
        "Provide only server access";
      uses ntp-ipv6-access-group-kod-grouping;
    }
  }

  grouping ntp-peer-server-attr-grouping {
    leaf burst-opt {
      description
        "Send a burst when peer is reachable (Default)";
      type empty;
    }
    leaf iburst-opt {
      description
        "Send a burst when peer is unreachable (Default)";
      type empty;
    }
    leaf burst {
      description
        "Send a burst when peer is reachable (Default)";
      type boolean;
      default "true";
      status deprecated;
    }
    leaf iburst {
      description
        "Send a burst when peer is unreachable (Default)";
      type boolean;
      default "true";
      status deprecated;
    }
    leaf key {
      description
        "Configure peer authentication key";
      type uint32 {
        range "1..4294967295";
      }
    }
    leaf maxpoll {
      description
        "Maximum poll interval";
      type uint8 {
        range "4..17";
      }
      default "10";
    }
    leaf minpoll {
      description
        "Minimum poll interval";
      type uint8 {
        range "4..17";
      }
      default "6";
    }
    leaf prefer {
      description
        "Prefer this peer when possible";
      type empty;
    }
    leaf version {
      description
        "    Configure NTP version";
      type uint8 {
        range "1..4";
      }
      default "4";
    }
    leaf periodic {
      description
        "Check server availability periodically and switch to a new server
         if required";
      type empty;
    }
  }

  grouping ntp-peer-server-grouping {
    list server-list {
      key "ip-address";
      leaf ip-address {
        type union {
          type inet:ipv4-address;
          type inet:ipv6-address;
          type string {
            length "1..64";
          }
        }
      }
      leaf source {
        description
          "Interface for source address";
        type string;
      }
      uses ntp-peer-server-attr-grouping;
    }
    list ip {
      description
        "Use IP for DNS resolution";
      key "host-name";
      leaf host-name {
        type string {
          length "1..64";
        }
      }
      leaf source {
        description
          "Interface for source address";
        type string;
      }
      uses ntp-peer-server-attr-grouping;
    }
    list ipv6 {
      description
        "Use IPv6 for DNS resolution";
      key "host-name";
      leaf host-name {
        type string {
          length "1..64";
        }
      }
      leaf source {
        description
          "Interface for source address";
        type string;
      }
      uses ntp-peer-server-attr-grouping;
    }
  }

  grouping ntp-peer-server-grouping-vrf {
    list server-list {
      key "ip-address";
      leaf ip-address {
        type union {
          type inet:ipv4-address;
          type inet:ipv6-address;
          type string {
            length "1..64";
          }
        }
      }
      leaf source {
        description
          "Interface for source address";
        status obsolete;
        type string;
      }
      uses ntp-peer-server-attr-grouping;
    }
    list ip {
      description
        "Use IP for DNS resolution";
      key "host-name";
      leaf host-name {
        type string {
          length "1..64";
        }
      }
      leaf source {
        description
          "Interface for source address";
        status obsolete;
        type string;
      }
      uses ntp-peer-server-attr-grouping;
    }
    list ipv6 {
      description
        "Use IPv6 for DNS resolution";
      key "host-name";
      leaf host-name {
        type string {
          length "1..64";
        }
      }
      leaf source {
        description
          "Interface for source address";
        status obsolete;
        type string;
      }
      uses ntp-peer-server-attr-grouping;
    }
  }

  grouping config-ntp-grouping {
    container access-group {
      description
        "Control NTP access";
      container ipv4 {
        description
          "ipv4 access lists";
        uses ntp-access-group-grouping-ipv4;
      }
      container ipv6 {
        description
          "ipv6 access lists";
        uses ntp-ipv6-access-group-grouping;
      }
      uses ntp-access-group-grouping;
    }
    container allow {
      description
        "Allow processing of packets";
      container mode {
        description
          "Allow processing of particular mode packets";
        container control {
          description
            "Allow processing control mode packets";
          presence "true";
          leaf delay {
            description
              "Rate limiting delay (s)";
            type uint8 {
              range "0..15";
            }
          }
        }
        leaf private {
          description
            "Allow processing private mode packets";
          type empty;
        }
      }
    }
    leaf authenticate {
      description
        "Authenticate time sources";
      type empty;
    }
    list authentication-key {
      description
        "Authentication key for trusted time sources";
      key "number";
      leaf number {
        type uint32 {
          range "1..4294967295";
        }
      }
      choice authtype {
        leaf md5-cfg {
          description
            "MD5 authentication";
          type string;
        }
        leaf cmac-aes-128 {
          description
            "CMAC-AES-128 (digest length = 128 bits,
              key length = [16 or 32] bytes)";
          type string;
        }
        leaf hmac-sha1 {
          description
            "HMAC-SHA1 (digest length = 160 bits,
              key length = [1-32] bytes)";
          type string;
        }
        leaf hmac-sha2-256 {
          description
            "HMAC-SHA2-256 (digest length = 256 bits,
              key length = [1-32] bytes)";
          type string;
        }
        leaf sha1 {
          description
            "SHA1 (digest length = 160 bits,
              key length = [1-32] bytes)";
          type string;
        }
        leaf sha2 {
          description
            "SHA-256 (digest length = 256 bits,
              key length = [1-32] bytes)";
          type string;
        }
      }
      leaf md5 {
        description
          "MD5 authentication";
        type string;
        status deprecated;
      }
      leaf encryption-type {
        description
          "Authentication key encryption type";
        type uint32;
      }
    }
    leaf broadcastdelay {
      description
        "Estimated round-trip delay in microseconds";
      type uint32 {
        range "1..999999";
      }
    }
    leaf clock-period {
      description
        "Length of hardware clock tick";
      type uint32;
    }
    leaf logging {
      description
        "Enable NTP message logging";
      type empty;
    }
    container master {
      description
        "Act as NTP master clock";
      presence "true";
      leaf stratum-number {
        type uint8 {
          range "1..15";
        }
        default "8";
      }
    }
    leaf max-associations {
      description
        "Set maximum number of associations";
      type uint32;
    }
    leaf maxdistance {
      description
        "Maximum Distance for synchronization";
      type uint8 {
        range "1..16";
      }
    }
    leaf mindistance {
      description
        "Minimum distance to consider for clockhop";
      type uint16 {
        range "1..500";
      }
    }
    leaf orphan {
      description
        "Threshold Stratum for orphan mode";
      type uint8 {
        range "1..16";
      }
    }
    container panic {
      description
        "Reject time updates > panic threshold (default 1000Sec)";
      leaf update {
        description
          "Reject time updates > panic threshold (default 1000Sec)";
        type empty;
      }
    }
    leaf passive {
      description
        "NTP passive mode";
      type empty;
    }
    container peer {
      description
        "Configure NTP peer";
      uses ntp-peer-server-grouping;
      list vrf {
        description
          "VPN Routing/Forwarding Information";
        key "name";
        leaf name {
          type string {
            length "1..32";
          }
        }
        uses ntp-peer-server-grouping-vrf;
      }
    }
    container server {
      description
        "Configure NTP server";
      uses ntp-peer-server-grouping;
      list vrf {
        description
          "VPN Routing/Forwarding Information";
        key "name";
        leaf name {
          type string {
            length "1..32";
          }
        }
        uses ntp-peer-server-grouping-vrf;
      }
    }
    container source {
      description
        "Configure interface for source address";
      uses ios-ifc:interface-grouping;
    }
    list trusted-key {
      description
        "Key numbers for trusted time sources";
      key "number";
      leaf number {
        type uint16 {
          range "1..65535";
        }
      }
      leaf hyphen {
        type empty;
      }
      leaf end-key {
        description
          "End Key range";
        type uint16 {
          range "1..65535";
        }
      }
    }
    leaf update-calendar {
      description
        "Periodically update calendar with NTP time";
      type empty;
    }
    container refclock {
      description
        "NTP internal reference clock";
      container gps {
        description
          "Use GPS as reference clock";
        presence "true";
        leaf interface {
          type string;
          description
            "Configure interface for ntp gps source";
          must '/ios:native/ios:interface/*[concat(local-name(), ios:name) = current()]' {
            error-message "Cellular interface does not exist";
          }
        }
      }
      leaf ptp {
        if-feature "ios-features:ntp-ptp";
        description
          "Enable/disable PTP as reference clock for NTP";
        type boolean;
        default "false";
      }
    }
  }

  grouping config-interface-ntp-grouping {
    container ntp {
      description
        "Configure NTP";
      list multicast {
        description
          "Configure NTP multicast service";
        key "ipv6";
        leaf ipv6 {
          description
            "Multicast group IPv6 address";
          type inet:ipv6-address;
        }
        leaf key {
          description
            "Configure multicast authentication key";
          type uint32 {
            range "0..4294967295";
          }
        }
        leaf ttl {
          description
            "TTL of the multicast packet";
          type uint16 {
            range "1..255";
          }
          default "128";
        }
        leaf version {
          description
            "Configure NTP version";
          type uint16 {
            range "1..4";
          }
          default "4";
        }
      }
      leaf broadcast {
        description
          "Configure NTP broadcast service";
        type boolean;
        default "false";
      }
      container broadcast-option {
        description
          "Configure NTP broadcast service";
        container broadcast {
          leaf client {
            description
              "Listen to NTP broadcasts";
            type boolean;
            default "false";
          }
        }
      }
      container disable {
        description
          "Disable NTP traffic (both IP and IPv6)";
        presence "true";
        must "not (../broadcast = 'true'
                   or ../broadcast-option/broadcast/client = 'true')" {
          error-message
            "%NTP: Unconfigure other NTP commands on this
             interface before executing 'ntp disable'";
        }
        leaf ip-ipv6 {
          type enumeration {
            enum ip {
              description
                "Disable IP based NTP traffic";
            }
            enum ipv6 {
              description
                "Disable IPv6 based NTP traffic";
            }
          }
        }
      }
    }
  }

  augment "/ios:native/ios:ntp" {
    uses config-ntp-grouping;
  }

  augment "/ios:native/ios:interface/ios:FastEthernet" {
    uses config-interface-ntp-grouping;
  }

  augment "/ios:native/ios:interface/ios:GigabitEthernet" {
    uses config-interface-ntp-grouping;
  }

  augment "/ios:native/ios:interface/ios:TenGigabitEthernet" {
    uses config-interface-ntp-grouping;
  }

  augment "/ios:native/ios:interface/ios:FiveGigabitEthernet" {
    uses config-interface-ntp-grouping;
  }

  augment "/ios:native/ios:interface/ios:AppGigabitEthernet" {
    uses config-interface-ntp-grouping;
  }

  augment "/ios:native/ios:interface/ios:TwentyFiveGigE" {
    uses config-interface-ntp-grouping;
  }

  augment "/ios:native/ios:interface/ios:TwentyFiveGigabitEthernet" {
    status obsolete;
    uses config-interface-ntp-grouping;
  }

  augment "/ios:native/ios:interface/ios:HundredGigE" {
    uses config-interface-ntp-grouping;
  }

  augment "/ios:native/ios:interface/ios:TwoGigabitEthernet" {
    uses config-interface-ntp-grouping;
  }

  augment "/ios:native/ios:interface/ios:FortyGigabitEthernet" {
    uses config-interface-ntp-grouping;
  }

  augment "/ios:native/ios:interface/ios:Loopback" {
    uses config-interface-ntp-grouping;
  }

  augment "/ios:native/ios:interface/ios:Tunnel" {
    uses config-interface-ntp-grouping;
  }

  augment "/ios:native/ios:interface/ios:Virtual-Template" {
    uses config-interface-ntp-grouping;
  }

  augment "/ios:native/ios:interface/ios:Vlan" {
    uses config-interface-ntp-grouping;
  }

  augment "/ios:native/ios:interface/ios:Dialer" {
    uses config-interface-ntp-grouping;
  }

  augment "/ios:native/ios:interface/ios:AppNav-Compress" {
    uses config-interface-ntp-grouping;
  }

  augment "/ios:native/ios:interface/ios:AppNav-UnCompress" {
    uses config-interface-ntp-grouping;
  }

  augment "/ios:native/ios:interface/ios:ATM" {
    uses config-interface-ntp-grouping;
  }

  augment "/ios:native/ios:interface/ios:ATM-subinterface" {
    uses config-interface-ntp-grouping;
  }

  augment "/ios:native/ios:interface/ios:Async" {
    uses config-interface-ntp-grouping;
  }

  augment "/ios:native/ios:interface/ios:BD-VIF" {
    uses config-interface-ntp-grouping;
  }

  augment "/ios:native/ios:interface/ios:BDI" {
    uses config-interface-ntp-grouping;
  }

  augment "/ios:native/ios:interface/ios:Cellular" {
    uses config-interface-ntp-grouping;
  }

  augment "/ios:native/ios:interface/ios:Embedded-Service-Engine" {
    uses config-interface-ntp-grouping;
  }

  augment "/ios:native/ios:interface/ios:Ethernet" {
    uses config-interface-ntp-grouping;
  }

  augment "/ios:native/ios:interface/ios:LISP" {
    uses config-interface-ntp-grouping;
  }

  augment "/ios:native/ios:interface/ios:Multilink" {
    uses config-interface-ntp-grouping;
  }

  augment "/ios:native/ios:interface/ios:Port-channel" {
    uses config-interface-ntp-grouping;
  }

  augment "/ios:native/ios:interface/ios:SM" {
    uses config-interface-ntp-grouping;
  }

  augment "/ios:native/ios:interface/ios:Serial" {
    uses config-interface-ntp-grouping;
  }

  augment "/ios:native/ios:interface/ios:VirtualPortGroup" {
    uses config-interface-ntp-grouping;
  }

  augment "/ios:native/ios:interface/ios:nve" {
    uses config-interface-ntp-grouping;
  }

  augment "/ios:native/ios:interface/ios:Vif" {
    uses config-interface-ntp-grouping;
  }

  augment "/ios:native/ios:interface/ios:Wlan-GigabitEthernet" {
    uses config-interface-ntp-grouping;
  }

  augment "/ios:native/ios:interface/ios:MFR" {
    uses config-interface-ntp-grouping;
  }

  augment "/ios:native/ios:interface/ios:MFR-subinterface" {
    uses config-interface-ntp-grouping;
  }

  augment "/ios:native/ios:interface/ios:Serial-subinterface" {
    uses config-interface-ntp-grouping;
  }

  augment "/ios:native/ios:interface/ios:ucse" {
    uses config-interface-ntp-grouping;
  }

  augment "/ios:native/ios:interface/ios:Ethernet-Internal" {
    uses config-interface-ntp-grouping;
  }

  augment "/ios:native/ios:interface/ios:Service-Engine" {
    uses config-interface-ntp-grouping;
  }

  augment "/ios:native/ios:interface/ios:LISP-subinterface" {
    uses config-interface-ntp-grouping;
  }

  augment "/ios:native/ios:interface/ios:Port-channel-subinterface" {
    uses config-interface-ntp-grouping;
  }

  augment "/ios:native/ios:interface/ios:GMPLS" {
    uses config-interface-ntp-grouping;
  }

  augment "/ios:native/ios:interface/ios:Group-Async" {
    uses config-interface-ntp-grouping;
  }

  augment "/ios:native/ios:interface/ios:Virtual-PPP" {
    uses config-interface-ntp-grouping;
  }

  augment "/ios:native/ios:interface/ios:vasileft" {
    uses config-interface-ntp-grouping;
  }

  augment "/ios:native/ios:interface/ios:vasiright" {
    uses config-interface-ntp-grouping;
  }
}
