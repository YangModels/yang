module Cisco-IOS-XE-route-map {
  yang-version 1.1;
  namespace "http://cisco.com/ns/yang/Cisco-IOS-XE-route-map";
  prefix ios-route-map;

  import cisco-semver {
    prefix cisco-semver;
  }
  import ietf-inet-types {
    prefix inet;
  }
  import Cisco-IOS-XE-types {
    prefix ios-types;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Route Map Yang model.
     Copyright (c) 2016-2021 by Cisco Systems, Inc.
     All rights reserved.";

  revision 2023-03-01 {
    description
      "- Hardened CLIs set ipv6 vrf next-hop , set ipv6 default vrf next-hop, set ipv6 vrf next-hop verify availability, set ipv6 vrf next-hop verify availability sequence track
       - Hardened set ipv6 next-hop verify-availability
       - Hardened CLI set tag
       - Hardened CLI match tag
       - Added new tos without presence container and deprecating tos container
       - Added new external number container and deprecating external container
       - Added a new descriptions list and deprecating description leaf";
    cisco-semver:module-version "4.0.0";
  }
  revision 2022-11-01 {
    description
      "- Update yang-version to 1.1
       - Hardened CLIs set ipv6 default global next-hop, set ipv6 default next-hop, set ipv6 global next-hop, set ipv6 global next-hop verify-availability";
    cisco-semver:module-version "3.0.0";
  }
  revision 2022-07-01 {
    description
      "- Migrate BGP-owned route-map nodes to BGP model
       - Deprecated set/ipv6/address/prefix-list from leaf-list to leaf
       - Moved deprecate annotations to annotation file";
    cisco-semver:module-version "2.5.0";
  }
  revision 2022-03-01 {
    description
      "- Add ordered-by user in match community and match extcommunity ";
    cisco-semver:module-version "2.4.0";
  }
  revision 2021-11-01 {
    description
      "- added additive option for set extended community color";
    cisco-semver:module-version "2.3.0";
  }
  revision 2021-03-01 {
    description
      "- Removed the tailf cli-diff-dependency";
    cisco-semver:module-version "2.2.1";
  }
  revision 2020-11-01 {
    description
      "Add large-community configurations";
    cisco-semver:module-version "2.2.0";
  }
  revision 2020-07-01 {
    description
      "Model change for match/length/max( and min), set/ipv6/default/next-hop
        and set/ipv6/next-hop";
    cisco-semver:module-version "2.1.0";
  }
  revision 2020-03-01 {
    description
      "Update set community-list configuration
       Add route-map continue configuration";
    cisco-semver:module-version "2.0.0";
  }
  revision 2019-11-01 {
    description
      "Changed address data type";
    cisco-semver:module-version "1.1.0";
  }
  revision 2019-07-01 {
    description
      "Establish semantic version baseline";
    cisco-semver:module-version "1.0.0";
  }
  revision 2019-03-06 {
    description
      "Fixed route-map set community configuration";
  }
  revision 2018-12-06 {
    description
      "Added Support of color extended community";
  }
  revision 2018-12-01 {
    description
      "Removed choice option from set ip nexthop so that multiple
       options can be configured at same time";
  }
  revision 2018-11-13 {
    description
      "Change to use + in multi-line descriptions to avoid NSO compile error";
  }
  revision 2018-08-30 {
    description
      "Added support for set nlri and set attribute-set";
  }
  revision 2018-08-10 {
    description
      "Added support for multiple IPv4 next-hop (set ip next-hop)";
  }
  revision 2018-05-02 {
    description
      "Add omp and nat-route to source-protocol matching";
  }
  revision 2018-03-08 {
    description
      "Add tailf:cli-flat-list-syntax to route-map/match-preference";
  }
  revision 2018-01-08 {
    description
      "Revise modeling for set metric";
  }
  revision 2017-10-20 {
    description
      "Add model omp-tag for set and match";
  }
  revision 2017-07-27 {
    description
      "Add model for set ip next-hop verify-availability<ipaddr> <range> track <range>";
  }
  revision 2017-06-07 {
    description
      "Add model for named ordering route-map enable";
  }
  revision 2017-02-07 {
    description
      "Initial revision";
  }

  grouping rt_map_interface-deprecated-grouping {
    choice interface-choice {
      leaf AppNav-Compress {
        status deprecated;
        description
          "Service-Context Virtual Interface Compress";
        type uint16;
      }
      leaf AppNav-UnCompress {
        status deprecated;
        description
          "Service-Context Virtual Interface UnCompress";
        type uint16;
      }
      leaf ATM {
        status deprecated;
        description
          "ATM interface";
        type string;
      }
      container ATM-subinterface {
        status deprecated;
        leaf ATM {
          status deprecated;
          type string;
        }
      }
      leaf ATM-ACR {
        status deprecated;
        description
          "ATM-ACR interface";
        type string {
          pattern '[0-9]';
        }
      }
      container ATM-ACRsubinterface {
        status deprecated;
        leaf ATM-ACR {
          status deprecated;
          type string {
            pattern '[0-9]\.([0-9]/){3}[0-9]';
          }
        }
      }
      leaf BDI {
        status deprecated;
        description
          "Bridge-Domain interface";
        type string;
      }
      leaf CEM {
        status deprecated;
        description
          "CEM interface";
        type string {
          pattern '([0-9]/){2}[0-9]';
        }
      }
      leaf CEM-ACR {
        status deprecated;
        description
          "CEM-ACR interface";
        type uint8 {
          range "0..255";
        }
      }
      leaf Embedded-Service-Engine {
        status deprecated;
        description
          "cisco embedded service engine module";
        type string;
      }
      leaf Ethernet {
        status deprecated;
        description
          "IEEE 802.3";
        type string;
      }
      leaf FastEthernet {
        status deprecated;
        description
          "FastEthernet IEEE 802.3";
        type string;
      }
      leaf GigabitEthernet {
        status deprecated;
        description
          "GigabitEthernet IEEE 802.3z";
        type string;
      }
      leaf FiveGigabitEthernet {
        status deprecated;
        description
          "Five GigabitEthernet ";
        type string;
      }
      leaf AppGigabitEthernet {
        status deprecated;
        description
          "App-hosting Gigabit Ethernet IEEE 802.3z";
        type string;
      }
      leaf TwentyFiveGigabitEthernet {
        status obsolete;
        description
          "Twenty Five GigabitEthernet ";
        type string;
      }
      leaf TwentyFiveGigE {
        status deprecated;
        description
          "Twenty Five GigabitEthernet ";
        type string;
      }
      leaf TwoGigabitEthernet {
        status deprecated;
        description
          "Two GigabitEthernet ";
        type string;
      }
      leaf FortyGigabitEthernet {
        status deprecated;
        description
          "Forty GigabitEthernet ";
        type string;
      }
      leaf HundredGigE {
        status deprecated;
        description
          "Hundred GigabitEthernet";
        type string;
      }
      leaf LISP {
        status deprecated;
        description
          "Locator/ID Separation Protocol Virtual Interface";
        type string;
      }
      container LISP-subinterface {
        status deprecated;
        description
          "Locator/ID Separation Protocol Virtual Interface";
        leaf LISP {
          status deprecated;
          type string {
            pattern '[0-9]*(. ?[1-9][0-9]*)*';
          }
        }
      }
      leaf Loopback {
        status deprecated;
        description
          "Loopback interface";
        type uint32;
      }
      leaf Multilink {
        status deprecated;
        description
          "Multilink-group interface";
        type uint16;
      }
      leaf nve {
        status deprecated;
        description
          "Network virtualization endpoint interface";
        type uint16;
      }
      leaf overlay {
        status deprecated;
        description
          "Overlay interface";
        type uint16;
      }
      leaf Port-channel {
        status deprecated;
        description
          "Ethernet Channel of interfaces";
        type uint32;
      }
      container Port-channel-subinterface {
        status deprecated;
        leaf Port-channel {
          status deprecated;
          type string;
        }
      }
      leaf pseudowire {
        status deprecated;
        description
          "Pseudowire Interface";
        type uint32;
      }
      leaf SM {
        status deprecated;
        description
          "SM Interface";
        type string;
      }
      leaf Cellular {
        status deprecated;
        description
          "Cellular Interface";
        type string;
      }
      leaf Dialer {
        status deprecated;
        description
          "Dialer Interface";
        type string;
      }
      leaf Serial {
        status deprecated;
        description
          "Serial interface";
        type string;
      }
      leaf Async {
        status deprecated;
        description
          "Async serial interface";
        type string;
      }
      leaf TenGigabitEthernet {
        status deprecated;
        description
          "Ten Gigabit Ethernet";
        type string;
      }
      leaf Tunnel {
        status deprecated;
        description
          "Tunnel interface";
        type uint32;
      }
      leaf Virtual-Template {
        status deprecated;
        description
          "Virtual Template interface";
        type uint16;
      }
      leaf Vlan {
        status deprecated;
        description
          "Iosxr Vlans";
        type uint16;
      }
      leaf VirtualPortGroup {
        status deprecated;
        description
          "Virtual Port Group";
        type uint16;
      }
      leaf vasileft {
        status deprecated;
        description
          "vasileft";
        type uint16;
      }
      leaf vasiright {
        status deprecated;
        description
          "vasiright";
        type uint16;
      }
      leaf BD-VIF {
        status deprecated;
        description
          "Bridge-Domain Virtual IP interface";
        type string;
      }
    }
  }

  grouping config-named-ordering-route-map-grouping {
    container named-ordering-route-map {
      description
        "named ordering route-map enable";
      leaf enable {
        description
          "named ordering enable";
        type empty;
      }
    }
  }

  grouping next-hop-address-grouping {
    container next-hop {
      description
        "Next hop along path";
      leaf-list address {
        type inet:ipv4-address;
      }
    }
  }

  grouping ip-access-list-grouping {
    leaf-list access-list {
      type ios-types:exp-acl-type;
    }
    leaf-list prefix-list {
      description
        "Match entries of prefix-lists";
      type string;
    }
  }

  grouping ipv6-access-list-grouping {
    leaf access-list {
      type string {
        pattern '[a-zA-Z].*';
      }
    }
    leaf prefix-list {
      description
        "IPv6 prefix-list";
      type string;
    }
  }

  grouping route-map-community-grouping {
    list community-id {
      status deprecated;
      key "community-id cost-value";
      leaf community-id {
        status deprecated;
        description
          "Community ID";
        type uint8 {
          range "0..255";
        }
      }
      leaf cost-value {
        status deprecated;
        description
          "Cost Value (No-preference Cost = 2147483647)";
        type uint32 {
          range "0..4294967295";
        }
      }
    }
  }

  grouping config-route-map-common-grouping {
    list descriptions {
      description
        "list of Route-map comments";
      key "description-leaf";
      leaf description-leaf {
        description
          "Route-map comment";
        type string;
      }
    }
    leaf description {
      description
        "Route-map comment";
      status deprecated;
      type string;
    }
    container set {
      description
        "Set values in destination routing protocol";
      container aigp-metric {
        description
          "accumulated metric value";
        leaf value {
          description
            "manual value";
          type uint32 {
            range "0..4294967295";
          }
        }
        leaf igp-metric {
          description
            "metric value from rib";
          type empty;
        }
      }
      container as-path {
        status deprecated;
        description
          "Modify BGP AS-path attribute (DEPRECATED - please use route-map configuration in Cisco-IOS-XE-bgp.yang)";
        container prepend {
          status deprecated;
          description
            "Prepend to the as-path (DEPRECATED - please use route-map configuration in Cisco-IOS-XE-bgp.yang)";
          container as-container {
            status deprecated;
            leaf as-number {
              status deprecated;
              description
                "<1-65535>;;AS number (DEPRECATED - please use route-map configuration in Cisco-IOS-XE-bgp.yang)";
              type string;
            }
          }
          container last-as-cont {
            status deprecated;
            leaf last-as {
              status deprecated;
              type uint16 {
                range "1..10";
              }
            }
          }
        }
        container tag {
          status deprecated;
          description
            "Set the tag as an AS-path attribute (DEPRECATED - please use route-map configuration in Cisco-IOS-XE-bgp.yang)";
          presence "tag";
        }
        container replace {
          status deprecated;
          description
            "Replace AS numbers in the AS-path with the local AS (DEPRECATED - please use route-map configuration in Cisco-IOS-XE-bgp.yang)";
          list as-container {
            status deprecated;
            ordered-by user;
            key "as-number";
            leaf as-number {
              status deprecated;
              description
                "<1-65535>;;AS number (DEPRECATED - please use route-map configuration in Cisco-IOS-XE-bgp.yang)";
              type string;
            }
          }
          leaf any {
            status deprecated;
            description
              "Replace each AS number in the AS-path with the local AS (DEPRECATED - please use route-map configuration in Cisco-IOS-XE-bgp.yang)";
            type empty;
          }
        }
      }
      leaf attribute-set {
        status deprecated;
        description
          "TE Profile name (DEPRECATED - please use route-map configuration in Cisco-IOS-XE-bgp.yang)";
        type string;
      }
      leaf automatic-tag {
        description
          "Automatically compute TAG value";
        type empty;
      }
      container clns {
        description
          "OSI summary address";
        uses next-hop-address-grouping;
      }
      container community {
        status deprecated;
        description
          "BGP community attribute (DEPRECATED - please use route-map configuration in Cisco-IOS-XE-bgp.yang)";
        choice community-well-known-choice {
          leaf none {
            status deprecated;
            description
              "No community attribute (DEPRECATED - please use route-map configuration in Cisco-IOS-XE-bgp.yang)";
            type empty;
          }
          container community-well-known {
            status deprecated;
            leaf-list community-list {
              status deprecated;
              ordered-by user;
              type union {
                type ios-types:community-number-type;
                type ios-types:community-well-known-type;
              }
            }
            leaf additive {
              status deprecated;
              type empty;
            }
          }
        }
      }
      container comm-list {
        status deprecated;
        description
          "set BGP community list (for deletion) (DEPRECATED - please use route-map configuration in Cisco-IOS-XE-bgp.yang)";
        choice comm-list-choice {
          status deprecated;
          leaf comm-list-standard {
            status deprecated;
            type uint16 {
              range "1..99";
            }
          }
          leaf comm-list-expanded {
            status deprecated;
            type uint16 {
              range "100..500";
            }
          }
          leaf comm-list-name {
            status deprecated;
            type string;
          }
        }
        leaf delete {
          status deprecated;
          description
            "Delete matching communities (DEPRECATED - please use route-map configuration in Cisco-IOS-XE-bgp.yang)";
          type empty;
        }
      }
      container dampening {
        status deprecated;
        description
          "Set BGP route flap dampening parameters (DEPRECATED - please use route-map configuration in Cisco-IOS-XE-bgp.yang)";
        list dampening-list {
          status deprecated;
          key "half-life-penalty restart-penalty suppress-penalty max-suppress-penalty";
          leaf half-life-penalty {
            status deprecated;
            description
              "half-life time for the penalty (DEPRECATED - please use route-map configuration in Cisco-IOS-XE-bgp.yang)";
            type uint8 {
              range "1..45";
            }
          }
          leaf restart-penalty {
            status deprecated;
            description
              "penalty to start reusing a route (DEPRECATED - please use route-map configuration in Cisco-IOS-XE-bgp.yang)";
            type uint16 {
              range "1..20000";
            }
          }
          leaf suppress-penalty {
            status deprecated;
            description
              "penalty to start suppressing a route (DEPRECATED - please use route-map configuration in Cisco-IOS-XE-bgp.yang)";
            type uint16 {
              range "1..20000";
            }
          }
          leaf max-suppress-penalty {
            status deprecated;
            description
              "Maximum duration to suppress a stable route (DEPRECATED - please use route-map configuration in Cisco-IOS-XE-bgp.yang)";
            type uint8 {
              range "1..255";
            }
          }
        }
      }
      container default {
        leaf-list interface-list {
          ordered-by user;
          description
            "SPAN source interface";
          must "not (starts-with(., 'AppNav-Compress')) or /ios:native/ios:interface/*[concat(local-name(), ios:name) = current()]" {
            error-message "AppNav-Compress interface must be created first and deleted last.";
          }
          must "not (starts-with(., 'AppNav-UnCompress')) or /ios:native/ios:interface/*[concat(local-name(), ios:name) = current()]" {
            error-message "AppNav-UnCompress interface must be created first and deleted last.";
          }
          must "not (starts-with(., 'ATM')) or /ios:native/ios:interface/*[concat(local-name(), ios:name) = current()]or /ios:native/ios:interface/ios:ATM-subinterface/*[concat(local-name(), ios:name) = current()]" {
            error-message "ATM interface must be created first and deleted last.";
          }
          must "not (starts-with(., 'ATM-ACR')) or /ios:native/ios:interface/*[concat(local-name(), ios:name) = current()]or /ios:native/ios:interface/ios:ATM-ACRsubinterface/*[concat(local-name(), ios:name) = current()]" {
            error-message "ATM-ACR interface must be created first and deleted last.";
          }
          must "not (starts-with(., 'BDI')) or /ios:native/ios:interface/*[concat(local-name(), ios:name) = current()]" {
            error-message "BDI interface must be created first and deleted last.";
          }
          must "not (starts-with(., 'CEM')) or /ios:native/ios:interface/*[concat(local-name(), ios:name) = current()]" {
            error-message "CEM interface must be created first and deleted last.";
          }
          must "not (starts-with(., 'CEM-ACR')) or /ios:native/ios:interface/*[concat(local-name(), ios:name) = current()]" {
            error-message "CEM-ACR interface must be created first and deleted last.";
          }
          must "not (starts-with(., 'Embedded-Service-Engine')) or /ios:native/ios:interface/*[concat(local-name(), ios:name) = current()]" {
            error-message "Embedded-Service-Engine interface must be created first and deleted last.";
          }
          must "not (starts-with(., 'Ethernet')) or /ios:native/ios:interface/*[concat(local-name(), ios:name) = current()]" {
            error-message "Ethernet interface must be created first and deleted last.";
          }
          must "not (starts-with(., 'FastEthernet')) or /ios:native/ios:interface/*[concat(local-name(), ios:name) = current()]" {
            error-message "FastEthernet interface must be created first and deleted last.";
          }
          must "not (starts-with(., 'GigabitEthernet')) or /ios:native/ios:interface/*[concat(local-name(), ios:name) = current()]" {
            error-message "GigabitEthernet interface must be created first and deleted last.";
          }
          must "not (starts-with(., 'FiveGigabitEthernet')) or /ios:native/ios:interface/*[concat(local-name(), ios:name) = current()]" {
            error-message "FiveGigabitEthernet interface must be created first and deleted last.";
          }
          must "not (starts-with(., 'AppGigabitEthernet')) or /ios:native/ios:interface/*[concat(local-name(), ios:name) = current()]" {
            error-message "AppGigabitEthernet interface must be created first and deleted last.";
          }
          must "not (starts-with(., 'TwentyFiveGigE')) or /ios:native/ios:interface/*[concat(local-name(), ios:name) = current()]" {
            error-message "TwentyFiveGigE interface must be created first and deleted last.";
          }
          must "not (starts-with(., 'TwoGigabitEthernet')) or /ios:native/ios:interface/*[concat(local-name(), ios:name) = current()]" {
            error-message "TwoGigabitEthernet interface must be created first and deleted last.";
          }
          must "not (starts-with(., 'FortyGigabitEthernet')) or /ios:native/ios:interface/*[concat(local-name(), ios:name) = current()]" {
            error-message "FortyGigabitEthernet interface must be created first and deleted last.";
          }
          must "not (starts-with(., 'HundredGigE')) or /ios:native/ios:interface/*[concat(local-name(), ios:name) = current()]" {
            error-message "HundredGigE interface must be created first and deleted last.";
          }
          must "not (starts-with(., 'LISP')) or /ios:native/ios:interface/*[concat(local-name(), ios:name) = current()]or /ios:native/ios:interface/ios:LISP-subinterface/*[concat(local-name(), ios:name) = current()]" {
            error-message "LISP interface must be created first and deleted last.";
          }
          must "not (starts-with(., 'Loopback')) or /ios:native/ios:interface/*[concat(local-name(), ios:name) = current()]" {
            error-message "Loopback interface must be created first and deleted last.";
          }
          must "not (starts-with(., 'Multilink')) or /ios:native/ios:interface/*[concat(local-name(), ios:name) = current()]" {
            error-message "Multilink interface must be created first and deleted last.";
          }
          must "not (starts-with(., 'nve')) or /ios:native/ios:interface/*[concat(local-name(), ios:name) = current()]" {
            error-message "nve interface must be created first and deleted last.";
          }
          must "not (starts-with(., 'overlay')) or /ios:native/ios:interface/*[concat(local-name(), ios:name) = current()]" {
            error-message "overlay interface must be created first and deleted last.";
          }
          must "not (starts-with(., 'Port-channel')) or /ios:native/ios:interface/*[concat(local-name(), ios:name) = current()]or /ios:native/ios:interface/ios:Port-channel-subinterface/*[concat(local-name(), ios:name) = current()]" {
            error-message "Port-channel interface must be created first and deleted last.";
          }
          must "not (starts-with(., 'pseudowire')) or /ios:native/ios:interface/*[concat(local-name(), ios:name) = current()]" {
            error-message "pseudowire interface must be created first and deleted last.";
          }
          must "not (starts-with(., 'SM')) or /ios:native/ios:interface/*[concat(local-name(), ios:name) = current()]" {
            error-message "SM interface must be created first and deleted last.";
          }
          must "not (starts-with(., 'Cellular')) or /ios:native/ios:interface/*[concat(local-name(), ios:name) = current()]" {
            error-message "Cellular interface must be created first and deleted last.";
          }
          must "not (starts-with(., 'Dialer')) or /ios:native/ios:interface/*[concat(local-name(), ios:name) = current()]" {
            error-message "Dialer interface must be created first and deleted last.";
          }
          must "not (starts-with(., 'Serial')) or /ios:native/ios:interface/*[concat(local-name(), ios:name) = current()]" {
            error-message "Serial interface must be created first and deleted last.";
          }
          must "not (starts-with(., 'Async')) or /ios:native/ios:interface/*[concat(local-name(), ios:name) = current()]" {
            error-message "Async interface must be created first and deleted last.";
          }
          must "not (starts-with(., 'TenGigabitEthernet')) or /ios:native/ios:interface/*[concat(local-name(), ios:name) = current()]" {
            error-message "TenGigabitEthernet interface must be created first and deleted last.";
          }
          must "not (starts-with(., 'Tunnel')) or /ios:native/ios:interface/*[concat(local-name(), ios:name) = current()]" {
            error-message "Tunnel interface must be created first and deleted last.";
          }
          must "not (starts-with(., 'Virtual-Template')) or /ios:native/ios:interface/*[concat(local-name(), ios:name) = current()]" {
            error-message "Virtual-Template interface must be created first and deleted last.";
          }
          must "not (starts-with(., 'Vlan')) or /ios:native/ios:interface/*[concat(local-name(), ios:name) = current()]" {
            error-message "Vlan interface must be created first and deleted last.";
          }
          must "not (starts-with(., 'VirtualPortGroup')) or /ios:native/ios:interface/*[concat(local-name(), ios:name) = current()]" {
            error-message "VirtualPortGroup interface must be created first and deleted last.";
          }
          must "not (starts-with(., 'vasileft')) or /ios:native/ios:interface/*[concat(local-name(), ios:name) = current()]" {
            error-message "vasileft interface must be created first and deleted last.";
          }
          must "not (starts-with(., 'vasiright')) or /ios:native/ios:interface/*[concat(local-name(), ios:name) = current()]" {
            error-message "vasiright interface must be created first and deleted last.";
          }
          must "not (starts-with(., 'BD-VIF')) or /ios:native/ios:interface/*[concat(local-name(), ios:name) = current()]" {
            error-message "BD-VIF interface must be created first and deleted last.";
          }
          type string;
        }
        container interface {
          status deprecated;
          description
            "SPAN source interface";
          uses rt_map_interface-deprecated-grouping;
        }
      }
      container extcomm-list {
        status deprecated;
        description
          "Set BGP/VPN extended community list (for deletion) (DEPRECATED - please use route-map configuration in Cisco-IOS-XE-bgp.yang)";
        list ext-range {
          status deprecated;
          key "comm-list-num";
          leaf comm-list-num {
            status deprecated;
            description
              "Extended community-list number (expanded) (DEPRECATED - please use route-map configuration in Cisco-IOS-XE-bgp.yang)";
            type uint16 {
              range "1..500";
            }
          }
          leaf delete {
            status deprecated;
            description
              "Delete matching extended communities (DEPRECATED - please use route-map configuration in Cisco-IOS-XE-bgp.yang)";
            type empty;
          }
        }
        list excomm-list-name {
          status deprecated;
          key "name";
          leaf name {
            status deprecated;
            description
              "extcommunity-list name (DEPRECATED - please use route-map configuration in Cisco-IOS-XE-bgp.yang)";
            type string;
          }
          leaf delete {
            status deprecated;
            type empty;
          }
        }
      }
      container extcommunity {
        status deprecated;
        description
          "BGP extended community attribute (DEPRECATED - please use route-map configuration in Cisco-IOS-XE-bgp.yang)";
        container color-additive {
          status deprecated;
          leaf color {
            status deprecated;
            description
              "Color Extended Community (DEPRECATED - please use route-map configuration in Cisco-IOS-XE-bgp.yang)";
            type uint32 {
              range "1..4294967295";
            }
          }
          leaf additive {
            status deprecated;
            when '../color';
            description
              "additive (DEPRECATED - please use route-map configuration in Cisco-IOS-XE-bgp.yang)";
            type empty;
          }
        }
        leaf color {
          status deprecated;
          description
            "Color Extended Community (DEPRECATED - use color-additive/color in Cisco-IOS-XE-bgp.yang instead)";
          type uint32 {
            range "1..4294967295";
          }
        }
        container cost {
          status deprecated;
          description
            "Cost extended community (DEPRECATED - please use route-map configuration in Cisco-IOS-XE-bgp.yang)";
          uses route-map-community-grouping;
          container igp {
            status deprecated;
            description
              "Compare following IGP cost comparison (DEPRECATED - please use route-map configuration in Cisco-IOS-XE-bgp.yang)";
            uses route-map-community-grouping;
          }
          container pre-bestpath {
            status deprecated;
            description
              "Compare before all other steps in bestpath calculation (DEPRECATED - please use route-map configuration in Cisco-IOS-XE-bgp.yang)";
            uses route-map-community-grouping;
          }
        }
        container rt {
          status deprecated;
          description
            "Route Target extended community (DEPRECATED - please use route-map configuration in Cisco-IOS-XE-bgp.yang)";
          leaf-list asn-nn {
            status deprecated;
            ordered-by user;
            type union {
              type ios-types:asn-ip-type;
              type enumeration {
                enum additive;
              }
            }
          }
          container range {
            status deprecated;
            description
              "Specify a range of extended community (DEPRECATED - please use route-map configuration in Cisco-IOS-XE-bgp.yang)";
            leaf lower-limit {
              status deprecated;
              description
                "VPN extended community lower limit (DEPRECATED - please use route-map configuration in Cisco-IOS-XE-bgp.yang)";
              type ios-types:asn-ip-type;
            }
            leaf high-limit {
              status deprecated;
              description
                "VPN extended community high limit (DEPRECATED - please use route-map configuration in Cisco-IOS-XE-bgp.yang)";
              type ios-types:asn-ip-type;
            }
            leaf additive {
              status deprecated;
              description
                "Add to the existing extcommunity (DEPRECATED - please use route-map configuration in Cisco-IOS-XE-bgp.yang)";
              type empty;
            }
          }
        }
        container soo {
          status deprecated;
          description
            "Site-of-Origin extended community (DEPRECATED - please use route-map configuration in Cisco-IOS-XE-bgp.yang)";
          leaf asn-nn {
            status deprecated;
            type ios-types:asn-ip-type;
          }
        }
        container vpn-distinguisher {
          status deprecated;
          description
            "VPN Distinguisher (DEPRECATED - please use route-map configuration in Cisco-IOS-XE-bgp.yang)";
          leaf asn-nn {
            status deprecated;
            type ios-types:asn-ip-type;
          }
          container range {
            status deprecated;
            description
              "Specify a range of extended community (DEPRECATED - please use route-map configuration in Cisco-IOS-XE-bgp.yang)";
            leaf lower-limit {
              status deprecated;
              description
                "VPN extended community lower limit (DEPRECATED - please use route-map configuration in Cisco-IOS-XE-bgp.yang)";
              type ios-types:asn-ip-type;
            }
            leaf high-limit {
              status deprecated;
              description
                "VPN extended community high limit (DEPRECATED - please use route-map configuration in Cisco-IOS-XE-bgp.yang)";
              type ios-types:asn-ip-type;
            }
            leaf additive {
              status deprecated;
              description
                "Add to the existing extcommunity (DEPRECATED - please use route-map configuration in Cisco-IOS-XE-bgp.yang)";
              type empty;
            }
          }
        }
      }
      leaf global {
        type empty;
      }
      leaf-list interface-list {
        ordered-by user;
        description
          "Interface specific information";
        must "not (starts-with(., 'AppNav-Compress')) or /ios:native/ios:interface/*[concat(local-name(), ios:name) = current()]" {
          error-message "AppNav-Compress interface must be created first and deleted last.";
        }
        must "not (starts-with(., 'AppNav-UnCompress')) or /ios:native/ios:interface/*[concat(local-name(), ios:name) = current()]" {
          error-message "AppNav-UnCompress interface must be created first and deleted last.";
        }
        must "not (starts-with(., 'ATM')) or /ios:native/ios:interface/ios:ATM-subinterface/*[concat(local-name(), ios:name) = current()] or /ios:native/ios:interface/*[concat(local-name(), ios:name) = current()]" {
          error-message "ATM interface must be created first and deleted last.";
        }
        must "not (starts-with(., 'ATM-ACR')) or /ios:native/ios:interface/ios:ATM-ACRsubinterface/*[concat(local-name(), ios:name) = current()]or /ios:native/ios:interface/*[concat(local-name(), ios:name) = current()]" {
          error-message "ATM-ACR interface must be created first and deleted last.";
        }
        must "not (starts-with(., 'BDI')) or /ios:native/ios:interface/*[concat(local-name(), ios:name) = current()]" {
          error-message "BDI interface must be created first and deleted last.";
        }
        must "not (starts-with(., 'CEM')) or /ios:native/ios:interface/*[concat(local-name(), ios:name) = current()]" {
          error-message "CEM interface must be created first and deleted last.";
        }
        must "not (starts-with(., 'CEM-ACR')) or /ios:native/ios:interface/*[concat(local-name(), ios:name) = current()]" {
          error-message "CEM-ACR interface must be created first and deleted last.";
        }
        must "not (starts-with(., 'Embedded-Service-Engine')) or /ios:native/ios:interface/*[concat(local-name(), ios:name) = current()]" {
          error-message "Embedded-Service-Engine interface must be created first and deleted last.";
        }
        must "not (starts-with(., 'Ethernet')) or /ios:native/ios:interface/*[concat(local-name(), ios:name) = current()]" {
          error-message "Ethernet interface must be created first and deleted last.";
        }
        must "not (starts-with(., 'FastEthernet')) or /ios:native/ios:interface/*[concat(local-name(), ios:name) = current()]" {
          error-message "FastEthernet interface must be created first and deleted last.";
        }
        must "not (starts-with(., 'GigabitEthernet')) or /ios:native/ios:interface/*[concat(local-name(), ios:name) = current()]" {
          error-message "GigabitEthernet interface must be created first and deleted last.";
        }
        must "not (starts-with(., 'FiveGigabitEthernet')) or /ios:native/ios:interface/*[concat(local-name(), ios:name) = current()]" {
          error-message "FiveGigabitEthernet interface must be created first and deleted last.";
        }
        must "not (starts-with(., 'AppGigabitEthernet')) or /ios:native/ios:interface/*[concat(local-name(), ios:name) = current()]" {
          error-message "AppGigabitEthernet interface must be created first and deleted last.";
        }
        must "not (starts-with(., 'TwentyFiveGigE')) or /ios:native/ios:interface/*[concat(local-name(), ios:name) = current()]" {
          error-message "TwentyFiveGigE interface must be created first and deleted last.";
        }
        must "not (starts-with(., 'TwoGigabitEthernet')) or /ios:native/ios:interface/*[concat(local-name(), ios:name) = current()]" {
          error-message "TwoGigabitEthernet interface must be created first and deleted last.";
        }
        must "not (starts-with(., 'FortyGigabitEthernet')) or /ios:native/ios:interface/*[concat(local-name(), ios:name) = current()]" {
          error-message "FortyGigabitEthernet interface must be created first and deleted last.";
        }
        must "not (starts-with(., 'HundredGigE')) or /ios:native/ios:interface/*[concat(local-name(), ios:name) = current()]" {
          error-message "HundredGigE interface must be created first and deleted last.";
        }
        must "not (starts-with(., 'LISP')) or /ios:native/ios:interface/*[concat(local-name(), ios:name) = current()]or /ios:native/ios:interface/ios:LISP-subinterface/*[concat(local-name(), ios:name) = current()]" {
          error-message "LISP interface must be created first and deleted last.";
        }
        must "not (starts-with(., 'Loopback')) or /ios:native/ios:interface/*[concat(local-name(), ios:name) = current()]" {
          error-message "Loopback interface must be created first and deleted last.";
        }
        must "not (starts-with(., 'Multilink')) or /ios:native/ios:interface/*[concat(local-name(), ios:name) = current()]" {
          error-message "Multilink interface must be created first and deleted last.";
        }
        must "not (starts-with(., 'nve')) or /ios:native/ios:interface/*[concat(local-name(), ios:name) = current()]" {
          error-message "nve interface must be created first and deleted last.";
        }
        must "not (starts-with(., 'overlay')) or /ios:native/ios:interface/*[concat(local-name(), ios:name) = current()]" {
          error-message "overlay interface must be created first and deleted last.";
        }
        must "not (starts-with(., 'Port-channel')) or /ios:native/ios:interface/*[concat(local-name(), ios:name) = current()]or /ios:native/ios:interface/ios:Port-channel-subinterface/*[concat(local-name(), ios:name) = current()]" {
          error-message "Port-channel interface must be created first and deleted last.";
        }
        must "not (starts-with(., 'pseudowire')) or /ios:native/ios:interface/*[concat(local-name(), ios:name) = current()]" {
          error-message "pseudowire interface must be created first and deleted last.";
        }
        must "not (starts-with(., 'SM')) or /ios:native/ios:interface/*[concat(local-name(), ios:name) = current()]" {
          error-message "SM interface must be created first and deleted last.";
        }
        must "not (starts-with(., 'Cellular')) or /ios:native/ios:interface/*[concat(local-name(), ios:name) = current()]" {
          error-message "Cellular interface must be created first and deleted last.";
        }
        must "not (starts-with(., 'Dialer')) or /ios:native/ios:interface/*[concat(local-name(), ios:name) = current()]" {
          error-message "Dialer interface must be created first and deleted last.";
        }
        must "not (starts-with(., 'Serial')) or /ios:native/ios:interface/*[concat(local-name(), ios:name) = current()]" {
          error-message "Serial interface must be created first and deleted last.";
        }
        must "not (starts-with(., 'Async')) or /ios:native/ios:interface/*[concat(local-name(), ios:name) = current()]" {
          error-message "Async interface must be created first and deleted last.";
        }
        must "not (starts-with(., 'TenGigabitEthernet')) or /ios:native/ios:interface/*[concat(local-name(), ios:name) = current()]" {
          error-message "TenGigabitEthernet interface must be created first and deleted last.";
        }
        must "not (starts-with(., 'Tunnel')) or /ios:native/ios:interface/*[concat(local-name(), ios:name) = current()]" {
          error-message "Tunnel interface must be created first and deleted last.";
        }
        must "not (starts-with(., 'Virtual-Template')) or /ios:native/ios:interface/*[concat(local-name(), ios:name) = current()]" {
          error-message "Virtual-Template interface must be created first and deleted last.";
        }
        must "not (starts-with(., 'Vlan')) or /ios:native/ios:interface/*[concat(local-name(), ios:name) = current()]" {
          error-message "Vlan interface must be created first and deleted last.";
        }
        must "not (starts-with(., 'VirtualPortGroup')) or /ios:native/ios:interface/*[concat(local-name(), ios:name) = current()]" {
          error-message "VirtualPortGroup interface must be created first and deleted last.";
        }
        must "not (starts-with(., 'vasileft')) or /ios:native/ios:interface/*[concat(local-name(), ios:name) = current()]" {
          error-message "vasileft interface must be created first and deleted last.";
        }
        must "not (starts-with(., 'vasiright')) or /ios:native/ios:interface/*[concat(local-name(), ios:name) = current()]" {
          error-message "vasiright interface must be created first and deleted last.";
        }
        must "not (starts-with(., 'BD-VIF')) or /ios:native/ios:interface/*[concat(local-name(), ios:name) = current()]" {
          error-message "BD-VIF interface must be created first and deleted last.";
        }
        type string;
      }
      container interface {
        status deprecated;
        uses rt_map_interface-deprecated-grouping;
      }
      container ip {
        description
          "IP specific information";
        container address {
          description
            "Specify IP address";
          leaf prefix-list {
            description
              "Specify prefix-list";
            type string;
          }
        }
        container default {
          description
            "Set default information";
          container global {
            description
              "global routing table";
            uses next-hop-address-grouping;
          }
          uses next-hop-address-grouping;
          container vrf {
            description
              "VRF name";
            list vrfs {
              key "vrf";
              leaf vrf {
                description
                  "WORD;;VRF name";
                type string;
              }
              uses next-hop-address-grouping;
            }
          }
        }
        leaf df {
          type uint8 {
            range "0..1";
          }
        }
        container global {
          description
            "global routing table";
          uses next-hop-address-grouping;
        }
        container next-hop {
          description
            "Next hop address";
          leaf-list address {
            type union {
              type inet:ipv4-address;
              type enumeration {
                enum force;
              }
            }
          }
          container dynamic {
            description
              "application dynamically sets next hop";
            leaf dhcp {
              description
                "DHCP learned next hop";
              type empty;
            }
          }
          container encapsulate {
            description
              "Encapsulation profile for VPN nexthop";
            leaf l3vpn {
              description
                "L3VPN";
              type string;
            }
          }
          leaf peer-address {
            description
              "Use peer address (for BGP only)";
            type empty;
          }
          container recursive {
            description
              "Recursive next-hop";
            leaf ipv4 {
              description
                "IP address of recursive next hop";
              type inet:ipv4-address;
            }
            leaf global {
              description
                "IP address of recursive next hop";
              type inet:ipv4-address;
            }
            container vrf {
              description
                "VRF name";
              list vrfs {
                key "vrf";
                leaf vrf {
                  description
                    "VRF name";
                  type string;
                }
                leaf ipv4 {
                  description
                    "IP address of recursive next hop";
                  type inet:ipv4-address;
                }
              }
            }
          }
          leaf self {
            description
              "Use self address (for BGP only)";
            type empty;
          }
          container verify-availability {
            description
              "Verify if nexthop is reachable";
            presence "true";
            list ipv4 {
              key "ipv4";
              leaf ipv4 {
                description
                  "IP address of next hop";
                type inet:ipv4-address;
              }
              leaf range {
                type uint16 {
                  range "1..65535";
                }
              }
              leaf track {
                description
                  "set the next hop depending on the state of a tracked object";
                type uint16 {
                  range "1..1000";
                }
              }
            }
          }
        }
        container precedence {
          description
            "Set precedence field";
          presence "true";
          leaf precedence-value {
            type uint8 {
              range "0..7";
            }
          }
          leaf precedence-fields {
            type enumeration {
              enum critical;
              enum flash;
              enum flash-override;
              enum immediate;
              enum internet;
              enum network;
              enum priority;
              enum routine;
            }
          }
        }
        container qos-group {
          description
            "Set QOS Group ID";
          presence "true";
          leaf qos-id {
            type uint8 {
              range "0..99";
            }
          }
        }
        container tos_without_presence {
          description
            "Set type of service field without presence";
          leaf service-values {
            type uint8 {
              range "0..15";
            }
          }
          leaf tos-field {
            type enumeration {
              enum max-reliability;
              enum max-throughput;
              enum min-delay;
              enum min-monetary-cost;
              enum normal;
            }
          }
        }
        container tos {
          description
            "Set type of service field";
          presence "true";
          status deprecated;
          leaf service-value {
            status deprecated;
            type uint8 {
              range "0..15";
            }
          }
          leaf tos-fields {
            status deprecated;
            type enumeration {
              enum max-reliability;
              enum max-throughput;
              enum min-delay;
              enum min-monetary-cost;
              enum normal;
            }
          }
        }
        container vrf {
          description
            "VRF name";
          list vrfs {
            key "vrf";
            leaf vrf {
              description
                "WORD;;VRF name";
              type string;
            }
            uses next-hop-address-grouping;
          }
        }
      }
      container ipv6 {
        description
          "IPv6 specific information";
        container address {
          description
            "IPv6 address";
          leaf plist {
            description
              "IPv6 prefix-list";
            type string;
          }
          leaf-list prefix-list {
            status deprecated;
            description
              "IPv6 prefix-list";
            type string;
          }
        }
        container default {
          description
            "Set default information";
          container global {
            description
              "global routing table";
            leaf-list next-hop-address {
              ordered-by user;
              description
                "Default Next hop IPv6 address";
              type inet:ipv6-address;
            }
            leaf next-hop {
              status deprecated;
              description
                "Next hop along path";
              type inet:ipv6-address;
            }
          }
          container next-hop {
            description
              "Next hop along path";
            leaf-list ipv6 {
              ordered-by user;
              description
                "Default next hop IPv6 address";
              type inet:ipv6-address;
            }
            list ipv6s {
              status deprecated;
              key "ipv6";
              leaf ipv6 {
                description
                  "Default next hop IPv6 address";
                type inet:ipv6-address;
                status deprecated;
              }
            }
            leaf next-hop-address {
              type inet:ipv6-address;
              status deprecated;
            }
          }
          list vrf {
            key "vrf";
            leaf vrf {
              description
                "VRF name";
              type string;
            }
            leaf-list next-hop {
              description
                "List entries of next-hop ipv6 addresses";
              type inet:ipv6-address;
            }
          }
          list dvrf {
            status obsolete;
            key "dvrf";
            leaf dvrf {
              status obsolete;
              description
                "VRF name";
              type string;
            }
            list dvrf0 {
              status obsolete;
              key "dvrf0";
              leaf dvrf0 {
                status obsolete;
                description
                  "VRF name";
                type string;
              }
              leaf next-hop {
                status obsolete;
                description
                  "Next hop along path";
                type empty;
              }
            }
          }
        }
        container global {
          description
            "global routing table";
          container next-hop {
            description
              "IPv6 Next hop";
            status obsolete;
            list nh-ipv6 {
              status obsolete;
              key "nh-ipv6";
              leaf nh-ipv6 {
                description
                  "Next hop address";
                status obsolete;
                type inet:ipv6-address;
              }
              leaf nh-ipv60 {
                description
                  "Next hop address";
                status obsolete;
                type inet:ipv6-address;
              }
            }
            leaf verify-availability {
              description
                "Next hop address";
              type inet:ipv6-address;
              status obsolete;
            }
          }
          container next-hop-conf {
            description
              "IPv6 Next hop";
            leaf-list ipv6-address {
              ordered-by user;
              description
                "Next hop address";
              type inet:ipv6-address;
            }
            container verify-availability {
              description
                "Verify if nexthop is reachable";
              list sequence-id {
                key "seq-id";
                leaf seq-id {
                  description
                    "Sequence to insert into next-hop list";
                  type uint16 {
                    range "1..65535";
                  }
                }
                leaf ipv6-address {
                  description
                    "Next hop address";
                  type inet:ipv6-address;
                }
                leaf track {
                  description
                    "tracked object number";
                  type uint16 {
                    range "1..1000";
                  }
                }
              }
            }
          }
        }
        container next-hop {
          description
            "IPv6 Next hop";
          leaf-list ipv6 {
            ordered-by user;
            description
              "Next hop IPv6 address";
            type inet:ipv6-address;
          }
          list nha-ipv6 {
            status deprecated;
            key "nha-ipv6";
            leaf nha-ipv6 {
              description
                "Next hop address";
              type inet:ipv6-address;
              status deprecated;
            }
            list nha-ipv60 {
              status deprecated;
              key "nha-ipv60";
              leaf nha-ipv60 {
                description
                  "Next hop address";
                type inet:ipv6-address;
                status deprecated;
              }
              leaf nh-ipv6 {
                description
                  "Next hop address";
                type inet:ipv6-address;
                status deprecated;
              }
            }
          }
          container encapsulate {
            description
              "Encapsulation profile for VPN nexthop";
            leaf l3vpn {
              description
                "Encapsulation profile name";
              type string;
            }
          }
          leaf peer-address {
            description
              "Use peer address (for BGP only)";
            type empty;
          }
          leaf recursive {
            description
              "IPv6 address of recursive next-hop";
            type inet:ipv6-address;
          }
          container verify-availability {
            description
              "Verify if nexthop is reachable";
            status obsolete;
            list va-ipv6 {
              status obsolete;
              key "va-ipv6";
              leaf va-ipv6 {
                status obsolete;
                description
                  "Next hop address";
                type inet:ipv6-address;
              }
              leaf seq-nh {
                status obsolete;
                description
                  "Sequence to insert into next-hop list";
                type uint16 {
                  range "1..65535";
                }
              }
            }
          }
          container verify-availability-conf {
            description
              "Verify if nexthop is reachable";
            list sequence-id {
              key "seq-id";
              leaf seq-id {
                description
                  "Sequence to insert into next-hop list";
                type uint16 {
                  range "1..65535";
                }
              }
              leaf ipv6-address {
                description
                  "Next hop address";
                type inet:ipv6-address;
              }
              leaf track {
                description
                  "tracked object number";
                type uint16 {
                  range "1..1000";
                }
              }
            }
          }
        }
        leaf precedence {
          description
            "Precedence value";
          type uint8 {
            range "0..7";
          }
        }
        list vrf {
          key "vrf";
          leaf vrf {
            description
              "VRF name";
            type string;
          }
          container next-hop {
            description
              "IPv6 Next hop";
            leaf-list ipv6 {
              description
                "List entries of next-hop ipv6 addresses";
              type inet:ipv6-address;
            }
            list verify-availability {
              description
                "Verify if nexthop is reachable";
              key "ipv6";
              leaf ipv6 {
                description
                  "IP address of next hop";
                type inet:ipv6-address;
              }
              leaf sequence {
                type uint16 {
                  range "1..65535";
                }
              }
              leaf track {
                description
                  "Set the next hop depending on the state
                   of a tracked object";
                must '../sequence';
                type uint16 {
                  range "1..1000";
                }
              }
            }
          }
        }
        list bvrf {
          status obsolete;
          key "bvrf";
          leaf bvrf {
            description
              "VRF name";
            type string;
            status obsolete;
          }
          list bvrf0 {
            status obsolete;
            key "bvrf0";
            leaf bvrf0 {
              status obsolete;
              description
                "VRF name";
              type string;
            }
            container next-hop {
              status obsolete;
              description
                "IPv6 Next hop";
              leaf bipv6 {
                status obsolete;
                description
                  "Next hop address";
                type inet:ipv6-address;
              }
              leaf verify-availability {
                status obsolete;
                description
                  "Verify if nexthop is reachable";
                type empty;
              }
            }
          }
        }
      }
      container large-community {
        status deprecated;
        description
          "BGP large community attribute (DEPRECATED - please use route-map configuration in Cisco-IOS-XE-bgp.yang)";
        choice large-community-choice {
          status deprecated;
          leaf none {
            status deprecated;
            description
              "No large community attribute (DEPRECATED - please use route-map configuration in Cisco-IOS-XE-bgp.yang)";
            type empty;
          }
          container large-community-value {
            status deprecated;
            description
              "large-community-format (DEPRECATED - please use route-map configuration in Cisco-IOS-XE-bgp.yang)";
            leaf-list large-community-list {
              status deprecated;
              description
                "large community number in aa:bb:cc format (DEPRECATED - please use route-map configuration in Cisco-IOS-XE-bgp.yang)";
              ordered-by user;
              type ios-types:large-community-number-type;
            }
            leaf additive {
              status deprecated;
              description
                "Add to the existing community (DEPRECATED - please use route-map configuration in Cisco-IOS-XE-bgp.yang)";
              when '../large-community-list';
              type empty;
            }
          }
        }
      }
      container largecomm-list {
        status deprecated;
        description
          "set BGP large community list (for deletion) (DEPRECATED - please use route-map configuration in Cisco-IOS-XE-bgp.yang)";
        presence "true";
        choice largecomm-list-choice {
          status deprecated;
          mandatory true;
          leaf largecomm-list-standard {
            status deprecated;
            description
              "Community-list number (standard) (DEPRECATED - please use route-map configuration in Cisco-IOS-XE-bgp.yang)";
            type uint16 {
              range "1..99";
            }
          }
          leaf largecomm-list-expanded {
            status deprecated;
            description
              "Community-list number (expanded) (DEPRECATED - please use route-map configuration in Cisco-IOS-XE-bgp.yang)";
            type uint16 {
              range "100..500";
            }
          }
          leaf largecomm-list-name {
            status deprecated;
            description
              "Large-Community-list name (DEPRECATED - please use route-map configuration in Cisco-IOS-XE-bgp.yang)";
            type string;
          }
        }
        leaf delete {
          status deprecated;
          description
            "Delete matching communities (DEPRECATED - please use route-map configuration in Cisco-IOS-XE-bgp.yang)";
          mandatory true;
          type empty;
        }
      }
      container level {
        description
          "Where to import route";
        leaf level-1 {
          description
            "Import into a level-1 area";
          type empty;
        }
        leaf level-1-2 {
          description
            "Import into level-1 and level-2";
          type empty;
        }
        leaf level-2 {
          description
            "Import into level-2 sub-domain";
          type empty;
        }
        leaf nssa-only {
          description
            "Import only into OSPF NSSA areas and don't propagate";
          type empty;
        }
      }
      container lisp {
        description
          "Locator ID Separation Protocol specific information";
        leaf locator-set {
          description
            "The name of the locator set";
          type string;
        }
      }
      leaf local-preference {
        status deprecated;
        description
          "Preference value (DEPRECATED - please use route-map configuration in Cisco-IOS-XE-bgp.yang)";
        type uint32 {
          range "0..4294967295";
        }
      }
      container metric {
        description
          "Metric value for destination routing protocol";
        choice metric-choice {
          case relative-value {
            leaf metric-change {
              description
                "+/-<metric>;;Add or subtract metric";
              type string {
                pattern '(\+|-)\d{1,10}';
              }
            }
          }
          case absolute-values {
            container values {
              leaf value {
                description
                  "Metric value or Bandwidth in Kbits per second";
                type uint32;
              }
              leaf delay {
                description
                  "EIGRP delay metric, in 10 microsecond units";
                when '../value';
                type string {
                  pattern '(\+|-)?\d{1,10}';
                }
              }
              leaf reliability {
                description
                  "EIGRP reliability metric where 255 is 100% reliable";
                when '../delay';
                must '../loading and ../MTU';
                type uint8;
              }
              leaf loading {
                description
                  "EIGRP Effective bandwidth metric (Loading) where 255 is 100% loaded";
                when '../delay';
                must '../reliability and ../MTU';
                type uint8 {
                  range "1..255";
                }
              }
              leaf MTU {
                description
                  "EIGRP MTU of the path";
                when '../delay';
                must '../reliability and ../loading';
                type uint32 {
                  range "1..4294967295";
                }
              }
            }
          }
        }
      }
      leaf metric-type {
        description
          "Type of metric for destination routing protocol";
        type enumeration {
          enum external;
          enum internal;
          enum type-1;
          enum type-2;
        }
      }
      leaf mpls-label {
        description
          "Set MPLS label for prefix";
        type empty;
      }
      container nlri {
        status deprecated;
        description
          "BGP NLRI type (DEPRECATED - please use route-map configuration in Cisco-IOS-XE-bgp.yang)";
        leaf unicast {
          status deprecated;
          description
            "Used in unicast RIB (DEPRECATED - please use route-map configuration in Cisco-IOS-XE-bgp.yang)";
          type empty;
        }
        leaf multicast {
          status deprecated;
          description
            "Used in multicast RIB (DEPRECATED - please use route-map configuration in Cisco-IOS-XE-bgp.yang)";
          type empty;
        }
      }
      leaf weight {
        status deprecated;
        description
          "BGP weight for routing table (DEPRECATED - please use route-map configuration in Cisco-IOS-XE-bgp.yang)";
        type uint32 {
          range "0..65535";
        }
      }
      leaf omp-tag {
        if-feature "ios-features:omp";
        description
          "OMP tag value for destination routing protocol";
        type uint32;
      }
      container origin {
        status deprecated;
        description
          "BGP origin code (DEPRECATED - please use route-map configuration in Cisco-IOS-XE-bgp.yang)";
        leaf origin-value {
          status deprecated;
          type enumeration {
            enum igp;
            enum incomplete;
          }
        }
        leaf egp {
          status deprecated;
          description
            "remote EGP (DEPRECATED - please use route-map configuration in Cisco-IOS-XE-bgp.yang)";
          type uint32 {
            range "0..65535";
          }
        }
      }
      leaf tag-val {
        description
          "Tag value for destination routing protocol";
        type union {
          type uint32 {
            range "0..4294967295";
          }
          type inet:ipv4-address;
        }
      }
      container tag {
        status deprecated;
        description
          "Tag value for destination routing protocol (DEPRECATED - please use tag-val)";
        leaf tag-val {
          status deprecated;
          description
            "Tag value (DEPRECATED - please use tag-val)";
          type uint32 {
            range "0..4294967295";
          }
        }
        leaf tag-ipv4 {
          status deprecated;
          description
            "Tag value(dotted decimal format) (DEPRECATED - please use tag-val)";
          type inet:ipv4-address;
        }
      }
      leaf traffic-index {
        description
          "Bucket number";
        type uint8 {
          range "1..64";
        }
      }
      leaf vrf {
        description
          "VPN Routing/Forwarding instance name";
        type string;
      }
    }
    container match {
      description
        "Match values from routing table";
      container additional-paths {
        status deprecated;
        description
          "BGP Add-Path match policies (DEPRECATED - please use route-map configuration in Cisco-IOS-XE-bgp.yang)";
        container advertise-set {
          status deprecated;
          description
            "BGP Add-Path advertise-set policy (DEPRECATED - please use route-map configuration in Cisco-IOS-XE-bgp.yang)";
          container all {
            status deprecated;
            description
              "BGP Add-Path advertise all paths (DEPRECATED - please use route-map configuration in Cisco-IOS-XE-bgp.yang)";
            presence "true";
            leaf best {
              status deprecated;
              description
                "BGP Add-Path best n paths to advertise (DEPRECATED - please use route-map configuration in Cisco-IOS-XE-bgp.yang)";
              type uint8 {
                range "1..3";
              }
            }
            leaf best-range {
              status deprecated;
              description
                "BGP Add-Path best paths to advertise (lower limit) (DEPRECATED - please use route-map configuration in Cisco-IOS-XE-bgp.yang)";
              type uint8 {
                range "1..3";
              }
            }
            container group-best {
              status deprecated;
              description
                "BGP Add-Path advertise group-best path (DEPRECATED - please use route-map configuration in Cisco-IOS-XE-bgp.yang)";
              presence "true";
              leaf best {
                status deprecated;
                description
                  "BGP Add-Path advertise best n paths (DEPRECATED - please use route-map configuration in Cisco-IOS-XE-bgp.yang)";
                type empty;
              }
              leaf best-range {
                status deprecated;
                description
                  "BGP Add-Path advertise best paths (range m to n) (DEPRECATED - please use route-map configuration in Cisco-IOS-XE-bgp.yang)";
                type empty;
              }
            }
          }
          container best {
            status deprecated;
            description
              "BGP Add-Path advertise best n paths (DEPRECATED - please use route-map configuration in Cisco-IOS-XE-bgp.yang)";
            list best-range {
              status deprecated;
              key "best-range";
              leaf best-range {
                status deprecated;
                description
                  "BGP Add-Path best n paths to advertise (DEPRECATED - please use route-map configuration in Cisco-IOS-XE-bgp.yang)";
                type uint8 {
                  range "1..3";
                }
              }
              leaf all {
                status deprecated;
                description
                  "BGP Add-Path advertise all paths (DEPRECATED - please use route-map configuration in Cisco-IOS-XE-bgp.yang)";
                type empty;
              }
              leaf group-best {
                status deprecated;
                description
                  "BGP Add-Path advertise group-best path (DEPRECATED - please use route-map configuration in Cisco-IOS-XE-bgp.yang)";
                type empty;
              }
            }
          }
          container best-range {
            status deprecated;
            description
              "BGP Add-Path advertise best paths (range m to n) (DEPRECATED - please use route-map configuration in Cisco-IOS-XE-bgp.yang)";
            list adv-path {
              status deprecated;
              key "adv-path";
              leaf adv-path {
                status deprecated;
                description
                  "BGP Add-Path best paths to advertise (lower limit) (DEPRECATED - please use route-map configuration in Cisco-IOS-XE-bgp.yang)";
                type uint8 {
                  range "1..3";
                }
              }
              leaf adv-path0 {
                status deprecated;
                description
                  "BGP Add-Path best paths to advertise (upper limit) (DEPRECATED - please use route-map configuration in Cisco-IOS-XE-bgp.yang)";
                type uint8 {
                  range "1..3";
                }
              }
            }
          }
          container group-best {
            status deprecated;
            description
              "BGP Add-Path advertise group-best path (DEPRECATED - please use route-map configuration in Cisco-IOS-XE-bgp.yang)";
            presence "true";
            leaf all {
              status deprecated;
              description
                "BGP Add-Path advertise all paths (DEPRECATED - please use route-map configuration in Cisco-IOS-XE-bgp.yang)";
              type empty;
            }
            leaf best {
              status deprecated;
              description
                "BGP Add-Path best n paths to advertise (DEPRECATED - please use route-map configuration in Cisco-IOS-XE-bgp.yang)";
              type uint8 {
                range "1..3";
              }
            }
            leaf best-range {
              status deprecated;
              description
                "BGP Add-Path best paths to advertise (lower limit) (DEPRECATED - please use route-map configuration in Cisco-IOS-XE-bgp.yang)";
              type uint8 {
                range "1..3";
              }
            }
          }
        }
      }
      container as-path {
        status deprecated;
        description
          "Match BGP AS path list (DEPRECATED - please use route-map configuration in Cisco-IOS-XE-bgp.yang)";
        leaf-list access-list {
          status deprecated;
          description
            "AS path access-list (DEPRECATED - please use route-map configuration in Cisco-IOS-XE-bgp.yang)";
          type uint16 {
            range "1..500";
          }
        }
      }
      container clns {
        description
          "CLNS information";
        leaf-list name {
          description
            "Named clna list";
          type string;
        }
      }
      container community {
        status deprecated;
        description
          "Match BGP community list (DEPRECATED - please use route-map configuration in Cisco-IOS-XE-bgp.yang)";
        leaf-list community-list {
          status deprecated;
          description
            "Named Access List (DEPRECATED - please use route-map configuration in Cisco-IOS-XE-bgp.yang)";
          ordered-by user;
          type string;
        }
        leaf-list name {
          description
            "Named Access List (DEPRECATED- please use community-list in Cisco-IOS-XE-bgp.yang)";
          status deprecated;
          type string;
        }
      }
      container extcommunity {
        status deprecated;
        description
          "Match BGP/VPN extended community list (DEPRECATED - please use route-map configuration in Cisco-IOS-XE-bgp.yang)";
        leaf-list extcommunity-list {
          status deprecated;
          description
            "Named Access List (DEPRECATED - please use route-map configuration in Cisco-IOS-XE-bgp.yang)";
          ordered-by user;
          type string;
        }
        leaf-list name {
          description
            "Named Access List (DEPRECATED- please use extcommunity-list in Cisco-IOS-XE-bgp.yang)";
          status deprecated;
          type string;
        }
      }
      container interface {
        description
          "SPAN source interface";
        leaf-list interface {
          type string;
        }
      }
      container ip {
        description
          "IP specific information";
        container address {
          description
            "Match address of route or match packet";
          uses ip-access-list-grouping;
        }
        container flowspec {
          description
            "Match address of route";
          container dest-pfx {
            description
              "Match dest prefix component of flowspec prefix";
            uses ip-access-list-grouping;
          }
          container src-pfx {
            description
              "Match source prefix component of flowspec prefix";
            uses ip-access-list-grouping;
          }
        }
        container next-hop {
          description
            "Match next-hop address of route";
          uses ip-access-list-grouping;
        }
        container redistribution-source {
          description
            "route redistribution source (EIGRP only)";
          uses ip-access-list-grouping;
        }
        container route-source {
          description
            "Match advertising source address of route";
          uses ip-access-list-grouping;
        }
      }
      container ipv6 {
        description
          "IPv6 specific information";
        container address {
          description
            "Match address of route";
          uses ipv6-access-list-grouping;
        }
        container flowspec {
          description
            "Match address of route";
          container dest-pfx {
            description
              "Match dest prefix component of flowspec prefix";
            uses ipv6-access-list-grouping;
          }
          container src-pfx {
            description
              "Match source prefix component of flowspec prefix";
            uses ipv6-access-list-grouping;
          }
        }
        container next-hop {
          description
            "Match next-hop address of route";
          uses ipv6-access-list-grouping;
        }
        container route-source {
          description
            "Match advertising source address of route";
          uses ipv6-access-list-grouping;
        }
      }
      container large-community {
        status deprecated;
        description
          "Match BGP large-community list (DEPRECATED - please use route-map configuration in Cisco-IOS-XE-bgp.yang)";
        leaf-list name {
          status deprecated;
          description
            "Large community-list name or number (DEPRECATED - please use route-map configuration in Cisco-IOS-XE-bgp.yang)";
          ordered-by user;
          type string;
        }
        leaf exact-match {
          status deprecated;
          description
            "Do exact matching of large communities (DEPRECATED - please use route-map configuration in Cisco-IOS-XE-bgp.yang)";
          when '../name';
          type empty;
        }
      }
      container length {
        description
          "Packet length";
        list lengths {
          max-elements 1;
          key "min-len max-len";
          leaf min-len {
            description
              "Minimum packet length";
            type uint32 {
              range "0..2147483647";
            }
          }
          leaf max-len {
            description
              "Maximum packet length";
            type uint32 {
              range "0..2147483647";
            }
          }
        }
      }
      container traffic-steering {
        if-feature "ios-features:pbr-sbit-switching";
        description
          "traffic-steering selection";
        leaf service-selector {
          description
            "Service selector value";
          type uint8 {
            range "1..255";
          }
        }
      }
      container local-preference {
        status deprecated;
        description
          "Local preference for route (DEPRECATED - please use route-map configuration in Cisco-IOS-XE-bgp.yang)";
        leaf-list values {
          status deprecated;
          type uint32 {
            range "0..4294967295";
          }
        }
      }
      container mdt-group {
        description
          "Match routes corresponding to MDT group";
        leaf-list name {
          description
            "IP Access List";
          type string;
        }
      }
      container metric {
        description
          "Match metric of route";
        leaf metric-value-number {
          type uint32 {
            range "1..4294967295";
          }
        }
        leaf metric-value {
          status deprecated;
          type string;
        }
        leaf external-number {
          description
            "match route using external protocol metric";
          type uint32 {
            range "1..4294967295";
          }
        }
        leaf external {
          status deprecated;
          description
            "match route using external protocol metric";
          type string;
        }
      }
      leaf mpls-label {
        description
          "Match routes which have MPLS labels";
        type empty;
      }
      container policy-list {
        description
          "Match IP policy list";
        leaf-list policy-map-names {
          description
            "IP Policy map name";
          type string;
        }
      }
      leaf omp-tag {
        if-feature "ios-features:omp";
        description
          "OMP Tag value for route match";
        type uint32;
      }
      container route-type {
        description
          "Match route-type of route";
        container external {
          description
            "external route (BGP, EIGRP and OSPF type 1/2)";
          presence "true";
          leaf type-1 {
            description
              "OSPF external type 1 route";
            type empty;
          }
          leaf type-2 {
            description
              "OSPF external type 2 route";
            type empty;
          }
        }
        leaf internal {
          description
            "internal route (including OSPF intra/inter area)";
          type empty;
        }
        leaf level-1 {
          description
            "IS-IS level-1 route";
          type empty;
        }
        leaf level-2 {
          description
            "IS-IS level-2 route";
          type empty;
        }
        leaf local {
          status deprecated;
          description
            "locally generated route (DEPRECATED - please use route-map configuration in Cisco-IOS-XE-bgp.yang)";
          type empty;
        }
        container nssa-external {
          description
            "nssa-external route (OSPF type 1/2)";
          presence "true";
          leaf type-1 {
            description
              "OSPF external type 1 route";
            type empty;
          }
          leaf type-2 {
            description
              "OSPF external type 2 route";
            type empty;
          }
        }
      }
      container rpki {
        description
          "Match RPKI state of route";
        leaf invalid {
          description
            "RPKI Invalid State";
          type empty;
        }
        leaf not-found {
          description
            "RPKI Not Found State";
          type empty;
        }
        leaf valid {
          description
            "RPKI Valid State";
          type empty;
        }
      }
      container source-protocol {
        description
          "Match source-protocol of route";
        presence "true";
        leaf-list bgp {
          description
            "Border Gateway Protocol (BGP)";
          type ios-types:bgp-as-number-type;
        }
        leaf connected {
          description
            "Connected";
          type empty;
        }
        leaf-list eigrp {
          description
            "Border Gateway Protocol (BGP)";
          type string;
        }
        leaf isis {
          description
            "ISO IS-IS";
          type empty;
        }
        leaf lisp {
          description
            "Locator ID Separation Protocol (LISP)";
          type empty;
        }
        leaf mobile {
          description
            "Mobile routes";
          type empty;
        }
        leaf-list ospf {
          description
            "Open Shortest Path First (OSPF)";
          type string;
        }
        leaf-list ospfv3 {
          description
            "OSPFv3";
          type string;
        }
        leaf rip {
          description
            "Routing Information Protocol (RIP)";
          type empty;
        }
        leaf static {
          description
            "Static routes";
          type empty;
        }
        leaf omp {
          if-feature "ios-features:omp";
          description
            "Overlay Management Protocol (OMP)";
          type empty;
        }
        leaf nat-route {
          if-feature "ios-features:sdwan";
          description
            "NAT Route Protocol";
          type empty;
        }
      }
      container tag {
        description
          "Match tag of route";
        leaf-list tag-val {
          description
            "Tag value for destination routing protocol";
          type union {
            type uint32 {
              range "0..4294967295";
            }
            type inet:ipv4-address;
          }
        }
        leaf-list tag_value {
          status deprecated;
          description
            "Tag value (DEPRECATED - please use tag-val)";
          type uint32 {
            range "0..4294967295";
          }
        }
        leaf-list ipv4-address {
          status deprecated;
          description
            "<A.B.C.D>;;Tag value(dotted decimal format) (DEPRECATED - please use tag-val)";
          type inet:ipv4-address;
        }
        container list {
          description
            "Route Tag List";
          leaf-list tag-names {
            description
              "Tag list name";
            type string;
          }
        }
      }
      leaf track {
        description
          "tracking object";
        type uint16 {
          range "1..1000";
        }
      }
    }
    container continue {
      description
        "Continue on a different entry within the route-map";
      presence "true";
      leaf sequence-number {
        description
          "Route-map entry sequence number";
        type uint16 {
          range "0..65535";
        }
      }
    }
  }

  grouping config-route-map-grouping {
    list route-map-seq {
      key "ordering-seq";
      leaf ordering-seq {
        description
          "Ordering seq tag";
        type string;
      }
      leaf operation {
        type enumeration {
          enum deny;
          enum permit;
        }
      }
      leaf sequence {
        type uint16 {
          range "0..65535";
        }
      }
      uses config-route-map-common-grouping;
    }
    list route-map-without-order-seq {
      key "seq_no";
      leaf seq_no {
        type uint16 {
          range "0..65535";
        }
      }
      leaf operation {
        type enumeration {
          enum deny;
          enum permit;
        }
      }
      uses config-route-map-common-grouping;
    }
  }

  augment "/ios:native" {
    uses config-named-ordering-route-map-grouping;
  }

  augment "/ios:native/ios:route-map" {
    uses config-route-map-grouping;
  }
}
