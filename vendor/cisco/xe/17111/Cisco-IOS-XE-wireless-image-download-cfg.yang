module Cisco-IOS-XE-wireless-image-download-cfg {
  yang-version 1.1;
  namespace "http://cisco.com/ns/yang/Cisco-IOS-XE-wireless-image-download-cfg";
  prefix wireless-image-download-cfg;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AP and MEWLC image download configurations
     Copyright (c) 2016-2020, 2022 by Cisco Systems, Inc.
     All rights reserved.";

  revision 2022-11-01 {
    description
      "Update yang-version to 1.1";
    reference
      "1.2.0";
    cisco-semver:module-version "1.2.0";
  }
  revision 2021-03-01 {
    description
      "- Added HTTP support for the image upgrade mode";
    reference
      "1.1.0";
    cisco-semver:module-version "1.1.0";
  }
  revision 2019-03-20 {
    description
      "Initial revision";
    reference
      "1.0.0";
    cisco-semver:module-version "1.0.0";
  }

  typedef image-download-mode {
    type enumeration {
      enum image-download-mode-unconfigured {
        value 0;
        description
          "Leave Mode Undefined";
      }
      enum image-download-mode-tftp {
        value 1;
        description
          "TFTP Image Download Mode";
      }
      enum image-download-mode-sftp {
        value 2;
        description
          "SFTP Image Download Mode";
      }
      enum image-download-mode-http {
        value 3;
        description
          "HTTP Image Download Mode";
      }
      enum image-download-mode-cco {
        value 4;
        description
          "Cisco Login Image Download Mode";
      }
      enum image-download-mode-https {
        value 5;
        description
          "Secure HTTP Image Download Mode";
      }
    }
    description
      "Image Download Mode Description";
  }

  typedef cco-version-type {
    type enumeration {
      enum cco-latest-version {
        value 0;
        description
          "Cisco Login Latest Version";
      }
      enum cco-suggested-version {
        value 1;
        description
          "Cisco Login Suggested Version";
      }
    }
    description
      "Cisco Login Version Type";
  }

  grouping st-image-download-profile-config {
    description
      "Details for the image download profile";
    leaf image-download-profile-name {
      type string;
      must "(../image-download-profile-name = 'default')" {
        error-message "image download name must be default";
        error-app-tag "must-violation";
      }
      description
        "image download profile name : 'default' always";
    }
    leaf description {
      type string;
      default "";
      description
        "Default Image Download Profile Name";
    }
    choice image-download-mode-choice {
      default "image-download-mode-unconfigured";
      description
        "Supported Transport Mode : TFTP, HTTP, SFTP, Cisco Login, HTTPS";
      case image-download-mode-unconfigured {
        leaf unconfigure {
          type uint32;
          default "0";
          description
            "Configure Image Download Mode to None";
        }
      }
      case image-download-mode-tftp {
        leaf tftp-image-server {
          type inet:ip-address;
          default "127.0.0.1";
          description
            "TFTP image server";
        }
        leaf tftp-image-path {
          type string;
          default "";
          description
            "TFTP image path";
        }
      }
      case image-download-mode-sftp {
        leaf sftp-image-server {
          type inet:ip-address;
          default "127.0.0.1";
          description
            "SFTP image server";
        }
        leaf sftp-image-path {
          type string;
          default "";
          description
            "SFTP image path";
        }
        leaf sftp-username {
          type string;
          default "";
          description
            "SFTP username";
        }
        leaf sftp-password {
          type string;
          default "";
          description
            "SFTP password";
        }
        leaf sftp-password-type {
          type wireless-enum-types:crypt-type;
          default "clear-to-aes";
          description
            "SFTP pass type";
        }
        leaf sftp-port {
          type uint32;
          must '(../sftp-port = 22)' {
            error-message "sftp port must be 22";
            error-app-tag "must-violation";
          }
          default "22";
          description
            "SFTP port";
        }
      }
      case image-download-mode-cco {
        leaf cco-username {
          type string;
          default "";
          description
            "Cisco Account username";
        }
        leaf cco-password {
          type string;
          default "";
          description
            "Cisco Account password";
        }
        leaf cco-password-type {
          type wireless-enum-types:crypt-type;
          default "clear-to-aes";
          description
            "Cisco Account password type";
        }
        leaf cco-auto-check {
          type boolean;
          default "true";
          description
            "Cisco Account auto check";
        }
        leaf cco-version {
          type wireless-image-download-cfg:cco-version-type;
          default "cco-suggested-version";
          description
            "Cisco Account version";
        }
      }
      case image-download-mode-https {
        leaf https-image-path {
          type string;
          default "";
          description
            "HTTPS image server";
        }
      }
      case image-download-mode-http {
        leaf auto-path {
          type boolean;
          must "../auto-path = 'true'" {
            error-message "HTTP mode only supports automatic paths";
            error-app-tag "must-violation";
          }
          description
            "HTTP auto path";
        }
      }
    }
  }

  container image-download-cfg-data {
    description
      "Top container for image download config";
    container image-download-profiless {
      description
        "image download profiles configurations";
      list image-download-profiles {
        key "image-download-profile-name";
        description
          "image download profiles configurations";
        uses wireless-image-download-cfg:st-image-download-profile-config;
      }
    }
  }
}
