module Cisco-IOS-XE-ospfv3-deviation {
  yang-version 1.1;
  namespace "http://cisco.com/ns/yang/Cisco-IOS-XE-ospfv3-deviation";
  prefix ios-ospfv3-d;

  import cisco-semver {
    prefix cisco-semver;
  }
  import Cisco-IOS-XE-native {
    prefix ios;
  }
  import Cisco-IOS-XE-ospfv3 {
    prefix ios-ospfv3;
  }

  organization
    "Cisco Systems";
  description
    "Cisco XE Native Deviation YANG module for IOS
     Copyright (c) 2021 by Cisco Systems, Inc.
     All rights reserved.";

  revision 2023-03-01 {
    description
      "- removed defaults for max-lsa under address-family
       - added not supported for redistribute maximum-prefix under address-family ipv4";
    cisco-semver:module-version "1.2.0";
  }
  revision 2022-11-01 {
    description
      "- Update yang-version to 1.1";
    cisco-semver:module-version "1.1.0";
  }
  revision 2021-01-08 {
    description
      "Added ospfv3 deviation";
    cisco-semver:module-version "1.0.0";
  }

  deviation "/ios:native/ios:interface/ios:Virtual-Template/ios-ospfv3:ospfv3/ios-ospfv3:process-id/ios-ospfv3:bfd" {
    deviate not-supported;
  }

  deviation "/ios:native/ios:interface/ios:Virtual-Template/ios-ospfv3:ospfv3/ios-ospfv3:bfd" {
    deviate not-supported;
  }

  deviation "/ios:native/ios:interface/ios:Virtual-Template/ios-ospfv3:ospfv3/ios-ospfv3:process-id/ios-ospfv3:ipv4/ios-ospfv3:bfd" {
    deviate not-supported;
  }

  deviation "/ios:native/ios:interface/ios:Virtual-Template/ios-ospfv3:ospfv3/ios-ospfv3:process-id/ios-ospfv3:ipv6/ios-ospfv3:bfd" {
    deviate not-supported;
  }

  deviation "/ios:native/ios:interface/ios:Dialer/ios-ospfv3:ospfv3/ios-ospfv3:process-id/ios-ospfv3:bfd" {
    deviate not-supported;
  }

  deviation "/ios:native/ios:interface/ios:Dialer/ios-ospfv3:ospfv3/ios-ospfv3:bfd" {
    deviate not-supported;
  }

  deviation "/ios:native/ios:interface/ios:Dialer/ios-ospfv3:ospfv3/ios-ospfv3:process-id/ios-ospfv3:ipv4/ios-ospfv3:bfd" {
    deviate not-supported;
  }

  deviation "/ios:native/ios:interface/ios:Dialer/ios-ospfv3:ospfv3/ios-ospfv3:process-id/ios-ospfv3:ipv6/ios-ospfv3:bfd" {
    deviate not-supported;
  }

  deviation "/ios:native/ios:router/ios-ospfv3:ospfv3/ios-ospfv3:address-family/ios-ospfv3:ipv6/ios-ospfv3:unicast/ios-ospfv3:redistribute/ios-ospfv3:nat-route-config/ios-ospfv3:dia" {
    deviate not-supported;
  }

  deviation "/ios:native/ios:router/ios-ospfv3:ospfv3/ios-ospfv3:address-family/ios-ospfv3:ipv6/ios-ospfv3:unicast/ios-ospfv3:redistribute/ios-ospfv3:nat-route-config/ios-ospfv3:outside" {
    deviate not-supported;
  }

  deviation "/ios:native/ios:router/ios-ospfv3:ospfv3/ios-ospfv3:address-family/ios-ospfv3:ipv6/ios-ospfv3:vrf/ios-ospfv3:redistribute/ios-ospfv3:nat-route-config/ios-ospfv3:dia" {
    deviate not-supported;
  }

  deviation "/ios:native/ios:router/ios-ospfv3:ospfv3/ios-ospfv3:address-family/ios-ospfv3:ipv6/ios-ospfv3:vrf/ios-ospfv3:redistribute/ios-ospfv3:nat-route-config/ios-ospfv3:outside" {
    deviate not-supported;
  }

  deviation "/ios:native/ios:router/ios-ospfv3:ospfv3/ios-ospfv3:address-family/ios-ospfv3:ipv4/ios-ospfv3:unicast/ios-ospfv3:redistribute/ios-ospfv3:maximum-prefix/ios-ospfv3:number" {
    deviate not-supported;
  }

  deviation "/ios:native/ios:router/ios-ospfv3:ospfv3/ios-ospfv3:address-family/ios-ospfv3:ipv4/ios-ospfv3:vrf/ios-ospfv3:redistribute/ios-ospfv3:maximum-prefix/ios-ospfv3:number" {
    deviate not-supported;
  }

  deviation "/ios:native/ios:router/ios-ospfv3:ospfv3/ios-ospfv3:address-family/ios-ospfv3:ipv6/ios-ospfv3:unicast/ios-ospfv3:max-lsa/ios-ospfv3:number" {
    deviate delete {
      default "50000";
    }
  }

  deviation "/ios:native/ios:router/ios-ospfv3:ospfv3/ios-ospfv3:address-family/ios-ospfv3:ipv6/ios-ospfv3:unicast/ios-ospfv3:max-lsa/ios-ospfv3:threshold-value" {
    deviate delete {
      default "75";
    }
  }

  deviation "/ios:native/ios:router/ios-ospfv3:ospfv3/ios-ospfv3:address-family/ios-ospfv3:ipv6/ios-ospfv3:unicast/ios-ospfv3:max-lsa/ios-ospfv3:ignore-count" {
    deviate delete {
      default "5";
    }
  }

  deviation "/ios:native/ios:router/ios-ospfv3:ospfv3/ios-ospfv3:address-family/ios-ospfv3:ipv6/ios-ospfv3:unicast/ios-ospfv3:max-lsa/ios-ospfv3:ignore-time" {
    deviate delete {
      default "5";
    }
  }

  deviation "/ios:native/ios:router/ios-ospfv3:ospfv3/ios-ospfv3:address-family/ios-ospfv3:ipv6/ios-ospfv3:unicast/ios-ospfv3:max-lsa/ios-ospfv3:reset-time" {
    deviate delete {
      default "10";
    }
  }

  deviation "/ios:native/ios:router/ios-ospfv3:ospfv3/ios-ospfv3:address-family/ios-ospfv3:ipv4/ios-ospfv3:unicast/ios-ospfv3:max-lsa/ios-ospfv3:number" {
    deviate delete {
      default "50000";
    }
  }

  deviation "/ios:native/ios:router/ios-ospfv3:ospfv3/ios-ospfv3:address-family/ios-ospfv3:ipv4/ios-ospfv3:unicast/ios-ospfv3:max-lsa/ios-ospfv3:threshold-value" {
    deviate delete {
      default "75";
    }
  }

  deviation "/ios:native/ios:router/ios-ospfv3:ospfv3/ios-ospfv3:address-family/ios-ospfv3:ipv4/ios-ospfv3:unicast/ios-ospfv3:max-lsa/ios-ospfv3:ignore-count" {
    deviate delete {
      default "5";
    }
  }

  deviation "/ios:native/ios:router/ios-ospfv3:ospfv3/ios-ospfv3:address-family/ios-ospfv3:ipv4/ios-ospfv3:unicast/ios-ospfv3:max-lsa/ios-ospfv3:ignore-time" {
    deviate delete {
      default "5";
    }
  }

  deviation "/ios:native/ios:router/ios-ospfv3:ospfv3/ios-ospfv3:address-family/ios-ospfv3:ipv4/ios-ospfv3:unicast/ios-ospfv3:max-lsa/ios-ospfv3:reset-time" {
    deviate delete {
      default "10";
    }
  }

  deviation "/ios:native/ios:router/ios-ospfv3:ospfv3/ios-ospfv3:address-family/ios-ospfv3:ipv4/ios-ospfv3:vrf/ios-ospfv3:max-lsa/ios-ospfv3:number" {
    deviate delete {
      default "50000";
    }
  }

  deviation "/ios:native/ios:router/ios-ospfv3:ospfv3/ios-ospfv3:address-family/ios-ospfv3:ipv4/ios-ospfv3:vrf/ios-ospfv3:max-lsa/ios-ospfv3:threshold-value" {
    deviate delete {
      default "75";
    }
  }

  deviation "/ios:native/ios:router/ios-ospfv3:ospfv3/ios-ospfv3:address-family/ios-ospfv3:ipv4/ios-ospfv3:vrf/ios-ospfv3:max-lsa/ios-ospfv3:ignore-count" {
    deviate delete {
      default "5";
    }
  }

  deviation "/ios:native/ios:router/ios-ospfv3:ospfv3/ios-ospfv3:address-family/ios-ospfv3:ipv4/ios-ospfv3:vrf/ios-ospfv3:max-lsa/ios-ospfv3:ignore-time" {
    deviate delete {
      default "5";
    }
  }

  deviation "/ios:native/ios:router/ios-ospfv3:ospfv3/ios-ospfv3:address-family/ios-ospfv3:ipv4/ios-ospfv3:vrf/ios-ospfv3:max-lsa/ios-ospfv3:reset-time" {
    deviate delete {
      default "10";
    }
  }

  deviation "/ios:native/ios:router/ios-ospfv3:ospfv3/ios-ospfv3:address-family/ios-ospfv3:ipv6/ios-ospfv3:vrf/ios-ospfv3:max-lsa/ios-ospfv3:number" {
    deviate delete {
      default "50000";
    }
  }

  deviation "/ios:native/ios:router/ios-ospfv3:ospfv3/ios-ospfv3:address-family/ios-ospfv3:ipv6/ios-ospfv3:vrf/ios-ospfv3:max-lsa/ios-ospfv3:threshold-value" {
    deviate delete {
      default "75";
    }
  }

  deviation "/ios:native/ios:router/ios-ospfv3:ospfv3/ios-ospfv3:address-family/ios-ospfv3:ipv6/ios-ospfv3:vrf/ios-ospfv3:max-lsa/ios-ospfv3:ignore-count" {
    deviate delete {
      default "5";
    }
  }

  deviation "/ios:native/ios:router/ios-ospfv3:ospfv3/ios-ospfv3:address-family/ios-ospfv3:ipv6/ios-ospfv3:vrf/ios-ospfv3:max-lsa/ios-ospfv3:ignore-time" {
    deviate delete {
      default "5";
    }
  }

  deviation "/ios:native/ios:router/ios-ospfv3:ospfv3/ios-ospfv3:address-family/ios-ospfv3:ipv6/ios-ospfv3:vrf/ios-ospfv3:max-lsa/ios-ospfv3:reset-time" {
    deviate delete {
      default "10";
    }
  }
}
