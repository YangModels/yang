module Cisco-IOS-XE-wireless-rfid-global-oper {
  yang-version 1.1;
  namespace "http://cisco.com/ns/yang/Cisco-IOS-XE-wireless-rfid-global-oper";
  prefix wireless-rfid-global-oper;

  import Cisco-IOS-XE-wireless-enum-types {
    prefix wireless-enum-types;
  }
  import Cisco-IOS-XE-wireless-types {
    prefix wireless-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains RFID operational data.
     Copyright (c) 2021-2022 by Cisco Systems, Inc.
     All rights reserved.";

  revision 2023-03-01 {
    description
      "Added RFID data";
    reference
      "1.2.0";
    cisco-semver:module-version "1.2.0";
  }
  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  typedef enm-rfid-cisco-vendor-type {
    type enumeration {
      enum rfid-type-g2 {
        value 0;
        description
          "Type of G2 vendor.";
      }
      enum rfid-type-aeroscout {
        value 1;
        description
          "Type of aero scout vendor.";
      }
      enum rfid-type-unknown {
        value 2;
        description
          "Unknown vendor.";
      }
    }
    description
      "This enum has a list of the cisco tag supported RFID
         vendor types such as G2, Aero scout. ";
  }

  typedef enm-rfid-data-type {
    type enumeration {
      enum bluesoft-rfid-data {
        value 0;
        description
          "Type of bluesoft RFID tag.";
      }
      enum cisco-rfid-data {
        value 1;
        description
          "Type of cisco RFID tag.";
      }
    }
    description
      "This enum has all the RFID
       tags supported types.";
  }

  grouping st-apf-seq-control {
    description
      "Sequence and fragmentation number.";
    leaf seq-num {
      type uint16;
      description
        "Sequence number of RFID tag packet.";
    }
    leaf frag-num {
      type uint16;
      description
        "Fragmentation number of RFID tag packet.";
    }
  }

  grouping st-rfid-cisco-cont-hdr {
    description
      "CTX content header contains attributes of ctx header of RFID";
    leaf ccx-version {
      type uint8;
      description
        "CCX version of RFID";
    }
    leaf tx-power {
      type int8;
      description
        "Tx power of RFID";
    }
    leaf channel {
      type uint8;
      description
        "Channel id of RFID";
    }
    leaf reg-class {
      type uint8;
      description
        "Regulatory class of RFID";
    }
    leaf burst-len {
      type uint8;
      description
        "Burst length of RFID";
    }
  }

  grouping st-bluesoft-rfid-data {
    description
      "Data of bluesoft rfid tag.";
    leaf last-seq-num {
      type uint8;
      description
        "Last sequence number of RFID tag.";
    }
    leaf tag-type {
      type uint8;
      description
        "Type of bluesoft RFID tag.";
    }
  }

  grouping st-ccx-payload-list {
    description
      "CCX payload contains ccx payload data of RFID";
    leaf-list data {
      type uint8;
      max-elements 500;
      ordered-by user;
      description
        "Data contains one byte of ccx payload data.";
    }
  }

  grouping st-cisco-rfid-data {
    description
      "Data of cisco RFID tag";
    container rfid-cisco-hdr {
      description
        "Cisco tag header.";
      uses wireless-rfid-global-oper:st-rfid-cisco-cont-hdr;
    }
    container seq-control {
      description
        "Sequence control number of RFID tag.";
      uses wireless-rfid-global-oper:st-apf-seq-control;
    }
    leaf payload-len {
      type uint16;
      description
        "Payload length of RFID packet.";
    }
    container ccx-payload {
      description
        "CCX payload length of RFID packet.";
      uses wireless-rfid-global-oper:st-ccx-payload-list;
    }
    leaf cisco-vendor-type {
      type wireless-rfid-global-oper:enm-rfid-cisco-vendor-type;
      description
        "Name of RFID vendor.";
    }
  }

  grouping st-vendor-spec-data {
    description
      "vendor specific data of rfid packet.";
    choice type-choice {
      description
        "Type of rfid tag supported.";
      case bluesoft-rfid-data {
        container bluesoft {
          description
            "Update of bluesoft RFID information.";
          uses wireless-rfid-global-oper:st-bluesoft-rfid-data;
        }
      }
      case cisco-rfid-data {
        container cisco {
          description
            "Cisco RFID tag information.";
          uses wireless-rfid-global-oper:st-cisco-rfid-data;
        }
      }
    }
  }

  grouping st-emltd-rfid-ap-data {
    description
      "ap entry list is list of ap data, max count of list is 16.";
    leaf rssi-value {
      type int8;
      description
        "RSSI parameters of RFID.";
    }
    leaf channel {
      type uint16;
      description
        "RFID channel";
    }
    leaf slot-id {
      type uint8;
      description
        "AP slot id";
    }
    leaf ap-name {
      type string;
      description
        "Value of AP name.";
    }
    leaf last-update-rcvd {
      type yang:date-and-time;
      description
        "Last update received";
    }
    leaf wtp-mode {
      type wireless-types:enm-ewlc-spam-ap-modes;
      description
        "ap_mac_addr represents ap mac address of AP.";
    }
  }

  grouping st-emltd-rfid-data {
    description
      "rfid data represents rfid parameters.";
    leaf rfid-mac-addr {
      type yang:mac-address;
      description
        "RFID device mac address";
    }
    leaf rfid-type {
      type wireless-rfid-global-oper:enm-rfid-data-type;
      description
        "Type of rfid tag.";
    }
    leaf rfid-auto-interval {
      type uint16;
      description
        "RFID packet interval.";
    }
    leaf rfid-bytes-rx {
      type uint32;
      description
        "Number of bytes received in RFID packet.";
    }
    leaf rfid-packets-rx {
      type uint32;
      description
        "Number of RFID packets received";
    }
    leaf rfid-last-heard-second {
      type yang:date-and-time;
      description
        "Time stamp of last RFID packet received.";
    }
    container rfid-vendor {
      description
        "Vendor type of RFID received.";
      uses wireless-rfid-global-oper:st-vendor-spec-data;
    }
    list ap-data {
      description
        "AP information of RFID packet received.";
      uses wireless-rfid-global-oper:st-emltd-rfid-ap-data;
    }
  }

  grouping st-rfid-count-data {
    description
      "This object contains RFID count data";
    leaf total-rfid-count {
      type uint32;
      description
        "This is the total number of unique RFID found in the RFID radio entry data";
    }
  }

  grouping rfid-radio-key {
    description
      "RFID radio entry";
    leaf rfid-mac-addr {
      type yang:mac-address;
      description
        "RFID MAC address";
    }
    leaf ap-mac-addr {
      type yang:mac-address;
      description
        "AP MAC address";
    }
    leaf slot {
      type uint8 {
        range "0..3";
      }
      description
        "Slot ID";
    }
  }

  grouping st-rfid-radio-entries {
    description
      "RFID radio entry data";
    leaf ap-name {
      type string;
      description
        "AP Name";
    }
    leaf rssi-last-heard {
      type yang:date-and-time;
      description
        "Time at which RFID was last heard by controller";
    }
    leaf rssi-value {
      type int8;
      units "dBm";
      description
        "RSSI value of the RFID tag when last heard by controller";
    }
    leaf snr-value {
      type int8;
      units "dBm";
      description
        "SNR signal to noise ratio value of RFID tag";
    }
    leaf radio-int-type {
      type wireless-enum-types:enm-radio-type;
      description
        "Radio type of the detecting AP that detected RFID";
    }
  }

  container rfid-global-oper-data {
    config false;
    description
      "RFID operational data";
    container rfid-total-count {
      presence "rfid-total-count";
      description
        "Total number of unique RFID entries";
      uses wireless-rfid-global-oper:st-rfid-count-data;
    }
    list rfid-data-detail {
      key "rfid-mac-addr";
      description
        "RFID data detail";
      uses wireless-rfid-global-oper:st-emltd-rfid-data;
    }
    list rfid-radio-data {
      key "rfid-mac-addr ap-mac-addr slot";
      description
        "Operational data of known RFID tags";
      uses wireless-rfid-global-oper:rfid-radio-key;
      uses wireless-rfid-global-oper:st-rfid-radio-entries;
    }
  }
}
