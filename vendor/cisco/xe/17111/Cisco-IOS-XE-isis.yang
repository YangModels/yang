module Cisco-IOS-XE-isis {
  yang-version 1.1;
  namespace "http://cisco.com/ns/yang/Cisco-IOS-XE-isis";
  prefix ios-isis;

  import cisco-semver {
    prefix cisco-semver;
  }
  import ietf-inet-types {
    prefix inet;
  }
  import Cisco-IOS-XE-types {
    prefix ios-types;
  }
  import Cisco-IOS-XE-snmp {
    prefix ios-snmp;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Intermediate System-to-Intermediate System (IS-IS) Yang model.
     Copyright (c) 2016-2020 by Cisco Systems, Inc.
     All rights reserved.";

  revision 2023-03-01 {
    description
      "- Added cli for te-metric feature";
    cisco-semver:module-version "6.1.0";
  }
  revision 2022-11-01 {
    description
      "- Update yang-version to 1.1
       - Added metric fallback anomaly";
    cisco-semver:module-version "6.0.0";
  }
  revision 2022-03-01 {
    description
      "- Added set-attached-bit under AF IPv6";
    cisco-semver:module-version "5.2.0";
  }
  revision 2021-11-01 {
    description
      "- Added multicast-intact
       - Added receive application flex-algo
       - Added back LAN grouping to tunnel and made obsolete";
    cisco-semver:module-version "5.1.0";
  }
  revision 2021-07-01 {
    description
      "- Added adjacency stagger
       - Added flood parallel suppression
       - Updated use of redistribute level grouping
       - Added cli-exit-command to router isis container
       - Added support for Port-channel-subinterface
       - On Tunnel interface used serial grouping instead of lan";
    cisco-semver:module-version "5.0.0";
  }
  revision 2021-03-01 {
    description
      "- Added prefix metric
       - Added ucmp local support
       - Added include-any
       - Added include-all";
    cisco-semver:module-version "4.1.0";
  }
  revision 2020-07-01 {
    description
      "- Added status obsolete for fast-reroute-remote-lfa-list
       - Added status obsolete for fast-reroute-tie-break-list";
    cisco-semver:module-version "4.0.0";
  }
  revision 2020-03-01 {
    description
      "- Added flex-algo
       - Deprecated commands not applicable to loopback interfaces
       - Added net-id constraint for flex-algo configuration";
    cisco-semver:module-version "3.0.0";
  }
  revision 2019-11-01 {
    description
      "- Added new knobs
       - Added rib process-id
       - Fixed issues with isis redistribute metric range as compatible to cli
       - Fixed issues with isis redistribute ipv6 leaf include-connected";
    cisco-semver:module-version "2.0.0";
  }
  revision 2019-07-01 {
    description
      "- Establish semantic version baseline
       - Add Tag leaf under ipv6 summary-prefix
       - Add default value and range values
       - Added mandatory for value leafs
       - Fixed issues with area-password and domain-password commands
       - Removed help, redistribute VRF and ISPF leaves as they are unsupported
       - Added missing leaves in fast-reroute, microloop commands
       - Added missing leaves for mpls command
       - Mandatory configuration of route-map and distribution-list during route leak
       - Added enable-poi to authentication command
       - Corrected hello-interval, hello-multiplier, password and priority commands under interface
       - Fixed issues related with redistribute static and bgp
       - Fixed redistribution of IS-IS to see relevant options based on area-tag
       - Added fast-reroute, prefix-attributes, metric under interface
       - Add interface BD-VIF isis";
    cisco-semver:module-version "1.0.0";
  }
  revision 2019-02-08 {
    description
      "Added clns-mtu";
  }
  revision 2019-01-22 {
    description
      "Added leaf for App-hosting Gigabit Ethernet interface";
  }
  revision 2018-11-22 {
    description
      "Cleanup spelling errors in description statements";
  }
  revision 2018-11-15 {
    description
      "Added OMP and NAT route redistribution";
  }
  revision 2018-06-28 {
    description
      "Added must constraints for deleting vrf";
  }
  revision 2017-11-27 {
    description
      "Added Change 25GE name";
  }
  revision 2017-11-14 {
    description
      "This revision has changes for the new 40 and 100GE interface addition";
  }
  revision 2017-09-15 {
    description
      "This revision has changes for the new 2gig interface addition";
  }
  revision 2017-08-16 {
    description
      "This revision has changes for new 5gig and 25gig interfaces addition";
  }
  revision 2017-07-20 {
    description
      "Add isis bfd";
  }
  revision 2017-04-28 {
    description
      "inet:ipv6-prefix changed to ios-types:ipv6-prefix";
  }
  revision 2017-03-28 {
    description
      "Added NED Yang Data Model support for MPLS-TE";
  }
  revision 2017-02-07 {
    description
      "Initial revision";
  }

  typedef isis-net {
    type string;
  }

  typedef isis-level-type {
    type enumeration {
      enum level-1;
      enum level-1-2;
      enum level-2;
    }
  }

  typedef isis-routes-level-type {
    type enumeration {
      enum level-1;
      enum level-1-2;
      enum level-2;
    }
  }

  typedef authentication-level-type {
    type enumeration {
      enum level-1;
      enum level-2;
    }
  }

  grouping isis-bfd-loopback-grouping {
    container bfd {
      description
        "Bidirectional Forwarding Protocol";
      status obsolete;
      presence "true";
      leaf disable {
        description
          "disable bfd";
        status obsolete;
        type empty;
      }
    }
  }

  grouping isis-bfd-grouping {
    container bfd {
      description
        "Bidirectional Forwarding Protocol";
      presence "true";
      leaf disable {
        description
          "disable bfd";
        type empty;
      }
    }
  }

  grouping config-interface-ip-router-isis-grouping {
    container isis {
      description
        "IS-IS Routing for IP";
      presence "true";
      must '../../ios:address/ios:primary/ios:address or ../../ios:unnumbered or ../../ios:address/ios:dhcp' {
        error-message "Please configure ip address on the interface";
      }
      must './tag or /ios:native/ios:router/isis' {
        error-message "router isis must be configured first";
      }
      leaf tag {
        type leafref {
          path "/ios:native/ios:router/isis-container/isis/area-tag";
        }
      }
    }
  }

  grouping config-interface-ipv6-router-isis-grouping {
    container isis {
      description
        "IS-IS Routing for IPv6";
      presence "true";
      must '../../ios:address/ios:autoconfig or ../../ios:address/ios:prefix-list or ../../ios:address/ios:link-local-address or ../../ios:address/ios:prefix-name or ../../ios:unnumbered or ../../ios:enable' {
        error-message "ipv6 is not enabled on this interface";
      }
      must './tag or /ios:native/ios:router/isis' {
        error-message "router isis must be configured first";
      }
      leaf tag {
        type leafref {
          path "/ios:native/ios:router/isis-container/isis/area-tag";
        }
      }
    }
  }

  grouping config-interface-clns-grouping {
    leaf mtu {
      type int64 {
        range "512..4294967295";
      }
      description
        "MTU packet size for interface";
    }
  }

  grouping config-interface-isis-network-grouping {
    container network {
      description
        "Network type";
      leaf point-to-point {
        default "false";
        type boolean;
      }
    }
  }

  grouping isis-interface-lan-authentication-grouping {
    list mode {
      description
        "Authentication mode";
      key "levels";
      leaf levels {
        type enumeration {
          enum level-1;
          enum level-2;
        }
      }
      leaf options {
        mandatory true;
        type enumeration {
          enum md5;
          enum text;
        }
      }
    }
    list key-chain {
      description
        "Authentication key-chain";
      key "levels";
      leaf levels {
        type enumeration {
          enum level-1;
          enum level-2;
        }
      }
      leaf name {
        type string;
      }
    }
    leaf-list send-only {
      description
        "Authentication send only, receive ignore";
      type enumeration {
        enum level-1;
        enum level-2;
      }
    }
  }

  grouping isis-interface-lan-tunnel-authentication-grouping {
    list mode {
      description
        "Authentication mode";
      status obsolete;
      key "levels";
      leaf levels {
        status obsolete;
        type enumeration {
          enum level-1;
          enum level-2;
        }
      }
      leaf options {
        status obsolete;
        mandatory true;
        type enumeration {
          enum md5;
          enum text;
        }
      }
    }
    list key-chain {
      description
        "Authentication key-chain";
      status obsolete;
      key "levels";
      leaf levels {
        status obsolete;
        type enumeration {
          enum level-1;
          enum level-2;
        }
      }
      leaf name {
        status obsolete;
        type string;
      }
    }
    leaf-list send-only {
      description
        "Authentication send only, receive ignore";
      status obsolete;
      type enumeration {
        enum level-1;
        enum level-2;
      }
    }
  }

  grouping isis-interface-serial-authentication-grouping {
    container mode {
      description
        "Authentication mode";
      leaf mode-options {
        type enumeration {
          enum md5;
          enum text;
        }
      }
    }
    container key-chain {
      description
        "Authentication key-chain";
      leaf name {
        type string;
      }
    }
    container send-only {
      description
        "Authentication send only, receive ignore";
      presence "Authentication send only, receive ignore";
    }
  }

  grouping config-interface-isis-serial-grouping {
    container adjacency-sid {
      description
        "Manual adjacency SID configuration";
      list adj-sid-list-absolute {
        must '../../../../ios:ip/ios:router/isis or ../../../../ios:ipv6/ios:router/isis' {
          error-message "Please configure ISIS on this interface";
        }
        key "sid-value";
        leaf sid-value {
          description
            "Adjacency-SID value";
          type uint32 {
            range "16 .. 1048575";
          }
        }
        leaf absolute {
          description
            "Specify SID absolute value";
          type empty;
        }
        leaf protected {
          description
            "Protected adjacency-SID configuration";
          type empty;
        }
      }
      list adj-sid-list-index {
        must '../../../../ios:ip/ios:router/isis or ../../../../ios:ipv6/ios:router/isis' {
          error-message "Please configure ISIS on this interface";
        }
        key "sid-value";
        leaf sid-value {
          description
            "Adjacency-SID value";
          type uint32 {
            range "16 .. 1048575";
          }
        }
        leaf index {
          description
            "Specify SID index value";
          type empty;
        }
        leaf protected {
          description
            "Protected adjacency-SID configuration";
          type empty;
        }
      }
    }
    container authentication-serial {
      description
        "ISIS authentication for interface related PDUs";
      container authentication {
        uses isis-interface-serial-authentication-grouping;
      }
    }
    container hello-interval-serial {
      description
        "Set Hello interval in seconds";
      leaf hello-interval {
        default "10";
        type union {
          type uint16 {
            range "1..65535";
          }
          type enumeration {
            enum minimal;
          }
        }
      }
    }
    container hello-multiplier-serial {
      description
        "Set multiplier for Hello holding time";
      leaf hello-multiplier {
        default "3";
        type uint16 {
          range "3..1000";
        }
      }
    }
    container password-serial {
      description
        "Configure the authentication password for interface";
      leaf password {
        type string;
      }
    }
    container three-way-handshake {
      description
        "Select Cisco or IETF three-way handshake";
      presence "true";
      leaf implementor {
        default "ietf";
        type enumeration {
          enum cisco;
          enum ietf;
        }
      }
    }
  }

  grouping config-interface-isis-lan-grouping {
    container authentication-lan {
      description
        "ISIS authentication for interface related PDUs";
      container authentication {
        uses isis-interface-lan-authentication-grouping;
      }
    }
    container hello-interval-lan {
      description
        "Set Hello interval in seconds";
      list hello-interval {
        key "levels";
        leaf levels {
          type enumeration {
            enum level-1;
            enum level-2;
          }
        }
        leaf value {
          default "10";
          type union {
            type uint16 {
              range "1..65535";
            }
            type enumeration {
              enum minimal;
            }
          }
        }
      }
    }
    container hello-multiplier-lan {
      description
        "Set multiplier for Hello holding time";
      list hello-multiplier {
        key "levels";
        leaf levels {
          type enumeration {
            enum level-1;
            enum level-2;
          }
        }
        leaf value {
          default "3";
          type uint16 {
            range "3..1000";
          }
        }
      }
    }
    container password-lan {
      description
        "Configure the authentication password for interface";
      list password {
        key "levels";
        leaf levels {
          type enumeration {
            enum level-1;
            enum level-2;
          }
        }
        leaf password {
          mandatory true;
          type string;
        }
      }
    }
  }

  grouping config-interface-isis-lan-tunnel-grouping {
    container authentication-lan {
      description
        "ISIS authentication for interface related PDUs";
      status obsolete;
      container authentication {
        status obsolete;
        uses isis-interface-lan-tunnel-authentication-grouping;
      }
    }
    container hello-interval-lan {
      description
        "Set Hello interval in seconds";
      status obsolete;
      list hello-interval {
        status obsolete;
        key "levels";
        leaf levels {
          status obsolete;
          type enumeration {
            enum level-1;
            enum level-2;
          }
        }
        leaf value {
          status obsolete;
          default "10";
          type union {
            type uint16 {
              range "1..65535";
            }
            type enumeration {
              enum minimal;
            }
          }
        }
      }
    }
    container hello-multiplier-lan {
      description
        "Set multiplier for Hello holding time";
      status obsolete;
      list hello-multiplier {
        status obsolete;
        key "levels";
        leaf levels {
          status obsolete;
          type enumeration {
            enum level-1;
            enum level-2;
          }
        }
        leaf value {
          status obsolete;
          default "3";
          type uint16 {
            range "3..1000";
          }
        }
      }
    }
    container password-lan {
      description
        "Configure the authentication password for interface";
      status obsolete;
      list password {
        status obsolete;
        key "levels";
        leaf levels {
          status obsolete;
          type enumeration {
            enum level-1;
            enum level-2;
          }
        }
        leaf password {
          status obsolete;
          mandatory true;
          type string;
        }
      }
    }
  }

  grouping interface-isis-affinity-grouping {
    container affinity {
      description
        "Interface affinity configuration";
      container flex-algo {
        description
          "Affinity attributes for flex-algo";
        list name {
          key "name";
          leaf name {
            type string;
          }
        }
      }
    }
  }

  grouping config-interface-isis-grouping {
    container adjacency-filter {
      description
        "Filter IS-IS adjacencies";
      leaf name {
        type string;
      }
      leaf match-all {
        description
          "Match all area addresses";
        type empty;
      }
    }
    container advertise {
      description
        "Control addresses advertisements in LSPs";
      leaf prefix {
        description
          "Interface IP address";
        type boolean;
      }
    }
    uses interface-isis-affinity-grouping;
    container circuit-type {
      description
        "Configure circuit type for interface";
      presence "true";
      leaf levels {
        type enumeration {
          enum level-1;
          enum level-1-2;
          enum level-2-only;
        }
      }
    }
    container csnp-interval {
      description
        "Set CSNP interval in seconds";
      list csnp-interval-list {
        key "levels";
        leaf levels {
          type enumeration {
            enum level-1;
            enum level-2;
          }
        }
        leaf value {
          default "10";
          type uint16;
        }
      }
    }
    container delay {
      container normalize {
        description
          "Delay normalization interval";
        leaf interval {
          type uint32 {
            range "1..16777215";
          }
        }
        leaf offset {
          description
            "Delay normalization offset";
          type uint32 {
            range "1..16777215";
          }
        }
      }
    }
    container fast-reroute {
      description
        "Fast-reroute Interface Configuration";
      container candidate {
        description
          "interface can be used for fast-reroute path";
        list fast-reroute-candidate-list {
          key "levels";
          leaf levels {
            type enumeration {
              enum level-1;
              enum level-2;
            }
          }
          leaf disable {
            type empty;
          }
        }
      }
      container exclude {
        list fast-reroute-exclude-list {
          key "levels";
          leaf levels {
            type enumeration {
              enum level-1;
              enum level-2;
            }
          }
          leaf interface {
            description
              "Interface name";
            must '/ios:native/ios:interface/*[concat(local-name(.), ios:name) = current()]or /ios:native/ios:interface/ios:Port-channel-subinterface/*[concat(local-name(), ios:name) = current()]';
            type string;
          }
        }
      }
      container protection {
        list fast-reroute-protection-list {
          key "levels";
          leaf levels {
            type enumeration {
              enum level-1;
              enum level-2;
            }
          }
          leaf disable {
            type empty;
          }
        }
      }
      container remote-lfa {
        container protection {
          list fast-reroute-remote-lfa-list {
            key "levels";
            leaf levels {
              type enumeration {
                enum level-1;
                enum level-2;
              }
            }
            leaf disable {
              type empty;
            }
          }
        }
      }
      container ti-lfa {
        container protection {
          list fast-reroute-tilfa-list {
            key "levels";
            leaf levels {
              type enumeration {
                enum level-1;
                enum level-2;
              }
            }
            leaf maximum-metric {
              type uint32 {
                range "1 .. 4294967295";
              }
            }
            leaf disable {
              type empty;
            }
          }
        }
      }
      container tie-break {
        list fast-reroute-tie-break-list {
          key "levels";
          leaf levels {
            type enumeration {
              enum level-1;
              enum level-2;
            }
          }
          container tie-break-grouping {
            leaf downstream {
              type uint16 {
                range "1 .. 255";
              }
            }
            leaf linecard-disjoint {
              default "40";
              type uint16 {
                range "1 .. 255";
              }
            }
            leaf lowest-backup-path-metric {
              default "30";
              type uint16 {
                range "1 .. 255";
              }
            }
            leaf node-protecting {
              type uint16 {
                range "1 .. 255";
              }
            }
            leaf primary-path {
              default "20";
              type uint16 {
                range "1 .. 255";
              }
            }
            leaf secondary-path {
              type uint16 {
                range "1 .. 255";
              }
            }
            leaf srlg-disjoint {
              type uint16 {
                range "1 .. 255";
              }
            }
          }
        }
      }
    }
    container hello {
      description
        "Add padding to IS-IS hello packets";
      container padding {
        description
          "Pad hello packets";
        presence "true";
        leaf always {
          description
            "Never pad hello packets if no prefix present";
          type empty;
        }
      }
    }
    container ipv6 {
      description
        "IPv6 interface configuration";
      uses isis-ipv6-metric-grouping;
      leaf tag {
        description
          "Assign an admin tag to an ISIS interface IPv6 route";
        type uint32 {
          range "1..4294967295";
        }
      }
      uses isis-bfd-grouping;
    }
    leaf lsp-interval {
      description
        "Set LSP transmission interval";
      default "33";
      type uint32 {
        range "1..4294967295";
      }
    }
    leaf mesh-group {
      description
        "Set ISIS mesh group";
      must '../../ios:ip/ios:router/isis or ../../ios:ipv6/ios:router/isis' {
        error-message "Please configure ISIS on this interface";
      }
      type union {
        type uint32 {
          range "1..4294967295";
        }
        type enumeration {
          enum blocked;
        }
      }
    }
    uses isis-metric-grouping;
    uses isis-te-metric-grouping;
    uses isis-metric-fallback-grouping;
    container prefix-attributes {
      description
        "Specify prefix-attributes options";
      list prefix-attributes-list {
        key "levels";
        leaf levels {
          type enumeration {
            enum level-1;
            enum level-2;
          }
        }
        leaf n-flag-clear {
          mandatory true;
          type empty;
        }
      }
    }
    container priority {
      description
        "Set priority for Designated Router election";
      list priority-list {
        key "levels";
        leaf levels {
          type enumeration {
            enum level-1;
            enum level-2;
          }
        }
        leaf value {
          default "64";
          type uint8 {
            range "0..127";
          }
        }
      }
    }
    container protocol {
      description
        "Set ISIS protocol's state under current interface";
      leaf shutdown {
        type boolean;
      }
    }
    leaf retransmit-interval {
      description
        "Set per-LSP retransmission interval";
      default "5";
      type uint16;
    }
    leaf retransmit-throttle-interval {
      description
        "Set interface LSP retransmission interval";
      default "0";
      type uint16;
    }
    leaf tag {
      description
        "Assign an admin tag to an ISIS interface IP route";
      type uint32 {
        range "1..4294967295";
      }
    }
    uses isis-bfd-grouping;
  }

  grouping config-interface-loopback-isis-grouping {
    container adjacency-filter {
      description
        "Filter IS-IS adjacencies";
      status obsolete;
      leaf name {
        status obsolete;
        type string;
      }
      leaf match-all {
        description
          "Match all area addresses";
        status obsolete;
        type empty;
      }
    }
    container advertise {
      description
        "Control addresses advertisements in LSPs";
      leaf prefix {
        description
          "Interface IP address";
        type boolean;
      }
    }
    container circuit-type {
      description
        "Configure circuit type for interface";
      presence "true";
      leaf levels {
        type enumeration {
          enum level-1;
          enum level-1-2;
          enum level-2-only;
        }
      }
    }
    container csnp-interval {
      description
        "Set CSNP interval in seconds";
      status obsolete;
      list csnp-interval-list {
        status obsolete;
        key "levels";
        leaf levels {
          status obsolete;
          type enumeration {
            enum level-1;
            enum level-2;
          }
        }
        leaf value {
          status obsolete;
          default "10";
          type uint16;
        }
      }
    }
    container fast-reroute {
      description
        "Fast-reroute Interface Configuration";
      status obsolete;
      container candidate {
        description
          "interface can be used for fast-reroute path";
        status obsolete;
        list fast-reroute-candidate-list {
          status obsolete;
          key "levels";
          leaf levels {
            status obsolete;
            type enumeration {
              enum level-1;
              enum level-2;
            }
          }
          leaf disable {
            status obsolete;
            type empty;
          }
        }
      }
      container exclude {
        status obsolete;
        list fast-reroute-exclude-list {
          status obsolete;
          key "levels";
          leaf levels {
            status obsolete;
            type enumeration {
              enum level-1;
              enum level-2;
            }
          }
          leaf interface {
            description
              "Interface name";
            status obsolete;
            must '/ios:native/ios:interface/*[concat(local-name(.), ios:name) = current()]or /ios:native/ios:interface/ios:Port-channel-subinterface/*[concat(local-name(), ios:name) = current()]';
            type string;
          }
        }
      }
      container protection {
        list fast-reroute-protection-list {
          status obsolete;
          key "levels";
          leaf levels {
            status obsolete;
            type enumeration {
              enum level-1;
              enum level-2;
            }
          }
          leaf disable {
            status obsolete;
            type empty;
          }
        }
      }
      container remote-lfa {
        status obsolete;
        container protection {
          status obsolete;
          list fast-reroute-remote-lfa-list {
            status obsolete;
            key "levels";
            leaf levels {
              status obsolete;
              type enumeration {
                enum level-1;
                enum level-2;
              }
            }
            leaf disable {
              status obsolete;
              type empty;
            }
          }
        }
      }
      container ti-lfa {
        status obsolete;
        container protection {
          list fast-reroute-tilfa-list {
            status obsolete;
            key "levels";
            leaf levels {
              status obsolete;
              type enumeration {
                enum level-1;
                enum level-2;
              }
            }
            leaf maximum-metric {
              status obsolete;
              type uint32 {
                range "1 .. 4294967295";
              }
            }
            leaf disable {
              status obsolete;
              type empty;
            }
          }
        }
      }
      container tie-break {
        status obsolete;
        list fast-reroute-tie-break-list {
          status obsolete;
          key "levels";
          leaf levels {
            status obsolete;
            type enumeration {
              enum level-1;
              enum level-2;
            }
          }
          container tie-break-grouping {
            status obsolete;
            leaf downstream {
              status obsolete;
              type uint16 {
                range "1 .. 255";
              }
            }
            leaf linecard-disjoint {
              status obsolete;
              default "40";
              type uint16 {
                range "1 .. 255";
              }
            }
            leaf lowest-backup-path-metric {
              status obsolete;
              default "30";
              type uint16 {
                range "1 .. 255";
              }
            }
            leaf node-protecting {
              status obsolete;
              type uint16 {
                range "1 .. 255";
              }
            }
            leaf primary-path {
              status obsolete;
              default "20";
              type uint16 {
                range "1 .. 255";
              }
            }
            leaf secondary-path {
              status obsolete;
              type uint16 {
                range "1 .. 255";
              }
            }
            leaf srlg-disjoint {
              status obsolete;
              type uint16 {
                range "1 .. 255";
              }
            }
          }
        }
      }
    }
    container hello {
      description
        "Add padding to IS-IS hello packets";
      status obsolete;
      container padding {
        description
          "Pad hello packets";
        status obsolete;
        presence "true";
        leaf always {
          description
            "Never pad hello packets if no prefix present";
          status obsolete;
          type empty;
        }
      }
    }
    container ipv6 {
      description
        "IPv6 interface configuration";
      uses isis-ipv6-metric-grouping;
      leaf tag {
        description
          "Assign an admin tag to an ISIS interface IPv6 route";
        type uint32 {
          range "1..4294967295";
        }
      }
      uses isis-bfd-loopback-grouping;
    }
    leaf lsp-interval {
      description
        "Set LSP transmission interval";
      status obsolete;
      default "33";
      type uint32 {
        range "1..4294967295";
      }
    }
    leaf mesh-group {
      description
        "Set ISIS mesh group";
      status obsolete;
      must '../../ios:ip/ios:router/isis or ../../ios:ipv6/ios:router/isis' {
        error-message "Please configure ISIS on this interface";
      }
      type union {
        type uint32 {
          range "1..4294967295";
        }
        type enumeration {
          enum blocked;
        }
      }
    }
    uses isis-metric-grouping;
    container prefix-attributes {
      description
        "Specify prefix-attributes options";
      list prefix-attributes-list {
        key "levels";
        leaf levels {
          type enumeration {
            enum level-1;
            enum level-2;
          }
        }
        leaf n-flag-clear {
          mandatory true;
          type empty;
        }
      }
    }
    container priority {
      description
        "Set priority for Designated Router election";
      status obsolete;
      list priority-list {
        status obsolete;
        key "levels";
        leaf levels {
          status obsolete;
          type enumeration {
            enum level-1;
            enum level-2;
          }
        }
        leaf value {
          status obsolete;
          default "64";
          type uint8 {
            range "0..127";
          }
        }
      }
    }
    container protocol {
      description
        "Set ISIS protocol's state under current interface";
      leaf shutdown {
        type boolean;
      }
    }
    leaf retransmit-interval {
      description
        "Set per-LSP retransmission interval";
      status obsolete;
      default "5";
      type uint16;
    }
    leaf retransmit-throttle-interval {
      description
        "Set interface LSP retransmission interval";
      status obsolete;
      default "0";
      type uint16;
    }
    leaf tag {
      description
        "Assign an admin tag to an ISIS interface IP route";
      type uint32 {
        range "1..4294967295";
      }
    }
    uses isis-bfd-loopback-grouping;
  }

  grouping config-interface-loopback-isis-lan-grouping {
    container authentication-lan {
      description
        "ISIS authentication for interface related PDUs";
      status obsolete;
      container authentication {
        uses isis-interface-lan-authentication-grouping;
      }
    }
    container hello-interval-lan {
      status obsolete;
      description
        "Set Hello interval in seconds";
      list hello-interval {
        status obsolete;
        key "levels";
        leaf levels {
          status obsolete;
          type enumeration {
            enum level-1;
            enum level-2;
          }
        }
        leaf value {
          status obsolete;
          default "10";
          type union {
            type uint16 {
              range "1..65535";
            }
            type enumeration {
              enum minimal;
            }
          }
        }
      }
    }
    container hello-multiplier-lan {
      description
        "Set multiplier for Hello holding time";
      status obsolete;
      list hello-multiplier {
        status obsolete;
        key "levels";
        leaf levels {
          status obsolete;
          type enumeration {
            enum level-1;
            enum level-2;
          }
        }
        leaf value {
          status obsolete;
          default "3";
          type uint16 {
            range "3..1000";
          }
        }
      }
    }
    container password-lan {
      description
        "Configure the authentication password for interface";
      status obsolete;
      list password {
        status obsolete;
        key "levels";
        leaf levels {
          status obsolete;
          type enumeration {
            enum level-1;
            enum level-2;
          }
        }
        leaf password {
          status obsolete;
          mandatory true;
          type string;
        }
      }
    }
  }

  grouping narrow-wide-transition-grouping {
    leaf narrow-wide {
      type isis-level-type;
    }
    leaf transition {
      description
        "Accept both styles of TLVs during transition";
      type isis-level-type;
    }
  }

  grouping spf-intervals-grouping {
    leaf interval {
      default "5";
      type uint32 {
        range "1 .. 120";
      }
    }
    leaf initial-wait {
      default "50";
      type uint32 {
        range "1 .. 120000";
      }
    }
    leaf minimum-wait {
      default "200";
      type uint32 {
        range "1 .. 120000";
      }
    }
  }

  grouping authenticate-snp-grouping {
    leaf authenticate {
      description
        "Authentication";
      type empty;
    }
    leaf snp {
      description
        "SNP PDUs";
      type enumeration {
        enum send-only;
        enum validate;
      }
    }
  }

  grouping lsp-gen-interval-grouping {
    leaf interval {
      default "5";
      type uint32 {
        range "1 .. 120";
      }
    }
    leaf initial-wait {
      default "50";
      type uint32 {
        range "1 .. 120000";
      }
    }
    leaf wait {
      default "200";
      type uint32 {
        range "1 .. 120000";
      }
    }
  }

  grouping set-overload-bit-suppress-grouping {
    choice suppress-grouping-choice {
      case external-interlevel {
        leaf external {
          description
            "If overload-bit set, don't advertise IP prefixes learned from other protocols";
          type empty;
        }
        leaf interlevel {
          description
            "If overload-bit set, don't advertise IP prefixes learned from another ISIS level";
          type empty;
        }
      }
      case prefixes {
        leaf prefixes {
          description
            "If overload-bit set, dont advertise any IP prefixes";
          type empty;
        }
      }
    }
  }

  grouping authentication-level-grouping {
    leaf levels {
      type authentication-level-type;
    }
  }

  grouping isis-authentication-grouping {
    list mode {
      description
        "Authentication mode";
      key "levels";
      leaf levels {
        type enumeration {
          enum level-1;
          enum level-2;
        }
      }
      leaf options {
        mandatory true;
        type enumeration {
          enum md5;
          enum text;
        }
      }
      leaf enable-poi {
        description
          "Enable Purge Originator Identification TLV";
        when "../options = 'md5'";
        type empty;
      }
    }
    list key-chain {
      description
        "Authentication key-chain";
      key "levels";
      leaf levels {
        type enumeration {
          enum level-1;
          enum level-2;
        }
      }
      leaf name {
        type string;
      }
      leaf enable-poi {
        description
          "Enable Purge Originator Identification TLV";
        type empty;
      }
    }
    leaf-list send-only {
      description
        "Authentication send only, receive ignore";
      type enumeration {
        enum level-1;
        enum level-2;
      }
    }
  }

  grouping isis-metric-grouping {
    container metric {
      description
        "Configure the metric for interface";
      list metric-list {
        key "levels";
        leaf levels {
          type enumeration {
            enum level-1;
            enum level-2;
          }
        }
        leaf value {
          mandatory true;
          type union {
            type uint32 {
              range "1..16777214";
            }
            type enumeration {
              enum maximum;
            }
          }
        }
      }
    }
  }

  grouping isis-metric-fallback-mode-grouping {
    choice fallback-mode {
      case delay {
        leaf delay {
          type empty;
        }
      }
      case loss {
        leaf loss {
          type empty;
        }
      }
    }
  }

  grouping isis-metric-fallback-anomaly-val-grouping {
    choice anomaly-value {
      mandatory true;
      case increment {
        leaf increment {
          type int64 {
            range "1..16777213";
          }
        }
      }
      case multiplier {
        leaf multiplier {
          type int64 {
            range "2..100000";
          }
        }
      }
      case maximum {
        leaf maximum {
          type empty;
        }
      }
    }
  }

  grouping isis-metric-fallback-grouping {
    container metric-fallback {
      container metric {
        container fallback {
          description
            "Configure metric fallback";
          list anomaly {
            key "levels";
            leaf levels {
              type enumeration {
                enum level-1;
                enum level-2;
              }
            }
            uses isis-metric-fallback-mode-grouping;
            uses isis-metric-fallback-anomaly-val-grouping;
          }
          container anomaly-te {
            list anomaly {
              key "levels";
              leaf levels {
                type enumeration {
                  enum level-1;
                  enum level-2;
                }
              }
              uses isis-metric-fallback-mode-grouping;
              leaf te-metric {
                description
                  "te-metric";
                mandatory true;
                type empty;
              }
              uses isis-metric-fallback-anomaly-val-grouping;
            }
          }
        }
      }
    }
  }

  grouping isis-te-metric-grouping {
    container te-metric {
      description
        "Configure the te-metric for interface";
      list te-metric-list {
        key "levels";
        leaf levels {
          type enumeration {
            enum level-1;
            enum level-2;
          }
        }
        leaf flex-algo {
          description
            "Flex algorithm";
          mandatory true;
          type empty;
        }
        leaf value {
          mandatory true;
          type uint32 {
            range "1..16777214";
          }
        }
      }
    }
  }

  grouping isis-ipv6-metric-grouping {
    container metric {
      description
        "Configure the metric for interface";
      list metric-list {
        key "levels";
        leaf levels {
          type enumeration {
            enum level-1;
            enum level-2;
          }
        }
        leaf value {
          mandatory true;
          type union {
            type uint32 {
              range "1..16777214";
            }
            type enumeration {
              enum maximum;
            }
          }
        }
      }
    }
  }

  grouping redist-level-grouping {
    leaf levels {
      default "level-2";
      type isis-routes-level-type;
    }
  }

  grouping redist-level-grouping-obsolete {
    leaf levels {
      status obsolete;
      default "level-2";
      type isis-routes-level-type;
    }
  }

  grouping isis-redist-grouping {
    leaf metric {
      description
        "ISIS default metric";
      type uint32 {
        range "0 .. 4261412864";
      }
    }
    leaf route-map {
      description
        "Route map reference";
      type string;
    }
    leaf metric-type {
      when '../metric';
      type enumeration {
        enum external;
        enum internal;
      }
    }
    leaf metric-type-rib {
      description
        "OSPF/IS-IS exterior metric type for redistributed routes";
      when 'not(../metric)';
      type enumeration {
        enum external;
        enum internal;
        enum rib-metric-as-external;
        enum rib-metric-as-internal;
      }
    }
  }

  grouping isis-redist-afv6-basic-grouping {
    leaf metric {
      description
        "ISIS default metric";
      type uint32 {
        range "0 .. 4261412864";
      }
    }
    leaf route-map {
      description
        "Route map reference";
      type string;
    }
    leaf metric-type {
      when '../metric';
      type enumeration {
        enum internal;
        enum external;
      }
    }
    leaf metric-type-rib {
      description
        "OSPF/IS-IS exterior metric type for redistributed routes";
      when 'not(../metric)';
      type enumeration {
        enum internal;
        enum external;
        enum rib-metric-as-external;
        enum rib-metric-as-internal;
      }
    }
  }

  grouping isis-redist-af-grouping {
    leaf include-connected {
      description
        "Include connected";
      type empty;
    }
    leaf metric {
      description
        "ISIS default metric";
      type uint32 {
        range "0 .. 4261412864";
      }
    }
    leaf route-map {
      description
        "Route map reference";
      type string;
    }
    leaf metric-type {
      when '../metric';
      type enumeration {
        enum internal;
        enum external;
      }
    }
    leaf metric-type-rib {
      description
        "OSPF/IS-IS exterior metric type for redistributed routes";
      when 'not(../metric)';
      type enumeration {
        enum internal;
        enum external;
        enum rib-metric-as-external;
        enum rib-metric-as-internal;
      }
    }
  }

  grouping isis-redist-ospf-match-grouping {
    leaf match {
      type empty;
    }
    leaf internal {
      description
        "Redistribute OSPF internal routes";
      when '../match';
      type empty;
    }
    leaf external {
      description
        "Redistribute OSPF external routes";
      when '../match';
      type ios-types:redist-ospf-external-type;
    }
    leaf external2 {
      description
        "Redistribute OSPF external routes";
      when '../match';
      must '. != ../external' {
        error-message "external and external2 values must be different";
      }
      type ios-types:redist-ospf-external-type;
    }
    leaf nssa-external {
      description
        "Redistribute OSPF NSSA external routes";
      when '../match';
      type ios-types:redist-ospf-external-type;
    }
    leaf nssa-external2 {
      description
        "Redistribute OSPF NSSA external routes";
      when '../match';
      must '. != ../nssa-external' {
        error-message "nssa-external and nssa-external2 values must be different";
      }
      type ios-types:redist-ospf-external-type;
    }
  }

  grouping isis-redist-v4-grouping {
    list application {
      description
        "Application";
      key "name";
      leaf name {
        description
          "Application name";
        type string;
      }
      uses isis-redist-grouping;
      uses redist-level-grouping-obsolete;
    }
    container bgp {
      description
        "Border Gateway Protocol (BGP)";
      list bgp-ip {
        key "as-number";
        max-elements 1;
        leaf as-number {
          type ios-types:bgp-as-number-type;
        }
        uses isis-redist-grouping;
        uses redist-level-grouping-obsolete;
      }
    }
    container connected {
      description
        "Connected";
      presence "Connected";
      uses isis-redist-grouping;
      uses redist-level-grouping-obsolete;
    }
    container mobile {
      description
        "Mobile routes";
      presence "Mobile routes";
      uses isis-redist-grouping;
      uses redist-level-grouping-obsolete;
    }
    container static-ip {
      container static {
        description
          "Static routes";
        container ip {
          presence "static routes";
          uses isis-redist-grouping;
          uses redist-level-grouping-obsolete;
        }
      }
    }
    list eigrp {
      description
        "Enhanced Interior Gateway Routing Protocol (EIGRP)";
      key "as-number";
      leaf as-number {
        type uint32 {
          range "1 .. 65535";
        }
      }
      uses isis-redist-grouping;
      uses redist-level-grouping-obsolete;
    }
    container isis-leak {
      description
        "ISIS leaking";
      container isis {
        list ip {
          description
            "Redistribution of IP routes between levels or processes";
          key "isis-redist-levels1 isis-redist-levels2";
          leaf isis-redist-levels1 {
            type enumeration {
              enum level-1;
              enum level-2;
            }
          }
          leaf into {
            description
              "from level-n into level-m";
            mandatory true;
            type empty;
          }
          leaf isis-redist-levels2 {
            must '../isis-redist-levels1 != .' {
              error-message "Cannot redistribute isis into itself";
            }
            type enumeration {
              enum level-1;
              enum level-2;
            }
          }
          choice isis-redist-isis-ip-choice {
            mandatory true;
            leaf distribute-list {
              description
                "select routes";
              type ios-types:isis-distribute-list-type;
            }
            leaf route-map {
              description
                "Route map for route matching";
              type string;
            }
          }
        }
      }
    }
    container isis-redistribute {
      description
        "ISO IS-IS";
      container isis-no-tag {
        description
          "redistribute ISIS without area-tag";
        container isis {
          container ip {
            presence "IS-IS routes";
            uses isis-redist-grouping;
            uses redist-level-grouping;
          }
        }
      }
      list isis {
        key "area-tag";
        leaf area-tag {
          type leafref {
            path "/ios:native/ios:router/isis-container/isis/area-tag";
          }
        }
        container ip {
          presence "ISIS routes";
          uses isis-redist-grouping;
          uses redist-level-grouping;
        }
      }
    }
    container iso-igrp {
      description
        "IGRP for OSI networks";
      list iso-igrp-area {
        key "name";
        leaf name {
          type string;
        }
        leaf route-map {
          description
            "Route map reference";
          type string;
        }
      }
      container default {
        leaf route-map {
          description
            "Route map reference";
          type string;
        }
      }
    }
    container lisp {
      description
        "Locator ID Separation Protocol (LISP)";
      presence "true";
      uses isis-redist-grouping;
      uses redist-level-grouping-obsolete;
    }
    container maximum-prefix {
      description
        "Maximum number of prefixes redistributed to protocol";
      leaf number {
        type uint32 {
          range "1 .. 4294967295";
        }
      }
      leaf threshold-value {
        type uint32 {
          range "1 .. 100";
        }
      }
      choice max-prefix-options {
        leaf warning-only {
          description
            "Only give warning message when limit is exceeded";
          type empty;
        }
        leaf withdraw {
          description
            "Withdraw redistributed prefixes";
          type empty;
        }
      }
    }
    container nat-route {
      if-feature "ios-features:sdwan";
      description
        "NAT Route";
      presence "NAT routes";
      leaf dia {
        description
          "Redistribute NAT Direct Internet Access routes";
        type empty;
      }
      leaf outside {
        description
          "Redistribute NAT outside routes";
        type empty;
      }
      uses isis-redist-grouping;
      uses redist-level-grouping-obsolete;
    }
    container omp {
      if-feature "ios-features:omp";
      description
        "Overlay Management Protocol (OMP)";
      presence "omp";
      uses isis-redist-grouping;
      uses redist-level-grouping-obsolete;
    }
    container odr {
      description
        "On Demand stub Routes";
      presence "On Demand stub Routes";
      uses isis-redist-grouping;
      uses redist-level-grouping-obsolete;
    }
    list ospf {
      description
        "Open Shortest Path First (OSPF)";
      key "process-id";
      leaf process-id {
        type uint32 {
          range "1 .. 65535";
        }
      }
      uses isis-redist-grouping;
      uses redist-level-grouping-obsolete;
      uses isis-redist-ospf-match-grouping;
    }
    list ospfv3 {
      description
        "Open Shortest Path First (OSPF)";
      key "process-id";
      leaf process-id {
        type uint32 {
          range "1 .. 65535";
        }
      }
      uses isis-redist-grouping;
      uses redist-level-grouping-obsolete;
      uses isis-redist-ospf-match-grouping;
    }
    container rip {
      description
        "Routing Information Protocol (RIP)";
      presence "Routing Information Protocol (RIP)";
      uses isis-redist-grouping;
      uses redist-level-grouping-obsolete;
    }
  }

  grouping isis-redist-v6-grouping {
    list application {
      description
        "Application";
      key "name";
      leaf name {
        description
          "Application name";
        type string;
      }
      uses isis-redist-af-grouping;
    }
    container bgp {
      description
        "Border Gateway Protocol (BGP)";
      list bgp-ip {
        key "as-number";
        max-elements 1;
        leaf as-number {
          type ios-types:bgp-as-number-type;
        }
        uses isis-redist-afv6-basic-grouping;
      }
    }
    container connected {
      description
        "Connected";
      presence "Connected";
      uses isis-redist-afv6-basic-grouping;
    }
    container static-ip {
      container static {
        description
          "Static routes";
        presence "static routes";
        uses isis-redist-afv6-basic-grouping;
      }
    }
    list eigrp {
      description
        "Enhanced Interior Gateway Routing Protocol (EIGRP)";
      key "as-number";
      leaf as-number {
        type uint32 {
          range "1 .. 65535";
        }
      }
      uses isis-redist-af-grouping;
    }
    container isis-leak {
      description
        "ISIS leaking";
      list isis {
        description
          "Redistribution of IP routes between levels or processes";
        key "isis-redist-levels1 isis-redist-levels2";
        leaf isis-redist-levels1 {
          type enumeration {
            enum level-1;
            enum level-2;
          }
        }
        leaf into {
          description
            "from level-n into level-m";
          mandatory true;
          type empty;
        }
        leaf isis-redist-levels2 {
          must '../isis-redist-levels1 != .' {
            error-message "Cannot redistribute isis into itself";
          }
          type enumeration {
            enum level-1;
            enum level-2;
          }
        }
        choice isis-redist-isis-ip-choice {
          mandatory true;
          leaf distribute-list {
            description
              "select routes";
            type ios-types:isis-distribute-list-type;
          }
          leaf route-map {
            description
              "Route map for route matching";
            type string;
          }
        }
      }
    }
    container isis-redistribute {
      description
        "ISO IS-IS";
      container isis-no-tag {
        description
          "redistribute ISIS without area-tag";
        container isis {
          uses isis-redist-af-grouping;
          uses redist-level-grouping;
        }
      }
      list isis {
        key "area-tag";
        leaf area-tag {
          type leafref {
            path "/ios:native/ios:router/isis-container/isis/area-tag";
          }
        }
        uses isis-redist-af-grouping;
        uses redist-level-grouping;
      }
    }
    container lisp {
      description
        "Locator ID Separation Protocol (LISP)";
      presence "true";
      uses isis-redist-af-grouping;
    }
    container nd {
      description
        "Neighbor Discovery";
      presence "Neighbor Discovery";
      uses isis-redist-af-grouping;
    }
    container omp {
      if-feature "ios-features:omp";
      description
        "Overlay Management Protocol (OMP)";
      presence "omp";
      uses isis-redist-af-grouping;
    }
    list ospf {
      description
        "Open Shortest Path First (OSPF)";
      key "process-id";
      leaf process-id {
        type uint32 {
          range "1 .. 65535";
        }
      }
      uses isis-redist-af-grouping;
      uses isis-redist-ospf-match-grouping;
    }
    list rip {
      description
        "Routing Information Protocol (RIP)";
      key "process-id";
      leaf process-id {
        description
          "Routing Information Protocol (RIP)";
        type string;
      }
      uses isis-redist-af-grouping;
    }
  }

  grouping isis-ipv4-ipv6-common-grouping {
    leaf adjacency-check {
      description
        "Check ISIS neighbor protocol support";
      type empty;
    }
    leaf router-id {
      description
        "Interface of stable IP address for system";
      must '/ios:native/ios:interface/*[concat(local-name(.), ios:name) = current()]or /ios:native/ios:interface/ios:Port-channel-subinterface/*[concat(local-name(), ios:name) = current()]';
      type string;
    }
  }

  grouping isis-common-grouping {
    container adjacency {
      description
        "ISIS adjacencies configuration";
      container stagger {
        description
          "Maximum P2P adjacencies in forming state";
        presence "stagger";
        leaf init-number {
          default "2";
          type uint32 {
            range "2 .. 64";
          }
        }
        leaf max-number {
          when '../init-number';
          default "64";
          type uint32 {
            range "2 .. 1024";
          }
        }
      }
    }
    container advertise {
      description
        "Control which IP routes flow in L1 and L2 LSPs";
      container link {
        description
          "Advertise protocol link";
        leaf attributes {
          description
            "Advertise link attributes";
          type empty;
        }
      }
      leaf passive-only {
        description
          "only interface address of passive interfaces";
        type empty;
      }
    }
    container default-information {
      description
        "Control distribution of default information";
      container originate {
        presence "Distribute a default route";
        description
          "Distribute a default route";
        leaf route-map {
          description
            "Route-map reference";
          type string;
        }
      }
    }
    container ucmp {
      description
        "Control UCMP RIB update";
      container local {
        presence "Enable Local UCMP";
        description
          "Enable Local UCMP";
        leaf prefix-list {
          description
            "Prefix-list reference";
          type string;
        }
      }
    }
    leaf maximum-paths {
      description
        "Forward packets over multiple paths";
      default "4";
      type uint32 {
        range "1 .. 32";
      }
    }
    container metric {
      description
        "Set ISIS metric for all interfaces";
      list metrics {
        key "level";
        leaf level {
          type enumeration {
            enum level-1;
            enum level-2;
          }
        }
        leaf metric {
          mandatory true;
          type uint32 {
            range "1..16777214";
          }
        }
      }
    }
    container prc-interval {
      description
        "Minimum interval between partial route calculations";
      leaf interval {
        default "5";
        type uint32 {
          range "1 .. 120";
        }
      }
      leaf initial-wait {
        default "50";
        type uint32 {
          range "1 .. 120000";
        }
      }
      leaf minimum-wait {
        default "200";
        type uint32 {
          range "1 .. 120000";
        }
      }
    }
    container set-attached-bit {
      description
        "Conditionally advertise us as attached to L2";
      leaf route-map {
        description
          "Route-map reference";
        type string;
      }
    }
    container set-overload-bit {
      description
        "Signal other routers not to use us in SPF";
      presence "Signal other routers not to use us in SPF";
      choice set-overload-bit-choice {
        container on-startup {
          description
            "Set overload-bit only temporarily after reboot";
          choice on-startup-choice {
            container time {
              leaf time {
                mandatory true;
                type uint32 {
                  range "5 .. 86400";
                }
              }
              container suppress {
                description
                  "If overload-bit set, suppress the following types of IP prefixes";
                uses set-overload-bit-suppress-grouping;
              }
            }
            container wait-for-bgp {
              description
                "Let BGP decide when to unset the overload bit";
              presence "Let BGP decide when to unset the overload bitW";
              container suppress {
                description
                  "If overload-bit set, suppress the following types of IP prefixes";
                uses set-overload-bit-suppress-grouping;
              }
            }
          }
        }
        container suppress {
          description
            "If overload-bit set, suppress the following types of IP prefixes";
          uses set-overload-bit-suppress-grouping;
        }
      }
    }
    container receive {
      description
        "Receiver behaviour";
      container application {
        description
          "Receiver application behaviour";
        container flex-algo {
          description
            "Receiver application flex-algo behaviour";
          container delay {
            description
              "Receiver application flex-algo delay behaviour";
            leaf app-only {
              description
                "Flex-algo delay uses application specific advertisement";
              default "false";
              type boolean;
            }
          }
        }
      }
    }
    container spf-interval {
      description
        "Minimum interval between SPF calculations";
      choice spf-interval-choice {
        list level-1-2 {
          key "level";
          leaf level {
            type enumeration {
              enum level-1;
              enum level-2;
            }
          }
          uses spf-intervals-grouping;
        }
        container intervals {
          uses spf-intervals-grouping;
        }
      }
    }
  }

  grouping isis-address-family-grouping {
    uses isis-common-grouping;
    uses isis-ipv4-ipv6-common-grouping;
    container bfd {
      description
        "BFD configuration commands";
      leaf all-interfaces {
        description
          "Enable BFD on all interfaces";
        type boolean;
      }
    }
    leaf distance {
      description
        "Administrative distance";
      default "115";
      type uint32 {
        range "1 .. 254";
      }
    }
    container distribute-list {
      description
        "Filter networks in routing updates";
      list prefix-list {
        description
          "Filter connections based on an IPv6 prefix-list";
        key "name interface";
        leaf name {
          type string;
        }
        leaf interface {
          must '/ios:native/ios:interface/*[concat(local-name(.), ios:name) = current()]or /ios:native/ios:interface/ios:Port-channel-subinterface/*[concat(local-name(), ios:name) = current()]';
          type string;
        }
        leaf in {
          description
            "Filter incoming routing updates";
          type empty;
        }
      }
      container prefix-list-in-only {
        leaf prefix-list {
          type string;
        }
        leaf in {
          type empty;
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type uint32;
            }
          }
        }
      }
    }
    container multi-topology {
      description
        "Enable multi-topology mode";
      must '../../../metric-style/wide' {
        error-message "Must enable wide metrics first";
      }
      presence "Enable multi-topology mode";
      leaf transition {
        description
          "Accept and generate both IS-IS IPv6 and Multi-topology IPv6 TLVs";
        type empty;
      }
    }
    container redistribute {
      description
        "Redistribute IPv6 prefixes from another routing protocol";
      uses isis-redist-v6-grouping;
    }
    list summary-prefix {
      description
        "Configure IPv6 summary prefix";
      key "prefix";
      leaf prefix {
        type ios-types:ipv6-prefix;
      }
      leaf levels {
        default "level-2";
        type enumeration {
          enum level-1;
          enum level-1-2;
          enum level-2;
        }
      }
      leaf tag {
        description
          "Set tag";
        type uint32 {
          range "1 .. 4294967295";
        }
      }
    }
  }

  grouping tie-break-prefer-repair-grouping {
    leaf downstream {
      description
        "priority number";
      type uint8 {
        range "1..255";
      }
    }
    leaf linecard-disjoint {
      description
        "priority number";
      type uint8 {
        range "1..255";
      }
    }
    leaf lowest-backup-path-metric {
      description
        "priority number";
      default "40";
      type uint8 {
        range "1..255";
      }
    }
    leaf node-protecting {
      description
        "priority number";
      default "30";
      type uint8 {
        range "1..255";
      }
    }
    leaf primary-path {
      description
        "priority number";
      type uint8 {
        range "1..255";
      }
    }
    leaf secondary-path {
      description
        "priority number";
      default "20";
      type uint8 {
        range "1..255";
      }
    }
    leaf srlg-disjoint {
      description
        "priority number";
      type uint8 {
        range "1..255";
      }
    }
  }

  grouping isis-topology-grouping {
    container distance {
      description
        "Define an administrative distance";
      container ip-distance {
        leaf number {
          default "115";
          type uint8 {
            range "1 .. 255";
          }
        }
        leaf ip {
          description
            "Distance applied for IP derived routes";
          type empty;
        }
      }
      container iplist {
        list ip-list {
          key "ip w-bits";
          leaf ip {
            description
              "IP Source address";
            type inet:ipv4-address;
          }
          leaf w-bits {
            type inet:ipv4-address;
          }
          leaf number {
            mandatory true;
            type uint8 {
              range "1 .. 255";
            }
          }
          leaf access-list {
            type ios-types:access-list-standard-id-type;
          }
        }
      }
      container clns-distance {
        leaf number {
          type uint8 {
            range "1 .. 255";
          }
        }
        leaf clns {
          description
            "Distance applied for CLNS derived routes";
          type empty;
        }
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type uint32 {
                range "1 .. 4294967295";
              }
            }
          }
        }
      }
    }
    leaf priority {
      description
        "priority value";
      default "64";
      type uint8 {
        range "0..127";
      }
    }
    container redistribute {
      description
        "Redistribute information from another routing protocol";
      uses isis-redist-v4-grouping;
    }
    uses ios-snmp:router-snmp-grouping;
    container traffic-share {
      description
        "How to compute traffic share over alternate paths";
      container min {
        description
          "All traffic shared among min metric paths";
        leaf across-interfaces {
          description
            "Use different interfaces for equal-cost paths";
          type empty;
        }
      }
    }
    uses isis-common-grouping;
  }

  grouping isis-af-ipv4-grouping {
    uses ios-snmp:router-snmp-grouping;
    list topology {
      description
        "Associate the routing protocol to a topology instance";
      key "name";
      leaf name {
        type string;
      }
      leaf tid {
        description
          "Configuring the routing protocol topology tid";
        type uint32 {
          range "5..4095";
        }
      }
      leaf ignore-attached-bit {
        description
          "Never install default route to closest L2 router";
        type empty;
      }
      uses isis-topology-grouping;
      list summary-address {
        description
          "Configure IP address summaries";
        must '../../../../net' {
          error-message "IS-IS NET must be configured before configuring this command";
        }
        key "ip mask";
        leaf ip {
          type inet:ipv4-address;
        }
        leaf mask {
          type inet:ipv4-address;
        }
        leaf levels {
          default "level-2";
          type enumeration {
            enum level-1;
            enum level-1-2;
            enum level-2;
          }
        }
        leaf tag {
          description
            "Set tag";
          type uint32 {
            range "1 .. 4294967295";
          }
        }
        leaf metric {
          description
            "Set metric for summary route";
          type uint32 {
            range "1 .. 4294967295";
          }
        }
      }
    }
  }

  grouping isis-flex-grouping {
    list flex-algo {
      description
        "Flex algorithm mode";
      must '../net' {
        error-message "IS-IS NET must be configured before configuring this command";
      }
      key "flex-algo-number";
      leaf flex-algo-number {
        description
          "Flex algorithm value";
        type uint32 {
          range "128..255";
        }
      }
      leaf advertise-definition {
        description
          "Advertise definition";
        type empty;
      }
      container affinity {
        description
          "Assign affinities to this flex algorithm";
        container exclude-any {
          description
            "Affinity attributes to exclude";
          list name {
            key "name";
            leaf name {
              type string;
            }
          }
        }
        container include-any {
          description
            "Affinity attributes for include-any";
          list name {
            key "name";
            leaf name {
              type string;
            }
          }
        }
        container include-all {
          description
            "Affinity attributes for include-all";
          list name {
            key "name";
            leaf name {
              type string;
            }
          }
        }
      }
      container fast-reroute {
        description
          "Fast-reroute";
        leaf disable {
          type empty;
        }
      }
      container metric-type {
        description
          "Metric type";
        choice metric-type {
          case delay {
            leaf type-delay {
              type empty;
            }
          }
          case te {
            leaf te {
              type empty;
            }
          }
        }
        leaf delay {
          status deprecated;
          type empty;
        }
      }
      container microloop {
        description
          "microloop avoidance";
        container avoidance {
          description
            "microloop avoidance";
          leaf disable {
            type empty;
          }
        }
      }
      leaf prefix-metric {
        description
          "Prefix metric";
        type empty;
      }
      leaf priority {
        description
          "Priority";
        type uint32 {
          range "0..255";
        }
      }
    }
  }

  grouping config-isis-main-grouping {
    leaf vrf {
      description
        "VRF name for this process";
      must '/ios:native/ios:vrf/ios:definition[ios:name=current()] or /ios:native/ios:ip/ios:vrf[ios:name=current()]' {
        error-message "VRF does not exist";
      }
      type string;
    }
    container metric-style {
      description
        "Use old-style (ISO 10589) or new-style packet formats";
      choice metric-style-choice {
        container narrow {
          description
            "Use old style of TLVs with narrow metric";
          presence "true";
          uses narrow-wide-transition-grouping;
        }
        container transition {
          description
            "Send and accept both styles of TLVs during transition";
          presence "true";
          leaf transition {
            type isis-level-type;
          }
        }
        container wide {
          description
            "Use new style of TLVs to carry wider metric";
          presence "true";
          uses narrow-wide-transition-grouping;
        }
      }
    }
    container address-family {
      description
        "Enter Address Family command mode";
      list ipv4 {
        description
          "Address family";
        key "v4-address-family-types";
        must '../../metric-style/wide' {
          error-message "Must enable wide metrics first";
        }
        leaf v4-address-family-types {
          type enumeration {
            enum unicast;
            enum multicast;
          }
        }
        uses isis-af-ipv4-grouping;
      }
      list ipv6 {
        description
          "Address family";
        key "v6-address-family-types";
        leaf v6-address-family-types {
          type enumeration {
            enum unicast;
          }
        }
        uses isis-address-family-grouping;
      }
    }
    uses isis-topology-grouping;
    container area-password {
      description
        "Configure the authentication password for an area";
      leaf name {
        type string;
      }
      uses authenticate-snp-grouping;
    }
    container distribute {
      description
        "Link-state distribution";
      container link-state {
        description
          "Enable link-state distribution";
        presence "true";
        choice link-state-options {
          container link-state-with-instance {
            leaf instance-id {
              description
                "Set distribution process instance identifier";
              mandatory true;
              type uint32 {
                range "32 .. 4294967294";
              }
            }
            leaf levels {
              description
                "Apply to level-1 or level-2";
              type enumeration {
                enum level-1;
                enum level-2;
              }
            }
            leaf throttle {
              description
                "Set throttle update in seconds";
              default "10";
              type uint8 {
                range "5 .. 20";
              }
            }
          }
          container link-state-only-levels {
            leaf levels {
              description
                "Apply to level-1 or level-2";
              type enumeration {
                enum level-1;
                enum level-2;
              }
            }
            leaf throttle {
              description
                "Set throttle update in seconds";
              default "10";
              type uint8 {
                range "5 .. 20";
              }
            }
          }
        }
      }
    }
    container authentication {
      description
        "ISIS authentication for LSPs";
      uses isis-authentication-grouping;
    }
    container bfd {
      description
        "BFD configuration commands";
      leaf all-interfaces {
        description
          "Enable BFD on all interfaces";
        type boolean;
      }
      leaf check-ctrl-plane-failure {
        description
          "BFD check control plane failure";
        type boolean;
      }
    }
    container distribute-list {
      description
        "Filter networks in routing updates";
      list distribute-list {
        key "interface";
        leaf interface {
          must '/ios:native/ios:interface/*[concat(local-name(.), ios:name) = current()]or /ios:native/ios:interface/ios:Port-channel-subinterface/*[concat(local-name(), ios:name) = current()]';
          type string;
        }
        choice list-types {
          leaf acl-name {
            type ios-types:access-list-standard-id-type-non-default;
          }
          case prefix-gateway-case {
            leaf prefix {
              description
                "Filter prefixes in routing updates";
              type string;
            }
            leaf gateway {
              description
                "Filtering incoming updates based on gateway";
              type string;
            }
          }
        }
        leaf in {
          description
            "Filter incoming routing updates";
          type empty;
        }
      }
      container acl {
        when 'not(../gateway-or-prefix/options) and not(../route-map/name)';
        leaf acl-name {
          type ios-types:access-list-standard-id-type-non-default;
        }
        leaf in {
          description
            "Filter incoming routing updates";
          type empty;
        }
      }
      container gateway-or-prefix {
        when 'not(../route-map/name) and not(../acl/acl-name)';
        leaf options {
          type enumeration {
            enum gateway;
            enum prefix;
          }
        }
        leaf name {
          description
            "Filter prefixes based on gateway or prefix";
          type string;
        }
        leaf in {
          description
            "Filter incoming routing updates";
          type empty;
        }
      }
      container route-map {
        when 'not(../gateway-or-prefix/options) and not(../acl/acl-name)';
        leaf name {
          description
            "Filter prefixes based on the route-map";
          type string;
        }
        leaf route-map-in {
          description
            "Filter incoming routing updates";
          type empty;
        }
      }
    }
    container domain-password {
      description
        "Set the authentication password for a routing domain";
      leaf name {
        type string;
      }
      uses authenticate-snp-grouping;
    }
    container fast-flood {
      description
        "Flood LSPs (that triggered SPF) before running SPF";
      presence "Flood LSPs (that triggered SPF) before running SPF";
      leaf number {
        default "10";
        type uint32 {
          range "1 .. 15";
        }
      }
    }
    container flood {
      description
        "flooding";
      container parallel {
        description
          "parallel flooding";
        leaf suppression {
          description
            "Suppress flooding over parallel links";
          type empty;
        }
      }
    }
    container fast-reroute {
      description
        "Configure Fast-Reroute";
      container interface {
        description
          "Loop-Free-Alternative global interface settings";
        container disable {
          description
            "Disable LFA protection on all interfaces by default";
          leaf level-1 {
            type empty;
          }
          leaf level-2 {
            type empty;
          }
        }
      }
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          choice apply-types {
            leaf all {
              description
                "Enable Fast-Reroute for primary paths";
              type empty;
            }
            leaf route-map {
              description
                "route-map name";
              type string;
            }
          }
        }
        container level-2 {
          description
            "Apply to level-2";
          choice apply-types {
            leaf all {
              description
                "Enable Fast-Reroute for primary paths";
              type empty;
            }
            leaf route-map {
              description
                "route-map name";
              type string;
            }
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              leaf max-met {
                description
                  "metric value";
                type uint32 {
                  range "1..4294967295";
                }
              }
            }
          }
        }
        container level-2 {
          description
            "Apply to level-2";
          container mpls-ldp {
            description
              "Use mpls-ldp tunnel type";
            presence "true";
            container maximum-metric {
              description
                "maximum metric to reach release node";
              leaf max-met {
                description
                  "metric value";
                type uint32 {
                  range "1..4294967295";
                }
              }
            }
          }
        }
      }
      container tie-break {
        description
          "Set repair path preference";
        container level-1 {
          description
            "Apply to level-1";
          uses tie-break-prefer-repair-grouping;
        }
        container level-2 {
          description
            "Apply to level-2";
          uses tie-break-prefer-repair-grouping;
        }
      }
      container ti-lfa {
        container level-1 {
          description
            "Apply to level-1";
          presence "true";
          leaf maximum-metric {
            description
              "maximum metric to reach release node";
            type uint32 {
              range "1..4294967295";
            }
          }
        }
        container level-2 {
          description
            "Apply to level-2";
          presence "true";
          leaf maximum-metric {
            description
              "maximum metric to reach release node";
            type uint32 {
              range "1..4294967295";
            }
          }
        }
      }
      container use-candidate-only {
        description
          "Use LFA candidates configured on interfaces only";
        choice levels {
          leaf level-1 {
            description
              "Configure ISIS level-1 to run MPLS LDP";
            type empty;
          }
          leaf level-2 {
            description
              "Configure ISIS level-2 to run MPLS LDP";
            type empty;
          }
        }
      }
    }
    uses isis-flex-grouping;
    container affinity-map {
      description
        "Affinity Map for Flex-Algo";
      list color-list {
        must '../../net' {
          error-message "IS-IS NET must be configured before configuring this command";
        }
        key "name";
        leaf name {
          description
            "Color name";
          type string;
        }
        container bit-position {
          description
            "Bit-position";
          leaf position {
            type uint8 {
              range "0..255";
            }
          }
        }
      }
    }
    container hello {
      description
        "Pad ISIS hello PDUs to full MTU";
      container padding {
        presence "true";
        leaf point-to-point {
          default "true";
          type boolean;
        }
        leaf multi-point {
          default "true";
          type boolean;
        }
      }
    }
    container hostname {
      description
        "Dynamic hostname for IS-IS";
      leaf dynamic {
        description
          "Dynamic hostname";
        default "true";
        type boolean;
      }
    }
    leaf ignore-lsp-errors {
      description
        "Ignore LSPs with bad checksums";
      default "true";
      type boolean;
    }
    container is-type {
      description
        "IS Level for this routing process (OSI only)";
      leaf levels {
        default "level-1-2";
        type enumeration {
          enum level-1;
          enum level-2-only;
          enum level-1-2;
        }
      }
      leaf backdoor {
        description
          "Not set attached-bit, install default route to other Ll-L2 router";
        when "../levels = 'level-1-2'";
        type empty;
      }
    }
    container log-adj-changes {
      description
        "Log changes in adjacency state";
      leaf log-adjacency-changes {
        description
          "Log changes in adjacency state";
        default "true";
        type boolean;
      }
      leaf all {
        description
          "Include changes generated by non-IIH event";
        type empty;
      }
    }
    container lsp-full {
      description
        "If we run out of LSP fragments";
      container suppress {
        description
          "suppress the following types of IP prefixes";
        choice lsp-full-choince {
          container external-interlevel-container {
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          uses lsp-gen-interval-grouping;
        }
        container intervals-levels {
          container intervals-level-1 {
            leaf level-1 {
              description
                "Set interval for level 1 only";
              type empty;
            }
            uses lsp-gen-interval-grouping;
          }
          container intervals-level-2 {
            leaf level-2 {
              description
                "Set interval for level 2 only";
              type empty;
            }
            uses lsp-gen-interval-grouping;
          }
        }
      }
    }
    leaf lsp-mtu {
      description
        "Set maximum LSP size";
      default "1492";
      type uint32 {
        range "128 .. 4352";
      }
    }
    leaf lsp-refresh-interval {
      description
        "Set LSP refresh interval";
      default "900";
      type uint32 {
        range "1 .. 65535";
      }
    }
    leaf max-area-addresses {
      description
        "Allow configuration of more manual area addresses";
      default "3";
      type uint32 {
        range "3 .. 254";
      }
    }
    leaf max-lsp-lifetime {
      description
        "Set maximum LSP lifetime";
      default "1200";
      type uint32 {
        range "1 .. 65535";
      }
    }
    leaf multicast-intact {
      description
        "Enable ISIS multicast-intact support";
      default "false";
      type boolean;
    }
    container uloop-avoidance {
      container microloop {
        description
          "Enable microloop protection configuration commands";
        container avoidance {
          description
            "Enable local microloop avoidance";
          presence "true";
          choice microloop-function {
            leaf disable {
              description
                "Disable Microloop avoidance";
              type boolean;
            }
            leaf protected {
              description
                "Microloop avoidance for protected link or prefix only";
              type boolean;
            }
            leaf segment-routing {
              description
                "Configuring Segment-Routing Microloop Avoidance";
              type boolean;
            }
          }
        }
      }
    }
    container uloop-ribupdate {
      container microloop {
        description
          "Enable microloop protection configuration commands";
        container avoidance {
          description
            "Enable local microloop avoidance";
          leaf rib-update-delay {
            description
              "Value of the delay in milliseconds";
            type uint32 {
              range "1..600000";
            }
          }
        }
      }
    }
    container mpls {
      description
        "Configure MPLS routing protocol parameters";
      container ldp {
        description
          "routing protocol commands for MPLS LDP";
        container autoconfig {
          description
            "Configure LDP automatic configuration";
          presence "true";
          choice levels {
            leaf level-1 {
              description
                "Configure ISIS level-1 to run MPLS LDP";
              type empty;
            }
            leaf level-2 {
              description
                "Configure ISIS level-2 to run MPLS LDP";
              type empty;
            }
          }
        }
        leaf sync {
          description
            "Configure LDP-IGP Synchronization";
          type empty;
        }
        leaf sync-igp-shortcuts {
          description
            "Configure LDP-IGP Synchronization on MPLS shortcuts";
          type empty;
        }
        container ac-igp-shortcuts {
          description
            "Auto-configure LDP on IGP shortcuts";
          presence "true";
          choice levels {
            leaf level-1 {
              description
                "Configure ISIS level-1 to run MPLS LDP";
              type empty;
            }
            leaf level-2 {
              description
                "Configure ISIS level-2 to run MPLS LDP";
              type empty;
            }
          }
        }
      }
      container traffic-eng {
        description
          "routing protocol commands for MPLS Traffic Engineering";
        leaf level-1 {
          description
            "Run MPLS TE on IS-IS level 1 only";
          must '../../../metric-style/wide' {
            error-message "Must enable wide metrics first";
          }
          type empty;
        }
        leaf level-2 {
          description
            "Run MPLS TE on IS-IS level 2 only";
          must '../../../metric-style/wide' {
            error-message "Must enable wide metrics first";
          }
          type empty;
        }
        leaf multicast-intact {
          description
            "MPLS TE and PIM interaction";
          type empty;
        }
        leaf router-id {
          description
            "Traffic Engineering stable IP address for system";
          must '/ios:native/ios:interface/*[concat(local-name(.), ios:name) = current()]or /ios:native/ios:interface/ios:Port-channel-subinterface/*[concat(local-name(), ios:name) = current()]';
          type string;
        }
        container scanner {
          description
            "Timer parameters for TE database";
          leaf interval {
            description
              "Time (secs) between LSPDB walks for TE";
            type uint32 {
              range "1 .. 60";
            }
          }
          container max-flash {
            description
              "Max. number of LSPs ISIS may send to TE db without delay";
            presence "true";
            leaf max-flash-value {
              description
                "Max. number of LSPs ISIS may send to TE db without delay: <0..200>";
              type uint32 {
                range "0 .. 200";
              }
            }
          }
        }
      }
    }
    list net {
      description
        "A Network Entity Title for this process (OSI only)";
      key "tag";
      leaf tag {
        type isis-net;
      }
    }
    container nsf {
      description
        "Non-stop forwarding";
      leaf cisco {
        description
          "Checkpoint method";
        must ". = 'false' or count(../../net) != 0" {
          error-message "ISIS is not running, please configure NET";
        }
        must ". = 'false' or ../ietf = 'false'" {
          error-message "Please disable nsf ietf to change mode";
        }
        default "false";
        type boolean;
      }
      leaf ietf {
        description
          "IETF method";
        must ". = 'false' or count(../../net) != 0" {
          error-message "ISIS is not running, please configure NET";
        }
        must ". = 'false' or ../cisco = 'false'" {
          error-message "Please disable nsf cisco to change mode";
        }
        default "false";
        type boolean;
      }
      container interface {
        description
          "Interface properties";
        when "../cisco = 'true' or ../ietf = 'true'";
        leaf wait {
          description
            "Seconds";
          type uint8 {
            range "1..60";
          }
        }
      }
      leaf interval {
        description
          "Minutes";
        when "../cisco = 'true' or ../ietf = 'true'";
        type uint16 {
          range "0..1440";
        }
      }
      container sync {
        description
          "LSPDB synchronization properties on p2p links";
        when "../cisco = 'true'";
        leaf wait {
          description
            "Seconds";
          type uint16 {
            range "1..300";
          }
        }
      }
      container advertise {
        description
          "Send information to neighbors";
        when "../ietf = 'true'";
        leaf holdtime {
          description
            "Adjust holdtime advertised in IIH when RR set";
          type uint16 {
            range "5..3600";
          }
        }
      }
      container t3 {
        description
          "Time to set overload-bit if LSPDB synchronization not completed";
        when "../ietf = 'true'";
        choice t3-options {
          leaf adjacency {
            description
              "Use minimum advertised adjacency holdtime for NSF T3 timeout";
            type empty;
          }
          leaf manual {
            description
              "Manually configure NSF T3 timeout";
            type uint16 {
              range "5..3600";
            }
          }
        }
      }
    }
    container partition {
      description
        "CLNS area partition";
      leaf avoidance {
        description
          "Withdraw area prefix if partition detected";
        type boolean;
      }
    }
    container passive-interface {
      description
        "Suppress routing updates on an interface";
      choice passive-interface-choice {
        leaf default {
          description
            "Suppress routing updates on all interfaces";
          type empty;
        }
        leaf-list interface {
          must '/ios:native/ios:interface/*[concat(local-name(.), ios:name) = current()]or /ios:native/ios:interface/ios:Port-channel-subinterface/*[concat(local-name(), ios:name) = current()]';
          must 'not(/ios:native/ios:interface/*[concat(local-name(.), ios:name) = current()]/ios:ip/ios:router/isis)' {
            error-message "ip router isis must not be present";
          }
          must 'not(/ios:native/ios:interface/*[concat(local-name(.), ios:name) = current()]/ios:ipv6/ios:router/isis)' {
            error-message "ipv6 router isis must not be present";
          }
          type string;
        }
      }
    }
    container protocol {
      description
        "Set protocol's administrative state";
      leaf shutdown {
        description
          "Set protocol's administrative state to disable";
        must '../../net' {
          error-message "Must configure net to shutdown protocol";
        }
        type empty;
      }
    }
    container skeptical {
      description
        "Be a cautious NSF helper when refresh adjacency";
      leaf interval {
        description
          "Minutes";
        default "5";
        type uint16 {
          range "0..1440";
        }
      }
    }
    list summary-address {
      description
        "Configure IP address summaries";
      must '../net' {
        error-message "IS-IS NET must be configured before configuring this command";
      }
      key "ip mask";
      leaf ip {
        type inet:ipv4-address;
      }
      leaf mask {
        type inet:ipv4-address;
      }
      leaf levels {
        default "level-2";
        type enumeration {
          enum level-1;
          enum level-1-2;
          enum level-2;
        }
      }
      leaf tag {
        description
          "Set tag";
        type uint32 {
          range "1 .. 4294967295";
        }
      }
      leaf metric {
        description
          "Set metric for summary route";
        type uint32 {
          range "1 .. 4294967295";
        }
      }
    }
    leaf update-queue-depth {
      description
        "Set Update process queue depth";
      default "200";
      type uint32 {
        range "1 .. 2147483647";
      }
    }
    container use {
      description
        "Use different algorithms during SPF";
      leaf external-metrics {
        description
          "Honour external metrics during SPF";
        type empty;
      }
    }
    uses isis-ipv4-ipv6-common-grouping;
  }

  grouping config-isis-container-grouping {
    container isis-container {
      list isis {
        description
          "ISO IS-IS";
        key "area-tag";
        leaf area-tag {
          type string;
        }
        uses config-isis-main-grouping;
      }
    }
  }

  grouping config-isis-grouping {
    container isis {
      description
        "ISO IS-IS";
      presence "true";
      uses config-isis-main-grouping;
    }
  }

  augment "/ios:native/ios:router" {
    uses config-isis-grouping;
    uses config-isis-container-grouping;
  }

  augment "/ios:native/ios:interface/ios:Ethernet/ios:isis" {
    uses config-interface-isis-grouping;
    uses config-interface-isis-network-grouping;
  }

  augment "/ios:native/ios:interface/ios:Ethernet/ios:isis" {
    when "ios-isis:network/ios-isis:point-to-point = 'true'";
    container isis-serial {
      uses config-interface-isis-serial-grouping;
    }
  }

  augment "/ios:native/ios:interface/ios:Ethernet/ios:isis" {
    when "ios-isis:network/ios-isis:point-to-point = 'false'";
    container isis-lan {
      uses config-interface-isis-lan-grouping;
    }
  }

  augment "/ios:native/ios:interface/ios:FastEthernet/ios:isis" {
    uses config-interface-isis-grouping;
    uses config-interface-isis-network-grouping;
  }

  augment "/ios:native/ios:interface/ios:FastEthernet/ios:isis" {
    when "ios-isis:network/ios-isis:point-to-point = 'true'";
    container isis-serial {
      uses config-interface-isis-serial-grouping;
    }
  }

  augment "/ios:native/ios:interface/ios:FastEthernet/ios:isis" {
    when "ios-isis:network/ios-isis:point-to-point = 'false'";
    container isis-lan {
      uses config-interface-isis-lan-grouping;
    }
  }

  augment "/ios:native/ios:interface/ios:GigabitEthernet/ios:isis" {
    uses config-interface-isis-grouping;
    uses config-interface-isis-network-grouping;
  }

  augment "/ios:native/ios:interface/ios:GigabitEthernet/ios:isis" {
    when "ios-isis:network/ios-isis:point-to-point = 'true'";
    container isis-serial {
      uses config-interface-isis-serial-grouping;
    }
  }

  augment "/ios:native/ios:interface/ios:GigabitEthernet/ios:isis" {
    when "ios-isis:network/ios-isis:point-to-point = 'false'";
    container isis-lan {
      uses config-interface-isis-lan-grouping;
    }
  }

  augment "/ios:native/ios:interface/ios:TenGigabitEthernet/ios:isis" {
    uses config-interface-isis-grouping;
    uses config-interface-isis-network-grouping;
  }

  augment "/ios:native/ios:interface/ios:TenGigabitEthernet/ios:isis" {
    when "ios-isis:network/ios-isis:point-to-point = 'true'";
    container isis-serial {
      uses config-interface-isis-serial-grouping;
    }
  }

  augment "/ios:native/ios:interface/ios:TenGigabitEthernet/ios:isis" {
    when "ios-isis:network/ios-isis:point-to-point = 'false'";
    container isis-lan {
      uses config-interface-isis-lan-grouping;
    }
  }

  augment "/ios:native/ios:interface/ios:FiveGigabitEthernet/ios:isis" {
    uses config-interface-isis-grouping;
    uses config-interface-isis-network-grouping;
  }

  augment "/ios:native/ios:interface/ios:FiveGigabitEthernet/ios:isis" {
    when "ios-isis:network/ios-isis:point-to-point = 'true'";
    container isis-serial {
      uses config-interface-isis-serial-grouping;
    }
  }

  augment "/ios:native/ios:interface/ios:FiveGigabitEthernet/ios:isis" {
    when "ios-isis:network/ios-isis:point-to-point = 'false'";
    container isis-lan {
      uses config-interface-isis-lan-grouping;
    }
  }

  augment "/ios:native/ios:interface/ios:AppGigabitEthernet/ios:isis" {
    uses config-interface-isis-grouping;
    uses config-interface-isis-network-grouping;
  }

  augment "/ios:native/ios:interface/ios:AppGigabitEthernet/ios:isis" {
    when "ios-isis:network/ios-isis:point-to-point = 'true'";
    container isis-serial {
      uses config-interface-isis-serial-grouping;
    }
  }

  augment "/ios:native/ios:interface/ios:AppGigabitEthernet/ios:isis" {
    when "ios-isis:network/ios-isis:point-to-point = 'false'";
    container isis-lan {
      uses config-interface-isis-lan-grouping;
    }
  }

  augment "/ios:native/ios:interface/ios:TwentyFiveGigE/ios:isis" {
    uses config-interface-isis-grouping;
    uses config-interface-isis-network-grouping;
  }

  augment "/ios:native/ios:interface/ios:TwentyFiveGigE/ios:isis" {
    when "ios-isis:network/ios-isis:point-to-point = 'true'";
    container isis-serial {
      uses config-interface-isis-serial-grouping;
    }
  }

  augment "/ios:native/ios:interface/ios:TwentyFiveGigE/ios:isis" {
    when "ios-isis:network/ios-isis:point-to-point = 'false'";
    container isis-lan {
      uses config-interface-isis-lan-grouping;
    }
  }

  augment "/ios:native/ios:interface/ios:TwoGigabitEthernet/ios:isis" {
    uses config-interface-isis-grouping;
    uses config-interface-isis-network-grouping;
  }

  augment "/ios:native/ios:interface/ios:TwoGigabitEthernet/ios:isis" {
    when "ios-isis:network/ios-isis:point-to-point = 'true'";
    container isis-serial {
      uses config-interface-isis-serial-grouping;
    }
  }

  augment "/ios:native/ios:interface/ios:TwoGigabitEthernet/ios:isis" {
    when "ios-isis:network/ios-isis:point-to-point = 'false'";
    container isis-lan {
      uses config-interface-isis-lan-grouping;
    }
  }

  augment "/ios:native/ios:interface/ios:FortyGigabitEthernet/ios:isis" {
    uses config-interface-isis-grouping;
    uses config-interface-isis-network-grouping;
  }

  augment "/ios:native/ios:interface/ios:FortyGigabitEthernet/ios:isis" {
    when "ios-isis:network/ios-isis:point-to-point = 'true'";
    container isis-serial {
      uses config-interface-isis-serial-grouping;
    }
  }

  augment "/ios:native/ios:interface/ios:FortyGigabitEthernet/ios:isis" {
    when "ios-isis:network/ios-isis:point-to-point = 'false'";
    container isis-lan {
      uses config-interface-isis-lan-grouping;
    }
  }

  augment "/ios:native/ios:interface/ios:HundredGigE/ios:isis" {
    uses config-interface-isis-grouping;
    uses config-interface-isis-network-grouping;
  }

  augment "/ios:native/ios:interface/ios:HundredGigE/ios:isis" {
    when "ios-isis:network/ios-isis:point-to-point = 'true'";
    container isis-serial {
      uses config-interface-isis-serial-grouping;
    }
  }

  augment "/ios:native/ios:interface/ios:HundredGigE/ios:isis" {
    when "ios-isis:network/ios-isis:point-to-point = 'false'";
    container isis-lan {
      uses config-interface-isis-lan-grouping;
    }
  }

  augment "/ios:native/ios:interface/ios:Loopback/ios:isis" {
    uses config-interface-loopback-isis-grouping;
    uses config-interface-loopback-isis-lan-grouping;
  }

  augment "/ios:native/ios:interface/ios:Tunnel/ios:isis" {
    uses config-interface-isis-grouping;
    uses config-interface-isis-lan-tunnel-grouping;
    container isis-serial {
      uses config-interface-isis-serial-grouping;
    }
  }

  augment "/ios:native/ios:interface/ios:Vlan/ios:isis" {
    uses config-interface-isis-grouping;
    uses config-interface-isis-network-grouping;
  }

  augment "/ios:native/ios:interface/ios:Vlan/ios:isis" {
    when "ios-isis:network/ios-isis:point-to-point = 'true'";
    container isis-serial {
      uses config-interface-isis-serial-grouping;
    }
  }

  augment "/ios:native/ios:interface/ios:Vlan/ios:isis" {
    when "ios-isis:network/ios-isis:point-to-point = 'false'";
    container isis-lan {
      uses config-interface-isis-lan-grouping;
    }
  }

  augment "/ios:native/ios:interface/ios:LISP/ios:isis" {
    uses config-interface-isis-grouping;
    uses config-interface-isis-lan-grouping;
  }

  augment "/ios:native/ios:interface/ios:Virtual-Template/ios:isis" {
    uses config-interface-isis-grouping;
    uses config-interface-isis-lan-grouping;
  }

  augment "/ios:native/ios:interface/ios:BDI/ios:isis" {
    uses config-interface-isis-grouping;
    uses config-interface-isis-network-grouping;
  }

  augment "/ios:native/ios:interface/ios:BDI/ios:isis" {
    when "ios-isis:network/ios-isis:point-to-point = 'true'";
    container isis-serial {
      uses config-interface-isis-serial-grouping;
    }
  }

  augment "/ios:native/ios:interface/ios:BDI/ios:isis" {
    when "ios-isis:network/ios-isis:point-to-point = 'false'";
    container isis-lan {
      uses config-interface-isis-lan-grouping;
    }
  }

  augment "/ios:native/ios:interface/ios:Port-channel/ios:isis" {
    uses config-interface-isis-grouping;
    uses config-interface-isis-network-grouping;
  }

  augment "/ios:native/ios:interface/ios:Port-channel/ios:isis" {
    when "ios-isis:network/ios-isis:point-to-point = 'true'";
    container isis-serial {
      uses config-interface-isis-serial-grouping;
    }
  }

  augment "/ios:native/ios:interface/ios:Port-channel/ios:isis" {
    when "ios-isis:network/ios-isis:point-to-point = 'false'";
    container isis-lan {
      uses config-interface-isis-lan-grouping;
    }
  }

  augment "/ios:native/ios:interface/ios:Port-channel-subinterface/ios:Port-channel/ios:isis" {
    uses config-interface-isis-grouping;
    uses config-interface-isis-network-grouping;
  }

  augment "/ios:native/ios:interface/ios:Port-channel-subinterface/ios:Port-channel/ios:isis" {
    when "ios-isis:network/ios-isis:point-to-point = 'true'";
    container isis-serial {
      uses config-interface-isis-serial-grouping;
    }
  }

  augment "/ios:native/ios:interface/ios:Port-channel-subinterface/ios:Port-channel/ios:isis" {
    when "ios-isis:network/ios-isis:point-to-point = 'false'";
    container isis-lan {
      uses config-interface-isis-lan-grouping;
    }
  }

  augment "/ios:native/ios:interface/ios:Ethernet/ios:ip/ios:router" {
    uses config-interface-ip-router-isis-grouping;
  }

  augment "/ios:native/ios:interface/ios:FastEthernet/ios:ip/ios:router" {
    uses config-interface-ip-router-isis-grouping;
  }

  augment "/ios:native/ios:interface/ios:GigabitEthernet/ios:ip/ios:router" {
    uses config-interface-ip-router-isis-grouping;
  }

  augment "/ios:native/ios:interface/ios:TenGigabitEthernet/ios:ip/ios:router" {
    uses config-interface-ip-router-isis-grouping;
  }

  augment "/ios:native/ios:interface/ios:FiveGigabitEthernet/ios:ip/ios:router" {
    uses config-interface-ip-router-isis-grouping;
  }

  augment "/ios:native/ios:interface/ios:AppGigabitEthernet/ios:ip/ios:router" {
    uses config-interface-ip-router-isis-grouping;
  }

  augment "/ios:native/ios:interface/ios:TwentyFiveGigE/ios:ip/ios:router" {
    uses config-interface-ip-router-isis-grouping;
  }

  augment "/ios:native/ios:interface/ios:TwoGigabitEthernet/ios:ip/ios:router" {
    uses config-interface-ip-router-isis-grouping;
  }

  augment "/ios:native/ios:interface/ios:FortyGigabitEthernet/ios:ip/ios:router" {
    uses config-interface-ip-router-isis-grouping;
  }

  augment "/ios:native/ios:interface/ios:HundredGigE/ios:ip/ios:router" {
    uses config-interface-ip-router-isis-grouping;
  }

  augment "/ios:native/ios:interface/ios:Loopback/ios:ip/ios:router" {
    uses config-interface-ip-router-isis-grouping;
  }

  augment "/ios:native/ios:interface/ios:Tunnel/ios:ip/ios:router" {
    uses config-interface-ip-router-isis-grouping;
  }

  augment "/ios:native/ios:interface/ios:Vlan/ios:ip/ios:router" {
    uses config-interface-ip-router-isis-grouping;
  }

  augment "/ios:native/ios:interface/ios:LISP/ios:ip/ios:router" {
    uses config-interface-ip-router-isis-grouping;
  }

  augment "/ios:native/ios:interface/ios:Virtual-Template/ios:ip/ios:router" {
    uses config-interface-ip-router-isis-grouping;
  }

  augment "/ios:native/ios:interface/ios:BDI/ios:ip/ios:router" {
    uses config-interface-ip-router-isis-grouping;
  }

  augment "/ios:native/ios:interface/ios:BD-VIF/ios:ip/ios:router" {
    uses config-interface-ip-router-isis-grouping;
  }

  augment "/ios:native/ios:interface/ios:Port-channel/ios:ip/ios:router" {
    uses config-interface-ip-router-isis-grouping;
  }

  augment "/ios:native/ios:interface/ios:Port-channel-subinterface/ios:Port-channel/ios:ip/ios:router" {
    uses config-interface-ip-router-isis-grouping;
  }

  augment "/ios:native/ios:interface/ios:Ethernet/ios:ipv6/ios:router" {
    uses config-interface-ipv6-router-isis-grouping;
  }

  augment "/ios:native/ios:interface/ios:FastEthernet/ios:ipv6/ios:router" {
    uses config-interface-ipv6-router-isis-grouping;
  }

  augment "/ios:native/ios:interface/ios:GigabitEthernet/ios:ipv6/ios:router" {
    uses config-interface-ipv6-router-isis-grouping;
  }

  augment "/ios:native/ios:interface/ios:TenGigabitEthernet/ios:ipv6/ios:router" {
    uses config-interface-ipv6-router-isis-grouping;
  }

  augment "/ios:native/ios:interface/ios:FiveGigabitEthernet/ios:ipv6/ios:router" {
    uses config-interface-ipv6-router-isis-grouping;
  }

  augment "/ios:native/ios:interface/ios:AppGigabitEthernet/ios:ipv6/ios:router" {
    uses config-interface-ipv6-router-isis-grouping;
  }

  augment "/ios:native/ios:interface/ios:TwentyFiveGigE/ios:ipv6/ios:router" {
    uses config-interface-ipv6-router-isis-grouping;
  }

  augment "/ios:native/ios:interface/ios:TwoGigabitEthernet/ios:ipv6/ios:router" {
    uses config-interface-ipv6-router-isis-grouping;
  }

  augment "/ios:native/ios:interface/ios:FortyGigabitEthernet/ios:ipv6/ios:router" {
    uses config-interface-ipv6-router-isis-grouping;
  }

  augment "/ios:native/ios:interface/ios:HundredGigE/ios:ipv6/ios:router" {
    uses config-interface-ipv6-router-isis-grouping;
  }

  augment "/ios:native/ios:interface/ios:Loopback/ios:ipv6/ios:router" {
    uses config-interface-ipv6-router-isis-grouping;
  }

  augment "/ios:native/ios:interface/ios:Tunnel/ios:ipv6/ios:router" {
    uses config-interface-ipv6-router-isis-grouping;
  }

  augment "/ios:native/ios:interface/ios:Vlan/ios:ipv6/ios:router" {
    uses config-interface-ipv6-router-isis-grouping;
  }

  augment "/ios:native/ios:interface/ios:LISP/ios:ipv6/ios:router" {
    uses config-interface-ipv6-router-isis-grouping;
  }

  augment "/ios:native/ios:interface/ios:Virtual-Template/ios:ipv6/ios:router" {
    uses config-interface-ipv6-router-isis-grouping;
  }

  augment "/ios:native/ios:interface/ios:BDI/ios:ipv6/ios:router" {
    uses config-interface-ipv6-router-isis-grouping;
  }

  augment "/ios:native/ios:interface/ios:BD-VIF/ios:ipv6/ios:router" {
    uses config-interface-ipv6-router-isis-grouping;
  }

  augment "/ios:native/ios:interface/ios:Port-channel/ios:ipv6/ios:router" {
    uses config-interface-ipv6-router-isis-grouping;
  }

  augment "/ios:native/ios:interface/ios:Port-channel-subinterface/ios:Port-channel/ios:ipv6/ios:router" {
    uses config-interface-ipv6-router-isis-grouping;
  }

  augment "/ios:native/ios:interface/ios:Ethernet/ios:clns" {
    uses config-interface-clns-grouping;
  }

  augment "/ios:native/ios:interface/ios:FastEthernet/ios:clns" {
    uses config-interface-clns-grouping;
  }

  augment "/ios:native/ios:interface/ios:GigabitEthernet/ios:clns" {
    uses config-interface-clns-grouping;
  }

  augment "/ios:native/ios:interface/ios:TenGigabitEthernet/ios:clns" {
    uses config-interface-clns-grouping;
  }

  augment "/ios:native/ios:interface/ios:FiveGigabitEthernet/ios:clns" {
    uses config-interface-clns-grouping;
  }

  augment "/ios:native/ios:interface/ios:AppGigabitEthernet/ios:clns" {
    uses config-interface-clns-grouping;
  }

  augment "/ios:native/ios:interface/ios:TwentyFiveGigE/ios:clns" {
    uses config-interface-clns-grouping;
  }

  augment "/ios:native/ios:interface/ios:TwoGigabitEthernet/ios:clns" {
    uses config-interface-clns-grouping;
  }

  augment "/ios:native/ios:interface/ios:FortyGigabitEthernet/ios:clns" {
    uses config-interface-clns-grouping;
  }

  augment "/ios:native/ios:interface/ios:HundredGigE/ios:clns" {
    uses config-interface-clns-grouping;
  }

  augment "/ios:native/ios:interface/ios:Loopback/ios:clns" {
    uses config-interface-clns-grouping;
  }

  augment "/ios:native/ios:interface/ios:Tunnel/ios:clns" {
    uses config-interface-clns-grouping;
  }

  augment "/ios:native/ios:interface/ios:Vlan/ios:clns" {
    uses config-interface-clns-grouping;
  }

  augment "/ios:native/ios:interface/ios:LISP/ios:clns" {
    uses config-interface-clns-grouping;
  }

  augment "/ios:native/ios:interface/ios:Virtual-Template/ios:clns" {
    uses config-interface-clns-grouping;
  }

  augment "/ios:native/ios:interface/ios:BDI/ios:clns" {
    uses config-interface-clns-grouping;
  }

  augment "/ios:native/ios:interface/ios:BD-VIF/ios:clns" {
    uses config-interface-clns-grouping;
  }

  augment "/ios:native/ios:interface/ios:Port-channel/ios:clns" {
    uses config-interface-clns-grouping;
  }

  augment "/ios:native/ios:interface/ios:Port-channel-subinterface/ios:Port-channel/ios:clns" {
    uses config-interface-clns-grouping;
  }
}
