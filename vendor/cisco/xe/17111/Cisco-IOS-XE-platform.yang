module Cisco-IOS-XE-platform {
  yang-version 1.1;
  namespace "http://cisco.com/ns/yang/Cisco-IOS-XE-platform";
  prefix ios-plt;

  import cisco-semver {
    prefix cisco-semver;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Platform Yang model.
     Copyright (c) 2016, 2019-2021 by Cisco Systems, Inc.
     All rights reserved.";

  revision 2023-03-01 {
    description
      "- Add CLI to enable platform FNF
       - Add CLI for platform qos sdwan max-session
       - Change platform qos sdwan max-session value range";
    cisco-semver:module-version "4.5.0";
  }
  revision 2022-11-01 {
    description
      "- Update yang-version to 1.1";
    cisco-semver:module-version "4.4.0";
  }
  revision 2022-07-01 {
    description
      "Added CLI to enable platform dependent mode on sslvpn";
    cisco-semver:module-version "4.3.0";
  }
  revision 2022-03-01 {
    description
      "- Updated bfd configuration";
    cisco-semver:module-version "4.2.0";
  }
  revision 2021-07-01 {
    description
      "- Updated range for leaf cause under punt configuration";
    cisco-semver:module-version "4.1.0";
  }
  revision 2021-03-01 {
    description
      "- CRFT platform configuration
       - Support crft remote collection command on reload
       - Added must in leaf per-ace for match-statistic per-filter";
    cisco-semver:module-version "4.0.0";
  }
  revision 2020-11-01 {
    description
      "- Flow logging configuration
       - Change leaf to list for port-channel-aggregate";
    cisco-semver:module-version "3.2.0";
  }
  revision 2020-07-01 {
    description
      "- Fix punt-policer cause range
       - Add platform qos CLI for SDWAN Adaptive-QoS
       - Add SDWAN Adaptive-QoS aggressive/normal mode";
    cisco-semver:module-version "3.1.0";
  }
  revision 2020-03-01 {
    description
      "- Added platform inspect match-statistic per-filter
       - Fixed typo issue in platform-resource leaf";
    cisco-semver:module-version "3.0.0";
  }
  revision 2019-11-01 {
    description
      "- Added new config";
    cisco-semver:module-version "2.0.0";
  }
  revision 2019-07-01 {
    description
      "- Establish semantic version baseline
       - Add platform multicast long reacher ethernet
       - Added platform crypto throughput levels for newer platforms";
    cisco-semver:module-version "1.0.0";
  }
  revision 2019-01-09 {
    description
      "Add  platform usb disable";
  }
  revision 2018-12-07 {
    description
      "Add missing platform crypto throughput levels";
  }
  revision 2018-11-07 {
    description
      "Cleanup spelling errors in description statements";
  }
  revision 2018-10-24 {
    description
      "Add additional platform qos cli";
  }
  revision 2018-09-05 {
    description
      "Add support for 'platform hardware throughput crypto' CLI";
  }
  revision 2018-08-21 {
    description
      "Add support for 'platform resource'";
  }
  revision 2018-05-17 {
    description
      "modified platform ipsec control type";
  }
  revision 2018-04-06 {
    description
      "Add support for platform hardware crypto-offload";
  }
  revision 2018-03-14 {
    description
      "Add support for platform ipsec";
  }
  revision 2017-11-29 {
    description
      "Add support for time-source ntp";
  }
  revision 2017-06-02 {
    description
      "Add dependency between qos match-statistics per-filter and per-ace";
  }
  revision 2017-02-07 {
    description
      "Initial revision";
  }

  grouping config-platform-grouping {
    leaf atm-cdvt {
      description
        "Configure platform atm cdvt";
      type boolean;
    }
    container cce {
      description
        "Platform specific cce configuration";
      container ogref {
        description
          "Configure cce object-group reference feature";
        leaf enable {
          description
            "Enable object-group reference";
          type empty;
        }
      }
    }
    leaf cfm {
      description
        "Configure Multi-NNI CFM feature";
      type empty;
    }
    container icmp {
      description
        "Configure platform icmp";
      container rate-limit {
        description
          "Rate limit of each ICMP types which are generated by data path";
        leaf packet {
          description
            "Maximum # of packets allowed given a duration";
          type uint32 {
            range "0..4294967295";
          }
        }
        leaf duration {
          description
            "Duration in seconds (default value is 1 second)";
          type uint32 {
            range "0..4294967295";
          }
        }
      }
    }
    container inspect {
      description
        "Platform specific inspect configuration";
      container match-statistics {
        description
          "Configure match stats";
        leaf per-filter {
          description
            "Configure per-filter match statistics";
          type empty;
        }
      }
      leaf flow-logging {
        description
          "Enable flow-logging for Zone-Based Firewall";
        type empty;
      }
    }
    container ip-ports {
      description
        "Configure Kernel IP ephemeral ports";
      leaf ephemeral-max {
        description
          "Maximum value for ephemeral ports for IOS";
        type uint16 {
          range "49152..65534";
        }
      }
    }
    container bfd {
      description
        "Platform specific BFD commands";
      leaf disable-offload {
        description
          "Disable bfd hw offload";
        type empty;
      }
      leaf allow-svi {
        type empty;
      }
      leaf enable-offload {
        type empty;
      }
      leaf limit-offload {
        description
          "Limit bfd hw offload session";
        type uint16 {
          range "4095..6000";
        }
      }
    }
    leaf bfd-debug-trace {
      type uint8;
    }
    container time-source {
      description
        "Configure time-source";
      container ntp {
        description
          "Configure ntp";
        presence "true";
        leaf time-scale {
          description
            "Configure ntp";
          type enumeration {
            enum epoch-1900;
            enum epoch-1970;
          }
        }
      }
    }
    container console {
      description
        "Direct IOS output to console";
      presence "true";
      leaf output {
        type enumeration {
          enum auto;
          enum serial;
          enum virtual;
        }
      }
    }
    container enable {
      list controller {
        key "SONET";
        leaf SONET {
          description
            "SONET";
          type string;
        }
      }
    }
    container external-alarm {
      leaf line {
        type uint32;
      }
      leaf alarm {
        type ios:logging-level-type;
      }
    }
    container hardware {
      description
        "Configure platform hardware";
      container lite {
        leaf license {
          type enumeration {
            enum enable;
          }
        }
      }
      container throughput {
        description
          "Configure throughput";
        choice throughput-choice {
          case throughput-disable {
            leaf disable {
              description
                "Disable throughput upgrade licenses";
              type enumeration {
                enum internal-license;
              }
            }
          }
          case throughput-level {
            container level {
              description
                "Configure the current traffic throughput level";
              leaf kbps {
                type enumeration {
                  enum 10000;
                  enum 25000;
                  enum 35000;
                  enum 50000;
                  enum 75000;
                  enum 100000;
                  enum 150000;
                  enum 200000;
                  enum 250000;
                  enum 300000;
                  enum 400000;
                  enum 500000;
                  enum 1000000;
                  enum 1500000;
                  enum 2000000;
                  enum 3000000;
                }
              }
              leaf MB {
                description
                  "Configure the current traffic throughput level in mbps";
                type enumeration {
                  enum 10;
                  enum 100;
                  enum 1000;
                  enum 10000;
                  enum 250;
                  enum 2500;
                  enum 50;
                  enum 500;
                  enum 5000;
                }
              }
              leaf eval-only {
                description
                  "Use only evaluation license";
                type empty;
              }
            }
          }
          case throughput-crypto {
            leaf crypto {
              description
                "Configure crypto throughput";
              type union {
                type enumeration {
                  enum 50000;
                  enum 150000;
                  enum 250000;
                  enum unthrottled;
                  enum 10M;
                  enum 20M;
                  enum 50M;
                  enum 100M;
                  enum 250M;
                  enum 500M;
                  enum 1G;
                  enum 2.5G;
                  enum 5G;
                  enum 10G;
                  enum 25G;
                  enum 50G;
                }
              }
            }
          }
        }
      }
      container crypto-offload {
        description
          "Configure crypto offload";
        leaf enable {
          description
            "Enable crypto offload";
          type empty;
        }
      }
    }
    container ipsec {
      description
        "Platform specific ipsec command";
      leaf arlog-supress {
        description
          "supress anti-replay error log";
        type empty;
      }
      leaf fips-mode {
        description
          "enable FIPS mode";
        type empty;
      }
      leaf gdoi {
        description
          "gdoi";
        type enumeration {
          enum accept-both;
        }
      }
      container llq {
        description
          "config LLQ";
        leaf qos-group {
          description
            "config LLQ QoS Group";
          type uint8 {
            range "1..99";
          }
        }
      }
      container reassemble {
        description
          "reassemble packets";
        leaf transit {
          description
            "transit IPSEC packets";
          type empty;
        }
      }
      leaf flexvpn-bypass-tcam {
        description
          " bypass TCAM for FlexVPN";
        type empty;
      }
      leaf modexp-throttle-window {
        description
          " set modexp throttle window";
        type uint8 {
          range "0..32";
        }
      }
      leaf control-plane {
        description
          "allocate extra crypto cores for control plane";
        type enumeration {
          enum heavy;
          enum medium;
        }
      }
    }
    container l2vpn {
      description
        "Configure platform l2vpn global configuration";
      leaf hdlc-pass-through {
        description
          "l2vpn HDLC force pass through";
        type empty;
      }
      container statistics {
        description
          "l2vpn statistics";
        leaf enable {
          description
            "enable the stats";
          type empty;
        }
      }
    }
    container multicast {
      description
        "Configure multicast";
      leaf lre {
        description
          "multicast long reacher ethernet";
        type enumeration {
          enum on;
          enum off;
        }
      }
      container mgre {
        description
          "Multi-point GRE tunnel";
        leaf injection {
          description
            "Enable packet injection";
          type empty;
        }
      }
      container oce {
        description
          "multicast oce";
        container flag {
          description
            "multicast oce flag";
          leaf suppress {
            description
              "Enable oce flag suppress";
            type empty;
          }
        }
      }
    }
    container qfp {
      description
        "Quantum Flow Processor";
      presence "true";
      container utilization {
        description
          "Utilization";
        container monitor {
          description
            "monitor";
          leaf load {
            description
              "load";
            type uint16 {
              range "50..99";
            }
            default "80";
          }
        }
      }
    }
    container punt-keepalive {
      description
        "punt-keepalive messages";
      presence "true";
      leaf disable-kernel-core {
        description
          "Disable IOSXE kernel core generation for keepalive fault";
        type boolean;
      }
      container settings {
        description
          "Set the keepalive parameters";
        leaf fatal-count {
          description
            "Set punt-inject keepalive fatal count";
          type uint16 {
            range "15..60";
          }
        }
        leaf transmit-interval {
          description
            "Set punt-inject keepalive transmit interval";
          type uint16 {
            range "2..30";
          }
        }
        leaf warning-count {
          description
            "Set punt-inject keepalive warning count";
          type uint16 {
            range "10..60";
          }
        }
      }
    }
    container punt-policer {
      description
        "Configures punt policers";
      list punt-num {
        if-feature "ios-features:punt-num";
        description
          "Configure punt cause to be policed";
        key "cause";
        leaf cause {
          type uint8 {
            range "1..164";
          }
        }
        leaf max-rate {
          type uint16 {
            range "10..32000";
          }
        }
        leaf high {
          description
            "High priority traffic only";
          type empty;
        }
      }
    }
    container qos {
      description
        "Platform specific qos configuration";
      leaf cac-policer {
        description
          "packet per second";
        type uint16 {
          range "1..10000";
        }
      }
      leaf count-l3-length {
        description
          "Configure count l3 length";
        type empty;
      }
      leaf marker-statistics {
        description
          "Configure marking statistics";
        type empty;
      }
      container match-statistics {
        description
          "Configure match stats";
        leaf per-filter {
          description
            "Configure per-filter match statistics";
          type empty;
        }
        leaf per-ace {
          description
            "Configure per-ace match statistics (per-filter must be enabled first)";
          must '../per-filter' {
            error-message "Configure per-ace match statistics (per-filter must be enabled first)";
          }
          type empty;
        }
      }
      leaf optimize-rate-ratios {
        description
          "Configure optimize rate ratios";
        type empty;
      }
      leaf performance-monitor {
        description
          "Configure performance-monitor statistics";
        type empty;
      }
      list port-channel-aggregate-config {
        description
          "port-channel interface number";
        key "id";
        leaf id {
          type uint8 {
            range "1..64";
          }
        }
      }
      leaf port-channel-aggregate {
        status deprecated;
        description
          "port-channel interface number";
        type uint8 {
          range "1..64";
        }
      }
      leaf punt-path-matching {
        description
          "Configure punt-path matching on input interface (PPPoE-Discovery, PPPoE-PPP-LCP)";
        type empty;
      }
      container sdwan {
        description
          "Configure SDWAN QoS parameters";
        container adapt {
          description
            "Configure SDWAN Adaptive-QoS parameters";
          leaf spoke-overlay-usage {
            description
              "Configure SDWAN Adaptive-QoS overlay usage threshold for spoke";
            type uint8 {
              range "1..100";
            }
          }
          leaf wan-loss-permillage {
            description
              "Configure SDWAN Adaptive-QoS WAN loss threshold";
            type uint16 {
              range "1..999";
            }
          }
          leaf mode {
            description
              "Configure SDWAN Adaptive-QoS mode";
            type enumeration {
              enum aggressive;
              enum normal;
            }
          }
        }
        leaf max-session {
          description
            "Configure maximum SDWAN sessions to which QoS is applied";
          type uint32 {
            range "100..6000";
          }
        }
      }
    }
    container fnf {
      description
        "Platform specific FNF configuration";
      leaf ager-short-interval {
        description
          "FNF age short interval";
        type uint32 {
          range "1..1000";
        }
      }
      leaf ager-inspected-flows {
        description
          "FNF age short inspected flows";
        type uint32 {
          range "10..1000000";
        }
      }
      leaf ager-continue-inspected {
        description
          "FNF age continue inspected flows";
        type empty;
      }
      leaf ager-export-flows {
        description
          "FNF age normal aging export flows";
        type uint32 {
          range "10..1000000";
        }
      }
      leaf ager-dis-emergency-aged {
        description
          "FNF age disable emergency aging";
        type empty;
      }
    }
    container reload {
      description
        "Platform specific reload command";
      leaf immediate {
        description
          "Immediately stop forwarding traffic";
        type empty;
      }
    }
    leaf resource {
      description
        "Select resource template";
      type enumeration {
        enum app-heavy;
        enum control-plane-extra-heavy;
        enum control-plane-heavy;
        enum data-plane-heavy;
        enum data-plane-normal;
        enum service-plane-heavy;
        enum service-plane-medium;
      }
    }
    leaf shell {
      description
        "Control platform shell access command availability";
      type boolean;
    }
    leaf tcam-parity-error {
      type enumeration {
        enum enable;
        enum disable;
      }
    }
    container urpf {
      description
        "Platform specific urpf commands";
      container loose {
        description
          "uRPF loose mode";
        container counter {
          description
            "drop counter";
          container ipv4 {
            description
              "ipv4 protocol";
            container supress {
              description
                "supress drop";
              leaf asymmetric_only {
                description
                  "it works only for asymmetric traffic";
                type empty;
              }
            }
          }
          container ipv6 {
            description
              "ipv6 protocol";
            container supress {
              description
                "supress drop";
              leaf asymmetric_only {
                description
                  "it works only for asymmetric traffic";
                type empty;
              }
            }
          }
        }
      }
    }
    container tcam-threshold {
      leaf alarm-frequency {
        type uint32;
      }
    }
    container usb {
      description
        "Disable USB ports";
      leaf disable {
        description
          "Disable USB ports";
        type empty;
      }
    }
    container trace {
      list runtime {
        key "slot bay";
        leaf slot {
          type uint8;
        }
        leaf bay {
          type uint8;
        }
        leaf process {
          type enumeration {
            enum iomd;
          }
        }
        leaf module {
          type enumeration {
            enum all-modules;
          }
        }
        leaf level {
          type enumeration {
            enum info;
          }
        }
      }
    }
    container sslvpn {
      description
        "Command to enable platform dependent mode on sslvpn";
      leaf use-pd {
        description
          "Command to enable platform dependent mode on sslvpn";
        type empty;
      }
    }
    container crft {
      description
        "Crimson function tracking operations";
      leaf collect-on-reload {
        description
          "Collect CRFT native data on reload";
        type empty;
      }
      leaf path {
        description
          "Remote Path for TFTP|FTP|HTTP";
        type string {
          length "1..256";
        }
      }
      leaf tag {
        description
          "TAG, user defined alphanumeric tag for reload archive name";
        type string {
          length "1..128";
        }
      }
      leaf vrf {
        description
          "VRF, forwarding, management or localhost are the only options";
        type string {
          length "1..32";
        }
        must ".='management' or .='forwarding' or .='localhost'" {
          error-message "VRF options include forwarding, management or localhost only";
        }
      }
    }
  }

  leaf flexvpn-bypass-tcam {
    description
      " bypass TCAM for FlexVPN";
    type empty;
  }
  leaf modexp-throttle-window {
    description
      " set modexp throttle window";
    type uint8 {
      range "0..32";
    }
  }

  grouping config-shell-grouping {
    container shell {
      description
        "Configure shell command";
      list trigger {
        description
          "Set shell trigger configuration";
        key "word";
        leaf word {
          type string;
        }
        leaf line {
          type string;
        }
      }
    }
  }

  augment "/ios:native/ios:platform" {
    uses config-platform-grouping;
  }

  augment "/ios:native" {
    uses config-shell-grouping;
  }
}
