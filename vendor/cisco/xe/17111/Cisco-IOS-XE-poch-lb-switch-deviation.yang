module Cisco-IOS-XE-poch-lb-switch-deviation {
  yang-version 1.1;
  namespace "http://cisco.com/ns/yang/Cisco-IOS-XE-poch-lb-switch-deviation";
  prefix ios-poch-lb-switch-;

  import cisco-semver {
    prefix cisco-semver;
  }
  import Cisco-IOS-XE-native {
    prefix ios;
  }
  import Cisco-IOS-XE-ethernet {
    prefix ios-eth;
  }

  organization
    "Cisco Systems";
  description
    "Cisco XE Native Deviation YANG module for IOS
     Copyright (c) 2020-2021 by Cisco Systems, Inc.
     All rights reserved.";

  revision 2022-11-01 {
    description
      "- Update yang-version to 1.1";
  }
  revision 2020-12-21 {
    description
      "Added port-channel lb switch deviation";
  }

  deviation "/ios:native/ios:port-channel/ios-eth:load-balance-hash-algo" {
    deviate not-supported;
  }
}
