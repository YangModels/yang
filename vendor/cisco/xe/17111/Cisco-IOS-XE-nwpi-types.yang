module Cisco-IOS-XE-nwpi-types {
  yang-version 1.1;
  namespace "http://cisco.com/ns/yang/Cisco-IOS-XE-nwpi-types";
  prefix Cisco-IOS-XE-nwpi-types;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Network Wide Path Insight Types.
     Copyright (c) 2020-2022 by Cisco Systems, Inc.
     All rights reserved.";

  revision 2022-11-01 {
    description
      "Update yang-version to 1.1";
    reference
      "1.2.0";
    cisco-semver:module-version "1.2.0";
  }
  revision 2021-07-01 {
    description
      "1, the option to update trace filter without changing trace mode.
       2, added domain info, domain filter and local state define.";
    reference
      "1.1.0";
    cisco-semver:module-version "1.1.0";
  }
  revision 2020-11-01 {
    description
      "Initial revision";
    reference
      "1.0.0";
    cisco-semver:module-version "1.0.0";
  }

  typedef nwpi-action-type {
    type enumeration {
      enum action-start-trace {
        value 0;
        description
          "Start trace";
      }
      enum action-stop-trace {
        value 1;
        description
          "Stop trace";
      }
      enum action-clear-trace {
        value 2;
        description
          "Clear trace data";
      }
      enum action-enable-nwpi {
        value 3;
        description
          "Enable Network Wide Path Insight";
      }
      enum action-disable-nwpi {
        value 4;
        description
          "Disable Network Wide Path Insight";
      }
      enum action-update-policy {
        value 5;
        description
          "Update trace policy";
      }
    }
    description
      "Network Wide Path Insight action type";
  }

  typedef nwpi-target-type {
    type enumeration {
      enum target-vpn-id {
        value 0;
        description
          "SD-WAN VPN identifier type";
      }
      enum target-vrf-name {
        value 1;
        description
          "VRF name type";
      }
    }
    description
      "Network Wide Path Insight target type";
  }

  grouping nwpi-domain-info {
    description
      "Domain information";
    leaf domain-id {
      type uint16;
      description
        "Domain identifier";
    }
    leaf domain-name {
      type string;
      description
        "Domain name";
    }
  }

  grouping nwpi-domain-filter {
    description
      "Internet domain and its host addresses";
    container info {
      description
        "Domain information";
      uses Cisco-IOS-XE-nwpi-types:nwpi-domain-info;
    }
    leaf-list host {
      type inet:ip-address;
      ordered-by user;
      description
        "List of hosts belong to the domain";
    }
  }

  grouping nwpi-local-state {
    description
      "Local trace state";
    leaf-list vpn {
      type uint16;
      ordered-by user;
      description
        "List of VPN where trace is running on";
    }
  }
}
