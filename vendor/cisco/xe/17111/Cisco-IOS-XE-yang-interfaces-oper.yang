module Cisco-IOS-XE-yang-interfaces-oper {
  yang-version 1.1;
  namespace "http://cisco.com/ns/yang/Cisco-IOS-XE-yang-interfaces-oper";
  prefix yang-interfaces-oper;

  import Cisco-IOS-XE-dmi-common-types {
    prefix dmi-common-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Operational data for YANG model-based interfaces.
     Copyright (c) 2021-2022 by Cisco Systems, Inc.
     All rights reserved.";

  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  typedef enm-local-vrf-state {
    type enumeration {
      enum down {
        value 0;
        description
          "Indicates the system is not listening for NETCONF connections on
           local host in the current VRF.";
      }
      enum up {
        value 1;
        description
          "Indicates the system is ready to accept NETCONF connections on
           local host in the current VRF.";
      }
    }
    description
      "List of states of the NETCONF server with respect to connections on
       local host in the current VRF.";
  }

  grouping dmi-ssh-local-vrf-oper {
    description
      "Operational data for NETCONF access on local host in a specific VRF.";
    leaf vrf-name {
      type dmi-common-types:enm-local-vrf-name;
      description
        "Name of the VRF.";
    }
    leaf state {
      type yang-interfaces-oper:enm-local-vrf-state;
      description
        "State of NETCONF server with respect to connections on local host
         is the current VRF.";
    }
  }

  container yang-interfaces-oper-data {
    config false;
    description
      "Configuration for YANG model-based interfaces.";
    list local-vrf {
      key "vrf-name";
      description
        "Operational data for NETCONF access on local host in a specific VRF.";
      uses yang-interfaces-oper:dmi-ssh-local-vrf-oper;
    }
  }
}
