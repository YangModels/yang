module ietf-yang-patch-ann {
  namespace "urn:dummy";
  prefix dummy;

  import tailf-common {
    prefix tailf;
  }

  description
    "Annotation module for ietf-yang-patch.";

  tailf:annotate-module 'ietf-yang-patch' {
    tailf:export rest;
  }
}
