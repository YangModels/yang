module Cisco-IOS-XE-dhcp {
  namespace "http://cisco.com/ns/yang/Cisco-IOS-XE-dhcp";
  prefix ios-dhcp;

  import cisco-semver {
    prefix cisco-semver;
  }
  import ietf-inet-types {
    prefix inet;
  }
  import Cisco-IOS-XE-native {
    prefix ios;
  }
  import Cisco-IOS-XE-types {
    prefix ios-types;
  }
  import Cisco-IOS-XE-interface-common {
    prefix ios-ifc;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Dynamic Host Configuration Protocol (DHCP) Yang model.
     Copyright (c) 2016-2019 by Cisco Systems, Inc.
     All rights reserved.";

  revision 2020-03-01 {
    description
      "- Added constraints and defaults";
    cisco-semver:module-version "2.1.0";
  }
  revision 2019-11-01 {
    description
      "- Added new subnet config";
    cisco-semver:module-version "2.0.0";
  }
  revision 2019-07-01 {
    description
      "- Establish semantic version baseline
       - Added dhcp relay options
       - Added <ipv6 dhcp binding> and <ipv6 dhcp ppp> options
       - dhcp pool utilization mark support";
    cisco-semver:module-version "1.0.0";
  }
  revision 2019-01-25 {
    description
      "Added leaf for App-hosting Gigabit Ethernet interface";
  }
  revision 2018-11-29 {
    description
      "make dhcp snooping changes updated in the netconf datastore";
  }
  revision 2018-11-16 {
    description
      "Cleanup spelling errors in description statements";
  }
  revision 2018-11-05 {
    description
      "Delete intf 'ipv6 dhcp relay destination vrf' before 'vrf forwaring'";
  }
  revision 2018-07-26 {
    description
      "Added some support for interface ipv6 dhcp relay";
  }
  revision 2018-07-25 {
    description
      "Add ip dhcp route";
  }
  revision 2018-07-24 {
    description
      "Fix ip dhcp secondary address and inline lease";
  }
  revision 2018-06-16 {
    description
      "Fix ip dhcp database";
  }
  revision 2018-06-13 {
    description
      "Add more ip dhcp support";
  }
  revision 2018-05-30 {
    description
      "Add ipv6 dhcp relay commands and remove unsupported guard command";
  }
  revision 2018-05-19 {
    description
      "Add dhcp models under ATM interface and sub interface";
  }
  revision 2018-05-17 {
    description
      "Added default-router container support with augmenting the Dialer interface";
  }
  revision 2018-05-11 {
    description
      "allow ip dhcp pool option to remove one ip in rpc";
  }
  revision 2018-05-07 {
    description
      "Add ip dhcp to interface Ethernet";
  }
  revision 2018-03-22 {
    description
      "Fix ip dhcp use vrf connected default behavior";
  }
  revision 2018-03-12 {
    description
      "Add vrf and high-address to the key for ip dhcp excluded-address";
  }
  revision 2018-02-26 {
    description
      "add ip dhcp use support";
  }
  revision 2018-01-16 {
    description
      "Make it take multiple vlans: ip dhcp snooping vlan <num>";
  }
  revision 2018-01-10 {
    description
      "Changed ip dhcp pool / dns-server to cli-flat-list-syntax";
  }
  revision 2017-11-27 {
    description
      "Added Change 25GE name";
  }
  revision 2017-11-14 {
    description
      "Add 100GE interface";
  }
  revision 2017-11-06 {
    description
      "Remove choice for ip dhcp pool / client-identifier and hardware-address";
  }
  revision 2017-11-01 {
    description
      "Add ip dhcp pool / host, client-name, client-identifier, hardware-address";
  }
  revision 2017-10-18 {
    description
      "Add modeling to interface mode: ip dhcp client route distance/track";
  }
  revision 2017-09-14 {
    description
      "This revison has changes for new 2gig interface addition";
  }
  revision 2017-08-16 {
    description
      "This revision has changes for new 5gig and 25gig interfaces addition";
  }
  revision 2017-04-28 {
    description
      "inet:ipv6-prefix changed to ios-types:ipv6-prefix";
  }
  revision 2017-03-02 {
    description
      "Re-arrange the order of vrf in ipv6 dhcp pool";
  }
  revision 2017-02-07 {
    description
      "Initial revision";
  }

  grouping config-interface-ip-dhcp-grouping {
    container client {
      description
        "DHCP client configuration";
      leaf hostname {
        description
          "Specify hostname to use";
        type string;
      }
      container option {
        description
          "DHCP Client options";
        list option-range {
          key "option-range";
          leaf option-range {
            description
              "DHCP option code (1-254)";
            type uint8 {
              range "1..254";
            }
          }
          container option_path {
            leaf hex {
              description
                "Input hex string";
              type string;
            }
            leaf ascii {
              description
                "Input ascii string";
              type string;
            }
            leaf-list ip {
              description
                "Input IP Address";
              type inet:host;
            }
          }
          container option125_path {
            leaf enterprise_id {
              type uint32;
            }
            leaf suboption {
              type uint8 {
                range "1..3";
              }
            }
            leaf ascii {
              description
                "Input ascii string";
              type string;
            }
            leaf hex {
              description
                "Input hex string";
              type string;
            }
          }
        }
      }
      container request {
        description
          "Specify options (not) to request";
        leaf option {
          description
            "DHCP options";
          type uint8 {
            range "1..254";
          }
        }
      }
      container route {
        description
          "Options for routes installed by dhcp";
        leaf distance {
          description
            "set distance for dhcp static routes";
          type uint8 {
            range "1..254";
          }
          default "254";
        }
        leaf track {
          description
            "Track dhcp routes";
          type uint16 {
            range "1..1000";
          }
        }
      }
      container default-router {
        description
          "Set DHCP default router related information";
        leaf distance {
          description
            "Set the DHCP derived default route metric";
          type uint8 {
            range "1..255";
          }
        }
      }
    }
    container server {
      description
        "Configure DHCP server behavior";
      container use {
        description
          "Configure use of options";
        choice client-type {
          container subscriber-id {
            description
              "Configure use of subscriber-id suboption";
            leaf client-id {
              description
                "Use subscriber-id suboption as client-id";
              type empty;
            }
          }
          container hardware-address {
            description
              "Configure use of hardware address";
            leaf client-id {
              description
                "Use hardware address as client-id";
              type empty;
            }
          }
        }
      }
    }
    container relay {
      description
        "DHCP relay configuration parameters";
      container information {
        description
          "DHCP relay information option";
        container check-reply {
          description
            "Validate relay information in BOOTREPLY";
          presence "true";
          leaf none {
            description
              "Set to none";
            type empty;
          }
        }
        container option {
          description
            "DHCP relay information option";
          leaf subscriber-id {
            description
              "Subscriber identifier sub option";
            type string;
          }
        }
        container option-insert {
          description
            "Insert relay information in BOOTREQUEST";
          presence "true";
          leaf none {
            description
              "Set to none";
            type empty;
          }
        }
        leaf policy-action {
          description
            "Define reforwarding policy";
          type enumeration {
            enum "drop";
            enum "encapsulate";
            enum "keep";
            enum "replace";
          }
        }
        leaf trusted {
          description
            "Received DHCP packet may contain relay info option with zero giaddr";
          type empty;
        }
      }
      leaf source-interface {
        description
          "Set source interface for relayed messages";
        type string;
      }
    }
    container snooping {
      description
        "DHCP Snooping";
      container limit {
        description
          "DHCP Snooping limit";
        leaf rate {
          description
            "DHCP Snooping limit";
          type uint16 {
            range "1..2048";
          }
        }
      }
      leaf trust {
        description
          "DHCP Snooping trust config";
        type empty;
      }
      list vlan {
        description
          "DHCP Snooping vlan";
        key "id";
        leaf id {
          type uint16 {
            range "1..4094";
          }
        }
        container information {
          description
            "DHCP Snooping information";
          container option {
            description
              "DHCP Snooping information option";
            container format-type {
              description
                "Option 82 information format";
              container circuit-id {
                description
                  "Circuit id option 82 format";
                leaf string {
                  description
                    "User defined string for circuit id";
                  type string {
                    length "3..63";
                  }
                }
              }
            }
          }
        }
      }
    }
  }

  grouping config-interface-ipv6-dhcp-grouping {
    choice client-server-relay-choice {
      container client {
        description
          "Act as an IPv6 DHCP client";
        container request {
          description
            "Request";
          leaf vendor {
            description
              "Request Vendor specific options";
            type empty;
          }
        }
      }
      list server {
        description
          "Act as an IPv6 DHCP server";
        key "word";
        leaf word {
          type string;
        }
        leaf preference {
          description
            "Preference";
          type uint8 {
            range "0..255";
          }
        }
      }
      container relay {
        description
          "Act as an IPv6 DHCP relay agent";
        container destination {
          description
            "Configure relay destination";
          list address {
            key "ipv6-address";
            leaf ipv6-address {
              description
                "IPv6 Address";
              type inet:ipv6-address;
            }
            leaf interface {
              description
                "Interface for IPv6 relay address";
              type string;
            }
          }
          list vrf {
            key "vrf-name relay-address";
            leaf vrf-name {
              type string;
            }
            leaf relay-address {
              description
                "Relay Agent IPv6 Address";
              type inet:ipv6-address;
            }
            leaf-list relay-interface {
              type string;
            }
          }
          list global {
            key "relay-address";
            leaf relay-address {
              description
                "Relay Agent IPv6 Address";
              type inet:ipv6-address;
            }
            leaf-list relay-interface {
              type string;
            }
          }
        }
        leaf trust {
          description
            "Interface is trusted to process relay-replies";
          type empty;
        }
        container option {
          description
            "Insert options in Relay-forward messages";
          leaf vpn {
            description
              "Insert VSS option in Relay-Forward Messages";
            type empty;
          }
        }
        container source-interface {
          description
            "Insert VSS option in Relay-Forward Messages";
          uses ios-ifc:interface-grouping;
        }
      }
    }
    container guard {
      description
        "Configure IPv6 DHCP guard on the interface";
      presence "true";
      leaf attach-policy {
        description
          "Apply a policy for feature DHCP Guard";
        type string;
      }
    }
  }

  grouping ip-dhcp-grouping {
    container aaa {
      description
        "Configure aaa attributes";
      container default {
        description
          "Specify default values for aaa attributes";
        leaf username {
          description
            "Default username for non-VRF pool subnet request or release";
          type string;
        }
      }
    }
    container bootp {
      description
        "BOOTP specific configuration";
      leaf ignore {
        description
          "Configure this DHCP server to ignore to BOOTP requests.";
        type empty;
      }
    }
    list class {
      description
        "Configure DHCP classes";
      key "id";
      leaf id {
        type string;
      }
      container option {
        description
          "Raw DHCP options";
        list option-list {
          key "option-range";
          leaf option-range {
            description
              "DHCP option code (1-254)";
            type uint8 {
              range "1..254";
            }
          }
          leaf LINE {
            description
              "Specify a regular expression string";
            type string;
          }
          list hex-list {
            key "hex-string";
            leaf hex-string {
              type string;
            }
            leaf mask {
              description
                "Specify a bit mask for the pattern";
              type inet:ipv4-address;
            }
          }
        }
      }
      container relay {
        description
          "Enter relay agent information option configuration submode";
        container agent {
          description
            "Enter relay agent information option configuration submode";
          leaf information {
            description
              "Enter relay agent information option configuration submode";
            type empty;
          }
        }
      }
      leaf remark {
        description
          "Specify a remark for this class";
        type string {
          length "1..240";
        }
      }
    }
    container ping {
      description
        "Specify ping parameters used by DHCP";
      container packets {
        description
          "Specify number of ping packets";
        presence "true";
        leaf number-packets {
          description
            "Number of ping packets (0 disables ping)";
          type uint8 {
            range "0..10";
          }
          default "2";
        }
      }
      leaf timeout {
        description
          "Specify ping timeout";
        type uint16 {
          range "100..10000";
        }
      }
    }
    container conflict {
      description
        "DHCP address conflict parameters";
      leaf logging {
        description
          "Record address conflicts in a log file";
        type boolean;
        default "true";
      }
      container resolution {
        description
          "DHCP address conflict resolution";
        presence "true";
        leaf interval {
          description
            "Time in Minutes";
          type uint32 {
            range "5..1440";
          }
        }
      }
    }
    container excluded-address {
      description
        "Prevent DHCP from assigning certain addresses";
      list low-address-list {
        key "low-address";
        leaf low-address {
          type inet:ipv4-address;
        }
      }
      list low-high-address-list {
        key "low-address high-address";
        leaf low-address {
          type inet:ipv4-address;
        }
        leaf high-address {
          type inet:ipv4-address;
        }
      }
      list vrf-low-address-list {
        key "vrf low-address";
        leaf vrf {
          description
            "VRF name for excluded address range";
          type string;
        }
        leaf low-address {
          type inet:ipv4-address;
        }
      }
      list vrf-low-high-address-list {
        key "vrf low-address high-address";
        leaf vrf {
          description
            "VRF name for excluded address range";
          type string;
        }
        leaf low-address {
          type inet:ipv4-address;
        }
        leaf high-address {
          type inet:ipv4-address;
        }
      }
    }
    container binding {
      description
        "DHCP address bindings";
      container cleanup {
        description
          "Remove expired bindings";
        leaf interval {
          description
            "Time in seconds";
          type uint16 {
            range "10..600";
          }
        }
      }
    }
    container database {
      description
        "Configure DHCP database agents";
      list resource {
        description
          "Uniform Resource Locator (URL)";
        key "resource-locator";
        leaf resource-locator {
          description
            "Uniform Resource Locator (URL)";
          type string;
        }
        leaf write-delay {
          description
            "Set the database write delay";
          type uint32 {
            range "60..4294967295";
          }
        }
        leaf timeout {
          description
            "Set the database transfer timeout";
          type uint16 {
            range "0..3600";
          }
        }
      }
    }
    container limit {
      description
        "Limit DHCP Lease";
      container lease {
        description
          "DHCP lease";
        leaf log {
          description
            "Limit DHCP Lease";
          type empty;
        }
        container per {
          description
            "per";
          leaf interface {
            description
              "interface";
            type uint16 {
              range "1..65535";
            }
          }
        }
      }
    }
    container subscriber-id {
      description
        "Global subscriber-id configuration";
      leaf interface-name {
        description
          "Use interface short-name";
        type empty;
      }
    }
    container route {
      description
        "Specify the type of routes for clients on unnumbered interfaces";
      leaf route {
        type enumeration {
          enum "connected";
          enum "static";
        }
        default "static";
      }
    }
    container relay {
      description
        "DHCP relay agent parameters";
      container information {
        description
          "Relay agent information option";
        leaf trust-all {
          description
            "Received DHCP packets may contain relay info option with zero giaddr";
          type empty;
        }
        container option {
          description
            "Insert relay information in BOOTREQUEST";
          leaf option-default {
            description
              "Default option, no vpn";
            type empty;
          }
          leaf vpn {
            description
              "Insert VPN sub-options and change the giaddr to the outgoing interface";
            type empty;
          }
        }
      }
    }
    list pool {
      description
        "Configure DHCP address pools";
      key "id";
      leaf id {
        type string;
      }
      container subnet {
        description
          "Subnet";
        leaf prefix-length {
          description
            "prefix length of subnet";
          type uint8 {
            range "1..32";
          }
        }
      }
      list address {
        description
          "ip address";
        must "../network/primary-network";
        key "ip";
        leaf ip {
          description
            "IP address";
          type inet:ipv4-address;
        }
        leaf client-id {
          description
            "Client ID for which address has to be assigned";
          type string;
        }
        leaf ascii {
          description
            "If the value given is ascii";
          type empty;
        }
      }
      container option {
        description
          "Raw DHCP options";
        list option-range {
          key "option-range";
          leaf option-range {
            description
              "DHCP option code";
            type uint8 {
              range "0..254";
            }
          }
          choice option-range-choice {
            case ascii-case {
              leaf ascii-new {
                description
                  "Data is an NVT ASCII string";
                type string {
                  length "1..225";
                }
              }
            }
            case hex-case {
              container hex-new {
                description
                  "Data is a hexadecimal string";
                leaf hex-line {
                  description
                    "Hexadecimal string, truncated to 180 hex characters entered";
                  type string {
                    length "1..180";
                  }
                }
                leaf none-new {
                  description
                    "No data";
                  type empty;
                }
              }
            }
            case ip-case {
              leaf-list ip-new {
                description
                  "Data is one or more IP addresses";
                type inet:host;
              }
            }
          }
          leaf ascii {
            description
              "Data is an NVT ASCII string";
            status deprecated;
            type string {
              length "1..225";
            }
          }
          container hex {
            description
              "Data is a hexadecimal string";
            status deprecated;
            leaf hex-line {
              status deprecated;
              description
                "Hexadecimal string, truncated to 180 hex characters entered";
              type string {
                length "1..180";
              }
            }
            leaf none {
              description
                "No data";
              status deprecated;
              type empty;
            }
          }
          leaf-list ip {
            description
              "Data is one or more IP addresses";
            status deprecated;
            type inet:host;
          }
        }
      }
      list class {
        description
          "Specify a DHCP class";
        key "name";
        leaf name {
          description
            "DHCP class name";
          type string;
        }
        container import {
          description
            "Programmatically importing DHCP option parameters";
          container interface {
            description
              "Specify interface to import options from";
            uses ios-ifc:interface-grouping;
          }
        }
        container option {
          description
            "DHCP option";
          leaf option {
            description
              "Options";
            type uint8 {
              range "1..254";
            }
          }
          leaf ascii {
            description
              "Data is an NVT ASCII string";
            type string;
          }
          leaf hex {
            description
              "Input hex string";
            type string;
          }
          leaf-list ip {
            description
              "Input IP Address";
            type inet:host;
          }
          container ext {
            leaf option {
              description
                "Options";
              type uint8 {
                range "1..254";
              }
            }
            leaf ascii {
              description
                "Data is an NVT ASCII string";
              type string;
            }
            leaf hex {
              description
                "Input hex string";
              type string;
            }
          }
        }
        container address {
          description
            "Specify an address range for this class";
          container range {
            leaf ipv4-start {
              description
                "Start IP address";
              type inet:ipv4-address;
            }
            leaf ipv4-end {
              description
                "End IP address";
              type inet:ipv4-address;
            }
          }
        }
      }
      leaf vrf {
        description
          "Associate this pool with a VRF";
        type string;
      }
      container lease {
        description
          "Address lease time";
        choice lease {
          container lease-value {
            description
              "lease in numbers";
            leaf days {
              description
                "Days";
              type uint16 {
                range "0..365";
              }
            }
            leaf hours {
              description
                "Hours";
              when "../days";
              type uint8 {
                range "0..23";
              }
            }
            leaf minutes {
              description
                "Minutes";
              when "../hours";
              type uint8 {
                range "0..59";
              }
            }
          }
          leaf infinite {
            description
              "Infinite lease";
            type empty;
          }
        }
      }
      container default-router {
        leaf-list default-router-list {
          description
            "Default routers";
          type union {
            type inet:ipv4-address;
            type string;
          }
        }
      }
      container utilization {
        description
          "Configure various utilization commands";
        container mark {
          description
            "Configure thresholds for subnet release or request";
          container high {
            description
              "Specify high utilization mark of the pool";
            leaf high-value {
              description
                "Specify high utilization mark of the pool";
              type uint8 {
                range "1..100";
              }
              must "(not (../../low/low-value)) or (current() > ../../low/low-value)" {
                error-message "High utilization must be greater than low utilization percentage.";
              }
            }
            leaf log {
              description
                "Log a system message when high/low state is detected";
              type empty;
            }
          }
          container low {
            description
              "Specify low utilization mark of the pool";
            leaf low-value {
              description
                "Specify low utilization mark of the pool";
              type uint8 {
                range "1..100";
              }
              must "(not (../../high/high-value)) or(current() < ../../high/high-value)" {
                error-message "Low utilization must be less than high utilization percentage.";
              }
            }
            leaf log {
              description
                "Log a system message when high/low state is detected";
              type empty;
            }
          }
        }
      }
      container dns-server {
        leaf-list dns-server-list {
          description
            "DNS servers";
          type union {
            type inet:ipv4-address;
            type string;
          }
        }
      }
      leaf domain-name {
        description
          "Domain name";
        type string;
      }
      container network {
        description
          "Network number and mask";
        container primary-network {
          description
            "Network number and mask";
          leaf number {
            description
              "Network number";
            type inet:ipv4-address;
          }
          leaf mask {
            description
              "Network mask";
            type union {
              type string;
              type inet:ipv4-address;
            }
          }
        }
        list secondary-network {
          description
            "Secondary number and mask";
          key "number";
          leaf number {
            description
              "Network number";
            type inet:ipv4-address;
          }
          leaf mask {
            description
              "Secondary mask";
            type union {
              type string;
              type inet:ipv4-address;
            }
          }
          leaf secondary {
            description
              "Configure as secondary subnet";
            type empty;
          }
        }
      }
      container host {
        description
          "Client IP address and mask";
        leaf number {
          type inet:ipv4-address;
        }
        leaf mask {
          type inet:ipv4-address;
        }
      }
      choice hardware-addr-cient-id-choice {
        container hardware-address {
          description
            "Client hardware address";
          leaf hardware-address-val {
            description
              "Dotted-hexadecimal string (aabb.ccdd.eeff ...)";
            type ios-types:cisco-mac-address-type;
          }
        }
        leaf client-identifier {
          description
            "Client identifier, Dotted-hexadecimal string (aabb.ccdd.eeff ...)";
          type string;
        }
      }
      leaf client-name {
        description
          "Client name, Client name (domain should not be included)";
        type string;
      }
    }
    leaf smart-relay {
      description
        "Enable Smart Relay feature";
      type empty;
    }
    leaf snooping {
      description
        "DHCP Snooping";
      type empty;
    }
    container snooping-conf {
      container snooping {
        description
          "DHCP Snooping";
        container database {
          description
            "DHCP snooping database agent";
          leaf url {
            type string;
          }
          leaf timeout {
            description
              "Configure abort timeout interval";
            type uint32 {
              range "0..86400";
            }
          }
          leaf write-delay {
            description
              "Configure delay timer for writes to URL";
            type uint32 {
              range "15..86400";
            }
          }
        }
        leaf glean {
          description
            "DHCP read only snooping";
          type empty;
        }
        container information {
          description
            "DHCP Snooping information";
          leaf option {
            type boolean;
            default "true";
          }
          container options {
            container option {
              description
                "DHCP Snooping information option";
              leaf allow-untrusted {
                description
                  "DHCP Snooping information option allow-untrusted";
                type empty;
              }
              container format {
                description
                  "Option 82 information format";
                container remote-id {
                  description
                    "Remote id option 82 format";
                  choice remote-id-choice {
                    leaf hostname {
                      description
                        "Use configured hostname for remote id";
                      type empty;
                    }
                    leaf string {
                      description
                        "User defined string for remote id";
                      type string;
                    }
                  }
                }
              }
            }
          }
        }
        container track {
          description
            "DHCP snooping track";
          leaf host {
            description
              "DHCP snooping track host";
            type empty;
          }
        }
        container verify {
          description
            "DHCP snooping verify";
          leaf mac-address {
            description
              "DHCP snooping verify mac-address";
            type empty;
          }
          leaf no-relay-agent-address {
            description
              "DHCP snooping verify giaddr";
            type empty;
          }
        }
        list vlan {
          description
            "DHCP Snooping vlan";
          key "id";
          leaf id {
            type uint16 {
              range "1..4094";
            }
          }
        }
        container wireless {
          description
            "DHCP snooping wireless";
          container bootp-broadcast {
            description
              "DHCP snooping wireless bootp-broadcast";
            leaf enable {
              description
                "DHCP snooping wireless bootp-broadcast enable";
              type empty;
            }
          }
        }
      }
    }
    container use {
      description
        "Configure use of certain parameters during allocation";
      choice client-type {
        container subscriber-id {
          leaf client-id {
            description
              "Use subscriber-id suboption as client-id";
            type empty;
          }
        }
        container hardware-address {
          description
            "Configure use of hardware address (i.e., MAC)";
          leaf client-id {
            description
              "Use hardware address as client-id";
            type empty;
          }
        }
      }
      container class {
        presence "true";
        leaf aaa {
          description
            "Configure use of aaa to get class";
          type empty;
        }
      }
      container vrf {
        description
          "Ignore or use receiving interface VRF";
        leaf connected {
          description
            "Use input interface VRF when servicing connected clients";
          type boolean;
          default "true";
        }
        leaf remote {
          description
            "Use input interface VRF when servicing remote clients";
          type empty;
        }
      }
    }
  }

  grouping ipv6-dhcp-grouping {
    container server {
      description
        "Configure IPv6 DHCP server";
      container vrf {
        description
          "Enable VRF Awareness on server";
        leaf enable {
          description
            "Enable Address/PD allocation based on VRF";
          type empty;
        }
      }
    }
    container guard {
      description
        "Configure IPv6 DHCP guard";
      list policy {
        description
          "Configure a policy for feature dhcp guard";
        key "dhcp-guard-policy-name";
        leaf dhcp-guard-policy-name {
          type string;
        }
        container device-role {
          description
            "Sets the role of the device attached to the port";
          leaf server {
            description
              "Attached device is a dhcp server";
            type empty;
          }
          leaf client {
            description
              "Attached device is a client (default)";
            type empty;
          }
        }
        container match {
          description
            "dhcp filtering";
          container server {
            description
              "permitted server source addresses";
            leaf access-list {
              description
                "specify access-list for match";
              type string;
            }
          }
        }
      }
    }
    list pool {
      description
        "Configure IPv6 DHCP pool";
      key "name";
      leaf name {
        description
          "DHCP pool name";
        type string;
      }
      leaf vrf {
        description
          "VRF name";
        type string;
      }
      container address {
        description
          "IPv6 address allocation";
        list prefix {
          description
            "IPv6 address allocation prefix";
          key "ipv6-address";
          leaf ipv6-address {
            type ios-types:ipv6-prefix;
          }
          container lifetime {
            description
              "Configure prefix lifetimes";
            leaf valid-lifetime {
              type union {
                type uint32 {
                  range "0 .. 4294967295";
                }
                type enumeration {
                  enum "infinite";
                }
              }
            }
            leaf preferred-lifetime {
              type union {
                type uint32 {
                  range "0 .. 4294967295";
                }
                type enumeration {
                  enum "infinite";
                }
              }
            }
          }
        }
      }
      leaf-list dns-server {
        description
          "Server's name or IPv6 address";
        type union {
          type inet:ipv6-address;
          type string;
        }
      }
      leaf domain-name {
        description
          "Domain name to complete unqualified host names";
        type string;
      }
      container import {
        description
          "Programmatically importing DHCP option parameters";
        leaf all {
          description
            "all DHCP options";
          type empty;
        }
        container interface {
          description
            "Specify interface to import options from";
          uses ios-ifc:interface-grouping;
        }
      }
      list link-address {
        description
          "Link-address to match";
        key "address";
        leaf address {
          type ios-types:ipv6-prefix;
        }
      }
      leaf bootfile-url {
        description
          "Boot file url";
        type string;
      }
    }
    container binding {
      description
        "Configure IPv6 DHCP binding parameters";
      container track {
        description
          "Track bindings associated with a virtual interface";
        leaf ppp {
          description
            "Clear bindings when PPP session goes down";
          type empty;
        }
      }
    }
    container ppp {
      description
        "PPP specific commands";
      container framed-prefix {
        description
          "Framed ipv6 prefix specific commands";
        leaf cache {
          description
            "Cache the Framed-IPv6 address for PPP sessions";
          type boolean;
        }
      }
      leaf terminate {
        description
          "Terminate a PPP session when prefix is not available";
        type boolean;
      }
    }
  }

  grouping ipv6-dhcp-relay-grouping {
    container bulk-lease {
      description
        "Configure IPv6 DHCP Bulk Lease Query";
      leaf disable {
        description
          "Disable bulk lease query";
        type empty;
      }
    }
    leaf source-interface {
      description
        "Set source interface for relayed messages";
      type string;
    }
    leaf trust-all {
      description
        "All interfaces are trusted to process relay-replies";
      type boolean;
    }
  }

  augment "/ios:native/ios:ip/ios:dhcp" {
    uses ip-dhcp-grouping;
  }
  augment "/ios:native/ios:ipv6/ios:dhcp" {
    uses ipv6-dhcp-grouping;
  }
  augment "/ios:native/ios:ipv6/ios:dhcp-relay" {
    uses ipv6-dhcp-relay-grouping;
  }
  augment "/ios:native/ios:interface/ios:Ethernet/ios:ip/ios:dhcp" {
    uses config-interface-ip-dhcp-grouping;
  }
  augment "/ios:native/ios:interface/ios:FastEthernet/ios:ip/ios:dhcp" {
    uses config-interface-ip-dhcp-grouping;
  }
  augment "/ios:native/ios:interface/ios:GigabitEthernet/ios:ip/ios:dhcp" {
    uses config-interface-ip-dhcp-grouping;
  }
  augment "/ios:native/ios:interface/ios:TenGigabitEthernet/ios:ip/ios:dhcp" {
    uses config-interface-ip-dhcp-grouping;
  }
  augment "/ios:native/ios:interface/ios:FiveGigabitEthernet/ios:ip/ios:dhcp" {
    uses config-interface-ip-dhcp-grouping;
  }
  augment "/ios:native/ios:interface/ios:AppGigabitEthernet/ios:ip/ios:dhcp" {
    uses config-interface-ip-dhcp-grouping;
  }
  augment "/ios:native/ios:interface/ios:TwentyFiveGigE/ios:ip/ios:dhcp" {
    uses config-interface-ip-dhcp-grouping;
  }
  augment "/ios:native/ios:interface/ios:TwoGigabitEthernet/ios:ip/ios:dhcp" {
    uses config-interface-ip-dhcp-grouping;
  }
  augment "/ios:native/ios:interface/ios:FortyGigabitEthernet/ios:ip/ios:dhcp" {
    uses config-interface-ip-dhcp-grouping;
  }
  augment "/ios:native/ios:interface/ios:HundredGigE/ios:ip/ios:dhcp" {
    uses config-interface-ip-dhcp-grouping;
  }
  augment "/ios:native/ios:interface/ios:Port-channel/ios:ip/ios:dhcp" {
    uses config-interface-ip-dhcp-grouping;
  }
  augment "/ios:native/ios:interface/ios:Loopback/ios:ip/ios:dhcp" {
    uses config-interface-ip-dhcp-grouping;
  }
  augment "/ios:native/ios:interface/ios:Tunnel/ios:ip/ios:dhcp" {
    uses config-interface-ip-dhcp-grouping;
  }
  augment "/ios:native/ios:interface/ios:Vlan/ios:ip/ios:dhcp" {
    uses config-interface-ip-dhcp-grouping;
  }
  augment "/ios:native/ios:interface/ios:Dialer/ios:ip/ios:dhcp" {
    uses config-interface-ip-dhcp-grouping;
  }
  augment "/ios:native/ios:interface/ios:vasileft/ios:ip/ios:dhcp" {
    uses config-interface-ip-dhcp-grouping;
  }
  augment "/ios:native/ios:interface/ios:vasiright/ios:ip/ios:dhcp" {
    uses config-interface-ip-dhcp-grouping;
  }
  augment "/ios:native/ios:interface/ios:ATM/ios:ip/ios:dhcp" {
    uses config-interface-ip-dhcp-grouping;
  }
  augment "/ios:native/ios:interface/ios:ATM-subinterface/ios:ATM/ios:ip/ios:dhcp" {
    uses config-interface-ip-dhcp-grouping;
  }
  augment "/ios:native/ios:interface/ios:FastEthernet/ios:ipv6/ios:dhcp" {
    uses config-interface-ipv6-dhcp-grouping;
  }
  augment "/ios:native/ios:interface/ios:GigabitEthernet/ios:ipv6/ios:dhcp" {
    uses config-interface-ipv6-dhcp-grouping;
  }
  augment "/ios:native/ios:interface/ios:TenGigabitEthernet/ios:ipv6/ios:dhcp" {
    uses config-interface-ipv6-dhcp-grouping;
  }
  augment "/ios:native/ios:interface/ios:FiveGigabitEthernet/ios:ipv6/ios:dhcp" {
    uses config-interface-ipv6-dhcp-grouping;
  }
  augment "/ios:native/ios:interface/ios:AppGigabitEthernet/ios:ipv6/ios:dhcp" {
    uses config-interface-ipv6-dhcp-grouping;
  }
  augment "/ios:native/ios:interface/ios:TwentyFiveGigE/ios:ipv6/ios:dhcp" {
    uses config-interface-ipv6-dhcp-grouping;
  }
  augment "/ios:native/ios:interface/ios:TwoGigabitEthernet/ios:ipv6/ios:dhcp" {
    uses config-interface-ipv6-dhcp-grouping;
  }
  augment "/ios:native/ios:interface/ios:FortyGigabitEthernet/ios:ipv6/ios:dhcp" {
    uses config-interface-ipv6-dhcp-grouping;
  }
  augment "/ios:native/ios:interface/ios:HundredGigE/ios:ipv6/ios:dhcp" {
    uses config-interface-ipv6-dhcp-grouping;
  }
  augment "/ios:native/ios:interface/ios:Port-channel/ios:ipv6/ios:dhcp" {
    uses config-interface-ipv6-dhcp-grouping;
  }
  augment "/ios:native/ios:interface/ios:Loopback/ios:ipv6/ios:dhcp" {
    uses config-interface-ipv6-dhcp-grouping;
  }
  augment "/ios:native/ios:interface/ios:Tunnel/ios:ipv6/ios:dhcp" {
    uses config-interface-ipv6-dhcp-grouping;
  }
  augment "/ios:native/ios:interface/ios:Vlan/ios:ipv6/ios:dhcp" {
    uses config-interface-ipv6-dhcp-grouping;
  }
  augment "/ios:native/ios:interface/ios:vasileft/ios:ipv6/ios:dhcp" {
    uses config-interface-ipv6-dhcp-grouping;
  }
  augment "/ios:native/ios:interface/ios:vasiright/ios:ipv6/ios:dhcp" {
    uses config-interface-ipv6-dhcp-grouping;
  }
  augment "/ios:native/ios:interface/ios:ATM/ios:ipv6/ios:dhcp" {
    uses config-interface-ipv6-dhcp-grouping;
  }
  augment "/ios:native/ios:interface/ios:ATM-subinterface/ios:ATM/ios:ipv6/ios:dhcp" {
    uses config-interface-ipv6-dhcp-grouping;
  }
}
