/*
 * Generated by confdc --mib2yang-std
 * Source: mgmt/dmi/model/mib/src/CISCO-FIREWALL-TC.mib
 */
/*
 * This YANG module has been generated by smidump 0.5.0:
 *
 *      smidump -f yang CISCO-FIREWALL-TC
 *
 * Do not edit. Edit the source file instead!
 */

module CISCO-FIREWALL-TC {

  namespace "urn:ietf:params:xml:ns:yang:smiv2:CISCO-FIREWALL-TC";
  prefix CISCO-FIREWALL-TC;

  import ietf-yang-smiv2 {
    prefix "smiv2";
  }

  organization
   "Cisco Systems Inc.";

  contact
   "       Cisco Systems
    Customer Service
    
    Postal: 170 W Tasman Drive
    San Jose, CA  95134
    USA
    
    Tel: +1 800 553-NETS
    E-mail: cs-firewalls@cisco.com";

  description
   "This MIB module defines textual conventions that
    are commonly used in modeling management information 
    pertaining to configuration, status and activity
    of firewalls.";

  revision 2006-03-03 {
    description
     "Initial version of this module.";
  }

  typedef CFWNetworkProtocol {
    type enumeration {
      enum "none" {
        value "1";
      }
      enum "other" {
        value "2";
      }
      enum "ip" {
        value "3";
      }
      enum "icmp" {
        value "4";
      }
      enum "gre" {
        value "5";
      }
      enum "udp" {
        value "6";
      }
      enum "tcp" {
        value "7";
      }
    }
    description
     "This type denotes protocols operating at 
      layers 3 or 4 of Open System Interconnection (OSI)
      model.
      
      The following values are defined:
      
      'none'
          Denotes the semantics of 'not applicable'.
      
      'other'
          Denotes any protocol not listed.
      
      'ip'
          Denotes Internet Protocol (IP).
      
      'icmp'
          Denotes Internet Control Message
          Protocol.
      
      'gre'
          Denotes Generic Route Encapsulation
          protocol.
      
      'udp'
          Denotes User Datagram Protocol.
      
      'tcp'
          Denotes Transmission Control Protocol.";
  }

  typedef CFWApplicationProtocol {
    type enumeration {
      enum "none" {
        value "1";
      }
      enum "other" {
        value "2";
      }
      enum "ftp" {
        value "3";
      }
      enum "telnet" {
        value "4";
      }
      enum "smtp" {
        value "5";
      }
      enum "http" {
        value "6";
      }
      enum "tacacs" {
        value "7";
      }
      enum "dns" {
        value "8";
      }
      enum "sqlnet" {
        value "9";
      }
      enum "https" {
        value "10";
      }
      enum "tftp" {
        value "11";
      }
      enum "gopher" {
        value "12";
      }
      enum "finger" {
        value "13";
      }
      enum "kerberos" {
        value "14";
      }
      enum "pop2" {
        value "15";
      }
      enum "pop3" {
        value "16";
      }
      enum "sunRpc" {
        value "17";
      }
      enum "msRpc" {
        value "18";
      }
      enum "nntp" {
        value "19";
      }
      enum "snmp" {
        value "20";
      }
      enum "imap" {
        value "21";
      }
      enum "ldap" {
        value "22";
      }
      enum "exec" {
        value "23";
      }
      enum "login" {
        value "24";
      }
      enum "shell" {
        value "25";
      }
      enum "msSql" {
        value "26";
      }
      enum "sybaseSql" {
        value "27";
      }
      enum "nfs" {
        value "28";
      }
      enum "lotusnote" {
        value "29";
      }
      enum "h323" {
        value "30";
      }
      enum "cuseeme" {
        value "31";
      }
      enum "realmedia" {
        value "32";
      }
      enum "netshow" {
        value "33";
      }
      enum "streamworks" {
        value "34";
      }
      enum "vdolive" {
        value "35";
      }
      enum "sap" {
        value "36";
      }
      enum "sip" {
        value "37";
      }
      enum "mgcp" {
        value "38";
      }
      enum "rtsp" {
        value "39";
      }
      enum "skinny" {
        value "40";
      }
      enum "gtpV0" {
        value "41";
      }
      enum "gtpV1" {
        value "42";
      }
      enum "echo" {
        value "43";
      }
      enum "discard" {
        value "44";
      }
      enum "daytime" {
        value "45";
      }
      enum "netstat" {
        value "46";
      }
      enum "ssh" {
        value "47";
      }
      enum "time" {
        value "48";
      }
      enum "tacacsDs" {
        value "49";
      }
      enum "bootps" {
        value "50";
      }
      enum "bootpc" {
        value "51";
      }
      enum "dnsix" {
        value "52";
      }
      enum "rtelnet" {
        value "53";
      }
      enum "ident" {
        value "54";
      }
      enum "sqlServ" {
        value "55";
      }
      enum "ntp" {
        value "56";
      }
      enum "pwdgen" {
        value "57";
      }
      enum "ciscoFna" {
        value "58";
      }
      enum "ciscoTna" {
        value "59";
      }
      enum "ciscoSys" {
        value "60";
      }
      enum "netbiosNs" {
        value "61";
      }
      enum "netbiosDgm" {
        value "62";
      }
      enum "netbiosSsn" {
        value "63";
      }
      enum "sqlSrv" {
        value "64";
      }
      enum "snmpTrap" {
        value "65";
      }
      enum "rsvd" {
        value "66";
      }
      enum "send" {
        value "67";
      }
      enum "xdmcp" {
        value "68";
      }
      enum "bgp" {
        value "69";
      }
      enum "irc" {
        value "70";
      }
      enum "qmtp" {
        value "71";
      }
      enum "ipx" {
        value "72";
      }
      enum "dbase" {
        value "73";
      }
      enum "imap3" {
        value "74";
      }
      enum "rsvpTunnel" {
        value "75";
      }
      enum "hpCollector" {
        value "76";
      }
      enum "hpManagedNode" {
        value "77";
      }
      enum "hpAlarmMgr" {
        value "78";
      }
      enum "microsoftDs" {
        value "79";
      }
      enum "creativeServer" {
        value "80";
      }
      enum "creativePartnr" {
        value "81";
      }
      enum "appleQtc" {
        value "82";
      }
      enum "igmpV3Lite" {
        value "83";
      }
      enum "isakmp" {
        value "84";
      }
      enum "biff" {
        value "85";
      }
      enum "who" {
        value "86";
      }
      enum "syslog" {
        value "87";
      }
      enum "router" {
        value "88";
      }
      enum "ncp" {
        value "89";
      }
      enum "timed" {
        value "90";
      }
      enum "ircServ" {
        value "91";
      }
      enum "uucp" {
        value "92";
      }
      enum "syslogConn" {
        value "93";
      }
      enum "sshell" {
        value "94";
      }
      enum "ldaps" {
        value "95";
      }
      enum "dhcpFailover" {
        value "96";
      }
      enum "msexchRouting" {
        value "97";
      }
      enum "entrustSvcs" {
        value "98";
      }
      enum "entrustSvcHandler" {
        value "99";
      }
      enum "ciscoTdp" {
        value "100";
      }
      enum "webster" {
        value "101";
      }
      enum "gdoi" {
        value "102";
      }
      enum "iscsi" {
        value "103";
      }
      enum "cddbp" {
        value "104";
      }
      enum "ftps" {
        value "105";
      }
      enum "telnets" {
        value "106";
      }
      enum "imaps" {
        value "107";
      }
      enum "ircs" {
        value "108";
      }
      enum "pop3s" {
        value "109";
      }
      enum "socks" {
        value "110";
      }
      enum "kazaa" {
        value "111";
      }
      enum "msSqlM" {
        value "112";
      }
      enum "msSna" {
        value "113";
      }
      enum "wins" {
        value "114";
      }
      enum "ica" {
        value "115";
      }
      enum "orasrv" {
        value "116";
      }
      enum "rdbDbsDisp" {
        value "117";
      }
      enum "vqp" {
        value "118";
      }
      enum "icabrowser" {
        value "119";
      }
      enum "kermit" {
        value "120";
      }
      enum "rsvpEncap" {
        value "121";
      }
      enum "l2tp" {
        value "122";
      }
      enum "pptp" {
        value "123";
      }
      enum "h323Gatestat" {
        value "124";
      }
      enum "rWinsock" {
        value "125";
      }
      enum "radius" {
        value "126";
      }
      enum "hsrp" {
        value "127";
      }
      enum "net8Cman" {
        value "128";
      }
      enum "oracleEmVp" {
        value "129";
      }
      enum "oracleNames" {
        value "130";
      }
      enum "oracle" {
        value "131";
      }
      enum "ciscoSvcs" {
        value "132";
      }
      enum "ciscoNetMgmt" {
        value "133";
      }
      enum "stun" {
        value "134";
      }
      enum "trRsrb" {
        value "135";
      }
      enum "ddnsV3" {
        value "136";
      }
      enum "aceSvr" {
        value "137";
      }
      enum "giop" {
        value "138";
      }
      enum "ttc" {
        value "139";
      }
      enum "ipass" {
        value "140";
      }
      enum "clp" {
        value "141";
      }
      enum "citrixImaClient" {
        value "142";
      }
      enum "sms" {
        value "143";
      }
      enum "citrix" {
        value "144";
      }
      enum "realSecure" {
        value "145";
      }
      enum "lotusMtap" {
        value "146";
      }
      enum "cifs" {
        value "147";
      }
      enum "msDotnetster" {
        value "148";
      }
      enum "tarantella" {
        value "149";
      }
      enum "fcipPort" {
        value "150";
      }
      enum "ssp" {
        value "151";
      }
      enum "iscsiTarget" {
        value "152";
      }
      enum "mySql" {
        value "153";
      }
      enum "msClusterNet" {
        value "154";
      }
      enum "ldapAdmin" {
        value "155";
      }
      enum "ieee80211Iapp" {
        value "156";
      }
      enum "oemAgent" {
        value "157";
      }
      enum "rtcPmPort" {
        value "158";
      }
      enum "dbControlAgent" {
        value "159";
      }
      enum "ipsecMsft" {
        value "160";
      }
      enum "sipTls" {
        value "161";
      }
      enum "aim" {
        value "162";
      }
      enum "pcAnyWhereData" {
        value "163";
      }
      enum "pcAnyWhereStat" {
        value "164";
      }
      enum "x11" {
        value "165";
      }
      enum "ircu" {
        value "166";
      }
      enum "n2h2Server" {
        value "167";
      }
      enum "h323CallSigAlt" {
        value "168";
      }
      enum "yahooMsgr" {
        value "169";
      }
      enum "msnMsgr" {
        value "170";
      }
    }
    description
     "This type denotes the application (OSI Layer 7)
      protocol/service corresponding to a firewall session
      or a connection.
      
      Description of constants of this type
      
      'none'
          Denotes the semantics of 'not applicable'.
      
      'other'
          Denotes any protocol not listed.";
    reference
     "The protocols enumerated in this textual convention
      may be correlated with the information on protocols/
      services defined by Internet Assigned Numbers Authority
      (IANA) found at 
      
      http://www.iana.com/assignments/port-numbers";
  }

  typedef CFWPolicy {
    type binary {
      length "0..128";
    }
    description
     "This type denotes the identity of a policy
      enforced by the firewall. In the context of firewalls,
      only security policies are relevant.
      
      Objects of this type must comprise printable,
      human readable ASCII characters. A zero length
      string is used to denote a 'null' policy.
      
      An example of a policy is the 'policy-map' entity
      configured using the Modular Policy Command
      framework.";
  }

  typedef CFWPolicyTarget {
    type binary {
      length "0..128";
    }
    description
     "In the context of policy management, the term 
      target refers to an entity on the managed device 
      to which the policy is applied thereby enforcing
      the policy on the traffic stream(s) associated 
      with the entity.
      
      The type 'CFWPolicyTarget' denotes the identity of
      a policy target. Examples of policy targets include
      interfaces, security zones, users, user groups and
      virtual contexts.
      
      Objects of this type must comprise printable,
      human readable ASCII characters. A zero length
      string is used to denote a 'null' target.";
  }

  typedef CFWPolicyTargetType {
    type enumeration {
      enum "all" {
        value "1";
      }
      enum "other" {
        value "2";
      }
      enum "interface" {
        value "3";
      }
      enum "zone" {
        value "4";
      }
      enum "zonepair" {
        value "5";
      }
      enum "user" {
        value "6";
      }
      enum "usergroup" {
        value "7";
      }
      enum "context" {
        value "8";
      }
    }
    description
     "This type is used to represent the type of 
      a policy target.
      
      The following values are defined:
      
      'all'
          Certain firewall implementations allow policies
          to be applied on all applicable targets. (Such
          policies are termed 'global'). The target type
          'all' denotes the set of all applicable
          targets.
      
      'other'
          Denotes an entity type that has yet not been
          classified in one of the other types. This
          value is useful in accomodating new target types
          before the textual convention is revised to 
          include them.
      
      'interface'
          The policy target is an interface of the managed 
          device.
      
      'zone'
          The policy target is a zone, where a zone is
          is a collection of interfaces of the managed 
          device.
      
      'zonepair'
          The policy target is a pair of zones.
      
      'user'
          Denotes the identity of a user who is 
          authorized to access the firewall itself or 
          the resources protected by the firewall.
      
      'usergroup'
          Denotes the identity of a user group.
          User group denotes a collection of user
          identities, as defined above.
      
      'context'
          Denotes a logical device defined in the managed
          device with a distinct management context. 
          Examples of such logical devices include
          virtual contexts defined by Firewall Service
          Module, virtual sensors defined by Intrusion
          Detection Service Module and Virtual Routing
          and Forwarding (VRFs) defined by IOS.";
  }

  typedef CFWUrlfVendorId {
    type enumeration {
      enum "other" {
        value "1";
      }
      enum "websense" {
        value "2";
      }
      enum "n2h2" {
        value "3";
      }
    }
    description
     "This type denotes the vendor of a URL filtering
      server which the firewall uses to implement URL
      filtering. 
      
      A URL filtering server provides a database of URLs
      with appropriate access restrictions (e.g., 
      deny or permit). Various security devices can make
      use of these filtering servers to provide URL filtering
      functionality to the users.
      
      The following values are defined:
      
      'other' 
          Other type of URL filtering servers than those
          specified below.
      
      'websense'
          Websense URL filtering server. One of the products
          provided by Websense is a Web Filtering Server. 
          More information about Websense Web Filtering
          product can be found at http://www.websense.com
      
      'n2h2'
          N2H2 URL filtering server. More information about
          N2H2 Filtering product can be found at
          http://www.n2h2.com";
  }

  typedef CFWUrlServerStatus {
    type enumeration {
      enum "online" {
        value "1";
      }
      enum "offline" {
        value "2";
      }
      enum "indeterminate" {
        value "3";
      }
    }
    description
     "This type denotes the status of the URL filtering 
      server which the firewall uses to implement URL
      filtering.
      
      The following values are defined:
      
      'online' 
          Indicates that the Server is online
      
      'offline'
          Indicates that the Server is offline
      
      'indeterminate'
          Indicates that the Server status 
          cannot be determined";
  }

  smiv2:alias "ciscoFirewallTc" {
    smiv2:oid "1.3.6.1.4.1.9.9.488";
  }

}
