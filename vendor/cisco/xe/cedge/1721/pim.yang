module pim {
  namespace "urn:cisco:params:xml:ns:yang:pim";
  prefix pim;

  import cisco-semver {
    prefix cisco-semver;
  }

  organization
    "
     Cisco Systems, Inc.
    ";
  contact
    "
     Cisco Systems, Inc.
     Customer Service
     
     Postal: 170 W Tasman Drive
      San Jose, CA 95134
     
     Tel: +1 1800 553-NETS
         
     E-mail: cs-yang@cisco.com
    ";
  description
    "
     The YANG-module for Protocol Independent Multicast (PIM). 
     The module defines configuration and operational data 
     for the following features:
     PIM Sparse Mode (PIM-SM)
     PIM Source-Specific Multicast (PIM-SSM)
     Bidirectional PIM (Bidir-PIM)
     Anycast-RP for PIM
     Bootstrap Router (BSR)  for PIM
     PIM Dense Mode (PIM-DM)
     Auto-RP - Cisco-propriatary";

  revision 2019-07-01 {
    description
      "Establish semantic version baseline";
    cisco-semver:module-version "1.0.0";
  }
  revision 2014-06-27 {
    description
      "v1.0";
  }

  feature auto-rp {
    description
      "Auto-RP is a Cisco-developed solution to create dynamic 
       group-to-RP-mappings. It is the predecessor of the BSR Mechanism for PIM.";
  }

  feature bsr {
    description
      "Bootstrap Router (BSR) Mechanism as defined in RFC5059";
  }

  identity group-to-rp-mapping-mode {
    description
      "The base-type for a PIM-mode giving context to a group-to-rp-mapping.";
  }

  identity dm-mapping-mode {
    description
      "The mapping is for Dense Mode.";
    base group-to-rp-mapping-mode;
  }

  identity sm-mapping-mode {
    description
      "The mapping is for Sparse Mode.";
    base group-to-rp-mapping-mode;
  }

  identity pim-bidir-mapping-mode {
    description
      "The mapping is for Bidirectional PIM.";
    base group-to-rp-mapping-mode;
  }

  identity ssm-mapping-mode {
    description
      "The mapping is for Source Specific Mode.";
    base group-to-rp-mapping-mode;
  }

  identity asm-mapping-mode {
    description
      "The mapping is for Any-Source Multicast (ASM) with PIM Sparse Mode.";
    base group-to-rp-mapping-mode;
  }

  identity other-mapping-mode {
    description
      "None of the available modes.";
    base group-to-rp-mapping-mode;
  }

  typedef Route-protocol-type {
    type enumeration {
      enum "other" {
        value 1;
      }
      enum "local" {
        value 2;
      }
      enum "netmgmt" {
        value 3;
      }
      enum "icmp" {
        value 4;
      }
      enum "egp" {
        value 5;
      }
      enum "ggp" {
        value 6;
      }
      enum "hello" {
        value 7;
      }
      enum "rip" {
        value 8;
      }
      enum "isIs" {
        value 9;
      }
      enum "esIs" {
        value 10;
      }
      enum "ciscoIgrp" {
        value 11;
      }
      enum "bbnSpfIgp" {
        value 12;
      }
      enum "ospf" {
        value 13;
      }
      enum "bgp" {
        value 14;
      }
      enum "idpr" {
        value 15;
      }
      enum "ciscoEigrp" {
        value 16;
      }
      enum "dvmrp" {
        value 17;
      }
    }
    description
      "A mechanism for learning routes.  Inclusion of values for
       routing protocols is not intended to imply that those
       protocols need be supported.";
  }

  typedef Mroute-protocol-type {
    type enumeration {
      enum "other" {
        value 1;
      }
      enum "local" {
        value 2;
      }
      enum "netmgmt" {
        value 3;
      }
      enum "dvmrp" {
        value 4;
      }
      enum "mospf" {
        value 5;
      }
      enum "pimSparseDense" {
        value 6;
      }
      enum "cbt" {
        value 7;
      }
      enum "pimSparseMode" {
        value 8;
      }
      enum "pimDenseMode" {
        value 9;
      }
      enum "igmpOnly" {
        value 10;
      }
      enum "bgmp" {
        value 11;
      }
      enum "msdp" {
        value 12;
      }
    }
    description
      "The multicast routing protocol.  Inclusion of values for
       multicast routing protocols is not intended to imply that
       those protocols need be supported.";
  }

  typedef Pim-mode {
    description
      "PIM mode active on an interface.";
    type enumeration {
      enum "sparse" {
        description
          "PIM sparse mode enabled on interface";
        value 1;
      }
      enum "dense" {
        description
          "PIM dense mode enable on interface.";
        value 2;
      }
      enum "sparse-dense" {
        description
          "PIM dense mode enable on interface.";
        value 3;
      }
      enum "dm-proxy" {
        description
          "PIM dense mode enable on interface.";
        value 4;
      }
      enum "none" {
        description
          "PIM dense mode enable on interface.";
        value 5;
      }
    }
  }

  typedef Origin {
    description
      "This type  verify all uses of origin in model describes where a state was learned.";
    type enumeration {
      enum "other-origin" {
        description
          "The state's origin is none of the available sources or it is unknown.";
        value 1;
      }
      enum "pim-request" {
        description
          "PIM-request-states are learned by PIM joins (between PIM-routers).";
        value 2;
      }
      enum "ssm-request" {
        description
          "SSM-Request-states are learned by SSM channel subscription, e.g., through 
           IGMP3 (primarily only on last-hop-routers, although routers within the domain can keep 
           this origin-type
           ).";
        value 3;
      }
      enum "fixed" {
        description
          "Fixed states are created automatically by the router at startup, to 
           correspond to the well-defined prefixes of link-local and unroutable group addresses. 
           These states are never destroyed.";
        value 4;
      }
      enum "embedded" {
        description
          "Embedded states are created by the router to correspond to group 
           prefixes that are to be treated as being in Embedded-RP format.";
        value 5;
      }
      enum "static" {
        description
          "Static states are created and destroyed as a result of static configuration.";
        value 6;
      }
      enum "config-ssm" {
        description
          "Config-SSM states are created and destroyed as a result of configuration 
           of SSM address ranges to the local router.";
        value 7;
      }
      enum "auto-rp" {
        description
          "Auto-RP states are created as a result of running Cisco's Auto-RP mechanism.";
        value 8;
      }
      enum "bsr" {
        description
          "BSR states are created as a result of running the PIM Bootstrap Router 
           (BSR) mechanism.";
        value 9;
      }
      enum "msdp" {
        description
          "MSDP states are (*, G)-entries learned through a Multicast Source Discovery 
           Protocol (MSDP) peer. This origin is applicable only for an RP running MSDP. ";
        value 10;
      }
    }
  }

  typedef IP-Multicast-Group-Address {
    description
      "The IP-Multicast-Group-Address type represents an IP multicast address and is 
       IP version neutral. The format of the textual representations implies the IP version.";
    type union {
      type IPv4-Multicast-Group-Address;
      type IPv6-Multicast-Group-Address;
    }
  }

  typedef IPv4-Multicast-Group-Address {
    description
      "The IPv4-Multicast-Group-Address type represents an IPv4 multicast address in 
       dotted-quad notation.";
    reference "RFC4607";
    type string {
      pattern "(2((2[4-9])|(3[0-9]))\\.)(([0-9]|[1-9][0-9]|1[0-9][0-9]|2[0-4][0-9]|25[0-5])\\.){2}([0-9]|[1-9][0-9]|1[0-9][0-9]|2[0-4][0-9]|25[0-5])";
    }
  }

  typedef IPv6-Multicast-Group-Address {
    description
      "The IPv6-Multicast-Group-Address type represents an IPv6 address in full, 
       mixed, shortened, and shortened-mixed notation.";
    reference
      "RFC4291 2.7.
       ietf-inet-types:ipv6-address";
    type string {
      pattern "(((FF|ff)[0-9a-fA-F]{2}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))";
      pattern "(([^:]+:){6}(([^:]+:[^:]+)|(.*\\..*)))|((([^:]+:)*[^:]+)?::(([^:]+:)*[^:]+)?)";
    }
  }

  typedef IP-Multicast-Group-Address-Prefix {
    description
      "The IP-Multicast-Group-Address-Prefix type represents an IP multicast address 
       prefix and is IP version neutral. The format of the textual representations implies the IP 
       version. It includes a prefix-length, separated by a '/' sign.";
    type union {
      type IPv4-Multicast-Group-Address-Prefix;
      type IPv6-Multicast-Group-Address-Prefix;
    }
  }

  typedef IPv4-Multicast-Group-Address-Prefix {
    description
      "The IPv4-Multicast-Group-Address-Prefix type represents an IPv4 multicast 
       address prefix in dotted-quad notation. It includes a prefix-length, separated by a '/' sign.";
    reference "RFC4607";
    type string {
      pattern "(2((2[4-9])|(3[0-9]))\\.)(([0-9]|[1-9][0-9]|1[0-9][0-9]|2[0-4][0-9]|25[0-5])\\.){2}([0-9]|[1-9][0-9]|1[0-9][0-9]|2[0-4][0-9]|25[0-5])(/(([4-9])|([1-2][0-9])|(3[0-2])))";
    }
  }

  typedef IPv6-Multicast-Group-Address-Prefix {
    description
      "The IPv6-Multicast-Group-Address-Prefix type represents an IPv6 multicast address 
       prefix in full, mixed, shortened, and shortened-mixed notation. It includes a prefix-length, separated by a '/' sign.";
    reference
      "RFC4291 2.7.
           
       ietf-inet-types:ipv6-address";
    type string {
      pattern "(((FF|ff)[0-9a-fA-F]{2}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/((1[6-9])|([2-9][0-9])|(1[0-1][0-9])|(12[0-8])))";
      pattern "(([^:]+:){6}(([^:]+:[^:]+)|(.*\\..*)))|((([^:]+:)*[^:]+)?::(([^:]+:)*[^:]+)?)(/.+)";
    }
  }

  typedef IP-SSM-Group-Address {
    description
      "The IP-SSM-Group-Address type represents an IP Source-Specific multicast 
       address and is IP version neutral. The format of the textual representations implies the IP version.";
    type union {
      type IPv4-SSM-Group-Address;
      type IPv6-SSM-Group-Address;
    }
  }

  typedef IPv4-SSM-Group-Address {
    description
      "The IPv4-SSM-Group-Address type represents an IPv4 Source-Specific multicast 
       address in dotted-quad notation.
       IPv4 addresses in the 232/8 range are designated as SSM.";
    reference
      "RFC4607
       IANA IPv4 Multicast Address Space Registry";
    type string {
      pattern "(232\\.)(([0-9]|[1-9][0-9]|1[0-9][0-9]|2[0-4][0-9]|25[0-5])\\.){2}([0-9]|[1-9][0-9]|1[0-9][0-9]|2[0-4][0-9]|25[0-5])";
    }
  }

  typedef IPv6-SSM-Group-Address {
    description
      "The IPv6-SSM-Group-Address type represents an IPv6 Source-Specific  
       multicast group address in shortened and shortened-mixed notation.";
    reference "RFC4607";
    type string {
      pattern "((FF3|ff3)([0-9a-fA-F]{1}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))";
      pattern "(([^:]+:){6}(([^:]+:[^:]+)|(.*\\..*)))|((([^:]+:)*[^:]+)?::(([^:]+:)*[^:]+)?)";
    }
  }
}
