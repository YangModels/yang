module Cisco-IOS-XE-zone {
  namespace "http://cisco.com/ns/yang/Cisco-IOS-XE-zone";
  prefix ios-zone;

  import cisco-semver {
    prefix cisco-semver;
  }
  import Cisco-IOS-XE-native {
    prefix ios;
  }
  import Cisco-IOS-XE-policy {
    prefix ios-policy;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Zone Interfaces Yang model.
     Copyright (c) 2016-2019 by Cisco Systems, Inc.
     All rights reserved.";

  revision 2019-11-01 {
    description
      "
       - Enabled zone config under UCSE interface";
    cisco-semver:module-version "1.1.0";
  }
  revision 2019-07-01 {
    description
      "- Establish semantic version baseline
       - Enable configuring zone for BDI and BD-VIF interface";
    cisco-semver:module-version "1.0.0";
  }
  revision 2019-01-22 {
    description
      "Added leaf for App-hosting Gigabit Ethernet interface";
  }
  revision 2019-01-07 {
    description
      "Enable configuring zone for BDI and BD-VIF interface";
  }
  revision 2018-12-06 {
    description
      "Change non-strict-leafref's to leafref's for threat-defense features";
  }
  revision 2018-11-16 {
    description
      "Cleanup spelling errors in description statements";
  }
  revision 2018-11-06 {
    description
      "Remove instances of max string length of 128/256/512";
  }
  revision 2018-10-17 {
    description
      "Enable configuring zone for VirtualPortGroup interface";
  }
  revision 2018-09-25 {
    description
      "Fix unable to move VPN between zones in a single transaction";
  }
  revision 2018-09-10 {
    description
      "Make zone-pair backward compatible";
  }
  revision 2018-09-02 {
    description
      "Add annotation to remove service-policy before modifying its value";
  }
  revision 2018-08-24 {
    description
      "Require source and destination zone to always be entered";
  }
  revision 2018-06-12 {
    description
      "Further restrict zone and zone-pair string lengths";
  }
  revision 2018-05-14 {
    description
      "Limit string lengths for threat-defense features";
  }
  revision 2018-04-28 {
    description
      "Add leaf-refs to other models to fix dependencies";
  }
  revision 2018-02-22 {
    description
      "Add threat-defense support for Ethernet interfaces";
  }
  revision 2018-02-09 {
    description
      "Add ZBFW VPN config";
  }
  revision 2017-11-27 {
    description
      "Added Change 25GE name";
  }
  revision 2017-09-15 {
    description
      "This revision has changes for new 2gig interface addition";
  }
  revision 2017-08-16 {
    description
      "This revision has changes for new 5gig and 25gig interfaces addition";
  }
  revision 2017-02-07 {
    description
      "Initial revision";
  }

  grouping config-interface-zone-member-grouping {
    container zone-member {
      description
        "Apply zone name";
      leaf security {
        description
          "Security zone";
        type leafref {
          path "/ios:native/ios:zone/ios-zone:security/ios-zone:id";
        }
      }
    }
  }

  grouping config-zone-grouping {
    list security {
      description
        "Security zone";
      key "id";
      leaf id {
        type string {
          length "1..64";
        }
      }
      leaf description {
        description
          "Zone description";
        type string {
          length "1..200";
        }
      }
      leaf protection {
        description
          "config sync cookie protection against sync flood";
        type leafref {
          path "/ios:native/ios:parameter-map/ios:type/ios-policy:inspect-zone/ios-policy:name";
        }
      }
      list vpn {
        description
          "config vpn and zone binding list";
        key "id";
        leaf id {
          description
            "VPN Number";
          type uint32;
        }
      }
    }
  }

  grouping config-zone-pair-grouping {
    description
      "Zone pair command";
    list security {
      description
        "Zone-pair name";
      key "id";
      leaf id {
        type string {
          length "1..128";
        }
      }
      leaf source {
        description
          "Source zone";
        mandatory true;
        type string {
          length "1..64";
        }
      }
      leaf destination {
        description
          "Destination zone";
        mandatory true;
        type string {
          length "1..64";
        }
      }
      leaf description {
        description
          "Zone description";
        type string {
          length "1..200";
        }
      }
      container service-policy {
        description
          "Configure Zone Pair Service Policy";
        container type {
          description
            "Service Policy type";
          leaf inspect {
            description
              "Configure Zone Pair Service Policy type inspect";
            type leafref {
              path "/ios:native/ios:policy/ios-policy:policy-map/ios-policy:name";
            }
          }
        }
      }
    }
  }

  augment "/ios:native/ios:zone" {
    uses config-zone-grouping;
  }
  augment "/ios:native/ios:zone-pair" {
    uses config-zone-pair-grouping;
  }
  augment "/ios:native/ios:interface/ios:Ethernet" {
    uses config-interface-zone-member-grouping;
  }
  augment "/ios:native/ios:interface/ios:FastEthernet" {
    uses config-interface-zone-member-grouping;
  }
  augment "/ios:native/ios:interface/ios:GigabitEthernet" {
    uses config-interface-zone-member-grouping;
  }
  augment "/ios:native/ios:interface/ios:TenGigabitEthernet" {
    uses config-interface-zone-member-grouping;
  }
  augment "/ios:native/ios:interface/ios:FiveGigabitEthernet" {
    uses config-interface-zone-member-grouping;
  }
  augment "/ios:native/ios:interface/ios:AppGigabitEthernet" {
    uses config-interface-zone-member-grouping;
  }
  augment "/ios:native/ios:interface/ios:TwentyFiveGigabitEthernet" {
    uses config-interface-zone-member-grouping;
  }
  augment "/ios:native/ios:interface/ios:TwentyFiveGigE" {
    uses config-interface-zone-member-grouping;
  }
  augment "/ios:native/ios:interface/ios:FortyGigabitEthernet" {
    uses config-interface-zone-member-grouping;
  }
  augment "/ios:native/ios:interface/ios:HundredGigE" {
    uses config-interface-zone-member-grouping;
  }
  augment "/ios:native/ios:interface/ios:LISP" {
    uses config-interface-zone-member-grouping;
  }
  augment "/ios:native/ios:interface/ios:TwoGigabitEthernet" {
    uses config-interface-zone-member-grouping;
  }
  augment "/ios:native/ios:interface/ios:Loopback" {
    uses config-interface-zone-member-grouping;
  }
  augment "/ios:native/ios:interface/ios:Tunnel" {
    uses config-interface-zone-member-grouping;
  }
  augment "/ios:native/ios:interface/ios:Virtual-Template" {
    uses config-interface-zone-member-grouping;
  }
  augment "/ios:native/ios:interface/ios:Vlan" {
    uses config-interface-zone-member-grouping;
  }
  augment "/ios:native/ios:interface/ios:vasileft" {
    uses config-interface-zone-member-grouping;
  }
  augment "/ios:native/ios:interface/ios:vasiright" {
    uses config-interface-zone-member-grouping;
  }
  augment "/ios:native/ios:interface/ios:VirtualPortGroup" {
    uses config-interface-zone-member-grouping;
  }
  augment "/ios:native/ios:interface/ios:BDI" {
    uses config-interface-zone-member-grouping;
  }
  augment "/ios:native/ios:interface/ios:BD-VIF" {
    uses config-interface-zone-member-grouping;
  }
  augment "/ios:native/ios:interface/ios:ucse" {
    uses config-interface-zone-member-grouping;
  }
}
