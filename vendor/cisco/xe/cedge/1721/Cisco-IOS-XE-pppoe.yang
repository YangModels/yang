module Cisco-IOS-XE-pppoe {
  namespace "http://cisco.com/ns/yang/Cisco-IOS-XE-pppoe";
  prefix ios-pppoe;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Point-to-Point over Ethernet Protocol (PPPoE) Yang model.
     Copyright (c) 2016-2019 by Cisco Systems, Inc.
     All rights reserved.";

  revision 2019-11-01 {
    description
      "
       - changed dial-pool-number from leaf to list
       - Added new dialer-pool config";
    cisco-semver:module-version "2.0.0";
  }
  revision 2019-07-01 {
    description
      "Establish semantic version baseline";
    cisco-semver:module-version "1.0.0";
  }
  revision 2019-02-25 {
    description
      "Initial revision";
  }

  grouping config-pppoe-grouping {
    container pppoe {
      description
        "PPPoE options";
      container enable {
        description
          "Enable pppoe";
        presence "true";
        leaf group {
          description
            "attach a BBA group";
          type union {
            type string;
            type enumeration {
              enum "global";
            }
          }
        }
      }
      leaf max-sessons {
        description
          "Maximum PPPoE sessions";
        type uint32 {
          range "1..16378";
        }
      }
    }
  }

  grouping config-pppoe-client-grouping {
    container pppoe-client {
      description
        "pppoe-client";
      when "../pppoe/enable";
      list dial-pool-number-list {
        description
          "dialer pool keyword";
        key "number";
        leaf number {
          description
            "dialer pool number";
          type uint32 {
            range "1..255";
          }
        }
      }
      leaf dial-pool-number {
        status deprecated;
        description
          "dialer pool keyword";
        type uint32 {
          range "1..255";
        }
      }
      leaf ppp-max-payload {
        description
          "Maximum MRU value to be negotiated during PPP LCP negotiation";
        when "../dial-pool-number-list";
        type uint32 {
          range "64..1792";
        }
      }
    }
  }

  grouping config-pppoe-session-grouping {
    container pppoe-session {
      description
        "Configure pppoe per-interface options";
      container threshold {
        description
          "Configure per-interface pppoe session loss threshold";
        leaf loss-threshold {
          description
            "Per-Interface pppoe session loss threshold";
          type uint32 {
            range "1..65535";
          }
        }
        container percent {
          description
            "Configure relative percentage session loss over time";
          leaf percantage {
            type uint32 {
              range "0..100";
            }
          }
          leaf interval {
            description
              "Duration over which percentage of session loss to be calculated";
            type uint32 {
              range "1..65535";
            }
          }
        }
      }
    }
  }

  augment "/ios:native/ios:interface/ios:Ethernet" {
    uses config-pppoe-session-grouping;
    uses config-pppoe-client-grouping;
    uses config-pppoe-grouping;
  }
}
