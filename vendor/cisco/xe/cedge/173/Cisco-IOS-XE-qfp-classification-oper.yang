module Cisco-IOS-XE-qfp-classification-oper {
  yang-version 1;
  namespace "http://cisco.com/ns/yang/Cisco-IOS-XE-qfp-classification-oper";
  prefix datapath-classification;

  import Cisco-IOS-XE-common-types {
    prefix common-types-ios-xe;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Quantum Flow Processor (QFP) classification operational data.
     Copyright (c) 2019-2020 by Cisco Systems, Inc.
     All rights reserved.";

  revision 2020-07-01 {
    description
      "Use extended location";
    reference "2.0.0";
    cisco-semver:module-version "2.0.0";
  }
  revision 2020-03-01 {
    description
      "Initial revision";
    reference "1.0.0";
    cisco-semver:module-version "1.0.0";
  }

  grouping exmem-usage {
    description
      "The memory usage of the Quantum Flow Processor features";
    leaf feature-id {
      type uint32;
      description
        "The internally assign identifier for the feature";
    }
    leaf client-name {
      type string;
      description
        "The human readable name of the feature";
    }
    leaf total-vmr-entries {
      type uint32;
      description
        "The number of value/mask allocations for this feature";
    }
    leaf total-exmem-usage {
      type uint32;
      units "bytes";
      description
        "Total external memory usage";
    }
    leaf total-percent-exmem-usage {
      type uint32;
      units "percentage";
      description
        "Total percentage of external memory usage";
    }
    leaf total-alloc {
      type uint32;
      description
        "Total number of allocations";
    }
    leaf total-free {
      type uint32;
      description
        "Total number of frees";
    }
  }

  container qfp-classification-oper-data {
    config false;
    description
      "QFP classification operational data";
    list location {
      key "fru slot bay chassis node";
      description
        "A list of data provider locations";
      uses common-types-ios-xe:extended-location;
      list exmem-usage {
        key "feature-id";
        description
          "The memory usage of various features within the Quantum Flow Processor";
        uses datapath-classification:exmem-usage;
      }
    }
  }
}
