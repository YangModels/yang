module Cisco-IOS-XE-features {
  namespace "http://cisco.com/ns/yang/Cisco-IOS-XE-features";
  prefix ios-features;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE feature Definitions
     Copyright (c) 2016-2019 by Cisco Systems, Inc.
     All rights reserved.";

  revision 2020-07-01 {
    description
      "- Added down-monitoring feature
       - Added IPSLA Service performance feature";
  }
  revision 2020-03-01 {
    description
      "Added rawsocket feature
       Added sg-epg-ignore-vrf feature for Security-Group and Endpoint-Group 
       translation";
  }
  revision 2019-10-01 {
    description
      "Added new features";
  }
  revision 2019-02-25 {
    description
      "Added iso-igrp feature";
  }
  revision 2018-11-20 {
    description
      "Added license-suite-command feature for license boot suite command";
  }
  revision 2017-02-07 {
    description
      "Initial revision";
  }

  feature switching-platform {
    description
      "switching platform specific features";
  }

  feature crypto {
    description
      "crypto feature";
  }

  feature device-tracking {
    description
      "device-tracking feature";
  }

  feature dhcp-border-relay {
    description
      "dhcp-border-relay feature";
  }

  feature dot1x {
    description
      "dot1x feature";
  }

  feature ecfm-llb {
    description
      "Ethernet CFM latching-loopback feature";
  }

  feature efp {
    description
      "Ethernet Flow Point (efp) feature";
  }

  feature esmc {
    description
      "Ethernet Synchronization Messaging Channel (esmc) feature";
  }

  feature eth-evc {
    description
      "Ethernet Virtual Circuit (EVC) feature";
  }

  feature ezpm {
    description
      "Easy Performance Monitor feature";
  }

  feature iso-igrp {
    description
      "ISO IGRP feature";
  }

  feature l2 {
    description
      "Layer2 VPN feature";
  }

  feature l2vpn {
    description
      "Layer2 VPN feature";
  }

  feature macsec {
    description
      "macsec";
  }

  feature mem-size {
    description
      "Memory size commands";
  }

  feature module {
    description
      "Device module feature";
  }

  feature multilink {
    description
      "PPP multilink global configuration";
  }

  feature mls {
    description
      "Multilayer Switching feature";
  }

  feature omp {
    description
      "Overlay Management Protocol (OMP) feature";
  }

  feature parameter-map {
    description
      "Parameter Map feature";
  }

  feature private-vlan {
    description
      "Private-vlan feature";
  }

  feature punt-num {
    description
      "Police punt feature";
  }

  feature qos-qsm {
    description
      "QoS queue softmax multiplier";
  }

  feature rawsocket {
    description
      "Rawsocket";
  }

  feature scada-gw {
    description
      "SCADA Gateway";
  }

  feature sdwan {
    description
      "sdwan feature";
  }

  feature sr-policy {
    description
      "BGP SR-TE Policy feature";
  }

  feature license-suite-command {
    description
      "license boot suite feature";
  }

  feature setup {
    description
      "Express setup feature";
  }

  feature switch-virtual {
    description
      "Switch-virtual feature";
  }

  feature table-map {
    description
      "table-map feature";
  }

  feature tod-clock {
    description
      "Time of Day clock feature";
  }

  feature transceiver {
    description
      "Transceiver commands";
  }

  feature virtual-template {
    description
      "Virtual-template commands";
  }

  feature vlan {
    description
      "Vlan feature";
  }

  feature med {
    description
      "Media End-point Discovery";
  }

  feature routing-platform {
    description
      "routing platform specific features";
  }

  feature mdns-switch {
    description
      "mDNS under interface vlan for switching platforms";
  }

  feature mdns-ewlc {
    description
      "mDNS under interface vlan for eWLC platforms";
  }

  feature l2pt-more-protocols {
    description
      "L2 protocol tunneling support new protocols: 
       MVRP,DTP,PTP Peer Delay Protocol,
       Multiple MAC Registration Protocol,ELMI,LINK-OAM,ESMC";
  }

  feature l2cp-fwd {
    description
      "Switchport support forwarding L2 PDUs:
       CDP,STP,VTP,LLDP,PAGP,LACP,UDLD,MVRP,DTP,PTP Peer Delay Protocol,
       Multiple MAC Registration Protocol,ELMI,LINK-OAM,ESMC,R4,R5,R6,R8,R9,
       RA,RB,RC,RD,RF";
  }

  feature sg-epg-ignore-vrf {
    description
      "Cisco TrustSec Security-Group and Endpoint-Group translation supports
       new functionality to disable VRF awareness";
  }

  feature bfd-dm {
    description
      "dampening with down-monitoring support";
  }

  feature service-performance {
    description
      "IPSLA Service Performance platform specific feature";
  }
}
