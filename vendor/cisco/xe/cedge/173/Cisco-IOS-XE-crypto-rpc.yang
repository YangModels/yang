submodule Cisco-IOS-XE-crypto-rpc {
  belongs-to Cisco-IOS-XE-rpc {
    prefix ios-xe-rpc;
  }

  import cisco-semver {
    prefix cisco-semver;
  }
  import Cisco-IOS-XE-types {
    prefix ios-types;
  }

  organization
    "Cisco Systems";
  contact
    "<mailto:cs-yang@cisco.com>";
  description
    "NED Crypto RPC YANG module for IOS
     Copyright (c) 2016-2020 by Cisco Systems, Inc.
     All rights reserved.";

  revision 2020-03-01 {
    description
      "- Added crypto key commands without a NO prefix";
  }
  revision 2019-11-01 {
    description
      "Added new key RPC";
  }
  revision 2019-07-01 {
    description
      "Establish semantic version baseline";
    cisco-semver:module-version "1.0.0";
  }

  grouping debug-level-grouping {
    container level {
      choice level-choice {
        case error-case {
          leaf error {
            description
              "Enable error debug";
            type empty;
          }
        }
        case info-case {
          leaf info {
            description
              "Enable info debug";
            type empty;
          }
        }
        case verbose-case {
          leaf verbose {
            description
              "Enable verbose debug";
            type empty;
          }
        }
        case warning-case {
          leaf warning {
            description
              "Enable warning debug";
            type empty;
          }
        }
      }
    }
  }

  grouping crypto-input-grouping {
    container pki {
      description
        "Public key components";
      choice subcommand {
        case benchmark {
          container benchmark {
            description
              "Benchmark commands";
            leaf start {
              description
                "Collection limit";
              type uint16 {
                range "0..9990";
              }
            }
            leaf wrap {
              description
                "Wrap data to the start of buffer";
              when "../start";
              type empty;
            }
            leaf stop {
              description
                "stop collecting benchmark data";
              type empty;
            }
          }
        }
        case crl {
          container crl {
            description
              "CRL command";
            leaf refresh-cache {
              description
                "Refresh the CRL in cache";
              type empty;
            }
            leaf request {
              description
                "Requests a current CRL";
              type string;
            }
          }
        }
        case authenticate {
          container authenticate {
            description
              "Authenticate trustpoint";
            leaf name-drop-node-name {
              description
                "trustpoint name";
              type string;
            }
          }
        }
        case enroll {
          container enroll {
            description
              "enroll trustpoint";
            leaf name-drop-node-name {
              description
                "trustpoint name";
              type string;
            }
          }
        }
        case export {
          container export {
            description
              "export certificate";
            leaf name-drop-node-name {
              description
                "trustpoint name";
              type string;
            }
            leaf pkcs12 {
              description
                "PKCS12 bundle url";
              type string;
            }
            leaf password {
              description
                "PKCS12 bundle password";
              type string;
            }
          }
        }
        case import {
          container import {
            description
              "import certificate";
            leaf name-drop-node-name {
              description
                "trustpoint name";
              type string;
            }
            leaf certificate {
              description
                "import id certificate";
              type empty;
            }
            leaf pkcs12 {
              description
                "PKCS12 bundle url";
              type string;
            }
            leaf password {
              description
                "PKCS12 bundle password";
              type string;
            }
          }
        }
        case certificate {
          container certificate {
            description
              "validate certificate";
            leaf validate {
              description
                "trustpoint name";
              type string;
            }
          }
        }
        case server {
          container server {
            description
              "Server command";
            leaf name-drop-node-name {
              description
                "server name";
              type string;
            }
            container grant {
              description
                "Grant enrollment requests";
              leaf id-drop-node-name {
                description
                  "Enrollment id";
                type uint16 {
                  range "1..999";
                }
              }
              leaf all {
                description
                  "Grant all pending requests";
                type empty;
              }
            }
            container password {
              description
                "One time password for SCEP enrollment";
              container generate {
                description
                  "Generate password";
                presence "true";
                leaf minutes-drop-node-name {
                  description
                    "Validity in minutes";
                  type uint16 {
                    range "1..1440";
                  }
                }
              }
            }
            container reject {
              description
                "Reject enrollment requests";
              leaf id-drop-node-name {
                description
                  "Enrollment id";
                type uint16 {
                  range "1..999";
                }
              }
              leaf all {
                description
                  "Reject all pending requests";
                type empty;
              }
            }
            container remove {
              description
                "Remove enrollment requests";
              leaf id-drop-node-name {
                description
                  "Enrollment id";
                type uint16 {
                  range "1..999";
                }
              }
              leaf all {
                description
                  "Remove all pending requests";
                type empty;
              }
            }
            container request {
              description
                "Retrieve an enrollment request";
              container pkcs10 {
                description
                  "PKCS10 enrollment request";
                leaf location-drop-node-name {
                  description
                    "Retrieval location";
                  type enumeration {
                    enum "bootflash:";
                    enum "cns:";
                    enum "disk0:";
                    enum "disk1:";
                    enum "flash:";
                    enum "ftp:";
                    enum "http:";
                    enum "https:";
                    enum "null:";
                    enum "nvram:";
                    enum "pram:";
                    enum "rcp:";
                    enum "scep";
                    enum "scp:";
                    enum "sftp:";
                    enum "system:";
                    enum "tar:";
                    enum "terminal";
                    enum "tftp:";
                    enum "tmpsys:";
                    enum "tti";
                    enum "unix:";
                    enum "webui:";
                  }
                }
                choice format {
                  case base64 {
                    leaf base64 {
                      description
                        "output in base64 format";
                      type empty;
                    }
                  }
                  case pem {
                    leaf pem {
                      description
                        "output in pem format";
                      type empty;
                    }
                  }
                  case hex {
                    container hex {
                      description
                        "output in hex format";
                      presence "true";
                      leaf tid-drop-node-name {
                        description
                          "Transaction ID";
                        type string;
                      }
                      leaf nonce-drop-node-name {
                        description
                          "nonce";
                        type string;
                      }
                      leaf rid-drop-node-name {
                        description
                          "Request ID";
                        type uint16 {
                          range "1..999";
                        }
                      }
                    }
                  }
                }
              }
            }
            leaf revoke {
              description
                "revoke certificate";
              type string {
                pattern "([0-9a-fA-FxX]+)";
              }
            }
            leaf unrevoke {
              description
                "unrevoke certificate";
              type string {
                pattern "([0-9a-fA-FxX]+)";
              }
            }
            leaf start {
              description
                "Start server";
              type empty;
            }
            leaf stop {
              description
                "Stop server";
              type empty;
            }
            container trim {
              description
                "Trim the CRL based on expired certificates";
              leaf url {
                description
                  "location of expired certs file";
                type enumeration {
                  enum "bootflash:";
                  enum "cns:";
                  enum "disk0:";
                  enum "disk1:";
                  enum "flash:";
                  enum "ftp:";
                  enum "http:";
                  enum "https:";
                  enum "null:";
                  enum "nvram:";
                  enum "pram:";
                  enum "rcp:";
                  enum "scp:";
                  enum "sftp:";
                  enum "system:";
                  enum "tar:";
                  enum "tftp:";
                  enum "tmpsys:";
                  enum "unix:";
                  enum "webui:";
                }
              }
              leaf verbose {
                type empty;
              }
            }
          }
        }
      }
    }

    grouping crypto-key-export-pem-grouping {
      container pem {
        description
          "File type to export";
        choice terminal-url {
          case terminal-case {
            container terminal {
              description
                "Export via the terminal (cut-and-paste)";
              choice des-3des {
                case pk-3des-case {
                  leaf pk-3des {
                    description
                      "Encrypt the private key with 3DES";
                    type string;
                  }
                }
                case des-case {
                  leaf des {
                    description
                      "Encrypt the private key with DES";
                    type string;
                  }
                }
              }
            }
          }
          case url-case {
            container url {
              description
                "Export via the file systems";
              uses crypto-key-url-file-ex-grouping;
              choice des-3des {
                case url-3des-case {
                  leaf url-3des {
                    description
                      "Encrypt the private key with 3DES";
                    type string;
                  }
                }
                case des-case {
                  leaf des {
                    description
                      "Encrypt the private key with DES";
                    type string;
                  }
                }
              }
            }
          }
        }
      }
    }

    grouping crypto-key-url-file-ex-grouping {
      leaf file {
        type string {
          pattern "(((bootflash:)|(crashinfo:)|(flash:)|(ftp:)|(http:)|(https:)|(null:)|(nvram:)|(pram:)|(rcp:)|(scp:)|(system:)|(tar:)|(tftp:)|(tmpfs:)|(webui:)).*)";
        }
      }
    }

    grouping crypto-key-url-file-im-grouping {
      leaf file {
        type string {
          pattern "(((bootflash:)|(cns:)|(crashinfo:)|(flash:)|(ftp:)|(http:)|(https:)|(null:)|(nvram:)|(pram:)|(rcp:)|(scp:)|(system:)|(tar:)|(tftp:)|(tmpfs:)|(webui:)).*)";
        }
      }
    }
    container key {
      description
        "Key related commands.";
      container zeroize {
        description
          "Remove RSA/EC keys";
        leaf rsa {
          description
            "Remove RSA keys";
          type string;
        }
      }
    }
    container generate {
      description
        "Generate new keys";
      container ec {
        description
          "Generate EC keys for ECDSA";
        leaf keysize {
          description
            "Number of bits";
          type enumeration {
            enum "256";
            enum "384";
          }
        }
        leaf exportable {
          description
            "Allow key to be exported";
          type empty;
        }
        leaf label {
          description
            "Provide a label";
          type string;
        }
      }
      container rsa {
        description
          "Generate RSA keys";
        presence "true";
        leaf encryption {
          description
            "Generate a general purpose RSA key pair for signing and encryption";
          type empty;
        }
        leaf exportable {
          description
            "Allow the key to be exported";
          type empty;
        }
        leaf general-keys {
          description
            "Generate a general purpose RSA key pair for signing and encryption";
          type empty;
        }
        leaf label {
          description
            "Provide a label";
          type string;
        }
        leaf modulus {
          description
            "Provide number of modulus bits on the command line";
          type uint16 {
            range "360..4096";
          }
        }
        leaf on {
          description
            "create key on specified device.";
          type string;
        }
        leaf redundancy {
          description
            "Allow the key to be synced to high-availability peer";
          type empty;
        }
        leaf signature {
          description
            "Generate a general purpose RSA key pair for signing and encryption";
          type empty;
        }
        leaf storage {
          description
            "Store key on specified device";
          type string;
        }
        leaf usage-keys {
          description
            "Generate separate RSA key pairs for signing and encryption";
          type empty;
        }
      }
    }
    container export {
      description
        "Export keys";
      list ec {
        description
          "Export EC keys";
        key "label";
        leaf label {
          type string;
        }
        uses crypto-key-export-pem-grouping;
      }
      list rsa {
        description
          "Export RSRA keys";
        key "label";
        leaf label {
          type string;
        }
        uses crypto-key-export-pem-grouping;
      }
    }
    container import {
      description
        "Import keys";
      list ec {
        description
          "Import EC keys";
        key "name";
        leaf name {
          type string;
        }
        leaf exportable {
          description
            "Allow key to be exported";
          type empty;
        }
        choice terminal-url {
          case terminal-case {
            leaf terminal {
              description
                "Import via the terminal (cut-and-paste)";
              type string;
            }
          }
          case url-case {
            container url {
              description
                "Export via the file systems";
              uses crypto-key-url-file-im-grouping;
              leaf key {
                type string;
              }
            }
          }
        }
      }
      list rsa {
        description
          "Import RSA keys";
        key "label";
        leaf label {
          type string;
        }
        leaf encryption {
          description
            "Encryption key";
          type empty;
        }
        leaf exportable {
          description
            "Allow the key to be exported";
          type empty;
        }
        leaf general-purpose {
          description
            "General Purpose key";
          type empty;
        }
        leaf on {
          description
            "Make this an on-token key";
          type string;
        }
        leaf pem {
          description
            "File type to import";
          type empty;
        }
        leaf redundancy {
          description
            "Sync this key to the standby";
          type empty;
        }
        leaf signature {
          description
            "Signature key";
          type empty;
        }
        leaf storage {
          description
            "Store key on specified device";
          type string;
        }
        leaf usage-keys {
          description
            "Usage key pairs";
          type empty;
        }
        choice terminal-url {
          case terminal-case {
            leaf terminal {
              description
                "Import via the terminal (cut-and-paste)";
              type string;
            }
          }
          case url-case {
            container url {
              description
                "Export via the file systems";
              uses crypto-key-url-file-im-grouping;
              leaf key {
                type string;
              }
            }
          }
        }
      }
    }
  }

  grouping debug-input-crypto-grouping {
    container crypto {
      description
        "Cryptographic subsystem";
      container pki {
        description
          "PKI debugging information";
        leaf API {
          description
            "PKI API debugging information";
          type empty;
        }
        leaf callbacks {
          description
            "PKI callbacks debugging information";
          type empty;
        }
        leaf messages {
          description
            "PKI messages debugging information";
          type empty;
        }
        leaf scep {
          description
            "PKI scep debugging information";
          type empty;
        }
        container server {
          description
            "PKI server debugging information";
          presence "true";
          leaf performance {
            description
              "PKI server performance debugging information";
            type empty;
          }
        }
        container transactions {
          description
            "PKI transaction debugging information";
          presence "true";
          leaf performance {
            description
              "PKI transaction performance debugging information";
            type empty;
          }
        }
        leaf validation {
          description
            "PKI validation debugging information";
          type empty;
        }
      }
      leaf est-client {
        description
          "EST client debugging information";
        type empty;
      }
      leaf ha {
        description
          "PKI HA debugging information";
        type empty;
      }
    }
  }

  grouping debug-platform-condition-feature-ipsec-grouping {
    container ipsec {
      description
        "IPSEC feature";
      container dataplane {
        description
          "packet/flow information";
        choice dataplane-debug-choice {
          case submode-case {
            container submode {
              description
                "submode information";
              choice submode-choice {
                case all-case {
                  container all {
                    description
                      "ipsec all submode";
                    uses debug-level-grouping;
                  }
                }
                case cce-case {
                  container cce {
                    description
                      "ipsec cce submode";
                    uses debug-level-grouping;
                  }
                }
                case pkt-dump {
                  container pkt-dump {
                    description
                      "ipsec pkt-dump submode";
                    uses debug-level-grouping;
                  }
                }
              }
            }
          }
          case droptype-case {
            leaf droptype {
              description
                "Set debug droptype";
              type union {
                type uint8 {
                  range "1..113";
                }
                type ios-types:range-string;
              }
            }
          }
          case pktcorrupt-case {
            leaf pktcorrupt {
              description
                "Set debug pkt corruption";
              type uint8 {
                range "1..255";
              }
            }
          }
        }
        leaf no {
          description
            "for no debug platform condition feature ipsec dataplane ...";
          type empty;
        }
      }
    }
  }
}
