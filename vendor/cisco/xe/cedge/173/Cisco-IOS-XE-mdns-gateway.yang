module Cisco-IOS-XE-mdns-gateway {
  namespace "http://cisco.com/ns/yang/Cisco-IOS-XE-mdns-gateway";
  prefix ios-mdns;

  import cisco-semver {
    prefix cisco-semver;
  }
  import ietf-inet-types {
    prefix inet;
  }
  import Cisco-IOS-XE-native {
    prefix ios;
  }
  import Cisco-IOS-XE-interface-common {
    prefix ios-ifc;
  }
  import Cisco-IOS-XE-features {
    prefix ios-features;
  }
  import Cisco-IOS-XE-vlan {
    prefix ios-vlan;
  }
  import Cisco-IOS-XE-switch {
    prefix ios-sw;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native MDNS Gateway Yang Model.
     Copyright (c) 2018-2020 by Cisco Systems, Inc.
     All rights reserved.";

  revision 2020-07-01 {
    description
      "- Added Yang support for 13 mDNS CLIs (BGP-EVPN)
       - Marked two nodes as obsolete
       - Added support for flex-profile CLI
       - Added 9991 as default port for controller-port
       - Added Yang support for micro location";
  }
  revision 2019-11-01 {
    description
      "- Added Yang support for all mDNS CLIs
       - Added regex config";
    cisco-semver:module-version "1.1.0";
  }
  revision 2019-07-01 {
    description
      "Establish semantic version baseline";
    cisco-semver:module-version "1.0.0";
  }
  revision 2018-11-29 {
    description
      "Corrected service-definition description 
       and added additional checks in service-list";
  }
  revision 2018-11-07 {
    description
      "Cleanup spelling errors in description statements";
  }
  revision 2018-07-07 {
    description
      "Initial revision";
  }

  grouping mdns-sd-gateway-common-global-grouping {
    leaf sdg-agent {
      description
        "Configure Service Discovery Gateway agent IPv4 address";
      type inet:ipv4-address;
    }
    container source-interface {
      description
        "Configure source interface to communicate with Service Discovery Gateway agent";
      uses ios-ifc:interface-grouping;
    }
    container any-query {
      description
        "Any Query configurations.";
      leaf forward {
        description
          "Enable any query forward to service discovery gateway
           agent.";
        type empty;
      }
    }
    container active-response {
      description
        "Active-response configurations";
      leaf timer {
        description
          "Configure timer for cache active response timer";
        type uint16 {
          range "5..60";
        }
      }
    }
    container mode {
      description
        "To select mode for mdns-sd gateway";
      choice mode-type {
        leaf service-peer {
          description
            "To enable mdns gateway in service-peer mode";
          type empty;
        }
        leaf sdg-agent {
          description
            "To enable mdns gateway in service discovery gateway agent mode";
          if-feature "ios-features:mdns-switch";
          type empty;
        }
      }
    }
    leaf service-announcement-count {
      description
        "Maximum Advertisements";
      type uint16 {
        range "10..500";
      }
    }
    container service-announcement-timer {
      description
        "Advertisement announcement timer periodicity in seconds";
      leaf periodicity {
        type uint16 {
          range "5..36000";
        }
      }
    }
    leaf service-query-count {
      description
        "Maximum Queries";
      type uint16 {
        range "10..500";
      }
    }
    container service-query-timer {
      description
        "Query Forward timer periodicity";
      leaf periodicity {
        type uint16 {
          range "5..36000";
        }
      }
    }
  }

  grouping mdns-sd-service-policy-ewlc-grouping {
    leaf location {
      description
        "mDNS Location Based Filtering";
      type enumeration {
        enum "lss";
        enum "site-tag";
        enum "ssid";
        enum "ap-name";
        enum "ap-location";
        enum "regex";
        enum "location-group";
      }
    }
    leaf regex-which {
      description
        "Regex based location filter";
      when "../location='regex'";
      type enumeration {
        enum "ap-name";
        enum "ap-location";
      }
    }
    leaf regex-str {
      description
        "Regex string for location filter";
      when "(../location='regex') and (../regex-which)";
      type string {
        length "1..164";
      }
    }
  }

  grouping mdns-sd-gateway-ewlc-global-grouping {
    container active-query {
      description
        "mDNS Global Active Query";
      leaf timer {
        description
          "Active Query Periodicity in Minutes";
        type uint16 {
          range "15..120";
        }
        default "30";
      }
    }
    container mdns-ap-service-policy {
      description
        "mDNS service policy for mDNS-AP";
      leaf sp-name {
        description
          "mdns service policy name for mdns AP";
        type leafref {
          path "/ios:native/ios-mdns:mdns-sd/ios-mdns:service-policy/ios-mdns:service-policy-name";
        }
      }
    }
    leaf transport {
      description
        "mDNS message processing on a specific transport";
      type enumeration {
        enum "both";
        enum "ipv4";
        enum "ipv6";
      }
      default "ipv4";
    }
  }

  grouping mdns-sd-gateway-switch-global-grouping {
    leaf air-print-helper {
      description
        "Enable or Disable Air Print Helper functionality";
      type enumeration {
        enum "enable";
        enum "disable";
      }
      default "disable";
    }
    leaf cache-memory-max {
      description
        "Configure the percentage memory for cache";
      type uint16 {
        range "10..100";
      }
    }
    container ingress-client {
      description
        "Ingress Client Packet Tuners";
      container query-reply {
        description
          "query reply count";
        when "/ios:native/ios-mdns:service-export/ios-mdns:mdns-sd/ios-mdns:controller";
        leaf service-count {
          description
            "service count for a query at once";
          type uint16 {
            range "10..200";
          }
        }
      }
      container query-suppression {
        description
          "Ingress Query Suppression";
        leaf enable {
          description
            "Enable Ingress Query Suppression";
          type empty;
        }
        leaf packet-gap {
          description
            "Response frequency for a query";
          type uint16 {
            range "5..60";
          }
        }
      }
    }
    leaf rate-limit {
      description
        "Enable rate limiting of incoming mDNS packets";
      type uint16 {
        range "1..1000";
      }
    }
    container service-type-enumeration {
      leaf period {
        description
          "Service Enumeration period in minutes";
        type uint16 {
          range "15..60";
        }
      }
    }
    container cache-sync {
      description
        "To send cache-sync event towards mDNS service-peer";
      leaf timer {
        description
          "Specify timer value";
        type uint16 {
          range "15..600";
        }
        units "minutes";
      }
    }
  }

  grouping mdns-sd-ewlc-global-grouping {
    list flex-profile {
      description
        "mdns-sd flex-profile configuration";
      key "name";
      leaf name {
        description
          "mDNS Flex profile name";
        type string;
      }
      container update-timer {
        description
          "mDNS Update timers for flex profile";
        leaf service-cache {
          description
            "mDNS service cache update timer";
          type uint16 {
            range "1..100";
          }
        }
        leaf statistics {
          description
            "mDNS statistics update timer";
          type uint16 {
            range "1..100";
          }
        }
      }
      leaf-list wired-vlan-range {
        description
          "mDNS Flex profile wired vlan filter range";
        max-elements "16";
        type uint16 {
          range "1..4094";
        }
      }
    }
  }

  grouping mdns-sd-switch-global-grouping {
    container service-peer-conf {
      description
        "mDNS service-peer command";
      container service-peer {
        container group {
          description
            "mDNS service-peer group command";
          list peer-group {
            description
              "Service peer group ID number";
            key "id";
            leaf id {
              type uint16 {
                range "1..1000";
              }
            }
            list service-peer {
              key "ip";
              leaf ip {
                type union {
                  type inet:ipv4-address;
                  type string;
                }
              }
              container location-group {
                leaf location-group-number {
                  must "not(../all)";
                  type uint16 {
                    range "1..4096";
                  }
                }
                leaf all {
                  must "not(../location-group-number)";
                  type empty;
                }
                leaf default {
                  type empty;
                }
              }
            }
            list service-policy {
              description
                "mDNS service policy";
              key "policy-name";
              leaf policy-name {
                must "/ios:native/ios-mdns:mdns-sd/ios-mdns:service-policy[ios-mdns:service-policy-name=current()]" {
                  error-message "% service-policy does not exist";
                }
                type string;
              }
            }
          }
        }
      }
    }
    container service-peer {
      status obsolete;
      description
        "This node is obsolete and replaced by service-peer-conf";
      list group {
        status obsolete;
        key "service-peer-grp-name";
        leaf service-peer-grp-name {
          status obsolete;
          type string;
        }
        list service-peer-grp-id {
          status obsolete;
          key "id";
          leaf id {
            status obsolete;
            type uint16 {
              range "1..1000";
            }
          }
          list service-peer {
            status obsolete;
            key "ip";
            leaf ip {
              status obsolete;
              type union {
                type inet:ipv4-address;
                type string;
              }
            }
            container service-group {
              status obsolete;
              leaf-list service-group-number {
                status obsolete;
                must "not(../all)";
                type union {
                  type enumeration {
                    enum "default";
                  }
                  type uint16 {
                    range "1..64";
                  }
                }
              }
              leaf all {
                status obsolete;
                must "not(../service-group-number)";
                type empty;
              }
            }
          }
        }
      }
    }
    list location-group {
      description
        "Configure mDNS location group";
      key "location-grp-id";
      leaf location-grp-id {
        description
          "Enter location group number";
        type uint16 {
          range "1..4096";
        }
      }
      list vlan {
        description
          "enter vlan number";
        max-elements "1";
        key "vlan-id";
        leaf vlan-id {
          description
            "vlan id";
          must "(/ios:native/ios:vlan/ios-vlan:configuration[ios-vlan:vlan-id=current()]/ios-mdns:mdns-sd/ios-mdns:gateway)" {
            error-message "Snooping must be enabled for the vlan";
          }
          type uint16 {
            range "1..4096";
          }
        }
        leaf description {
          description
            "Location Group description";
          type string;
        }
        container interface {
          description
            "Add interfaces to location-group";
          uses ios-ifc:interface-grouping;
        }
      }
    }
    list location-filter {
      key "loc-fil-name";
      leaf loc-fil-name {
        description
          "mDNS Location Filter Name";
        type string;
      }
      container match {
        presence "true";
        container loc_grp_configured {
          leaf location-group {
            type leafref {
              path "/ios:native/ios-mdns:mdns-sd/ios-mdns:location-group/ios-mdns:location-grp-id";
            }
          }
          leaf vlan {
            type leafref {
              path "/ios:native/ios-mdns:mdns-sd/ios-mdns:location-group[ios-mdns:location-grp-id = current()/../location-group]/ios-mdns:vlan/ios-mdns:vlan-id";
            }
          }
        }
        container loc_grp_all {
          leaf location-group {
            type empty;
          }
          leaf all {
            type empty;
          }
          leaf vlan {
            must "not(/ios:native/ios-mdns:mdns-sd/ios-mdns:location-filter/ios-mdns:match/ios-mdns:loc_grp_configured/ios-mdns:vlan = current() or /ios:native/ios-mdns:mdns-sd/ios-mdns:location-filter/ios-mdns:match/ios-mdns:loc_grp_default/ios-mdns:vlan = current())" {
              error-message "%Error: location-group 'all' is allowed only if none of the location-groups are configured for the vlan";
            }
            type uint16 {
              range "1..4096";
            }
          }
        }
        container loc_grp_default {
          leaf location-group {
            type empty;
          }
          leaf default {
            type empty;
          }
          leaf vlan {
            must "not(/ios:native/ios-mdns:mdns-sd/ios-mdns:location-filter/ios-mdns:match/ios-mdns:loc_grp_all/ios-mdns:vlan = current())" {
              error-message "%Error: location-group 'all' is already configured, cannot configure location-group";
            }
            type uint16 {
              range "1..4096";
            }
          }
        }
      }
    }
    list service-group {
      description
        "Configure mDNS service group";
      key "service-group-number";
      leaf service-group-number {
        description
          "Enter service group number";
        type uint8 {
          range "1..64";
        }
      }
      list vlan {
        description
          "vlan number";
        max-elements "1";
        key "vlan";
        leaf vlan {
          description
            "vlan id";
          must "(/ios:native/ios:vlan/ios-vlan:configuration[ios-vlan:vlan-id=current()]/ios-mdns:mdns-sd/ios-mdns:gateway)" {
            error-message "Snooping must be enabled for the vlan";
          }
          type uint16 {
            range "1..4096";
          }
        }
        container interface {
          description
            "Add interfaces to service-group";
          uses ios-ifc:interface-grouping;
        }
      }
    }
  }

  grouping mdns-sd-common-global-grouping {
    container gateway {
      description
        "mDNS Gateway Configuration";
      presence "true";
      uses mdns-sd-gateway-common-global-grouping;
      uses mdns-sd-gateway-switch-global-grouping {
        if-feature "ios-features:mdns-switch";
      }
      uses mdns-sd-gateway-ewlc-global-grouping {
        if-feature "ios-features:mdns-ewlc";
      }
    }
    list service-policy {
      description
        "mDNS Service Policy";
      key "service-policy-name";
      leaf service-policy-name {
        description
          "mDNS Service Policy Name";
        type string {
          length "1..164";
        }
      }
      uses mdns-sd-service-policy-ewlc-grouping {
        if-feature "ios-features:mdns-ewlc";
      }
      list service-list {
        key "name";
        leaf name {
          description
            "mDNS Service List Name";
          type leafref {
            path "/ios:native/ios-mdns:mdns-sd/service-list/service-list-name";
          }
        }
        leaf direction {
          description
            "Select Service List Direction IN/OUT";
          type enumeration {
            enum "IN";
            enum "OUT";
          }
        }
      }
    }
    list service-list {
      description
        "mDNS Service List";
      key "service-list-name";
      leaf service-list-name {
        description
          "mDNS Service List Name";
        type string {
          length "1..164";
        }
      }
      list direction {
        description
          "Direction IN/OUT for mDNS service-list";
        max-elements "1";
        key "dir";
        leaf dir {
          description
            "Select direction IN/OUT";
          type enumeration {
            enum "IN";
            enum "OUT";
          }
        }
        container IN {
          must "../dir = 'IN'" {
            error-message "Configuration allowed for IN direction";
          }
          description
            "IN Bound Filtering";
          presence "true";
          list match {
            description
              "Specify service to match";
            key "name";
            leaf name {
              description
                "mDNS Service Definition Name";
              type string {
                length "1..164";
              }
            }
            leaf message-type {
              description
                "To set the message type";
              type enumeration {
                enum "any";
                enum "announcement";
                enum "query";
              }
              default "any";
            }
          }
        }
        container OUT {
          must "../dir = 'OUT'" {
            error-message "Configuration allowed for OUT direction";
          }
          description
            "Out Bound Filtering";
          presence "true";
          list match {
            description
              "Specify service to match";
            key "name";
            leaf name {
              type string {
                length "1..164";
              }
            }
            leaf location-filter {
              if-feature "ios-features:mdns-switch";
              description
                "Specify location-filter";
              must "/ios:native/ios-mdns:mdns-sd/ios-mdns:location-filter[ios-mdns:loc-fil-name=current()]" {
                error-message "% location filter does not exist";
              }
              type string;
            }
          }
        }
      }
    }
    list service-definition {
      description
        "mDNS Service Definition";
      key "name";
      leaf name {
        description
          "mDNS Service Definition Name";
        type string {
          length "1..164";
        }
      }
      leaf description {
        description
          "Description of the Custom Service";
        type string {
          length "1..164";
        }
      }
      list service-type {
        key "service-type-name";
        leaf service-type-name {
          description
            "Specify Service-Type String";
          type string {
            length "1..164";
          }
        }
      }
    }
  }

  grouping config-mdns-sd-grouping {
    container mdns-sd {
      description
        "Configure mDNS Service Discovery";
      uses mdns-sd-common-global-grouping;
      uses mdns-sd-switch-global-grouping {
        if-feature "ios-features:mdns-switch";
      }
      uses mdns-sd-ewlc-global-grouping {
        if-feature "ios-features:mdns-ewlc";
      }
    }
  }

  grouping service-export-grouping {
    container service-export {
      description
        "service export";
      container mdns-sd {
        description
          "Controller MDNS configuration";
        list controller {
          description
            "Controller name";
          max-elements "1";
          key "controller-name";
          leaf controller-name {
            type string {
              length "1..164";
            }
          }
          leaf controller-address {
            description
              "Controller Address";
            type union {
              type inet:ipv4-address;
              type inet:ipv6-address;
            }
          }
          leaf controller-port {
            description
              "Controller port where service need to be exported";
            type uint16 {
              range "1..65535";
            }
            default "9991";
          }
          container controller-service-policy {
            description
              "Configure Filter to export";
            leaf csp_name {
              type string {
                length "1..164";
              }
            }
            leaf OUT {
              type empty;
            }
          }
          container controller-source-interface {
            description
              "Configure Source interface to export services";
            uses ios-ifc:interface-grouping;
          }
          leaf global-service-buffer {
            description
              "Global service instance buffer from Controller";
            type enumeration {
              enum "disable";
              enum "enable";
            }
            default "enable";
          }
        }
      }
    }
  }

  grouping mdns-sd-gateway-common-intf-vlan-grouping {
    container service-policy {
      description
        "mDNS Service Policy";
      leaf name {
        description
          "mDNS Service Policy Name";
        type leafref {
          path "/ios:native/ios-mdns:mdns-sd/ios-mdns:service-policy/ios-mdns:service-policy-name";
        }
      }
    }
  }

  grouping mdns-sd-gateway-switch-common-intf-grouping {
    container active-query {
      description
        "mDNS Active Query on interface";
      leaf timer {
        description
          "Active Query Periodicity in Sec";
        type uint16 {
          range "60..3600";
        }
        default "1800";
      }
    }
    leaf transport {
      description
        "mDNS message processing on a specific transport";
      type enumeration {
        enum "both";
        enum "ipv4";
        enum "ipv6";
      }
      default "both";
    }
    leaf service-inst-suffix {
      description
        "Configure Service Instance Suffix to append";
      type string {
        length "0..10";
      }
    }
    leaf service-mdns-query {
      description
        "mDNS Query request message processing";
      type enumeration {
        enum "all";
        enum "ptr";
      }
      default "all";
    }
  }

  grouping mdns-sd-gateway-switch-intf-vlan-grouping {
    uses mdns-sd-gateway-switch-common-intf-grouping;
  }

  grouping mdns-sd-gateway-intf-vlan-grouping {
    container mdns-sd {
      description
        "mDNS Service Discovery configuration under interface vlan";
      container gateway {
        description
          "mDNS Gateway configuration under interface vlan";
        presence "true";
        uses mdns-sd-gateway-common-intf-vlan-grouping;
        uses mdns-sd-gateway-switch-intf-vlan-grouping {
          if-feature "ios-features:mdns-switch";
        }
      }
    }
  }

  grouping mdns-sd-switch-vlan-config-grouping {
    uses mdns-sd-gateway-common-intf-vlan-grouping;
    uses mdns-sd-gateway-switch-common-intf-grouping;
    container source-interface {
      description
        "Configure source interface to communicate with Service Discovery Gateway agent";
      uses ios-ifc:interface-grouping;
    }
    leaf sdg-agent {
      description
        "Configure Service Discovery Gateway agent IPv4 address";
      type inet:ipv4-address;
    }
    container service-peer {
      status obsolete;
      description
        "Configure service-peer group";
      leaf group {
        status obsolete;
        description
          "Configure service-peer group name";
        type leafref {
          path "/ios:native/ios-mdns:mdns-sd/ios-mdns:service-peer/ios-mdns:group/ios-mdns:service-peer-grp-name";
        }
      }
    }
  }

  grouping mdns-sd-vlan-config-grouping {
    container mdns-sd {
      description
        "mDNS config on vlan config";
      container gateway {
        description
          "Enable mDNS gateway on interface";
        presence "true";
        uses mdns-sd-switch-vlan-config-grouping {
          if-feature "ios-features:mdns-switch";
        }
      }
    }
  }

  grouping mdns-sd-switch-eth-intf-grouping {
    container mdns-sd {
      description
        "mDNS commands";
      presence "true";
      leaf trust {
        description
          "Trust config for not including trunk port in any service-group";
        must "../../ios:switchport/ios-sw:mode/ios-sw:trunk" {
          error-message "Error: Not a trunk port, trust config is not allowed";
        }
        type empty;
      }
    }
  }

  augment "/ios:native" {
    uses config-mdns-sd-grouping;
    uses service-export-grouping {
      if-feature "ios-features:mdns-switch";
    }
  }
  augment "/ios:native/ios:interface/ios:Vlan" {
    uses mdns-sd-gateway-intf-vlan-grouping {
      if-feature "ios-features:vlan";
    }
  }
  augment "/ios:native/ios:vlan/ios-vlan:configuration" {
    uses mdns-sd-vlan-config-grouping;
  }
  augment "/ios:native/ios:interface/ios:GigabitEthernet" {
    uses mdns-sd-switch-eth-intf-grouping {
      if-feature "ios-features:mdns-switch";
    }
  }
  augment "/ios:native/ios:interface/ios:FastEthernet" {
    uses mdns-sd-switch-eth-intf-grouping {
      if-feature "ios-features:mdns-switch";
    }
  }
  augment "/ios:native/ios:interface/ios:TwoGigabitEthernet" {
    uses mdns-sd-switch-eth-intf-grouping {
      if-feature "ios-features:mdns-switch";
    }
  }
  augment "/ios:native/ios:interface/ios:FiveGigabitEthernet" {
    uses mdns-sd-switch-eth-intf-grouping {
      if-feature "ios-features:mdns-switch";
    }
  }
  augment "/ios:native/ios:interface/ios:AppGigabitEthernet" {
    uses mdns-sd-switch-eth-intf-grouping {
      if-feature "ios-features:mdns-switch";
    }
  }
  augment "/ios:native/ios:interface/ios:TenGigabitEthernet" {
    uses mdns-sd-switch-eth-intf-grouping {
      if-feature "ios-features:mdns-switch";
    }
  }
  augment "/ios:native/ios:interface/ios:TwentyFiveGigE" {
    uses mdns-sd-switch-eth-intf-grouping {
      if-feature "ios-features:mdns-switch";
    }
  }
  augment "/ios:native/ios:interface/ios:FortyGigabitEthernet" {
    uses mdns-sd-switch-eth-intf-grouping {
      if-feature "ios-features:mdns-switch";
    }
  }
  augment "/ios:native/ios:interface/ios:HundredGigE" {
    uses mdns-sd-switch-eth-intf-grouping {
      if-feature "ios-features:mdns-switch";
    }
  }
}
