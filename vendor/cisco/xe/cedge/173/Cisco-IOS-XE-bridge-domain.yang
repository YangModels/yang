module Cisco-IOS-XE-bridge-domain {
  namespace "http://cisco.com/ns/yang/Cisco-IOS-XE-bridge-domain";
  prefix ios-bd;

  import cisco-semver {
    prefix cisco-semver;
  }
  import ietf-inet-types {
    prefix inet;
  }
  import Cisco-IOS-XE-native {
    prefix ios;
  }
  import Cisco-IOS-XE-l2vpn {
    prefix ios-l2vpn;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Bridge Domain Yang model
     Copyright (c) 2017 - 2020 by Cisco Systems, Inc.
     All rights reserved.";

  revision 2020-03-01 {
    description
      "- Changed leaf node service-instance to a list node";
  }
  revision 2019-11-01 {
    description
      "- Added pseudo wire config";
    cisco-semver:module-version "2.0.0";
  }
  revision 2019-07-01 {
    description
      "- Establish semantic version baseline
       - Add bridge-domain member BD-VIF";
    cisco-semver:module-version "1.0.0";
  }
  revision 2018-11-07 {
    description
      "Cleanup spelling errors in description statements";
  }
  revision 2018-07-30 {
    description
      "Support EVPN instance";
  }
  revision 2017-02-07 {
    description
      "Initial revision";
  }

  typedef bdomain-member-interface {
    type string {
      pattern "([Ff][Aa][Ss][Tt][Ee][Tt][Hh][Ee][Rr][Nn][Ee][Tt]|[Gg][Ii][Gg][Aa][Bb][Ii][Tt][Ee][Tt][Hh][Ee][Rr][Nn][Ee][Tt]|[Tt][Ww][Oo][Gg][Ii][Gg][Aa][Bb][Ii][Tt][Ee][Tt][Hh][Ee][Rr][Nn][Ee][Tt]|[Ff][Ii][Vv][Ee][Gg][Ii][Gg][Aa][Bb][Ii][Tt][Ee][Tt][Hh][Ee][Rr][Nn][Ee][Tt]|[Aa][Pp][Pp][Gg][Ii][Gg][Aa][Bb][Ii][Tt][Ee][Tt][Hh][Ee][Rr][Nn][Ee][Tt]|[Tt][Ee][Nn][Gg][Ii][Gg][Aa][Bb][Ii][Tt][Ee][Tt][Hh][Ee][Rr][Nn][Ee][Tt]|[Tt][Ww][Ee][Nn][Tt][Yy][Ff][Ii][Vv][Ee][Gg][Ii][Gg][Ee]|[Ff][Oo][Rr][Tt][Yy][Gg][Ii][Gg][Aa][Bb][Ii][Tt][Ee][Tt][Hh][Ee][Rr][Nn][Ee][Tt]|[Hh][Uu][Nn][Dd][Rr][Ee][Dd][Gg][Ii][Gg][Ee]|[Pp][Oo][Rr][Tt]-[Cc][Hh][Aa][Nn][Nn][Ee][Ll]).*";
    }
  }

  grouping config-bdomain-mode-grouping {
    container ip {
      description
        "IP related commands";
      container igmp {
        description
          "IP igmp commands";
        container snooping {
          description
            "IP igmp snooping commands";
          presence "true";
          container check {
            description
              "enforce TTL or Rtr-Alert Option checking";
            leaf rtr-alert-option-boolean {
              description
                "Only accept IGMP packets with router-alert option";
              type boolean;
              default "true";
            }
            leaf rtr-alert-option {
              status deprecated;
              description
                "Only accept IGMP packets with router-alert option, deprecated and replaced by rtr-alert-option-boolean";
              type empty;
            }
            leaf ttl-boolean {
              description
                "Only accept IGMP packets with TTL=1";
              type boolean;
              default "true";
            }
            leaf ttl {
              status deprecated;
              description
                "Only accept IGMP packets with TTL=1, deprecated and replaced by ttl-boolean";
              type empty;
            }
          }
          container explicit-tracking {
            description
              "IGMP explicit host tracking configuration";
            leaf limit-value {
              description
                "Explicit Host Tracking DB limit";
              type uint32 {
                range "0..128000";
              }
            }
            leaf limit {
              status obsolete;
              description
                "Explicit Host Tracking DB limit";
              type empty;
            }
          }
          leaf immediate-leave {
            description
              "Enable IGMPv2 immediate leave processing";
            type empty;
          }
          leaf last-member-query-count {
            description
              "Last member query count";
            type uint8 {
              range "1..7";
            }
          }
          leaf last-member-query-interval {
            description
              "Last member query interval";
            type uint16 {
              range "100..32767";
            }
          }
          container mrouter {
            description
              "Configure an L2 port as a multicast router port";
            list interface-cfg {
              description
                "next-hop interface to mrouter";
              key "name";
              leaf name {
                type string {
                  pattern "[FfGgTtPp][OoIiEeWw].*";
                }
              }
              leaf efp_id {
                description
                  "efp number on the interface";
                type uint16 {
                  range "1..8000";
                }
              }
            }
            leaf interface {
              status obsolete;
              description
                "next-hop interface to mrouter";
              type empty;
            }
          }
          container querier {
            description
              "Enable IGMP querier for this Bdomain";
            presence "true";
            leaf address-value {
              description
                "IGMP querier source IP address";
              type inet:ipv4-address;
            }
            leaf address {
              status obsolete;
              description
                "IGMP querier source IP address";
              type empty;
            }
            leaf max-response-time-value {
              description
                "IGMP querier maximum response time (sec)";
              type uint8 {
                range "1..25";
              }
            }
            leaf max-response-time {
              status obsolete;
              description
                "IGMP querier maximum response time (sec)";
              type empty;
            }
            leaf query-interval-value {
              description
                "IGMP querier query interval (sec)";
              type uint16 {
                range "1..18000";
              }
            }
            leaf query-interval {
              status obsolete;
              description
                "IGMP querier query interval (sec)";
              type empty;
            }
            container tcn-parameters {
              description
                "IGMP querier TCN related parameters";
              container query {
                leaf count {
                  description
                    "IGMP querier TCN query count";
                  type uint16 {
                    range "1..10";
                  }
                }
                leaf interval {
                  description
                    "IGMP querier TCN query interval (sec)";
                  type uint16 {
                    range "1..255";
                  }
                }
              }
            }
            leaf tcn {
              status obsolete;
              description
                "IGMP querier TCN related parameters";
              type empty;
            }
            container timer-expiry {
              description
                "IGMP other querier timer";
              leaf expiry {
                description
                  "IGMP querier other querier time out (sec)";
                type uint16 {
                  range "60..300";
                }
              }
            }
            leaf timer {
              status obsolete;
              description
                "IGMP other querier timer";
              type empty;
            }
            leaf version-value {
              description
                "IGMP version";
              type uint8 {
                range "1..3";
              }
            }
            leaf version {
              status obsolete;
              description
                "IGMP version";
              type empty;
            }
          }
          leaf report-suppression-boolean {
            description
              "Enable IGMP report suppression";
            type boolean;
            default "true";
          }
          leaf report-suppression {
            status deprecated;
            description
              "Enable IGMP report suppression, deprecated and replaced by report-suppression-boolean";
            type empty;
          }
          leaf robustness-variable {
            description
              "IGMP snooping bdomain robustness variable";
            type uint8 {
              range "1..3";
            }
          }
          list static-cfg {
            description
              "Configure an L2 port as a member of a group";
            key "group-addr";
            leaf group-addr {
              description
                "IP address of the group";
              type inet:ipv4-address;
            }
            list interface {
              description
                "Specify an interface statically configured";
              key "name";
              leaf name {
                type string {
                  pattern "[FfGgTtPp][OoIiEeWw].*";
                }
              }
            }
            list source {
              description
                "a source of the group";
              key "source-ip-addr interface";
              leaf source-ip-addr {
                description
                  "IP address of the source";
                type inet:ipv4-address;
              }
              leaf interface {
                description
                  "Specify an interface statically configured";
                type string {
                  pattern "[FfGgTtPp][OoIiEeWw].*";
                }
              }
              leaf service-instance {
                description
                  "service instance number";
                type uint16 {
                  range "1..8000";
                }
              }
            }
          }
          leaf static {
            status obsolete;
            description
              "Configure an L2 port as a member of a group";
            type inet:ipv4-address;
          }
        }
      }
    }
    container mac {
      description
        "MAC Address related commands";
      leaf aging-time {
        description
          "Set age time of mac addresses per bridge domain";
        type uint16 {
          range "30..21600";
        }
      }
      leaf learning-boolean {
        description
          "Disable mac learning on bridge domain";
        type boolean;
        default "true";
      }
      leaf learning {
        status deprecated;
        description
          "Disable mac learning on bridge domain, deprecated and replaced by learning-boolean";
        type empty;
      }
      container limit {
        description
          "Limit the MAC Addresses learnt";
        container action {
          description
            "action when exceeding the limit";
          container flooding {
            description
              "Mac flooding";
            leaf disable {
              description
                "disable";
              type empty;
            }
          }
        }
        container maximum {
          description
            "Maximum";
          leaf addresses {
            description
              "Addresses";
            type uint32 {
              range "1..65536";
            }
          }
        }
      }
    }
    container member {
      description
        "bridge-domain member";
      list mem-ipv4 {
        key "mem-ipv4";
        leaf mem-ipv4 {
          description
            "IP address of the peer";
          type inet:ipv4-address;
        }
        list mem-vcid {
          key "mem-vcid";
          leaf mem-vcid {
            description
              "<1..4294967295>;;Enter VC ID value";
            type uint32 {
              range "1..4294967295";
            }
          }
          container encapsulation {
            description
              "Data encapsulation method";
            presence "true";
            leaf mpls {
              description
                "Use MPLS encapsulation";
              type empty;
            }
          }
          container template {
            description
              "Template to use for encapsulation and protocol configuration";
            presence "true";
            leaf template {
              description
                "<WORD>;;template name (Max size 32)";
              type string;
            }
          }
        }
        container encapsulation {
          description
            "Data encapsulation method";
          leaf mpls {
            description
              "Use MPLS encapsulation";
            type empty;
          }
        }
        leaf template {
          description
            "Template to use for encapsulation and protocol configuration";
          type string;
        }
      }
      list ACR {
        key "acr-int";
        leaf acr-int {
          description
            "<WORD>;;Virtual ACR interface";
          type string;
        }
        container service-instance {
          description
            "ethernet service instance";
          list id {
            key "id";
            leaf id {
              description
                "<1..8000>;;Service Instance Identifier";
              type uint16 {
                range "1..8000";
              }
            }
            leaf split-horizon {
              description
                "Configure this port as a member of a split horizon group";
              type empty;
            }
          }
        }
      }
      leaf Analysis-Module {
        description
          "Cisco network analysis service module";
        type uint8;
      }
      leaf Fcpa {
        description
          "Fiber Channel";
        type uint8;
      }
      leaf SBC {
        description
          "Session Border Controller";
        type uint32 {
          range "0..2147483647";
        }
      }
      leaf SONET_ACR {
        description
          "Virtual SONET-ACR controller";
        type uint8;
      }
      leaf _controller {
        status obsolete;
        type string {
          pattern "(OBSOLETED)";
        }
      }
      leaf Service-Engine {
        description
          "Cisco service engine module";
        type uint8;
      }
      leaf Tunnel-tp {
        description
          "MPLS Transport Profile interface";
        type uint16 {
          range "0..65535";
        }
      }
      leaf VPN {
        description
          "VPN interface";
        type uint32 {
          range "0..2147483647";
        }
      }
      leaf Virtual-TokenRing {
        description
          "Virtual TokenRing";
        type uint32 {
          range "0..2147483647";
        }
      }
      leaf ucse {
        description
          "Cisco ucse server";
        type uint8;
      }
      leaf vasileft {
        description
          "VasiLeft interface";
        type uint16 {
          range "1..2000";
        }
      }
      leaf vasiright {
        description
          "VasiRight interface";
        type uint16 {
          range "1..2000";
        }
      }
      leaf vfi {
        description
          "Enter VFI name";
        must "/ios:native/ios:l2vpn/ios-l2vpn:vfi/ios-l2vpn:context[ios-l2vpn:vfi-nm = current()]/ios-l2vpn:vpn/ios-l2vpn:id" {
          error-message "A VFI context must be configured with a valid vpn id first";
        }
        type string;
      }
      leaf vni {
        type uint32 {
          range "4096..16777215";
        }
      }
      list member-interface {
        key "interface";
        leaf interface {
          type bdomain-member-interface;
        }
        leaf interface-id {
          status obsolete;
          type union {
            type string;
            type uint32;
          }
        }
        list service-instance-list {
          description
            "ethernet service instance";
          key "instance-id";
          leaf instance-id {
            type uint32 {
              range "1..8000";
            }
          }
          container split-horizon {
            description
              "Configure this port as a member of a split horizon group";
            leaf group {
              description
                "Split-horizon group";
              type uint8;
            }
          }
          container remote {
            description
              "remote peer configuration commands";
            container circuit {
              description
                "Remote peer circuit configuration";
              leaf id {
                description
                  "Remote peer circuit ID";
                type uint16;
              }
            }
          }
        }
        leaf service-instance {
          description
            "ethernet service instance. This node is deprecated and replaced
             by service-instance-list";
          status deprecated;
          type uint32 {
            range "1..8000";
          }
        }
        container split-horizon {
          description
            "Configure this port as a member of a split horizon group. This node
             is deprecated and replaced by service-instance-list/split-horizon";
          status deprecated;
          leaf group {
            description
              "Split-horizon group. This node is deprecated and replaced
               by service-instance-list/split-horizon/group";
            status deprecated;
            type uint8;
          }
        }
        container remote {
          description
            "remote peer configuration commands. This node is deprecated
             and replaced by service-instance-list/remote";
          status deprecated;
          container circuit {
            description
              "Remote peer circuit configuration. This node is deprecated
               and replaced by service-instance-list/remote/circuit";
            status deprecated;
            leaf id {
              description
                "Remote peer circuit ID. This node is deprecated and replaced
                 by service-instance-list/remote/circuit/id";
              status deprecated;
              type uint16;
            }
          }
        }
      }
      list evpn-instance {
        description
          "Ethernet Virtual Private Network (EVPN) instance";
        key "instance-num";
        leaf instance-num {
          description
            "EVPN instance number.";
          type uint16 {
            range "1..65535";
          }
        }
        choice evpn-service-type {
          description
            "Evpn Service type.";
          leaf ethernet-tag {
            when "/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware and (/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation = 'mpls' or not(/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation))";
            description
              "Ethernet tag value.";
            type uint16 {
              range "1..4094";
            }
          }
          leaf vni {
            when "/ios:native/ios:l2vpn/ios-l2vpn:evpn_cont/ios-l2vpn:evpn-instance/ios-l2vpn:evpn/ios-l2vpn:instance/ios-l2vpn:instance[ios-l2vpn:evpn-instance-num = current()/../instance-num]/ios-l2vpn:vlan-aware/ios-l2vpn:encapsulation = 'vxlan'";
            description
              "VxLAN VNI.";
            type uint32 {
              range "4096..16777215";
            }
          }
        }
      }
      list pseudowire {
        description
          "Pseudowire Interface";
        must "current()/../ios-bd:vfi" {
          error-message "A VFI member must be configured first";
        }
        key "name";
        leaf name {
          type uint32 {
            range "1..231072";
          }
        }
        leaf peer-addr {
          description
            "IP address of the peer";
          type inet:ipv4-address;
        }
        leaf vc-id {
          description
            "VC ID value";
          type uint32;
        }
        choice pw-encap-templ {
          leaf encapsulation {
            description
              "Data encapsulation method";
            type enumeration {
              enum "mpls";
            }
          }
          leaf template {
            description
              "Template to use for encapsulation and protocol configuration";
            type string;
          }
        }
      }
      list BD-VIF {
        description
          "Bridge-Domain Virtual IP interface";
        key "name";
        leaf name {
          type uint16;
        }
      }
    }
    leaf shutdown {
      description
        "Take the bridge domain admin down";
      type empty;
    }
  }

  grouping config-bridge-domain-grouping {
    list brd-id {
      key "bridge-domain-id";
      leaf bridge-domain-id {
        description
          "<1..16000>;;bridge-domain ID";
        type uint16 {
          range "1..16000";
        }
      }
      uses config-bdomain-mode-grouping;
    }
    container c-mac {
      description
        "Configure c-mac global commands";
      leaf aging-time {
        description
          "Configure aging time for c-mac bridge domains";
        type uint16 {
          range "30..21600";
        }
      }
    }
    container otv {
      description
        "Configure overlay bridge domains";
      container default {
        description
          "Change default setting of overlay bridge domains";
        leaf age-time {
          description
            "Configure default mac aging time of overlay bridge domains";
          type uint16 {
            range "30..21600";
          }
        }
      }
    }
    container parameterized {
      description
        "bridge-domain is derived from parameters";
      container vlan {
        description
          "bridge-domain from service instance vlan";
        presence "true";
        uses config-bdomain-mode-grouping;
      }
    }
  }

  augment "/ios:native/ios:bridge-domain" {
    uses config-bridge-domain-grouping;
  }
}
