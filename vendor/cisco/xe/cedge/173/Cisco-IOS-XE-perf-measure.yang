module Cisco-IOS-XE-perf-measure {
  namespace "http://cisco.com/ns/yang/Cisco-IOS-XE-perf-measure";
  prefix ios-performance-measurement;

  import cisco-semver {
    prefix cisco-semver;
  }
  import ietf-inet-types {
    prefix inet;
  }
  import Cisco-IOS-XE-native {
    prefix ios;
  }
  import Cisco-IOS-XE-types {
    prefix ios-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Performance-Measurement Yang model.
     Copyright (c) 2016, 2018-2019 by Cisco Systems, Inc.
     All rights reserved.";

  revision 2020-03-01 {
    description
      "- Added next-hop config";
  }
  revision 2019-11-01 {
    description
      "Initial revision";
    cisco-semver:module-version "1.0.0";
  }

  typedef ipv4-address-sweep-range {
    type string {
      pattern "((127)\\.)(([0-9]|[1-9][0-9]|1[0-9][0-9]|2[0-4][0-9]|25[0-5])\\.){2}([0-9]|[1-9][0-9]|11[0-9]|12[0-7])";
    }
  }

  grouping config-perf-measure-advertisement-grouping {
    description
      "Common node for delay profile advertisment";
    container advertisement {
      description
        "Advertisement Profile";
      container accelerated {
        description
          "Accelerated Advertisement Profile";
        presence "true";
        leaf threshold {
          description
            "Accelerated advertisement threshold percentage";
          type ios-types:percentage;
          units "percentage";
          default "20";
        }
        leaf minimum-change {
          description
            "Accelerated advertisement minimum value in
             microseconds (uSec)";
          type uint32 {
            range "0..1000000";
          }
          units "microseconds";
          default "500";
        }
      }
      container periodic {
        description
          "Periodic Advertisement Profile";
        leaf interval {
          description
            "Periodic advertisement interval in seconds";
          type uint32 {
            range "30..3600";
          }
          units "second";
          default "120";
        }
        leaf threshold {
          description
            "Periodic advertisement threshold percentage";
          type ios-types:percentage;
          units "percentage";
          default "10";
        }
        leaf minimum-change {
          description
            "Periodic advertisement minimum value in microseconds (uSec)";
          type uint32 {
            range "0..1000000";
          }
          units "microsecond";
        }
        leaf disable {
          description
            "Disable Performance Measurement Periodic Advertisement";
          type empty;
        }
      }
    }
  }

  grouping config-perf-measure-advertisement-grouping-srpolicy {
    description
      "Common node for delay profile advertisment";
    container advertisement {
      description
        "Advertisement Profile";
      container accelerated {
        description
          "Accelerated Advertisement Profile";
        presence "true";
        leaf threshold {
          description
            "Accelerated advertisement threshold percentage";
          type ios-types:percentage;
          units "percentage";
          default "20";
        }
        leaf minimum-change {
          description
            "Accelerated advertisement minimum value in
             microseconds (uSec)";
          type uint32 {
            range "0..1000000";
          }
          units "microseconds";
          default "500";
        }
      }
      container periodic {
        description
          "Periodic Advertisement Profile";
        leaf interval {
          description
            "Periodic advertisement interval in seconds";
          type uint32 {
            range "30..3600";
          }
          units "second";
          default "120";
        }
        leaf threshold {
          description
            "Periodic advertisement threshold percentage";
          type ios-types:percentage;
          units "percentage";
          default "10";
        }
        leaf minimum-change {
          description
            "Periodic advertisement minimum value in microseconds (uSec)";
          type uint32 {
            range "0..1000000";
          }
          units "microsecond";
        }
        leaf disable {
          description
            "Disable Performance Measurement Periodic Advertisement";
          type empty;
        }
      }
      container threshold-check {
        description
          "Threshold Check";
        choice mode-choice {
          default "average-delay";
          case average-delay {
            leaf average-delay {
              description
                "Enable average-delay threshold check";
              type empty;
            }
          }
          case minimum-delay {
            leaf minimum-delay {
              description
                "Enable minimum-delay threshold check";
              type empty;
            }
          }
          case maximum-delay {
            leaf maximum-delay {
              description
                "Enable maximum-delay threshold check";
              type empty;
            }
          }
        }
      }
    }
  }

  grouping config-perf-measure-probe-grouping {
    container probe {
      description
        "PM Delay Profile Probe";
      leaf computation-interval {
        description
          "The value for delay profile probe interval in seconds";
        type uint32 {
          range "3..3600";
        }
        units "second";
        default "30";
      }
      container measurement-mode {
        description
          "Delay measurement mode";
        choice mode-choice {
          default "two-way";
          case two-way {
            leaf two-way {
              description
                "Enable two-way delay measurement";
              type empty;
            }
          }
          case one-way {
            leaf one-way {
              type empty;
              description
                "Enable one-way delay measurement";
            }
          }
        }
      }
      leaf burst-interval {
        description
          "The value for delay profile probe burst
           interval in milliseconds";
        type uint32 {
          range "30..15000";
        }
        units "millisecond";
        default "3000";
      }
      container protocol {
        description
          "Protocol used to send probes";
        choice protocol-choice {
          default "pm-mpls";
          case pm-mpls {
            leaf pm-mpls {
              description
                "Interface delay measurement using RFC 6374 with MPLS encap";
              type empty;
            }
          }
          case twamp-light {
            leaf twamp-light {
              description
                "Interface delay measurement using RFC 5357";
              type empty;
            }
          }
        }
      }
    }
  }

  grouping config-perf-measure-probe-grouping-srpolicy {
    container probe {
      description
        "PM Delay Profile Probe";
      leaf computation-interval {
        description
          "The value for delay profile probe interval in seconds";
        type uint32 {
          range "3..3600";
        }
        units "second";
        default "30";
      }
      container measurement-mode {
        description
          "Delay measurement mode";
        choice mode-choice {
          default "one-way";
          case two-way {
            leaf two-way {
              description
                "Enable two-way delay measurement";
              type empty;
            }
          }
          case one-way {
            leaf one-way {
              description
                "Enable one-way delay measurement";
              type empty;
            }
          }
        }
      }
      leaf burst-interval {
        description
          "The value for delay profile probe burst
           interval in milliseconds";
        type uint32 {
          range "30..15000";
        }
        units "millisecond";
        default "3000";
      }
      container protocol {
        description
          "Protocol used to send probes";
        choice protocol-choice {
          default "pm-mpls";
          case pm-mpls {
            leaf pm-mpls {
              description
                "SR Policy delay measurement using RFC 6374 with MPLS encap";
              type empty;
            }
          }
          case twamp-light {
            leaf twamp-light {
              description
                "SR Policy delay measurement using RFC 5357";
              type empty;
            }
          }
        }
      }
      container sweep {
        description
          "Enable ECMP hashing by sweeping a field in the probe";
        container destination {
          description
            "Sweep a range of IP destination addresses";
          leaf ipv4 {
            description
              "IPv4 address";
            type ipv4-address-sweep-range;
          }
          leaf range {
            description
              " Start of the IPv4 address range";
            type uint16 {
              range "0..128";
            }
          }
        }
      }
    }
  }

  grouping config-perf-measure-grouping {
    list interface {
      description
        "Configure a performance-measurement interface";
      key "interface-name";
      leaf interface-name {
        type string;
      }
      container delay-measurement {
        description
          "Interface delay measurement";
        presence "true";
        leaf advertise-delay {
          description
            "The value for interface delay measurement
             advertisement delay in uSec";
          type uint32 {
            range "0..16777215";
          }
          units "microsecond";
        }
      }
      container next-hop {
        description
          "next-hop address";
        choice nexthop-address-choice {
          case nexthop-ipv4-address {
            leaf ipv4 {
              description
                "IPv4 address";
              type inet:ipv4-address;
            }
          }
          case nexthop-ipv6-address {
            leaf ipv6 {
              description
                "IPv6 address";
              type inet:ipv6-address;
            }
          }
        }
      }
    }
    container delay-profile {
      description
        "Performance-measurement delay profile";
      container interfaces {
        description
          "Performance-measurement interface delay profile";
        uses config-perf-measure-advertisement-grouping;
        uses config-perf-measure-probe-grouping;
      }
      container sr-policy {
        description
          "Performance-measurement sr-policy delay profile";
        uses config-perf-measure-advertisement-grouping-srpolicy;
        uses config-perf-measure-probe-grouping-srpolicy;
      }
    }
    container protocol {
      description
        "Supported Protocol";
      container twamp-light {
        description
          "Enter twamp-light protocol submode";
        container measurement {
          description
            "Supported measurement types";
          container delay {
            description
              "Enter delay measurement submode";
            container unauthenticated {
              description
                "Enter unauthenticated mode";
              leaf querier-dst-port {
                description
                  "<11000-14999>  Port number";
                type uint16 {
                  range "11000..14999";
                }
              }
              leaf querier-src-port {
                description
                  "<11000-14999>  Port number";
                must "not (. = ../querier-dst-port)" {
                  error-message "querier-dst-port and querier-src-port cannot be configured equal";
                }
                type uint16 {
                  range "11000..14999";
                }
              }
            }
          }
        }
      }
    }
    leaf max-pps {
      description
        "Configure maximum packets per second allowed";
      type uint16 {
        range "0..2000";
      }
    }
  }

  augment "/ios:native/ios:performance-measurement" {
    uses config-perf-measure-grouping;
  }
}
