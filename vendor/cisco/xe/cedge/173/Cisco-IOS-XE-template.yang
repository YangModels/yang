module Cisco-IOS-XE-template {
  namespace "http://cisco.com/ns/yang/ios-xe/template";
  prefix ios-template;

  import cisco-semver {
    prefix cisco-semver;
  }
  import ietf-inet-types {
    prefix inet;
  }
  import Cisco-IOS-XE-native {
    prefix ios;
  }
  import Cisco-IOS-XE-features {
    prefix ios-features;
  }
  import Cisco-IOS-XE-interface-common {
    prefix ios-ifc;
  }
  import Cisco-IOS-XE-policy {
    prefix ios-policy;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Template Yang Model.
     Copyright (c) 2016-2019 by Cisco Systems, Inc.
     All rights reserved.";

  revision 2020-07-02 {
    description
      "- Initial revision for 17.3.2";
  }
  revision 2020-07-01 {
    description
      "- Added policy container under segment-routing traffic-eng
       - Removed policy container under segment-routing traffic-eng";
  }
  revision 2020-03-01 {
    description
      "Added device-tracking and ra guard template";
  }
  revision 2019-11-01 {
    description
      "Added new template";
    cisco-semver:module-version "2.0.0";
  }
  revision 2019-07-01 {
    description
      "- Establish semantic version baseline
       - Added template type pseudowire support
       - Added support for access-session control-direction and host-mode clis inside template";
    cisco-semver:module-version "1.0.0";
  }
  revision 2019-01-29 {
    description
      "Added template type pseudowire support";
  }
  revision 2018-11-07 {
    description
      "Cleanup spelling errors in description statements";
  }
  revision 2018-08-20 {
    description
      "Added some model for template";
  }
  revision 2017-11-06 {
    description
      "Make some option switch platform dependent";
  }
  revision 2017-02-13 {
    description
      "Initial Revision";
  }

  grouping vlanlist-grouping {
    container vlan {
      description
        "Vlan list for which this policy applies";
      leaf add {
        description
          "add VLANs to the current list";
        type string;
      }
      leaf except {
        description
          "all VLANs except the following";
        type string;
      }
      leaf remove {
        description
          "remove VLANs from the current list";
        type string;
      }
      leaf vlan-range {
        description
          "VLAN IDs of the VLANs for which this policy applies";
        type string;
      }
      leaf all {
        description
          "all VLANs";
        type empty;
      }
      leaf none {
        description
          "no VLANs";
        type empty;
      }
    }
  }

  grouping template-grouping {
    container dot1x {
      description
        "Interface Config Commands for IEEE 802.1X";
      leaf pae {
        description
          "Set 802.1x interface pae type";
        type enumeration {
          enum "authenticator";
          enum "both";
          enum "supplicant";
        }
      }
      leaf max-reauth-req {
        description
          "Max No. of Reauthentication Attempts";
        type uint8 {
          range "1..10";
        }
        default "2";
      }
      leaf max-req {
        description
          "Max No. of Retries";
        type uint8 {
          range "1..10";
        }
        default "2";
      }
      container timeout {
        description
          "Various Timeouts";
        leaf quiet-period {
          description
            "QuietPeriod in Seconds";
          type uint16 {
            range "1..65535";
          }
          default "60";
        }
        leaf ratelimit-period {
          description
            "Ratelimit Period in seconds";
          type uint16 {
            range "1..65535";
          }
        }
        leaf server-timeout {
          description
            "Timeout for Radius Retries";
          type uint16 {
            range "1..65535";
          }
        }
        leaf supp-timeout {
          description
            "Timeout for supplicant reply";
          type uint16 {
            range "1..65535";
          }
          default "30";
        }
        leaf tx-period {
          description
            "Timeout for supplicant retries";
          type uint16 {
            range "1..65535";
          }
          default "30";
        }
      }
    }
    container service-policy {
      description
        "Configure CPL Service Policy";
      container input {
        description
          "Assign policy-map to the input of an interface";
        leaf policy-map-name {
          description
            "policy-map name";
          type string;
        }
      }
      container output {
        description
          "Assign policy-map to the output of an interface";
        leaf policy-map-name {
          description
            "policy-map name";
          type string;
        }
      }
      container type {
        description
          "Configure CPL Service Policy";
        container control {
          description
            "Apply a control policy to the interface";
          leaf subscriber {
            description
              "Apply a subscriber control policy to the interface";
            must "(/ios:native/ios:policy/ios-policy:policy-map[ios-policy:name = current()]/ios-policy:type = 'control' or .='BUILTIN_AUTOCONF_POLICY')" {
              error-message "policy map should be of same type and should exist";
            }
            type string;
          }
        }
      }
    }
    container source {
      description
        "Get config from another source";
      leaf template {
        description
          "Get config from a template";
        type string {
          length "1..max";
        }
      }
    }
    container switchport {
      description
        "Set switching mode characteristics";
      if-feature "ios-features:switching-platform";
      container mode {
        description
          "Set trunking mode of the interface";
        leaf trunk {
          description
            "Set trunking mode to TRUNK unconditionally";
          type empty;
        }
        leaf access {
          description
            "Set trunking mode to ACCESS unconditionally";
          type empty;
        }
      }
      leaf nonegotiate {
        description
          "Device will not engage in negotiation protocol on this interface";
        type empty;
      }
      container block {
        description
          "Disable forwarding of unknown uni/multi cast addresses";
        leaf unicast {
          description
            "Block unknown unicast addresses";
          type empty;
        }
      }
      container port-security {
        description
          "Security related command";
        presence "true";
        container aging {
          description
            "Port-security aging commands";
          leaf static {
            description
              "Enable aging for configured secure addresses";
            type empty;
          }
          leaf time {
            description
              "Port-security aging time";
            type uint16 {
              range "1..1440";
            }
          }
          container type {
            description
              "Port-security aging type";
            presence "true";
            leaf inactivity {
              description
                "Aging based on inactivity time period";
              type empty;
            }
          }
        }
        container maximum {
          description
            "Max secure addresses";
          list range {
            key "range";
            leaf range {
              description
                "Maximum addresses";
              type uint16 {
                range "1..3072";
              }
            }
            container vlan {
              description
                "Max secure addresses per vlan";
              presence "true";
              leaf access {
                description
                  "access vlan";
                type empty;
              }
            }
          }
        }
        container violation {
          description
            "Security violation mode";
          leaf protect {
            description
              "Security violation protect mode";
            type empty;
          }
          leaf restrict {
            description
              "Security violation restrict mode";
            type empty;
          }
          leaf shutdown {
            description
              "Security violation shutdown mode";
            type empty;
          }
        }
      }
      container access {
        description
          "Set access mode characteristics of the interface";
        leaf vlan {
          description
            "VLAN ID of the VLAN when this port is in access mode";
          type uint16 {
            range "1..4094";
          }
        }
      }
      container voice {
        description
          "Voice appliance attributes";
        leaf vlan {
          description
            "Vlan for voice traffic";
          type uint16 {
            range "1..4094";
          }
        }
      }
    }
    container mab {
      description
        "MAC Authentication Bypass Interface Config Commands";
      presence "true";
      leaf eap {
        description
          "Use EAP authentication for MAC Auth Bypass";
        type empty;
      }
    }
    container access-session {
      description
        "Access Session specific Interface Configuration Commands";
      leaf closed {
        description
          "Enable closed access on port (disabled by default, i.e. open access)";
        type empty;
      }
      leaf port-control {
        description
          "Set the port-control value";
        type enumeration {
          enum "auto";
          enum "force-authorized";
          enum "force-unauthorized";
        }
        default "force-authorized";
      }
      leaf control-direction {
        description
          "Set the control-direction on the interface";
        type enumeration {
          enum "both";
          enum "in";
        }
        default "both";
      }
      leaf host-mode {
        description
          "Set the Host mode for authentication on this interface";
        type enumeration {
          enum "multi-auth";
          enum "multi-domain";
          enum "multi-host";
          enum "single-host";
        }
        default "multi-auth";
      }
      container interface-template {
        description
          "Set the local interface-template sticky";
        container sticky {
          description
            "Interface templates set to sticky";
          presence "true";
          leaf timer {
            description
              "Sticky timer value";
            type uint16 {
              range "1..65535";
            }
          }
        }
      }
    }
    container authentication {
      description
        "Auth Manager Interface Configuration Commands";
      leaf periodic {
        description
          "Enable or Disable Reauthentication for this port";
        type empty;
      }
      container timer {
        description
          "Set authentication timer values";
        container reauthenticate {
          description
            "Time in seconds after which an automatic re-authentication should be initiated (default 1 hour)";
          choice value {
            leaf server {
              description
                "Obtain re-authentication timeout value from the server";
              type empty;
            }
            leaf range {
              description
                "Enter a value between 1 and 65535";
              type uint16 {
                range "1..65535";
              }
              default "3600";
            }
          }
        }
      }
    }
    container spanning-tree {
      description
        "Spanning Tree Subsystem";
      presence "true";
      container bpduguard {
        description
          "Don't accept BPDUs on this interface";
        leaf enable {
          description
            "Enable BPDU guard for this interface";
          type empty;
        }
      }
      leaf service-policy {
        description
          "help";
        type empty;
      }
      container portfast {
        description
          "Portfast options for the interface";
        presence "true";
        leaf disable {
          description
            "Disable portfast for this interface";
          type empty;
        }
        leaf edge {
          description
            "Enable portfast edge on the interface";
          type empty;
        }
        leaf network {
          description
            "Enable portfast network on the interface";
          type empty;
        }
      }
    }
    container storm-control {
      description
        "storm configuration";
      if-feature "ios-features:switching-platform";
      container broadcast {
        description
          "Broadcast address storm control";
        container level {
          description
            "Set storm suppression level on this interface";
          container pps {
            description
              "Enter suppression level in packets per second";
            leaf threshold {
              description
                "Enter threshold";
              type string;
            }
          }
          container bps {
            description
              "Enter suppression level in bits per second";
            leaf threshold {
              description
                "Enter threshold";
              type decimal64 {
                fraction-digits 1;
                range "0.0..10000000000.0";
              }
            }
            leaf b-unit {
              type string;
            }
          }
          leaf threshold {
            description
              "Enter threshold";
            type decimal64 {
              fraction-digits 2;
              range "0.00..100.00";
            }
          }
        }
      }
      container multicast {
        description
          "Multicast address storm control";
        container level {
          description
            "Set storm suppression level on this interface";
          container pps {
            description
              "Enter suppression level in packets per second";
            leaf threshold {
              description
                "Enter threshold";
              type string;
            }
          }
          container bps {
            description
              "Enter suppression level in bits per second";
            leaf threshold {
              description
                "Enter threshold";
              type decimal64 {
                fraction-digits 1;
                range "0.0..10000000000.0";
              }
            }
            leaf b-unit {
              type string;
            }
          }
          leaf threshold {
            description
              "Enter threshold";
            type decimal64 {
              fraction-digits 2;
              range "0.00..100.00";
            }
          }
        }
      }
      container action {
        description
          "Action to take for storm-control";
        leaf shutdown {
          description
            "Shutdown this interface if a storm occurs";
          type empty;
        }
        leaf trap {
          description
            "Send SNMP trap if a storm occurs";
          type empty;
        }
      }
    }
    leaf load-interval {
      description
        "Load interval delay in seconds";
      type uint16 {
        range "30..600";
      }
    }
    container ip {
      description
        "IP template config";
      container dhcp {
        description
          "DHCP template config";
        if-feature "ios-features:switching-platform";
        container snooping {
          description
            "DHCP Snooping";
          container limit {
            description
              "DHCP Snooping limit";
            leaf rate {
              description
                "DHCP snooping rate limit";
              type uint16 {
                range "1..2048";
              }
            }
          }
          leaf trust {
            description
              "DHCP Snooping trust config";
            type empty;
          }
        }
      }
    }
    container subscriber {
      description
        "Subscriber inactivity timeout value.";
      container aging {
        description
          "Obtain inactivity timeout value from the server";
        choice timer-probe {
          container inactivity-timer {
            description
              "Inactivity timeout value";
            leaf value {
              description
                "Enter a value between 1 and 65535 in seconds";
              type uint16 {
                range "1..65535";
              }
            }
            leaf probe {
              description
                "ARP probe";
              type empty;
            }
          }
          leaf probe {
            description
              "ARP probe";
            type empty;
          }
        }
      }
    }
    container ipv6 {
      description
        "IPv6 interface config commands";
      container nd {
        description
          "IPv6 interface Neighbor Discovery subcommands";
        container raguard {
          presence "Attach default RA guard policy on interface";
          description
            "Configure RA guard on the interface";
          container attach-policy {
            description
              "Apply a policy for feature RA guard";
            list policy-name {
              description
                "policy name for feature RA guard";
              key "policy-name";
              leaf policy-name {
                type string;
              }
              uses vlanlist-grouping;
            }
          }
          uses vlanlist-grouping;
        }
      }
    }
    container device-tracking {
      presence "Attach default device-tracking policy on interface";
      description
        "Configure device-tracking on the interface";
      container attach-policy {
        description
          "Apply a policy for feature device-tracking";
        list policy-name {
          description
            "policy name for device tracking";
          key "policy-name";
          leaf policy-name {
            type string;
          }
          uses vlanlist-grouping;
        }
      }
      uses vlanlist-grouping;
    }
  }

  grouping config-template-sw-grouping {
    container IP_CAMERA_INTERFACE_TEMPLATE {
      description
        "built-in modified";
      uses template-grouping;
    }
    container LAP_INTERFACE_TEMPLATE {
      description
        "built-in modified";
      uses template-grouping;
    }
    container AP_INTERFACE_TEMPLATE {
      description
        "built-in modified";
      uses template-grouping;
    }
    container DMP_INTERFACE_TEMPLATE {
      description
        "built-in modified";
      presence "true";
      uses template-grouping;
    }
    container IP_PHONE_INTERFACE_TEMPLATE {
      description
        "built-in modified";
      presence "true";
      uses template-grouping;
    }
    container MSP_CAMERA_INTERFACE_TEMPLATE {
      description
        "built-in modified";
      uses template-grouping;
    }
    container MSP_VC_INTERFACE_TEMPLATE {
      description
        "built-in modified";
      uses template-grouping;
    }
    container PRINTER_INTERFACE_TEMPLATE {
      description
        "built-in modified";
      uses template-grouping;
    }
    container ROUTER_INTERFACE_TEMPLATE {
      description
        "built-in modified";
      uses template-grouping;
    }
    container SWITCH_INTERFACE_TEMPLATE {
      description
        "built-in modified";
      uses template-grouping;
    }
    container TP_INTERFACE_TEMPLATE {
      description
        "built-in modified";
      uses template-grouping;
    }
  }

  grouping template-error-disable-grouping {
    leaf error-disable-interface {
      type empty;
    }
  }

  grouping template-threshold-grouping-64k {
    container threshold {
      description
        "threshold";
      container high {
        description
          "High Threshold";
        leaf high-range {
          description
            "Set the high threshold";
          type uint16 {
            range "1..65535";
          }
        }
        leaf none {
          description
            "Disable high threshold";
          type empty;
        }
      }
      leaf low {
        description
          "Set the low threshold";
        type uint16 {
          range "0..65535";
        }
      }
    }
  }

  grouping template-window-grouping-64k {
    leaf window {
      description
        "Set window size in number of 10000 frames";
      type uint16 {
        range "1..65535";
      }
    }
  }

  grouping template-window-grouping-1800 {
    leaf window {
      description
        "Set window size in number of 10000 frames";
      type uint16 {
        range "10..1800";
      }
    }
  }

  grouping template-type-pseudowire-grouping {
    leaf encapsulation {
      description
        "Data encapsulation method";
      type enumeration {
        enum "l2tpv3";
        enum "mpls";
      }
    }
    leaf control-word {
      description
        "Include control-word in pseudowire packets";
      when "../encapsulation = 'mpls'";
      type empty;
    }
    container load-balance {
      description
        "Loadbalancing for pseudowire";
      when "../encapsulation = 'mpls'";
      container flow {
        description
          "Enable flow based load balancing for pseudowire";
        presence "true";
        leaf ethernet {
          description
            "Ethernet pseudowire flow classification";
          type enumeration {
            enum "dst-mac";
            enum "src-dst-mac";
            enum "src-mac";
          }
        }
      }
    }
    container monitor {
      description
        "Active monitoring of xconnect peer";
      when "../encapsulation = 'mpls'";
      container peer {
        description
          "Active monitoring of xconnect peer";
        container bfd {
          description
            "BFD active monitoring for the xconnect peer";
          presence "true";
          container local {
            description
              "Specify local endpoint information to map to a BFD session";
            container interface {
              description
                "Source interface for pseudowire";
              uses ios-ifc:interface-grouping;
            }
          }
        }
      }
    }
    container preferred-path {
      description
        "Preferred path";
      container interface {
        description
          "Output Interface";
        choice Tunnel-Tunnel-tp {
          case Tunnel-case {
            leaf Tunnel {
              description
                "Tunnel interface";
              type uint64 {
                range "0..2147483647";
              }
            }
          }
          case Tunnel-tp-case {
            leaf Tunnel-tp {
              description
                "MPLS Transport Profile interface";
              type uint16;
            }
          }
        }
        leaf disable-fallback {
          description
            "disable fall back to alternative route";
          type empty;
        }
      }
      container peer-container {
        leaf peer {
          description
            "Peer Address";
          type union {
            type string;
            type inet:ipv4-address;
          }
        }
        leaf disable-fallback {
          description
            "disable fall back to alternative route";
          type empty;
        }
      }
      container segment-routing {
        description
          "Segment-routing option";
        container traffic-eng {
          description
            "Segment-routing traffic engineering option";
          container attribute-set {
            description
              "Set MPLS traffic engineering attribute for auto-tunnel";
            leaf te-profile {
              description
                "MPLS traffic engineering profile name";
              type string;
            }
            leaf disable-fallback {
              description
                "disable fall back to alternative route";
              type empty;
            }
          }
        }
      }
    }
    container signaling {
      description
        "Signaling options";
      when "../encapsulation = 'mpls'";
      leaf protocol {
        description
          "Signaling protocol to use";
        type enumeration {
          enum "ldp";
          enum "none";
        }
      }
    }
    leaf sequencing {
      description
        "Sequencing options for pseudowire";
      when "../encapsulation = 'mpls' or ../encapsulation = 'l2tpv3'";
      type enumeration {
        enum "both";
        enum "receive";
        enum "resync";
        enum "transmit";
      }
    }
    container status {
      description
        "Pseudowire status capabilities";
      presence "true";
      container admin-down {
        description
          "Admin down of Attachment Circuit";
        when "../../encapsulation = 'l2tpv3'";
        leaf disconnect {
          description
            "Disconnect the session";
          type empty;
        }
      }
      container control-plane {
        description
          "control plane status events";
        leaf route-watch {
          description
            "listen on the control plane to route-watch events";
          type empty;
        }
      }
      leaf decoupled {
        description
          "Reflect standby status of the attachment circuit as up on the pseudowire";
        type empty;
      }
      container peer {
        description
          "peer status configuration";
        container topology {
          description
            "change status behaviour based on peer topology";
          leaf dual-homed {
            description
              "Our peer(s) are participating in a redundant solution with some form of redundancyprotocol running between the peer routers, Only one of the remote peers will advertise astatus of UP at a time. The other will advertise standby. Change our configuration so we can send a status of UP on both active and redundant pseudowires";
            type empty;
          }
        }
      }
      container redundancy {
        description
          "Xconnect redundancy configuration";
        leaf master {
          description
            "Put the xconnect redundancy group on this node in master mode";
          type empty;
        }
      }
    }
    container switching {
      description
        "Switching TLV on/off for pseudowire";
      when "../encapsulation = 'mpls'";
      leaf tlv {
        description
          "Switching TLV on/off for pseudowire";
        type empty;
      }
    }
  }

  grouping config-template-grouping {
    list template_details {
      key "template_name";
      leaf template_name {
        description
          "Template name";
        type string;
      }
      container ethernet {
        description
          "Ethernet service";
        container oam {
          description
            "Operations, Administration and Maintenance";
          container link-monitor {
            description
              "Ethernet OAM Link Monitor";
            container frame {
              description
                "Errored frames in a period measured by time";
              uses template-threshold-grouping-64k;
            }
            leaf window {
              description
                "Set window size in multiple of 100 milliseconds (will be rounded off to second)";
              type uint16 {
                range "10..600";
              }
            }
            container frame-period {
              description
                "Errored frames in a period measured by number of frames";
              uses template-threshold-grouping-64k;
              uses template-window-grouping-64k;
            }
            container frame-seconds {
              description
                "Errored frame seconds in a period";
              container threshold {
                description
                  "Errored frame-seconds threshold";
                container high {
                  description
                    "High Threshold";
                  leaf high-range {
                    description
                      "Set the high errored frame-seconds threshold in number of seconds";
                    type uint16 {
                      range "1..900";
                    }
                  }
                  leaf none {
                    description
                      "Disable high threshold";
                    type empty;
                  }
                }
                leaf low {
                  description
                    "Set the low errored frame-seconds threshold in number of seconds";
                  type uint16 {
                    range "1..900";
                  }
                }
              }
              leaf window {
                description
                  "Set window size in multiple of 100 milliseconds (will be rounded off to second)";
                type uint16 {
                  range "100..9000";
                }
              }
            }
            container high-threshold {
              description
                "Additional high threshold configuration";
              container action {
                description
                  "Specify an action when the high threshold is crossed";
                uses template-error-disable-grouping;
              }
            }
            container receive-crc {
              description
                "Received frames with CRC errors in a period";
              uses template-threshold-grouping-64k;
              uses template-window-grouping-1800;
            }
            container symbol-period {
              description
                "Errored symbols in a period";
              uses template-threshold-grouping-64k;
              uses template-window-grouping-64k;
            }
            container transmit-crc {
              description
                "Transmitted frames with CRC errors in a period";
              uses template-threshold-grouping-64k;
              uses template-window-grouping-1800;
            }
          }
          container remote-failure {
            description
              "Ethernet OAM remote failure indication";
            container critical-event {
              description
                "Critical event";
              container action {
                description
                  "Specify an action when a remote failure is detected";
                uses template-error-disable-grouping;
              }
            }
            container dying-gasp {
              description
                "Dying gasp";
              container action {
                description
                  "Specify an action when a remote failure is detected";
                presence "true";
                uses template-error-disable-grouping;
              }
            }
            container link-fault {
              description
                "Link fault";
              container action {
                description
                  "Specify an action when a remote failure is detected";
                presence "true";
                uses template-error-disable-grouping;
              }
            }
          }
        }
      }
      uses template-grouping;
    }
    uses config-template-sw-grouping {
      if-feature "ios-features:switching-platform";
    }
    container type {
      description
        "Type of the template";
      if-feature "ios-features:l2vpn";
      list pseudowire {
        key "name";
        leaf name {
          description
            "Template customized interface pseudowire";
          type string;
        }
        uses template-type-pseudowire-grouping;
      }
    }
  }

  augment "/ios:native/ios:template" {
    uses config-template-grouping;
  }
}
