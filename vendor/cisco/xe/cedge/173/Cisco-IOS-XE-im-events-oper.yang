module Cisco-IOS-XE-im-events-oper {
  yang-version 1;
  namespace "http://cisco.com/ns/yang/Cisco-IOS-XE-im-events-oper";
  prefix im-events-ios-xe-oper;

  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for ioxman eventq data.
     Copyright (c) 2018-2020 by Cisco Systems, Inc.
     All rights reserved.";

  revision 2020-07-01 {
    description
      "- Remove unused empty container im-events";
    reference "2.0.0";
    cisco-semver:module-version "2.0.0";
  }
  revision 2019-05-01 {
    description
      "Added semantic version";
    reference "1.1.0";
    cisco-semver:module-version "1.1.0";
  }
  revision 2018-03-19 {
    description
      "Initial revision";
    reference "1.0.0";
    cisco-semver:module-version "1.0.0";
  }

  typedef im-event-type {
    type enumeration {
      enum "im-iox-enable" {
        value 0;
        description
          "IOX enable";
      }
      enum "im-app-install" {
        value 1;
        description
          "IOxMan application install";
      }
      enum "im-app-uninstall" {
        value 2;
        description
          "IOxMan application uninstall";
      }
      enum "im-app-start" {
        value 3;
        description
          "IOxMan application start event";
      }
      enum "im-app-no-start" {
        value 4;
        description
          "IOxMan application stop event";
      }
      enum "im-unsolicited-event" {
        value 5;
        description
          "IOxMan unsolicited event";
      }
    }
    description
      "IOxMan event type";
  }

  typedef im-notification-severity {
    type enumeration {
      enum "critical" {
        value 0;
      }
      enum "major" {
        value 1;
      }
      enum "minor" {
        value 2;
      }
    }
    description
      "Notification severity";
  }

  typedef im-status-type {
    type enumeration {
      enum "im-status-pass" {
        value 0;
        description
          "IOxMan status pass";
      }
      enum "im-status-fail" {
        value 1;
        description
          "IOxMan status fail";
      }
    }
    description
      "IOxMan status type";
  }

  typedef im-app-state {
    type enumeration {
      enum "im-state-deployed" {
        value 0;
        description
          "Deployed state";
      }
      enum "im-state-activated" {
        value 1;
        description
          "Activated state";
      }
      enum "im-state-running" {
        value 2;
        description
          "Running state";
      }
      enum "im-state-stopped" {
        value 3;
        description
          "Stopped state";
      }
      enum "im-state-uninstalled" {
        value 4;
        description
          "Uninstalled state";
      }
    }
    description
      "IOxMan Application state";
  }

  grouping im-event {
    description
      "IOxMan eventq element example";
    leaf severity-level {
      type im-events-ios-xe-oper:im-notification-severity;
      description
        "Event severity";
    }
    leaf host-name {
      type string;
      description
        "Host name";
    }
    leaf system-ip {
      type inet:ip-address;
      description
        "IP address";
    }
    leaf vrf-name {
      type string;
      description
        "VRF name";
    }
    leaf app-id {
      type string;
      description
        "App ID";
    }
    leaf ev-type {
      type im-events-ios-xe-oper:im-event-type;
      description
        "Event type";
    }
    leaf status {
      type im-events-ios-xe-oper:im-status-type;
      description
        "Status for the event";
    }
    leaf message {
      type string;
      description
        "Message describing the event";
    }
    leaf app-state {
      type im-events-ios-xe-oper:im-app-state;
      description
        "App State";
    }
  }

  notification im-event {
    description
      "IOxMan eventq";
    uses im-events-ios-xe-oper:im-event;
  }
}
