module Cisco-IOS-XE-voice {
  namespace "http://cisco.com/ns/yang/Cisco-IOS-XE-voice";
  prefix ios-voice;

  import cisco-semver {
    prefix cisco-semver;
  }
  import Cisco-IOS-XE-native {
    prefix ios;
  }
  import ietf-inet-types {
    prefix inet;
  }
  import Cisco-IOS-XE-types {
    prefix ios-types;
  }
  include Cisco-IOS-XE-voice-register;
  include Cisco-IOS-XE-voice-class;
  include Cisco-IOS-XE-voice-dspfarm;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Voice Yang model.
     Copyright (c) 2016, 2018-2020 by Cisco Systems, Inc.
     All rights reserved.";

  revision 2020-07-02 {
    description
      "- Removed mins option from mode border-element license periodicity CLI 
       - Changed the range of hours from 1..23 to 8..23";
  }
  revision 2020-07-01 {
    description
      "- Updated fax and modem configuration
       - Updated sip bind command under dial-peer and global
       - Added voice class tenant
       - Added voice service voip related clis
       - Updated voice service voip configurations
       - Separate DSPFarm into a new module
       - Added dependency of pool configuration on global and max-pool configurations in Cisco-IOS-XE-voice-register yang file
       - Added dial-peer voip restriction for both bind and pass-thru
       - Marked the leaves ls-redundancy , hs-redundancy and version  as Obsolete
       - Removing the CLI dependency of allow-connection sip to sip for media bulk-stats under voice service voip";
  }
  revision 2020-03-01 {
    description
      "- Added global voice configuration
       - Added trunk group configuration
       - Added the DSPFarm services
       - Added SCCP configuration";
  }
  revision 2019-11-01 {
    description
      "- Added trunk group config
       - Added statement mandatory for leaves Cisco-IOS-XE-voice-register yang file";
    cisco-semver:module-version "2.0.0";
  }
  revision 2019-07-01 {
    description
      "- Establish semantic version baseline
       - Added voice class codec
       - Added voice service voip commands
       - Added the ip address trusted list option
       - Added dsapp line feature access code command
       - Added voice register mode for SRST
       - Added the dial-peer voice <tag> voip CLIs";
    cisco-semver:module-version "1.0.0";
  }
  revision 2018-10-23 {
    description
      "Added redundancy-group command in voice service voip command";
  }
  revision 2018-09-20 {
    description
      "Add SIP LINE CLI support";
  }
  revision 2017-02-07 {
    description
      "Initial revision";
  }

  typedef voice-cadence-type {
    type uint16 {
      range "50..10000";
    }
  }

  typedef catlife-keepalive-options-type {
    type enumeration {
      enum "30";
      enum "70";
      enum "150";
      enum "310";
      enum "630";
      enum "1270";
      enum "2550";
    }
  }

  grouping config-voice-translation-profile-grouping {
    container translation-profile {
      description
        "Translation profile";
      leaf incoming {
        description
          "Translation Profile for incoming call leg";
        type leafref {
          path "/ios:native/ios-voice:voice/ios-voice:translation-profile/ios-voice:id";
        }
      }
      leaf outgoing {
        description
          "Translation Profile for outgoing call leg";
        type leafref {
          path "/ios:native/ios-voice:voice/ios-voice:translation-profile/ios-voice:id";
        }
      }
    }
  }

  grouping config-tls-sni-grouping {
    leaf description {
      description
        "Define the description of input options";
      type string {
        length "1..80";
      }
    }
    leaf trustpoint {
      description
        "Define the trustpoint name";
      type string {
        length "1..142";
      }
    }
    leaf client-vtp {
      description
        "Set Client Verification Trustpoint";
      type string {
        length "1..142";
      }
    }
    container cn-san {
      description
        "Certificate CN/SAN options";
      container validate {
        description
          "Enable CN/SAN validation for certificate";
        leaf server {
          description
            "Enable CN/SAN validation for server certificate";
          type empty;
        }
      }
    }
    container cipher {
      description
        "Cipher Settings";
      choice cipher-choice {
        case ecdsa-cipher {
          container ecdsa-cipher {
            description
              "Use ECDSA Ciphers";
            presence "true";
            leaf curve-size {
              description
                "Size of Elliptic Curve to use.";
              type enumeration {
                enum "384";
              }
            }
          }
        }
        case strict-cipher {
          leaf strict-cipher {
            description
              "Use only ciphers use by SIP standards";
            type empty;
          }
        }
      }
    }
    container sni {
      description
        "TLS Server Name Indication Extension";
      leaf send {
        description
          "Include SNI extension in outbound TLS connections";
        type empty;
      }
    }
  }

  grouping config-sip-ua-grouping {
    container sip-ua {
      description
        "SIP User Agent (UA) ";
      presence "true";
      container crypto {
        description
          "sip-ua crypto commands";
        container signaling {
          description
            "Configure crypto signaling for sip-ua configuration mode";
          container default {
            description
              "Configure the default trust point";
            leaf tls-profile {
              description
                "Associate a tls-profile";
              type leafref {
                path "/ios:native/voice/class/tls-profile/id";
              }
            }
          }
          list remote-addr {
            description
              "Associate an IP network to a trustpoint";
            max-elements "10";
            key "ipv4address subnetmask";
            leaf ipv4address {
              description
                "Enter the IP address";
              type inet:ipv4-address;
            }
            leaf subnetmask {
              description
                "Enter the mask";
              type union {
                type inet:ipv4-address;
                type string {
                  pattern "/([0-9]|[1-2][0-9]|3[0-2])";
                }
              }
            }
            leaf tls-profile {
              description
                "Associate a tls-profile";
              mandatory true;
              type leafref {
                path "/ios:native/voice/class/tls-profile/id";
              }
            }
          }
        }
      }
    }
  }

  grouping config-srtp-options-grouping {
    choice srtp-choice {
      case fallback-case {
        leaf fallback {
          description
            "Allow Secure calls fallback to non secure";
          type empty;
        }
      }
      case pass-through-case {
        leaf pass-thru {
          description
            "Allow transparent passthru of unsupported crypto suites";
          type empty;
        }
      }
    }
  }

  typedef config-codec-type {
    type enumeration {
      enum "g711alaw" {
        description
          "G.711 A Law 64000 bps (for E1)";
      }
      enum "g711ulaw" {
        description
          "G.711 u Law 64000 bps (for T1)";
      }
    }
  }

  grouping config-pass-through-grouping {
    leaf pass-through {
      description
        "Use an audio codec for fax transport";
      type config-codec-type;
    }
  }

  grouping config-fax-protocol-grouping {
    choice protocol-choice {
      case none-case {
        leaf none {
          description
            "Disable fax transport";
          type empty;
        }
      }
      case pass-through-case {
        uses config-pass-through-grouping;
      }
      case t38-case {
        container t38 {
          description
            "Use T.38 protocol";
          presence "true";
          leaf nse {
            description
              "Use Cisco NSEs to signal T.38 mode switch";
            type empty;
          }
          leaf force {
            description
              "Unconditionally use Cisco NSEs to signal T.38 mode switch";
            when "../nse";
            type empty;
          }
          leaf version {
            description
              "T.38 fax version";
            type enumeration {
              enum "0";
              enum "3";
            }
            default "0";
          }
          container redundancy-config {
            leaf ls-redundancy {
              description
                "t38 low speed redundancy";
              type uint8 {
                range "0..5";
              }
              default "0";
            }
            leaf hs-redundancy {
              description
                "t38 high speed redundancy";
              when "../ls-redundancy";
              type uint8 {
                range "0..2";
              }
              default "0";
            }
          }
          container fallback {
            description
              "fax transport to use if T.38 unsupported on far end";
            choice protocol-choice {
              case none-case {
                leaf none {
                  description
                    "No fallback";
                  type empty;
                }
              }
              case pass-through-case {
                uses config-pass-through-grouping;
              }
            }
          }
        }
      }
    }
  }

  grouping config-modem-grouping {
    choice modem-choice {
      case passthrough-case {
        container passthrough {
          description
            "Pass modem traffic via clear channel";
          container nse {
            description
              "Use Named Signaling Events (NSE)";
            choice nse-choice {
              case codec-case {
                leaf codec {
                  description
                    "Codec selections for upspeed";
                  type config-codec-type;
                }
              }
              case payload-type-case {
                container payload-type-conifg {
                  leaf payload-type {
                    description
                      "Payload type value";
                    type uint8 {
                      range "98..117";
                    }
                    default "100";
                  }
                  leaf codec {
                    description
                      "Codec selections for upspeed";
                    type config-codec-type;
                  }
                }
              }
            }
          }
        }
      }
      case relay-case {
        container relay {
          description
            "Relay modem traffic between the gateways";
          choice relay-choice {
            case gateway-xid-case {
              container gateway-xid {
                description
                  "Do XID negotiation between gateways";
                presence "true";
              }
            }
            case nse-case {
              container nse {
                description
                  "Use Named Signaling Events (NSE)";
                choice nse-choice {
                  case codec-case {
                    container codec-gw-controller {
                      leaf codec {
                        description
                          "Codec selections for upspeed";
                        type config-codec-type;
                      }
                      leaf gw-controlled {
                        description
                          "GW Controlled MR";
                        type empty;
                      }
                    }
                  }
                  case payload-type-case {
                    container payload-type-config {
                      leaf payload-type {
                        description
                          "Payload type value";
                        type uint8 {
                          range "98..117";
                        }
                        default "100";
                      }
                      leaf codec {
                        description
                          "Codec selections for upspeed";
                        type config-codec-type;
                      }
                      leaf gw-controlled {
                        description
                          "GW Controlled MR";
                        type empty;
                      }
                    }
                  }
                }
              }
            }
            case sprt-case {
              container sprt {
                description
                  "Configure SPRT (Simple packet relay transport)";
                leaf retries {
                  description
                    "Maximum retries for an SPRT packet";
                  type uint32 {
                    range "6..30";
                  }
                }
              }
            }
            case sse-case {
              container sse {
                description
                  "SSE negotiation parameters for modem relay (Applicable only to SIP)";
                leaf v150mer {
                  description
                    "Enable V 150.1 MER (Applicable only to SIP)";
                  type empty;
                }
              }
            }
          }
        }
      }
    }
  }

  grouping config-port-range-grouping {
    container port-range {
      description
        "Port range";
      leaf min-port {
        description
          "Minimum port number";
        must ". mod 2 = 0" {
          error-message "Minimum port value must be even";
        }
        type uint16 {
          range "8000..48198";
        }
      }
      leaf max-port {
        description
          "Maximum port number";
        must ". mod 2 = 0" {
          error-message "Maximum port value must be even";
        }
        must "../min-port <= ." {
          error-message "Maximum port must be greater than or equal to minimum port";
        }
        type uint16 {
          range "8000..48198";
        }
      }
    }
  }

  grouping config-extended-port-range-grouping {
    container port-range-extended {
      container port-range {
        description
          "Media address port range";
        presence "true";
        list port {
          max-elements "10";
          key "min-port max-port";
          leaf min-port {
            description
              "Start media address extended port";
            type uint16 {
              range "5500..65498";
            }
          }
          leaf max-port {
            description
              "Stop media address extended port";
            must "../min-port <= ." {
              error-message "Starting port is greater than ending port";
            }
            type uint16 {
              range "5500..65498";
            }
          }
        }
      }
    }
  }

  grouping config-voice-grouping {
    container voice {
      description
        "Global voice configuration";
      leaf vrf {
        description
          "Voice VRF";
        must "/ios:native/ios:vrf/ios:definition[ios:name=current()] or /ios:native/ios:ip/ios:vrf[ios:name=current()]" {
          error-message "VRF must be created 1st, deleted last";
        }
        type string {
          length "1..32";
        }
      }
      container hpi {
        description
          "Host port interface";
        container capture {
          description
            "HPI control message capture";
          leaf buffer {
            description
              "HPI control message capture buffer size";
            type int32 {
              range "880..60000000";
            }
          }
          leaf destination {
            description
              "HPI control message capture data file destination";
            type string {
              pattern ".*";
              length "1..1023";
            }
          }
        }
      }
      container pcm {
        description
          "PCM Capture";
        container capture {
          description
            "PCM control message capture";
          leaf buffer {
            description
              "configure PCM capture buffer number";
            type int32 {
              range "0..200000";
            }
            default "0";
          }
          leaf destination {
            description
              "configure destination target for PCM capture data file";
            type string {
              pattern ".*";
              length "1..1023";
            }
          }
          leaf on-demand-trigger {
            description
              "configure PCM capture user trigger on-demand";
            type empty;
          }
          container user-trigger-string {
            description
              "configure PCM user trigger string";
            leaf trigger-start-string {
              description
                "configure user trigger start string up to 16 characters";
              type string {
                pattern "[0-9#\\*]{1,16}";
              }
            }
            leaf trigger-stop-string {
              description
                "configure user trigger stop string up to 16 characters";
              type string {
                pattern "[0-9#\\*]{1,16}";
              }
            }
            leaf stream {
              description
                "PCM stream bitmap in hex";
              type string {
                pattern "[1-9A-F][0-9A-F]{0,6}";
              }
            }
            leaf duration {
              description
                "PCM capture duration in second";
              type uint8 {
                range "0..255";
              }
            }
          }
        }
      }
      list translation-rule {
        description
          "Translation Rule configuration commands";
        key "id";
        leaf id {
          type uint32 {
            range "1..1073741823";
          }
        }
        list rule {
          description
            "Translation rule";
          key "id";
          leaf id {
            description
              "Translation rule number";
            type uint8 {
              range "1..100";
            }
          }
          choice rule-choice {
            leaf reject {
              description
                "Call block rule";
              type string {
                pattern ".*";
                length "1..66";
              }
            }
            leaf matching-replacement-pattern {
              description
                "Matching and replacement pattern, i.e., /xxx/ /xxx/";
              type string {
                pattern ".*";
                length "1..133";
              }
            }
          }
        }
      }
      list translation-profile {
        description
          "Translation profile configuration commands";
        key "id";
        leaf id {
          type string {
            length "1..31";
          }
        }
        container translate {
          description
            "Specify numbers that should be translated";
          leaf called {
            description
              "Translation rule for the called-number";
            type leafref {
              path "../../../translation-rule/id";
            }
          }
          leaf calling {
            description
              "Translation rule for the calling-number";
            type leafref {
              path "../../../translation-rule/id";
            }
          }
        }
      }
      container class {
        description
          "Control parameters class";
        uses config-voice-class-tenant-grouping;
        list custom-cptone {
          description
            "Configuration of customized Call Progress Tones";
          key "id";
          leaf id {
            type string {
              length "1..20";
            }
          }
          list dualtone {
            description
              "Configure call progress dual tones";
            key "id";
            leaf id {
              type enumeration {
                enum "busy";
                enum "conference";
                enum "disconnect";
                enum "number-unobtainable";
                enum "out-of-service";
                enum "reorder";
                enum "ringback";
              }
            }
            leaf-list frequency {
              description
                "Configure dual tone frequencies";
              max-elements "2";
              type uint16 {
                range "300..3600";
              }
            }
            container cadence {
              description
                "Configure dual tone cadences";
              leaf first-on-cadence {
                description
                  "First On cadence";
                type voice-cadence-type;
              }
              leaf first-off-cadence {
                description
                  "First Off cadence";
                type voice-cadence-type;
              }
              leaf second-on-cadence {
                description
                  "Second On cadence";
                type voice-cadence-type;
              }
              leaf second-off-cadence {
                description
                  "First Off cadence";
                type voice-cadence-type;
              }
              leaf third-on-cadence {
                description
                  "Third On cadence";
                type voice-cadence-type;
              }
              leaf third-off-cadence {
                description
                  "Third Off cadence";
                type voice-cadence-type;
              }
              leaf fourth-on-cadence {
                description
                  "Fourth On cadence";
                type voice-cadence-type;
              }
              leaf fourth-off-cadence {
                description
                  "Fourth Off cadence";
                type voice-cadence-type;
              }
            }
          }
        }
        list dualtone-detect-params {
          description
            "Dual tone detection parameters";
          key "id";
          leaf id {
            description
              "Voice class dual tone detect parameter tag";
            type uint32 {
              range "1..10000";
            }
          }
          leaf cadence-variation {
            description
              "Cadence variation allowed";
            type uint8 {
              range "0..200";
            }
            default "10";
          }
          leaf freq-max-delay {
            description
              "Timing difference between two frequencies";
            type uint8 {
              range "10..100";
            }
            default "10";
          }
          leaf freq-max-deviation {
            description
              "Maximum frequency deviation allowed for each frequency";
            type uint8 {
              range "10..125";
            }
            default "10";
          }
          leaf freq-max-power {
            description
              "Absolute value of upper limit for tone power per frequency";
            type uint8 {
              range "0..20";
            }
            default "10";
          }
          leaf freq-min-power {
            description
              "Absolute value of lower limit for tone power per frequency";
            type uint8 {
              range "10..35";
            }
            default "30";
          }
          leaf freq-power-twist {
            description
              "The difference between the power of two frequencies";
            type uint8 {
              range "0..15";
            }
            default "6";
          }
        }
        list codec {
          description
            "Set codec global parameters";
          max-elements "10000";
          key "codec-tag";
          leaf codec-tag {
            description
              "Voice class codec tag";
            type uint16 {
              range "1..10000";
            }
          }
          container codec {
            description
              "Set class codec parameters";
            list preference {
              description
                "Set priority order for using this codec";
              max-elements "24";
              key "preference-tag";
              unique "codec-type";
              leaf preference-tag {
                description
                  "Priority order (1 = Highest)";
                type uint8 {
                  range "1..24";
                }
              }
              leaf codec-type {
                type enumeration {
                  enum "g711ulaw";
                  enum "g711alaw";
                  enum "g729r8";
                  enum "ilbc";
                  enum "g722-64";
                }
              }
              leaf bytes {
                description
                  "Specify number of voice data bytes per frame";
                when "../codec-type = 'g711alaw' or ../codec-type = 'g711ulaw' or ../codec-type = 'g722-64' ";
                type enumeration {
                  enum "80";
                  enum "160";
                  enum "240";
                }
                default "160";
              }
              container g729r8-conf {
                when "../codec-type = 'g729r8'";
                leaf bytes {
                  description
                    "Specify number of voice data bytes per frame";
                  type enumeration {
                    enum "10";
                    enum "20";
                    enum "30";
                    enum "40";
                    enum "50";
                    enum "60";
                    enum "70";
                    enum "80";
                    enum "90";
                    enum "100";
                    enum "110";
                    enum "120";
                    enum "130";
                    enum "140";
                    enum "150";
                    enum "160";
                    enum "170";
                    enum "180";
                    enum "190";
                    enum "200";
                    enum "210";
                    enum "220";
                    enum "230";
                    enum "240";
                  }
                }
              }
              container ilbc-conf {
                when "../codec-type = 'ilbc'";
                container mode {
                  description
                    "Specify the value of the mode";
                  choice mode-choice {
                    case twenty-case {
                      container twenty {
                        leaf bytes {
                          description
                            "Specify number of voice data bytes";
                          type enumeration {
                            enum "38";
                            enum "76";
                            enum "114";
                            enum "152";
                            enum "190";
                            enum "228";
                          }
                        }
                      }
                    }
                    case thirty-case {
                      container thirty {
                        leaf bytes {
                          description
                            "Specify number of voice data bytes";
                          type enumeration {
                            enum "50";
                            enum "100";
                            enum "150";
                            enum "200";
                          }
                        }
                      }
                    }
                  }
                }
              }
            }
          }
        }
        list tls-profile {
          description
            "Associate a tls-profile";
          key "id";
          leaf id {
            type uint16 {
              range "1..10000";
            }
          }
          uses config-tls-sni-grouping;
        }
      }
      list service {
        description
          "Global packet telephony service commands";
        key "type";
        leaf type {
          type enumeration {
            enum "pots";
            enum "saf";
            enum "voatm";
            enum "vofr";
            enum "voip";
          }
        }
        container stun {
          description
            "STUN configuration commands";
          when "../type = 'voip'";
          presence "true";
          container stun {
            description
              "Stun parameters";
            container flowdata {
              description
                "FlowData parameters";
              container agent-id-config {
                leaf agent-id {
                  description
                    "Set Authorization Agent Id";
                  type uint8;
                }
                leaf boot-count {
                  description
                    "Set boot count";
                  type uint16;
                  default "0";
                }
              }
              container shared-secret {
                description
                  "Set Shared-secret Key";
                choice shared-secret-choice {
                  case zero-case {
                    leaf zero {
                      description
                        "Specifies an UNENCRYPTED shared secret key";
                      type string {
                        length "12..80";
                      }
                    }
                  }
                  case six-case {
                    leaf six {
                      description
                        "Specifies an ENCRYPTED shared secret key";
                      type string {
                        length "26..162";
                      }
                    }
                  }
                }
              }
              container catlife-config {
                leaf catlife {
                  description
                    "Set how often a new CAT token is generated(default value 1270 = (21 min 10 sec))";
                  type catlife-keepalive-options-type;
                  default "1270";
                }
                leaf keepalive {
                  description
                    "Set how often keepalives are sent (default 30 sec)";
                  must ". <= ../catlife" {
                    error-message "keepalive should be less than or equal to catlife";
                  }
                  type catlife-keepalive-options-type;
                  default "30";
                }
              }
            }
            leaf transaction-timer {
              description
                "Set STUN Transaction Timer";
              type uint16 {
                range "10..50";
              }
              default "10";
            }
          }
        }
        container clid {
          description
            "Caller ID option";
          when "../type = 'voip'";
          leaf network-provided {
            description
              "Set screen ind in oct3a to network-provided for SIP calls";
            type empty;
          }
          container strip {
            description
              "Remove calling party name and number when PI restricted for SIP";
            container pi-restrict {
              description
                "Remove calling party name and number when PI restricted for SIP";
              leaf all {
                description
                  "Remove calling party name and number when PI restricted for SIP";
                type empty;
              }
            }
          }
          container substitute {
            description
              "Sub calling num for missing display name for SIP if PI allows";
            leaf name {
              description
                "Sub calling num for missing display name for SIP if PI allows";
              type empty;
            }
          }
        }
        leaf dtmf-interworking {
          description
            "Dtmf Interworking";
          when "../type = 'voip'";
          type enumeration {
            enum "rtp-nte" {
              description
                "Digit-begin and digit-end events of RTP NTE packets are sent separately";
            }
            enum "standard" {
              description
                "RFC compliance RTP NTE packets";
            }
          }
        }
        leaf gcid {
          description
            "Enable Global Call Identification for voip";
          when "../type = 'voip'";
          type empty;
        }
        container notify {
          description
            "send facility indication to application";
          when "../type = 'voip'";
          container redirect {
            description
              "send redirect notification to application for handling";
            leaf ip2ip {
              description
                "send redirect notification to application for ip-to-ip calls";
              type boolean;
              default "true";
            }
            leaf ip2pots {
              description
                "send redirect notification to application for ip-to-pots calls";
              type empty;
            }
          }
        }
        container redirect {
          description
            "voip call redirect";
          when "../type = 'voip'";
          leaf ip2ip {
            description
              "Redirect IP-to-IP calls";
            type empty;
          }
        }
        container rtp-media-loop {
          description
            "Global setting for rtp media loop count";
          when "../type = 'voip'";
          leaf count {
            description
              "specify the max count";
            type uint8 {
              range "6..21";
            }
          }
        }
        container rtp-ssrc {
          description
            "Global setting to handle multiple RTP SSRC's";
          when "../type = 'voip'";
          leaf multiplex {
            description
              "RTCP multiplexing with RTP";
            must "/ios:native/voice/service[type='voip']/allow-connections/sip/to/sip" {
              error-message "Config allow-connections sip to sip";
            }
            type empty;
          }
        }
        container srtp {
          description
            "Allow Secure calls";
          when "../type = 'voip'";
          presence "true";
          uses config-srtp-options-grouping;
        }
        leaf shutdown {
          description
            "Stop VoIP services gracefully without dropping active calls";
          when "../type = 'voip'";
          type boolean;
          default "false";
        }
        container media-recording {
          description
            "Media recording commands";
          when "../type = 'pots'";
          leaf licenses {
            description
              "Allocate media recording licenses";
            type uint16 {
              range "1..500";
            }
          }
        }
        container allow-connections {
          description
            "Allow call connection types";
          when "../type = 'voip'";
          container sip {
            description
              "from-type sip";
            container to {
              description
                "to";
              leaf sip {
                description
                  "to-type sip";
                type empty;
              }
            }
          }
        }
        container media {
          description
            "Global media setting for voip calls";
          leaf bulk-stats {
            description
              "Retrieve bulk statistics is enabled";
            type empty;
          }
          leaf statistics {
            description
              "Media statistics is enabled";
            must "/ios:native/voice/service[type='voip']/allow-connections/sip/to/sip" {
              error-message "Config allow-connections sip to sip";
            }
            type empty;
          }
        }
        container media-address {
          description
            "Voice Media IP Address Range";
          when "../type = 'voip'";
          container range {
            description
              "Address range";
            must "count(./ipv4) + count(./ipv6) <= 10" {
              error-message "Exceeds maximum number of allowed address ranges";
            }
            list ipv4 {
              key "start-ipv4-address end-ipv4-address";
              leaf start-ipv4-address {
                description
                  "Enter start ip address";
                type inet:ipv4-address;
              }
              leaf end-ipv4-address {
                description
                  "Enter end ip address";
                type inet:ipv4-address;
              }
              uses config-port-range-grouping {
                refine "port-range";
              }
              uses config-extended-port-range-grouping;
            }
            list ipv6 {
              key "start-ipv6-address end-ipv6-address";
              leaf start-ipv6-address {
                description
                  "Start IPv6 address";
                type inet:ipv6-address;
              }
              leaf end-ipv6-address {
                description
                  "End IPv6 address";
                type inet:ipv6-address;
              }
              uses config-port-range-grouping {
                refine "port-range";
              }
              uses config-extended-port-range-grouping;
            }
          }
          list voice-vrf {
            description
              "voice vrf id";
            max-elements "100";
            key "vrfname";
            leaf vrfname {
              description
                "WORD;;VRF name";
              must "/ios:native/ios:vrf/ios:definition[ios:name=current()] or /ios:native/ios:ip/ios:vrf[ios:name=current()]" {
                error-message "VRF must be created 1st, deleted last";
              }
              type string;
            }
            uses config-port-range-grouping {
              refine "port-range";
            }
            uses config-extended-port-range-grouping;
          }
        }
        container rtp-port {
          description
            "Global setting for rtp port range";
          when "../type = 'voip'";
          container range {
            description
              "Port range";
            uses config-port-range-grouping {
              refine "port-range";
            }
          }
        }
        leaf cpa {
          description
            "Enable Call Progress Analysis for voip calls";
          when "../type = 'voip'";
          type boolean;
          default "true";
        }
        container cpa-config {
          when "../cpa = 'true' and ../type = 'voip'";
          container cpa {
            description
              "Enable Call Progress Analysis for voip calls";
            container threshold {
              description
                "Configure cpa thresholds";
              leaf active-signal {
                description
                  "Active signal threshold related to measured noise floor level";
                type enumeration {
                  enum "9db";
                  enum "12db";
                  enum "15db";
                  enum "18db";
                  enum "21db";
                }
                default "15db";
              }
              container noise-level {
                description
                  "Noise floor level limits";
                leaf max {
                  description
                    "Maximum noise floor level";
                  type enumeration {
                    enum "-45dBm0";
                    enum "-50dBm0";
                    enum "-55dBm0";
                    enum "-60dBm0";
                  }
                  default "-50dBm0";
                }
                leaf min {
                  description
                    "Minimum noise floor level";
                  type enumeration {
                    enum "-55dBm0";
                    enum "-60dBm0";
                    enum "-65dBm0";
                    enum "-70dBm0";
                  }
                  default "-60dBm0";
                }
              }
              container term-tone {
                description
                  "Answering machine terminating tone thresholds";
                leaf min-duration {
                  description
                    "Minimum answering machine terminating tone duration in ms";
                  type uint16 {
                    range "80..2000";
                  }
                  units "miliseconds";
                  default "80";
                }
                leaf min-freq {
                  description
                    "Minimum answering machine terminating tone duration in Hz";
                  type uint16 {
                    range "300..2000";
                  }
                  units "hertz";
                  default "300";
                }
              }
            }
            container timing {
              description
                "Configure cpa timing parameters";
              leaf live-person {
                description
                  "Longest typical greeting time if call is answered by live human";
                type uint16 {
                  range "1..60000";
                }
                units "miliseconds";
                default "2500";
              }
              leaf noise-period {
                description
                  "Amount of time to estimate the noise floor level";
                type uint16 {
                  range "1..60000";
                }
                units "miliseconds";
                default "100";
              }
              leaf silent {
                description
                  "Amount of silent after valid speech to declare a live voice";
                type uint16 {
                  range "1..60000";
                }
                units "miliseconds";
                default "375";
              }
              leaf term-tone {
                description
                  "Amount of time to wait for answering machine terminating tone";
                type uint16 {
                  range "1..60000";
                }
                units "miliseconds";
                default "15000";
              }
              leaf timeout {
                description
                  "Timeout when no active signal present";
                type uint16 {
                  range "1..60000";
                }
                units "miliseconds";
                default "3000";
              }
              leaf valid-speech {
                description
                  "Active speech duration";
                type uint16 {
                  range "1..60000";
                }
                units "miliseconds";
                default "112";
              }
            }
          }
        }
        leaf callmonitor {
          description
            "Call Monitoring";
          when "../type = 'voip'";
          type empty;
        }
        container supplementary-service {
          description
            "Config supplementary service features";
          when "../type = 'voip'";
          container sip {
            description
              "sip supplementary service";
            leaf handle-replaces {
              description
                "Handle INVITE with REPLACES header (SIP-SIP only)";
              type empty;
            }
            leaf moved-temporarily {
              description
                "enable/disable sip moved-temporarily";
              type empty;
            }
            leaf refer {
              description
                "enable/disable sip refer";
              type empty;
            }
          }
        }
        container sip {
          description
            "SIP configuration commands";
          when "../type = 'voip'";
          presence "true";
          container srtp {
            description
              "Allow SIP related SRTP options";
            container negotiate {
              description
                "SRTP negotiate options";
              leaf cisco {
                description
                  "allow RTP answer to SRTP offer";
                type empty;
              }
            }
          }
          container registrar {
            description
              "SIP Registrar config";
            container server {
              description
                "Enable Local SIP Registrar";
              container expires {
                description
                  "Registration Expires time";
                presence "true";
                must "./min  <= ./max" {
                  error-message "Max must be greater than min";
                }
                leaf max {
                  description
                    "Default registration max expires time";
                  type uint32 {
                    range "120..86400";
                  }
                  default "3600";
                }
                leaf min {
                  description
                    "Default registration min expires time";
                  type uint16 {
                    range "60..3600";
                  }
                  default "60";
                }
              }
            }
          }
          container call {
            description
              "Global setting to start/stop processing SIP Calls";
            container service {
              description
                "SIP service configuration";
              container stop {
                description
                  "Stop SIP service - Active calls not affected";
                presence "true";
                leaf forced {
                  description
                    "Forced shutdown of SIP service - Active calls will be torn down";
                  type empty;
                }
              }
            }
          }
          container g729 {
            description
              "G729 codec interoperability settings";
            leaf annexb-all {
              description
                "g729b representing g729a and g729b to interop with CCM";
              type empty;
            }
          }
          container session {
            description
              "SIP Voice Protocol session config";
            uses config-session-transport-grouping;
          }
          uses config-sip-bind-grouping;
        }
        container ip {
          description
            "Voice service voip ip setup";
          when "../type = 'voip'";
          container address {
            description
              "Voice service voip ip address setup";
            container trusted {
              description
                "ip address trusted (toll fraud prevention) setup";
              leaf authenticate {
                description
                  "ip address trusted (toll fraud prevention) authenticate control flag";
                type empty;
              }
              leaf call-block {
                description
                  "ip address trusted (toll fraud prevention) call-block";
                type empty;
              }
              container list {
                description
                  "ip address trusted (toll fraud prevention) list setup";
                must "count(./ipv4/address) + count(./ipv6/address) <= 100" {
                  error-message "Trusted list entries has exceeded the maximum";
                }
                list ipv4 {
                  description
                    "ip address trusted (toll fraud prevention) list entry";
                  max-elements "100";
                  key "address";
                  leaf address {
                    description
                      "IPv4 Address";
                    type inet:ipv4-address;
                  }
                  leaf mask {
                    description
                      "IPv4 Address Mask";
                    type union {
                      type inet:ipv4-address;
                      type string {
                        pattern "/([0-9]|[1-2][0-9]|3[0-2])";
                      }
                    }
                  }
                }
                list ipv6 {
                  description
                    "ipv6 address trusted (toll fraud prevention) list entry";
                  max-elements "100";
                  key "address";
                  leaf address {
                    description
                      "IPv6 Prefix";
                    type ios-types:ipv6-prefix;
                  }
                }
              }
            }
          }
        }
        container fax-relay {
          description
            "Global fax relay commands";
          when "../type = 'voip'";
          leaf ans-disable {
            description
              "Allow Ans-am tones to be disabled for SG3 machines to operate at G3 speeds using fax relay";
            type empty;
          }
          leaf ans-treatment {
            description
              "Enable Modem and Fax Answer Tone Treatment";
            type empty;
          }
          leaf sg3-to-g3 {
            description
              "Allow SG3 Fax machines to operate at G3 speeds using fax relay";
            type empty;
          }
        }
        container fax {
          description
            "Global fax commands";
          leaf protocol {
            description
              "The system-wide fax protocol type";
            type enumeration {
              enum "cisco";
              enum "none";
              enum "pass-through";
              enum "t38";
            }
          }
          leaf fallback {
            description
              "fax transport to use if T.38 unsupported on far end";
            when "../protocol = 't38'";
            type enumeration {
              enum "cisco";
              enum "none";
              enum "pass-through";
            }
          }
          leaf codec {
            when "../protocol = 'pass-through' or ../fallback = 'pass-through'";
            type enumeration {
              enum "g711alaw";
              enum "g711ulaw";
            }
          }
          leaf ls-redundancy {
            status obsolete;
            description
              "t38 low speed redundancy";
            when "../protocol = 't38'";
            type uint8 {
              range "0..5";
            }
          }
          leaf hs-redundancy {
            status obsolete;
            description
              "t38 high speed redundancy";
            when "../protocol = 't38'";
            type uint8 {
              range "0..2";
            }
          }
          leaf version {
            status obsolete;
            description
              "t38 fax version";
            when "../protocol = 't38'";
            type enumeration {
              enum "0";
              enum "3";
            }
          }
        }
        container modem {
          description
            "Global modem commands";
          when "../type = 'voip'";
          uses config-modem-grouping;
        }
        leaf redundancy-group {
          description
            "Associate redundancy-group with voice HA";
          type uint8 {
            range "1..2";
          }
        }
        container mode {
          description
            "Global mode setting for voip calls";
          when "../type = 'voip'";
          choice mode-choice {
            case border-element-case {
              container border-element {
                description
                  "Mode setting for Border-Element";
                presence "true";
                container license {
                  description
                    "License setting for Border-Element is deprecated";
                  container periodicity {
                    description
                      "Licence periodicity setting for Border-Element";
                    choice periodicity-choice {
                      case mins-case {
                        leaf mins {
                          status obsolete;
                          description
                            "Periodicity interval in mins";
                          type uint8 {
                            range "1..59";
                          }
                        }
                      }
                      case hours-case {
                        leaf hours {
                          description
                            "Periodicity interval in hours";
                          type uint8 {
                            range "8..23";
                          }
                        }
                      }
                      case days-case {
                        leaf days {
                          description
                            "Periodicity interval in days";
                          type uint8 {
                            range "1..30";
                          }
                        }
                      }
                    }
                  }
                }
              }
            }
          }
        }
      }
      uses config-voice-register-grouping;
    }
  }

  grouping config-voice-card-grouping {
    list voice-card-sb {
      description
        "Configure a specific voice-card";
      key "sb";
      leaf sb {
        type ios-types:slot-bay-type;
      }
      leaf local-bypass {
        description
          "Enable TDM hair pin";
        type boolean;
        default "true";
      }
      container dsp {
        description
          "To configure DSP service dspfarm";
        container services {
          description
            "To configure dsp services on this voice-card";
          leaf dspfarm {
            description
              "To enable dspfarm service on this voice-card";
            type empty;
          }
        }
      }
    }
    list voice-card {
      status obsolete;
      description
        "Configure a specific voice-card (OBSOLETE)";
      key "id";
      leaf id {
        status obsolete;
        type ios-types:slot-bay-type;
      }
      leaf slot {
        status obsolete;
        type uint8 {
          range "0..2";
        }
      }
    }
  }

  grouping config-dtmf-relay-grouping {
    container dtmf-relay {
      description
        "Transport digits across IP link. Enter relay options in order of preference.";
      leaf rtp-nte {
        description
          "RTP Named Telephone Event RFC 2833";
        type empty;
      }
      leaf digit-drop {
        description
          "RTP Named Telephone Event RFC 2833";
        when "../rtp-nte";
        type empty;
      }
      leaf sip-info {
        description
          "Relay via SIP INFO messages";
        type empty;
      }
      leaf sip-kpml {
        description
          "Relay over SIP SUBSCRIBE/NOTIFY";
        type empty;
      }
      leaf sip-notify {
        description
          "Relay via SIP NOTIFY messages";
        type empty;
      }
    }
  }

  grouping config-dial-peer-grouping {
    container dial-peer {
      description
        "Dial Map (Peer) configuration commands";
      list voice {
        description
          "Voice type";
        key "dialpeertag";
        leaf dialpeertag {
          description
            "Voice dial-peer tag";
          type uint32 {
            range "1..1073741823" {
              error-message "Input dial-peer tag is out of range. It should be in range of 1..1073741823";
            }
          }
        }
        leaf type {
          description
            "Dial peer type";
          type enumeration {
            enum "pots";
            enum "voip";
          }
        }
        leaf description {
          description
            "Dial peer specific description";
          when "../type = 'pots' or ../type = 'voip'";
          type string {
            pattern ".*";
            length "1..64";
          }
        }
        container srtp {
          description
            "Allow Secure calls";
          when "../type = 'voip'";
          presence "true";
          uses config-srtp-options-grouping;
        }
        leaf destination-pattern {
          description
            "A full E.164 telephone number prefix";
          when "../type = 'pots' or ../type = 'voip'";
          type string {
            pattern "([0-9,A-F#*.?+%()-]*T?)" {
              error-message "Incorrect format for E.164 Number: regular expression must be of the form  [0-9,A-F#*.?+%()-]*T?";
            }
          }
        }
        leaf direct-inward-dial {
          when "../type = 'pots'";
          description
            "Use Called Number as final call destination";
          type empty;
        }
        container forward-digits {
          description
            "Configure the destination digits forward of this dial-peer";
          when "../type = 'pots'";
          choice fwd-digit-choice {
            leaf num-digits {
              description
                "Number of right-justified dial digits to be forwarded";
              type uint8 {
                range "0..32";
              }
            }
            leaf all {
              description
                "Forward all destination digits";
              type empty;
            }
            container extra {
              description
                "Extra dial digits to be forwarded";
              presence "true";
              leaf inband {
                description
                  "Digits to be forwarded inband";
                type empty;
              }
            }
          }
        }
        container incoming {
          description
            "Incoming called number";
          when "../type = 'pots' or ../type = 'voip'";
          leaf called-number {
            description
              "An incoming called number pattern";
            type string {
              pattern "([0-9,A-F#*.?+%()-]*T?)" {
                error-message "Incorrect format for E.164 Number: regular expression must be of the form  [0-9,A-F#*.?+%()-]*T?";
              }
            }
          }
        }
        container fax-rate-config {
          leaf fax-rate {
            description
              "The fax rate to be attempted in getting to this peer";
            type enumeration {
              enum "12000";
              enum "14400";
              enum "2400";
              enum "4800";
              enum "7200";
              enum "9600";
              enum "disable";
              enum "voice";
            }
            default "voice";
          }
          leaf bytes {
            when "../fax-rate";
            description
              "Bytes of fax data per frame";
            type uint32 {
              range "0 | 10..255";
            }
            default "0";
          }
        }
        container fax-relay {
          description
            "fax-relay options";
          leaf ans-disable {
            when "../../type = 'voip'";
            description
              "Allow Ans-am tones to be disabled for SG3 machines to operate at G3 speeds using fax relay";
            type empty;
          }
          leaf ans-treatment {
            when "../../type = 'voip'";
            description
              "Enable Modem and Fax Answer Tone Treatment";
            type empty;
          }
          container sg3-to-g3 {
            description
              "Allow SG3 Fax machines to operate at G3 speeds using fax relay";
            presence "true";
            leaf system {
              when "../../../type = 'voip'";
              description
                "Use the system configuration for fax relay sg3-to-g3";
              type empty;
            }
          }
          container ecm {
            when "../../type = 'voip'";
            description
              "ECM mode options for FAX Relay";
            leaf disable {
              description
                "Disables ECM mode for FAX Relay";
              type empty;
            }
          }
        }
        container fax {
          description
            "Configure fax";
          when "../type = 'voip'";
          container protocol {
            description
              "The fax protocol to be attempted in getting to this peer";
            uses config-fax-protocol-grouping;
          }
        }
        container modem {
          description
            "Modem commands through this peer";
          when "../type = 'voip'";
          uses config-modem-grouping;
        }
        container media-recording {
          description
            "Media recording commands";
          when "../type = 'pots'";
          leaf dialpeertag {
            description
              "Recording server dial peer";
            type uint32 {
              range "1..1073741823";
            }
          }
        }
        container pcm-dump {
          description
            "Enable PCM capture stream for this dial-peer";
          container caplog {
            description
              "Enable PCM capture log";
            leaf pcm-stream-bit-map {
              description
                "PCM stream index in hex";
              type string {
                pattern "[1-9A-F][0-9A-F]{0,6}";
              }
            }
            leaf capture-time {
              description
                "PCM capture interval";
              type uint8 {
                range "0..255";
              }
              default "255";
            }
          }
        }
        leaf port {
          description
            "Voice port associated with this peer";
          when "../type = 'pots'";
          type string;
        }
        leaf prefix {
          description
            "The pattern to be appended before the dial num";
          when "../type = 'pots'";
          type string {
            length "1..32";
          }
        }
        leaf shutdown {
          description
            "Change the Admin State of this peer to down";
          when "../type = 'pots' or ../type = 'voip'";
          type boolean;
          default "false";
        }
        uses config-voice-translation-profile-grouping;
        container voice-class {
          description
            "Set Dial-peer voice class control parameters";
          container sip {
            description
              "Set SIP parameters";
            container extension {
              description
                "Configure SIP extension";
              leaf voip_ext {
                when "../../../../type = 'voip'";
                type enumeration {
                  enum "system";
                  enum "cucm";
                  enum "gw-ana";
                }
                default "system";
              }
              leaf pots_ext {
                when "../../../../type = 'pots'";
                type enumeration {
                  enum "system";
                  enum "gw-ana";
                }
                default "system";
              }
            }
            uses config-sip-bind-grouping {
              when "../../type = 'voip'";
            }
            container options-keepalive {
              description
                "send out-of-dialogue OPTIONS PING to configured proxy/session-target";
              when "../../../type = 'voip'";
              presence "true";
            }
            uses pass-thru-grouping {
              when "../../type = 'voip'";
            }
            leaf tenant {
              description
                "Set SIP-Tenant parameters";
              when "../../../type = 'voip'";
              type leafref {
                path "/ios:native/ios-voice:voice/ios-voice:class/ios-voice:tenant/ios-voice:id";
              }
            }
          }
          container codec {
            description
              "Set Global Codec parameters";
            when "../../type = 'voip'";
            leaf codectag {
              type leafref {
                path "../../../../../voice/class/codec/codec-tag";
              }
            }
            leaf offer-all {
              description
                "Offer All the codec configured in this voice-class codec";
              when "../codectag > 0";
              type empty;
            }
          }
        }
        container session {
          description
            "The session [ target | protocol | transport ] for this peer";
          when "../type = 'voip'";
          uses config-session-transport-grouping;
          leaf protocol {
            description
              "The session protocol to be used in getting to this peer";
            type enumeration {
              enum "cisco" {
                description
                  "Ciso Session Protocol";
              }
              enum "sipv2" {
                description
                  "IETF Session Initiation Protocol";
              }
              enum "multicast" {
                description
                  "Multicast Session Protocol(voice conferencing)";
              }
            }
            default "cisco";
          }
          container target {
            description
              "The session target for this peer";
            when "../../session[protocol='sipv2']";
            choice target-choice {
              case address-choice {
                leaf address {
                  description
                    "WORD A string specifying the session target";
                  type string {
                    pattern "(loopback:rtp)|(dns:.*)|(sip-server)|(sip-uri)|(ipv4:[0-9]+\\.[0-9]+\\.[0-9]+\\.[0-9]+(:[0-9]+)?)|(ipv6:\\[([0-9A-Fa-f.:])+\\](:[0-9]+)?)" {
                      error-message "Must be of the form (loopback:rtp)|(dns:.*)|(sip-server)|(sip-uri)|(ipv4:[0-9]+.[0-9]+.[0-9]+.[0-9]+(:[0-9]+)?) | ((ipv6:[([0-9A-Fa-f.:])+](:[0-9]+)?))";
                    }
                  }
                }
              }
              case dhcp-choice {
                leaf dhcp {
                  description
                    "Provision session target using DHCP";
                  type empty;
                }
              }
              case registrar-choice {
                leaf registrar {
                  description
                    "Provision session target using Registration";
                  type empty;
                }
              }
            }
          }
        }
        leaf huntstop {
          description
            "Stop hunting on Dial-Peers";
          when "../type = 'pots' or ../type = 'voip'";
          type boolean;
          default "false";
        }
        leaf preference {
          description
            "Configure the preference order of this dial-peer";
          type uint16 {
            range "0..10" {
              error-message "Input Number is out of range. Should be 1..10";
            }
          }
        }
        uses config-dtmf-relay-grouping {
          when "type = 'voip' and session[protocol='sipv2']";
        }
        list trunkgroup {
          description
            "trunk groups associated with this peer";
          key "id";
          leaf id {
            description
              "Trunk group ID";
            type string {
              length "1..64";
            }
          }
          leaf trunk-group-preference {
            description
              "trunk group preference value";
            type uint8 {
              range "1..64";
            }
          }
        }
      }
    }
  }

  grouping config-dsapp-line-grouping {
    container dsapp {
      description
        "Configure Device Service Application";
      leaf line {
        description
          "Configure DSAPP Line";
        type empty;
      }
      container dsappline {
        container line {
          description
            "Configure DSAPP Line";
          container feature {
            description
              "Specify the format of each call feature code";
            container access-code {
              description
                "Specify the format of feature access code";
              presence "true";
              leaf prefix {
                description
                  "Select feature access code prefix string";
                type string {
                  pattern "[\\*#]{1,5}";
                }
                default "**";
              }
              container call {
                description
                  "Select call forward feature";
                container forward {
                  description
                    "Select call forward all feature";
                  leaf all {
                    description
                      "Select call forward all feature code";
                    type string {
                      pattern "[0-9\\*#]{1,4}";
                    }
                    default "1";
                  }
                  leaf cancel {
                    description
                      "Select call forward cancel feature code";
                    type string {
                      pattern "[0-9\\*#]{1,4}";
                    }
                    default "2";
                  }
                }
              }
              container pickup {
                description
                  "Select call pickup feature code";
                leaf local {
                  description
                    "Select pickup local group feature code";
                  type string {
                    pattern "[0-9\\*#]{1,4}";
                  }
                  default "5";
                }
                leaf group {
                  description
                    "Select pickup different group feature code";
                  type string {
                    pattern "[0-9\\*#]{1,4}";
                  }
                  default "7";
                }
                leaf direct {
                  description
                    "Select pickup extension feature code";
                  type string {
                    pattern "[0-9\\*#]{1,4}";
                  }
                  default "6";
                }
              }
              leaf cancel-call-waiting {
                description
                  "Select cancel call waiting feature code";
                type string {
                  pattern "[0-9\\*#]{1,4}";
                }
                default "9";
              }
              leaf last-redial {
                description
                  "Select last redial feature code";
                type string {
                  pattern "[0-9\\*#]{1,4}";
                }
                default "3";
              }
            }
          }
        }
      }
    }
  }

  grouping config-ccm-manager-grouping {
    container ccm-manager {
      description
        "Call Manager";
      container sipana {
        description
          "Enable Call Manager Application SIP Line Side mode";
        container auto-config {
          description
            "SIP line side auto configuration";
          container local {
            description
              "Specify local interface to use for SIP analog device registration";
            leaf GigabitEthernet {
              description
                "GigabitEthernet IEEE 802.3z";
              type leafref {
                path "/ios:native/ios:interface/ios:GigabitEthernet/ios:name";
              }
            }
          }
        }
      }
      container config {
        description
          "XML download configuration";
        leaf server {
          description
            "set the Call Manager configuration download TFTP server address/name";
          type union {
            type inet:ipv4-address;
            type inet:ipv6-address;
            type inet:domain-name;
          }
        }
      }
    }
  }

  grouping config-trunk-group-grouping {
    container trunk {
      description
        "Global trunk configuration";
      list group {
        description
          "Specify a trunk group";
        key "id";
        leaf id {
          description
            "Trunk group label";
          type string {
            length "1..64";
          }
        }
        container hunt-scheme {
          description
            "The hunt scheme in trunk group";
          presence "true";
          leaf hunt-method {
            description
              "hunt scheme method";
            type enumeration {
              enum "least-idle";
              enum "least-used";
              enum "longest-idle";
              enum "random";
              enum "round-robin";
              enum "sequential";
            }
          }
          leaf precedence-type {
            when "../hunt-method != 'random'";
            description
              "hunt time slot order";
            type enumeration {
              enum "both";
              enum "even";
              enum "odd";
            }
          }
        }
        leaf max-retry {
          description
            "Maximum number of outgoing call attempts";
          type uint8 {
            range "1..5";
          }
        }
        list max-calls {
          description
            "Maximum number of calls allowed";
          key "call-type direction";
          leaf call-type {
            description
              "Call type";
            type enumeration {
              enum "any";
              enum "data";
              enum "voice";
            }
          }
          leaf direction {
            description
              "Specify direction of calls";
            type enumeration {
              enum "in";
              enum "out";
            }
          }
          leaf num-call {
            description
              "Specify number of calls allowed";
            type uint16 {
              range "0..1000";
            }
          }
        }
      }
    }
  }

  augment "/ios:native" {
    uses config-sip-ua-grouping;
    uses config-voice-grouping;
    uses config-voice-call-manager-fallback-grouping;
    uses config-voice-card-grouping;
    uses config-dial-peer-grouping;
    uses config-dspfarm-profile-grouping;
    uses config-sccp-grouping;
    uses config-dsapp-line-grouping;
    uses config-ccm-manager-grouping;
    uses config-trunk-group-grouping;
  }
}
