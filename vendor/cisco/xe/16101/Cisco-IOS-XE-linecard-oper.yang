module Cisco-IOS-XE-linecard-oper {
  yang-version 1;
  namespace "http://cisco.com/ns/yang/Cisco-IOS-XE-linecard-oper";
  prefix linecard-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring linecards in a Network Element.
     Copyright (c) 2018 by Cisco Systems, Inc.
     All rights reserved.";

  revision 2018-03-26 {
    description
      "Initial revision";
    reference "1.0.0";
  }

  grouping linecard {
    description
      "Attributes of linecard";
    leaf name {
      type string;
      description
        "Physical location description of the linecard";
    }
    leaf power-admin-state {
      type boolean;
      description
        "Power provided to the linecard: Enabled/Disabled";
    }
  }

  container linecard-oper-data {
    config false;
    description
      "Top-level container for linecard operational data";
    list linecard {
      key "name";
      description
        "List of linecard instances, keyed by slot";
      uses linecard-ios-xe-oper:linecard;
    }
  }
}
