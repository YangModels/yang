module Cisco-IOS-XE-wireless-mobility-types {
  yang-version 1;
  namespace "http://cisco.com/ns/yang/Cisco-IOS-XE-wireless-mobility-types";
  prefix wireless-mobility-types;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless mobility data types.
     Copyright (c) 2016-2017 by Cisco Systems, Inc.
     All rights reserved.";

  revision 2018-04-03 {
    description
      "Add DTLS and keepalive role negotiation";
    reference "2.1.0";
  }
  revision 2018-01-24 {
    description
      "The first generally available version";
    reference "2.0.0";
  }
  revision 2017-05-05 {
    description
      "Initial revision";
    reference "1.0.0";
  }

  typedef mm-client-roam-type {
    type enumeration {
      enum "mm-roam-type-none" {
        value 0;
        description
          "Mobility roam type none (not L2, L3, L3 requested 
           or L3 forced";
      }
      enum "mm-roam-type-l2" {
        value 1;
        description
          "L2 roam because of VLAN match";
      }
      enum "mm-roam-type-l3" {
        value 2;
        description
          "L3 roam because of VLAN difference";
      }
      enum "mm-roam-type-l3-requested" {
        value 3;
        description
          "L3 roam because of L2 anchoring";
      }
      enum "mm-roam-type-l3-forced" {
        value 4;
        description
          "L3 roam because of platform difference";
      }
    }
    description
      "Mobility client roaming type";
  }

  typedef mm-mobility-state {
    type enumeration {
      enum "mm-mobility-incomplete" {
        value 0;
        description
          "Inclomplet mobility";
      }
      enum "mm-mobility-complete" {
        value 1;
        description
          "Mobility completed";
      }
    }
    description
      "Mobility state";
  }

  typedef mm-client-role {
    type enumeration {
      enum "mm-client-role-unassoc" {
        value 0;
        description
          "Init mobile client";
      }
      enum "mm-client-role-local" {
        value 1;
        description
          "Local mobile client";
      }
      enum "mm-client-role-anchor" {
        value 2;
        description
          "Anchor mobile client";
      }
      enum "mm-client-role-foreign" {
        value 3;
        description
          "Foreign mobile client";
      }
      enum "mm-client-role-export-anchor" {
        value 4;
        description
          "Export anchor mobile client";
      }
      enum "mm-client-role-export-foreign" {
        value 5;
        description
          "Export foreign mobile client";
      }
      enum "mm-client-role-handoff" {
        value 6;
        description
          "Handoff mobile client";
      }
    }
    description
      "Role of mobility client";
  }

  typedef mm-client-type {
    type enumeration {
      enum "mm-client-type-wireless" {
        value 0;
        description
          "Wireless mobile client";
      }
      enum "mm-client-type-wireless-export" {
        value 1;
        description
          "Wireless export mobile client";
      }
      enum "mm-client-type-wgb" {
        value 2;
        description
          "WGB mobile client";
      }
      enum "mm-client-type-wgb-export" {
        value 3;
        description
          "WGB export mobile client";
      }
      enum "mm-client-type-wgb-wired" {
        value 4;
        description
          "WGB wired mobile client";
      }
      enum "mm-client-type-wgb-wired-export" {
        value 5;
        description
          "WGB wired export mobile client";
      }
      enum "mm-client-type-wired-export" {
        value 6;
        description
          "Wired export mobility client";
      }
    }
    description
      "Mobility client type";
  }

  typedef mm-client-mode {
    type enumeration {
      enum "mm-client-mode-local" {
        value 0;
        description
          "Local mobility client";
      }
      enum "mm-client-mode-flex-local-sw" {
        value 1;
        description
          "Flex, locally switched mobility client";
      }
      enum "mm-client-mode-flex-central-sw" {
        value 2;
        description
          "Flex, centrally switched mobility client";
      }
      enum "mm-client-mode-fabric" {
        value 3;
        description
          "Fabric mobility client";
      }
    }
    description
      "Mode of mobility client";
  }

  typedef unified-link-status {
    type enumeration {
      enum "status-unknown" {
        value 0;
        description
          "Unknown status for mobility tunnel";
      }
      enum "data-path-down" {
        value 1;
        description
          "Data path is down for mobility tunnel";
      }
      enum "ctrl-path-down" {
        value 2;
        description
          "Control path is down for mobility tunnel";
      }
      enum "ctrl-data-path-down" {
        value 3;
        description
          "Control and data path is down for mobility tunnel";
      }
      enum "up" {
        value 4;
        description
          "mobility tunnel is UP";
      }
    }
    description
      "Combined mobility tunnel state";
  }

  typedef arch-capability {
    type enumeration {
      enum "mm-arch-unknown" {
        value 0;
        description
          "Unknown mobility architectural";
      }
      enum "mm-arch-new" {
        value 1;
        description
          "New mobility architecture";
      }
      enum "mm-arch-old" {
        value 2;
        description
          "Old mobility architecture";
      }
      enum "mm-arch-ewlc" {
        value 3;
        description
          "EWLC mobility architecture";
      }
    }
    description
      "Mobility architectural capability";
  }

  typedef dtls-capability {
    type enumeration {
      enum "mm-dtls-capability-unknown" {
        value 0;
        description
          "DTLS capability unknown for mobile client";
      }
      enum "mm-dtls-capability-unsupported" {
        value 1;
        description
          "DTLS capability not supported for mobile client";
      }
      enum "mm-dtls-capability-supported" {
        value 2;
        description
          "DTLS capability supported for client";
      }
      enum "mm-dtls-capability-any" {
        value 3;
        description
          "*DTLS capability ";
      }
    }
    description
      "DTLS capability of moblie client";
  }

  typedef tunnel-capability {
    type enumeration {
      enum "mm-unknown-tunnel" {
        value 0;
        description
          "Tunnel capability unknown for mobility client";
      }
      enum "mm-eoip-tunnel" {
        value 1;
        description
          "Mobility client has EOIP tunnel capability";
      }
      enum "mm-capwap-tunnel" {
        value 2;
        description
          "Mobility client has CAPWAP tunnel capability";
      }
      enum "mm-both-tunnel" {
        value 3;
        description
          "Mobility client has both EOIP and CAPWAP tunnel 
           capability";
      }
    }
    description
      "Tunnel capability for mobility client";
  }

  typedef mm-dtls-status {
    type enumeration {
      enum "mm-dtls-disabled" {
        value 0;
        description
          "DTLS connection is disabled for mobility client";
      }
      enum "mm-dtls-init" {
        value 1;
        description
          "DTLS connection is initialised for mobility 
           connection";
      }
      enum "mm-dtls-in-handshake" {
        value 2;
        description
          "DTLS connection is in handshake state for mobility 
           client";
      }
      enum "mm-dtls-in-cert-verify" {
        value 3;
        description
          "DTLS connection is in certificate verification 
           state for mobility client";
      }
      enum "mm-dtls-sess-established" {
        value 4;
        description
          "DTLS connection is in session established state 
           for mobility client";
      }
      enum "mm-dtls-in-key-plumbing" {
        value 5;
        description
          "DTLS connection is in key plumbing state for 
           mobility client";
      }
      enum "mm-dtls-key-plumbed" {
        value 6;
        description
          "DTLS connection has plumbed the key for mobility 
           client";
      }
    }
    description
      "DTLS connection status for mobility client";
  }

  grouping mm-msg-stats {
    description
      "Message statistics for mobility client";
    leaf type {
      type uint32;
      description
        "CAPWAP messages type for mobility client";
    }
    leaf allocs {
      type uint32;
      description
        "Number of CAPWAP messages allocated for mobility 
         client";
    }
    leaf frees {
      type uint32;
      description
        "Number of CAPWAP messages freed for mobility client";
    }
    leaf tx {
      type uint32;
      description
        "Number of CAPWAP messages transmitted for mobility 
         client";
    }
    leaf rx {
      type uint32;
      description
        "Number of CAPWAP messages received for mobility 
         client";
    }
    leaf forwarded {
      type uint32;
      description
        "Number of CAPWAP messages forwarded for mobility 
         client";
    }
    leaf tx-errors {
      type uint32;
      description
        "Number of CAPWAP message transmit errors for 
         mobility client";
    }
    leaf rx-errors {
      type uint32;
      description
        "Number of CAPWAP message receive errors for mobility 
         client";
    }
    leaf tx-retries {
      type uint32;
      description
        "Number of retries for CAPWAP message transmit error 
         for mobility client";
    }
    leaf built {
      type uint32;
      description
        "Number of CAPWAP messages built fot mobility client";
    }
    leaf processed {
      type uint32;
      description
        "Number of processed CAPWAP messages for mobility 
         client";
    }
    leaf drops {
      type uint32;
      description
        "Number of dropped CAPWAP messages for mobility 
         client";
    }
  }
}
