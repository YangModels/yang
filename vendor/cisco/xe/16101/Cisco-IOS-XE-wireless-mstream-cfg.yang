module Cisco-IOS-XE-wireless-mstream-cfg {
  yang-version 1;
  namespace "http://cisco.com/ns/yang/Cisco-IOS-XE-wireless-mstream-cfg";
  prefix wireless-mstream-cfg;

  import Cisco-IOS-XE-wireless-enum-types {
    prefix wireless-enum-types;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing multicast configurations
     Copyright (c) 2016-2018 by Cisco Systems, Inc.
     All rights reserved.";

  revision 2018-01-24 {
    description
      "The first generally available version";
    reference "2.0.0";
  }
  revision 2017-05-05 {
    description
      "Initial revision";
    reference "1.0.0";
  }

  grouping mstreamgrp {
    description
      "multicast group";
    leaf group-name {
      type string;
      description
        "multicast group name";
    }
    leaf start-ip-addr {
      type inet:ip-address;
      default "0.0.0.0";
      description
        "multicast start IP address";
    }
    leaf end-ip-addr {
      type inet:ip-address;
      default "0.0.0.0";
      description
        "multicast end IP address";
    }
    leaf pak-size {
      type uint16 {
        range "100 .. 1500";
      }
      default "1200";
      description
        "multicast packet size";
    }
    leaf bandwidth {
      type uint16 {
        range "1 .. 35000";
      }
      default "1000";
      description
        "multicast bandwidth";
    }
    leaf is-admitted {
      type boolean;
      default "true";
      description
        "multicast is admitted";
    }
    leaf is-periodical {
      type boolean;
      default "false";
      description
        "multicast is periodical";
    }
    leaf qos {
      type wireless-enum-types:media-stream-qos;
      default "mstream-video";
      description
        "multicast qos";
    }
    leaf priority {
      type uint16 {
        range "1 .. 8";
      }
      default "4";
      description
        "multicast priority";
    }
    leaf rrc-violation {
      type uint16 {
        range "1 .. 2";
      }
      default "2";
      description
        "multicast rrc violation";
    }
    leaf rrc-type {
      type uint16;
      default "1";
      description
        "multicast rrc type";
    }
  }

  grouping mstreamglob {
    description
      "multicast stream glob";
    leaf multicadirect-state {
      type boolean;
      default "false";
      description
        "multicast direct state";
    }
    leaf url {
      type string;
      default "";
      description
        "multicast url";
    }
    leaf email {
      type string;
      default "";
      description
        "multicast email";
    }
    leaf phone {
      type string;
      default "";
      description
        "multicast phone";
    }
    leaf note {
      type string;
      default "";
      description
        "multicast note";
    }
    leaf msg-state {
      type boolean;
      default "false";
      description
        "multicast msg state";
    }
  }

  container mstream-cfg-data {
    description
      "multicast Cisco_IOS_XE_wireless_mstream_cfg";
    container mstream-groups {
      description
        "Multicast stream groups";
      list mstream-group {
        key "group-name";
        description
          "List of multicast stream groups";
        uses wireless-mstream-cfg:mstreamgrp;
      }
    }
    container mstream-glob {
      presence "mstreamglob";
      description
        "multicast stream glob";
      uses wireless-mstream-cfg:mstreamglob;
    }
  }
}
