module Cisco-IOS-XE-wireless-fqdn-oper {
  yang-version 1;
  namespace "http://cisco.com/ns/yang/Cisco-IOS-XE-wireless-fqdn-oper";
  prefix wireless-fqdn-ios-oper;

  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing the client fqdn operational data 
     Copyright (c) 2016-2018 by Cisco Systems, Inc.
     All rights reserved.";

  revision 2018-05-28 {
    description
      "Addition of filter ID for urlfilter lists";
    reference "1.1.0";
  }
  revision 2018-01-11 {
    description
      "Initial revision";
    reference "1.0.0";
  }

  grouping st-fqdn-ipv4 {
    description
      "IPv4 Addresses structure learned as part of dns snooping";
    leaf rule-id {
      type uint8;
      description
        "Rule ID used by AP for plumbing the ACL rule";
    }
    leaf action {
      type uint8;
      description
        "Action Applied by AP for the plumbed ACL rule";
    }
    leaf ttl {
      type uint32;
      description
        "Time to Live period of the IP addressed learned";
    }
    leaf learned-time {
      type uint32;
      description
        "Timestamp at which the IPv4 addressed learned";
    }
    leaf ipv4-dns-resolved-addr {
      type inet:ipv4-address;
      description
        "Ipv4 address learned as part of dns snooping";
    }
    leaf fqdn-url {
      type string;
      description
        "The url for which Ipv4 address is learned as part of dns snooping";
    }
  }

  grouping st-fqdn-ipv6 {
    description
      "IPv6 Addresses structure learned as part of dns snooping";
    leaf rule-id {
      type uint8;
      description
        "Rule ID Applied by AP for the plumbed IPv6 ACL rule";
    }
    leaf action {
      type uint8;
      description
        "Action Applied by AP for the plumbed IPv6 ACL rule";
    }
    leaf ttl {
      type uint32;
      description
        "Time to Live period of the IPv6 addressed learned";
    }
    leaf learned-time {
      type uint32;
      description
        "Timestamp at which the IPv6 addressed learned";
    }
    leaf ipv6-dns-resolved-addr {
      type inet:ipv6-address;
      description
        "IPv6 address learned as part of dns snooping";
    }
    leaf fqdn-url {
      type string;
      description
        "URL for which IPv6 address learned as part of dns snooping";
    }
  }

  grouping st-client-fqdn-data {
    description
      "structure to store the operational data for the dns learned ips.";
    leaf client-mac {
      type yang:mac-address;
      description
        "client mac address for which dns learned ips are stored.";
    }
    leaf url-acl-name {
      type string;
      description
        "urllist name which is applied to the client.";
    }
    leaf client-state {
      type uint8;
      description
        "client state on AP.";
    }
    list ipv4-addr-list {
      description
        "List of IPv4 addresses learned as part of dns snooping.";
      uses wireless-fqdn-ios-oper:st-fqdn-ipv4;
    }
    list ipv6-addr-list {
      description
        "List of IPv6 addresses learned as part of dns snooping.";
      uses wireless-fqdn-ios-oper:st-fqdn-ipv6;
    }
  }

  grouping st-fqdn-list {
    description
      "structure to store the operational data for the mapping of urlfilter name and id.";
    leaf url-list-name {
      type string;
      description
        "Name for urlfilter lists which will contain url domain names";
    }
    leaf url-list-id {
      type uint32;
      description
        "Filter id (a unique reference number) for urlfilter lists created";
    }
  }

  container fqdn-oper-data {
    config false;
    description
      "Top container for client operational data of dns snooping.";
    list client-fqdn-data {
      key "client-mac";
      description
        "Represents the client operational fqdn data.";
      uses wireless-fqdn-ios-oper:st-client-fqdn-data;
    }
    list fqdn-list {
      key "url-list-name";
      description
        "Represents the operational mapping for  fqdn data.";
      uses wireless-fqdn-ios-oper:st-fqdn-list;
    }
  }
}
