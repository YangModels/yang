module Cisco-IOS-XE-wireless-general-cfg {
  yang-version 1;
  namespace "http://cisco.com/ns/yang/Cisco-IOS-XE-wireless-general-cfg";
  prefix wireless-general-cfg;

  import Cisco-IOS-XE-wireless-enum-types {
    prefix wireless-enum-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing misc WLC configurations
     Copyright (c) 2016-2018 by Cisco Systems, Inc.
     All rights reserved.";

  revision 2018-08-16 {
    description
      "- Rename mcast/bcast to multicast/broadcast
       - Add support for Lawful Interception.
       - Rename icap-port to airsense-port";
    reference "3.0.0";
  }
  revision 2018-03-22 {
    description
      "Add container for AP upgrade";
    reference "2.1.0";
  }
  revision 2018-01-24 {
    description
      "The first generally available version";
    reference "2.0.0";
  }
  revision 2017-05-05 {
    description
      "Initial revision";
    reference "1.0.0";
  }

  grouping dtls-config {
    description
      "DTLS AP join configs";
    leaf dtls-version {
      type wireless-types:enm-dtls-version;
      default "dtls-all";
      description
        "DTLS version used for AP join";
    }
    leaf dtls-ciphersuite {
      type wireless-types:enm-ciphersuite;
      default "tls-null-with-null-null";
      description
        "Configure DTLS ciphersuite";
    }
  }

  grouping na-server-cert {
    description
      "Credentials of the tesseract server";
    leaf protocol {
      type wireless-types:download-protocol;
      default "protocol-none";
      description
        "Protocol to be used for tesseract server";
    }
    leaf server-ip {
      type inet:ip-address;
      default "0.0.0.0";
      description
        "Server IP of the tesseract server";
    }
    leaf path {
      type string;
      default "";
      description
        "Path where certificate is placed";
    }
    leaf filename {
      type string;
      default "";
      description
        "Filename of the certificate";
    }
    leaf encrypted {
      type boolean;
      default "false";
      description
        "Flag to enable or disable encryption";
    }
    leaf username {
      type string;
      description
        "Username to be used for tesseract server";
    }
    leaf password {
      type string;
      default "";
      description
        "Password to be used for tesseract server";
    }
    leaf password-type {
      type wireless-enum-types:crypt-type;
      default "clear";
      description
        "Password encrypted or in cler";
    }
  }

  grouping wsa-config {
    description
      "WSA configuration";
    leaf enable {
      type boolean;
      default "false";
      description
        "Flag to enable or disable WSA";
    }
    leaf url {
      type string;
      default "";
      description
        "URL for the WSA server";
    }
    leaf token {
      type string;
      default "";
      description
        "ID-token for the WSA server";
    }
    leaf enable-dataplane-statistics {
      type boolean;
      default "false";
      description
        "Flag to enable dataplane statistics";
    }
    leaf interval-dataplane-statistics {
      type uint16;
      default "5";
      description
        "Interval for dataplane statistics collection";
    }
    leaf icap-port {
      type uint16;
      default "0";
      description
        "ICap port number";
    }
  }

  grouping li-host-addr {
    description
      "Lawful-interception host configurations";
    leaf li-host-ip-address {
      type inet:ip-address;
      must "(../li-host-ip-address != '255.255.255.0') and (../li-host-ip-address != '255.255.0.0') and (../li-host-ip-address != '255.0.0.0')" {
        error-message "Invalid IPv4 host address provided";
        error-app-tag "must-violation";
      }
      must "../li-host-ip-address != '255.255.255.255'" {
        error-message "Broadcast IPv4 address is invalid";
        error-app-tag "must-violation";
      }
      must "not(starts-with(../li-host-ip-address, '127.'))" {
        error-message "Loopback IPv4 address is invalid";
        error-app-tag "must-violation";
      }
      must "not(starts-with(../li-host-ip-address, '224.')) and not(starts-with(../li-host-ip-address, '225.')) and not(starts-with(../li-host-ip-address, '226.')) and not(starts-with(../li-host-ip-address, '227.')) and not(starts-with(../li-host-ip-address, '228.')) and not(starts-with(../li-host-ip-address, '229.')) and not(starts-with(../li-host-ip-address, '230.')) and not(starts-with(../li-host-ip-address, '231.')) and not(starts-with(../li-host-ip-address, '232.')) and not(starts-with(../li-host-ip-address, '233.')) and not(starts-with(../li-host-ip-address, '234.')) and not(starts-with(../li-host-ip-address, '235.')) and not(starts-with(../li-host-ip-address, '236.')) and not(starts-with(../li-host-ip-address, '237.')) and not(starts-with(../li-host-ip-address, '238.')) and not(starts-with(../li-host-ip-address, '239.'))" {
        error-message "Multicast IPv4 address is invalid";
        error-app-tag "must-violation";
      }
      must "not(contains(substring(../li-host-ip-address, 1, 4), 'fe80'))" {
        error-message "Link-local IPv6 address is invalid";
        error-app-tag "must-violation";
      }
      must "not(contains(substring(../li-host-ip-address, 1, 4), 'fec0'))" {
        error-message "Site-local IPv6 address is invalid";
        error-app-tag "must-violation";
      }
      must "not(contains(substring(../li-host-ip-address, 1, 4), 'ff00'))" {
        error-message "Multicast IPv6 address is invalid";
        error-app-tag "must-violation";
      }
      default "0.0.0.0";
      description
        "Lawful-interception server IP address";
    }
  }

  grouping broadcast-vlan-config {
    description
      "Wireless Broadcast related configuration";
    leaf vlan-id {
      type uint32 {
        range "1 .. 4094";
      }
      description
        "Wireless Broadcast vlan Id";
    }
  }

  grouping multicast-non-ip-vlan-config {
    description
      "Wireless non-IP multicast related configuration";
    leaf vlan-id {
      type uint32 {
        range "1 .. 4094";
      }
      description
        "Non-IP multicast vlan Id";
    }
  }

  grouping multicast-config {
    description
      "Broadcast/Multicast related configuration";
    leaf is-multicast-enabled {
      type boolean;
      default "false";
      description
        "multicast enable/disable";
    }
    leaf multicast-over-multicast-ipv4-addr {
      type inet:ipv4-address;
      default "0.0.0.0";
      description
        "IPv4 Multicast group address for CAPWAP used by APs";
    }
    leaf multicast-over-multicast-ipv6-addr {
      type inet:ipv6-address;
      default "0:0:0:0:0:0:0:0";
      description
        "IPv6 Multicast group address for CAPWAP used by APs";
    }
    leaf is-non-ip-multicast-enabled {
      type boolean;
      default "false";
      description
        "non-ip multicast enable/disable";
    }
    leaf is-mdns-enabled {
      type boolean;
      description
        "Flag to enable or disable mdns";
    }
    leaf multicast-mode {
      type boolean;
      default "false";
      description
        "V4 Multicast over multicast enabled";
    }
    leaf multicast-v6-mode {
      type boolean;
      default "false";
      description
        "V6 Multicast over multicast enabled";
    }
    leaf is-broadcast-enabled {
      type boolean;
      default "false";
      description
        "broadcast enable/disable";
    }
  }

  grouping exclusionlist-file-record {
    description
      "exclusive list record";
    leaf mac-addr {
      type yang:mac-address;
      description
        "Mac address of the controller";
    }
    leaf description {
      type string;
      default "";
      description
        "Reason for exclusion";
    }
  }

  grouping sim-l3-interface-cache-data {
    description
      "Object stores the wireless management interface details";
    leaf interface-name {
      type string;
      default "";
      description
        "Wireless management interface name";
    }
    leaf test-ip-address {
      type inet:ip-address;
      default "0.0.0.0";
      description
        "Test ip address";
    }
    leaf nat-ip-address {
      type inet:ip-address;
      default "0.0.0.0";
      description
        "NAT IP Address";
    }
    leaf nat-enable {
      type boolean;
      default "false";
      description
        "NAT IP Address is enabled or disabled";
    }
    leaf private-ip-discovery {
      type boolean;
      default "true";
      description
        "Discovery Response from Private IP is enabled or disabled";
    }
    leaf public-ip-discovery {
      type boolean;
      default "false";
      description
        "Discovery Response from Public IP is enabled or disabled";
    }
  }

  grouping capwap-global-lag-info {
    description
      "Object stores the lag info details";
    leaf enabled {
      type boolean;
      default "false";
      description
        "Global lag status";
    }
  }

  grouping cac-config {
    description
      "CAC Resources";
    leaf iplearnq-high-threshold {
      type uint32 {
        range "1000 .. 1600";
      }
      default "1300";
      description
        "High Threshold Value for IplearnQ";
    }
    leaf aaa-high-threshold {
      type uint32 {
        range "300 .. 700";
      }
      default "500";
      description
        "High Threshold Value for AAA Outstanding request queue";
    }
    leaf ipc-high-threshold {
      type uint32 {
        range "80 .. 95";
      }
      must "../ipc-low-threshold < ../ipc-high-threshold" {
        error-message "ipc-high-threshold must be greater than ipc-low-threshold";
        error-app-tag "must-violation";
      }
      default "85";
      description
        "High Threshold Value for IPC resources";
    }
    leaf ipc-low-threshold {
      type uint32 {
        range "70 .. 80";
      }
      default "75";
      description
        "Low Threshold Value for IPC resources";
    }
    leaf cpu-high-threshold {
      type uint32 {
        range "85 .. 95";
      }
      default "90";
      description
        "High Threshold Value for cpu resource";
    }
  }

  grouping st-ap-upgrade-config {
    description
      "Staggered AP Upgrade Configurations";
    leaf percentage {
      type wireless-types:enum-ewlc-ap-upgrade-config;
      default "ap-staggered-upgrade-percent-15";
      description
        "Percentage AP per iteration";
    }
  }

  container general-cfg-data {
    description
      "General wireless configuration";
    container cac-config {
      presence "cacconfig";
      description
        "CAC Resources values configuration";
      uses wireless-general-cfg:cac-config;
    }
    container fips-cfg {
      presence "fips-cfg";
      description
        "DTLS for AP join configurations";
      uses wireless-general-cfg:dtls-config;
    }
    container exclusion-list-file-records {
      description
        "Exclusion list records";
      list exclusion-list-file-record {
        key "mac-addr";
        description
          "exclusion list record";
        uses wireless-general-cfg:exclusionlist-file-record;
      }
    }
    container wsa-config {
      presence "wsa-config";
      description
        "WSA configuration";
      uses wireless-general-cfg:wsa-config;
    }
    container na-server-cert {
      presence "na-server-cert";
      description
        "tessarect server details";
      uses wireless-general-cfg:na-server-cert;
    }
    container sim-l3-interface-cache-data {
      presence "simL3InterfaceCacheData-t";
      description
        "wireless management interface data";
      uses wireless-general-cfg:sim-l3-interface-cache-data;
    }
    container laginfo {
      presence "laginfo";
      description
        "AP lag info";
      uses wireless-general-cfg:capwap-global-lag-info;
    }
    container multicast-config {
      presence "bcastCfg";
      description
        "Broadcast/Multicast config";
      uses wireless-general-cfg:multicast-config;
    }
    container multicast-non-ip-config {
      description
        "Non-IP Multicast configuration";
      list multicast-non-ip-vlan-config {
        key "vlan-id";
        description
          "Non-IP Multicast vlan configuration";
        uses wireless-general-cfg:multicast-non-ip-vlan-config;
      }
    }
    container broadcast-config {
      description
        "Wireless Broadcast configuration";
      list broadcast-vlan-config {
        key "vlan-id";
        description
          "Wireless Broadcast vlan configuration";
        uses wireless-general-cfg:broadcast-vlan-config;
      }
    }
    container ap-upgrade-config {
      description
        "AP Upgrade Configurations";
      uses wireless-general-cfg:st-ap-upgrade-config;
    }
    container li-global-config {
      presence "li-global-config";
      description
        "LI server IP address configuration";
      uses wireless-general-cfg:li-host-addr;
    }
  }
}
