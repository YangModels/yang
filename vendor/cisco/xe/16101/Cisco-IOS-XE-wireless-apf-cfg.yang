module Cisco-IOS-XE-wireless-apf-cfg {
  yang-version 1;
  namespace "http://cisco.com/ns/yang/Cisco-IOS-XE-wireless-apf-cfg";
  prefix wireless-apf-cfg;

  import Cisco-IOS-XE-wireless-enum-types {
    prefix wireless-enum-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing global dot11 parameters 
     Copyright (c) 2016-2018 by Cisco Systems, Inc.
     All rights reserved.";

  revision 2018-08-13 {
    description
      "- Add FRA sensor support
       - name changed for blacklist flags
       - Default value of country code changed
       - SIP prefered call configuration added";
    reference "4.0.0";
  }
  revision 2018-05-25 {
    description
      "AP auth support with serial number and Client Onboarding Event";
    reference "3.0.0";
  }
  revision 2018-01-24 {
    description
      "The first generally available version";
    reference "2.0.0";
  }
  revision 2017-05-05 {
    description
      "Initial revision";
    reference "1.0.0";
  }

  grouping snooping-ports {
    description
      "SIP snooping start and end ports";
    leaf start-port {
      type uint32 {
        range "0 .. 65535";
      }
      description
        "SIP snooping start port";
    }
    leaf end-port {
      type uint32 {
        range "0 .. 65535";
      }
      description
        "SIP snooping end port";
    }
  }

  grouping st-apf {
    description
      "container for apf attributes";
    leaf dot11-country-code {
      type string;
      default "00";
      description
        "This field configures the country of operation";
    }
    leaf system-mgmt-via-wireless {
      type boolean;
      default "false";
      description
        "This field enables management access from wireless clients";
    }
    leaf enable-client-onboarding-event {
      type boolean;
      default "false";
      description
        "Enable Client Onboarding Event";
    }
    leaf network-name {
      type string;
      default "default";
      description
        "This field sets RF-Network name";
    }
    leaf assoc-interval {
      type uint32 {
        range "100 .. 10000";
      }
      default "10000";
      description
        "This attribute configures association request limit per AP slot in a given interval";
    }
    leaf assoc-limit {
      type uint32 {
        range "1 .. 100";
      }
      default "100";
      description
        "This attribute configures the association request limit interval";
    }
    leaf enable-assoc-limit {
      type boolean;
      default "false";
      description
        "the attribute enables the association request limit interval";
    }
    leaf blacklist-dot1x-timeout {
      type boolean;
      default "true";
      description
        "This flag specifies if client should be excluded (blacklisted) if re    peated 802.1x Authentication Timeout occurs with a client.";
    }
    leaf blacklist-dot1x-auth {
      type boolean;
      default "true";
      description
        "This flag specifies if client should be excluded (blacklisted) if repeated 802.1x Authentication Failures occurs with a client.";
    }
    leaf blacklist-dot11-assoc {
      type boolean;
      default "true";
      description
        "This flag specifies if client should be excluded (blacklisted) if repeated 802.11 Association Failures occurs with a client.";
    }
    leaf blacklist-dot11-auth {
      type boolean;
      default "true";
      description
        "This flag specifies if client should be excluded (blacklisted) if repeated 802.11 Authentication Failures occurs with a client.";
    }
    leaf blacklist-ip-theft {
      type boolean;
      default "true";
      description
        "This flag specifies if client should be excluded (blacklisted) if it appears to be reusing an IP Address.(Possible IP Theft)";
    }
    leaf blacklist-web-auth {
      type boolean;
      default "true";
      description
        "This flag specifies if client should be excluded (blacklisted) if repeated Web Authentication Failures occurs with a client.";
    }
    leaf blacklist-cids-shun {
      type boolean;
      default "true";
      description
        "Cids Shun failure";
    }
    leaf blacklist-misconfiguration {
      type boolean;
      default "true";
      description
        "this flag specifies if a client should be diabled in case of repeated misconfiguration";
    }
    leaf blacklist-failed-qos-policy {
      type boolean;
      default "true";
      description
        "This flag specifies if client should be excluded (blacklisted) due to failed qos policy";
    }
    leaf blacklist-failed-epm {
      type boolean;
      default "true";
      description
        "This flag specifies if client should be excluded (blacklisted) due to failed epm";
    }
    leaf probe-limit {
      type uint16 {
        range "1 .. 100";
      }
      default "2";
      description
        "this value indicate the probe request limit";
    }
    leaf probe-interval {
      type uint16 {
        range "100 .. 64000";
      }
      default "500";
      description
        "this value indicate the probe request interval";
    }
    leaf client-failed-aaa-alert-enabled {
      type boolean;
      default "false";
      description
        "Configures notifications for client authentication failures";
    }
    leaf client-roam-alert-enabled {
      type boolean;
      default "false";
      description
        "Configures notifications for client roam failures";
    }
    leaf client-aaa-alert-threshold {
      type uint32 {
        range "1 .. 100";
      }
      default "20";
      description
        "Configures threshold for client authentication failure notifications";
    }
    leaf client-roam-alert-threshold {
      type uint32 {
        range "1 .. 100";
      }
      default "20";
      description
        "Configures threshold for client roam failure notifications";
    }
    leaf client-failed-interval {
      type uint32 {
        range "1 .. 1440";
      }
      default "10";
      description
        "configure the time in minutes for client measurement interval";
    }
    leaf band-steering-cycle-count {
      type uint32 {
        range "1 .. 10";
      }
      default "2";
      description
        "Maximum number of band select probe cycles not responding";
    }
    leaf band-steering-cycle-threshold {
      type uint32 {
        range "1 .. 1000";
      }
      default "200";
      description
        "Sets the time threshold for a new scanning cycle";
    }
    leaf band-steering-age-out-suppression {
      type uint32 {
        range "10 .. 200";
      }
      default "20";
      description
        "Sets suppression band select expire time in seconds";
    }
    leaf band-steering-age-out-dual-band {
      type uint32 {
        range "10 .. 300";
      }
      default "60";
      description
        "This objects specifies age out period after which mobile station entry will be removed for dual band AP.";
    }
    leaf band-steering-client-rssi {
      type int32 {
        range "-90 .. -20";
      }
      default "-80";
      description
        "This object specifies minimum mobile station RSSI threshold.Mobile stations having RSSI below this value will not be recorded in suppressed table";
    }
    leaf band-steering-client-mid-rssi {
      type int32 {
        range "-90 .. -20";
      }
      default "-80";
      description
        "This object specifies medium mobile station RSSI threshold.Mobile station between this value and cldBandSelectClientRssi will be recorded in suppressed table but will not be denied.";
    }
    leaf max-user-logins {
      type uint32 {
        range "0 .. 8";
      }
      default "0";
      description
        "This attribute specifies the maximum number of concurrent logins that the switch will allow for a single user. A value 0 implies that there is no restriction on the number of concurrent logins with a single username.";
    }
    leaf dot11-authentication-response-timeout {
      type uint32 {
        range "5 .. 600";
      }
      default "10";
      description
        "This attribute shall specify the number of TU that a responding STA should wait for the next frame in the authentication sequence.";
    }
    leaf wgb-client-auth-list {
      type string;
      default "";
      description
        "Configure the authentication list name for WGB client";
    }
    leaf force-sha1-cert {
      type boolean;
      default "false";
      description
        "Disable usage of SHA-2 certificate for DTLS connections";
    }
    leaf web-auth-max-retries {
      type uint8 {
        range "0 .. 20";
      }
      default "3";
      description
        "Value specifies Maximum number of WebAuth request retries";
    }
    leaf dot1x-eapol-key-max-retries {
      type uint8 {
        range "0 .. 4";
      }
      default "2";
      description
        "Value specifies Maximum number of EAPOL key retries";
    }
    leaf dot1x-eapol-key-timeout {
      type uint32 {
        range "200 .. 5000";
      }
      default "1000";
      description
        "value specify EAPOL key retransmission timeout in milliseconds";
    }
    leaf dot1x-eap-id-request-max-retries {
      type uint8 {
        range "1 .. 20";
      }
      default "2";
      description
        "Value specify maximum number of EAP ID request retransmissions";
    }
    leaf dot1x-eap-id-request-timeout {
      type uint8 {
        range "1 .. 120";
      }
      default "30";
      description
        "Value specify EAP ID request-timeout value in seconds";
    }
    leaf dot1x-eap-request-max-retries {
      type uint8 {
        range "0 .. 20";
      }
      default "2";
      description
        "Maximum number of EAP request retransmissions";
    }
    leaf dot1x-eap-request-timeout {
      type uint8 {
        range "1 .. 120";
      }
      default "30";
      description
        "EAP request retransmission timeout value in seconds";
    }
    leaf dot1x-eap-broadcast-key-interval {
      type uint32 {
        range "120 .. 86400";
      }
      default "3600";
      description
        "EAP-broadcast key renew interval time in seconds";
    }
    leaf tech-support-tftp-offload-log-interval {
      type uint32;
      default "0";
      description
        "Log Interval for the command output in minutes";
    }
    leaf tech-support-tftp-offload-ip-address {
      type inet:ip-address;
      default "0.0.0.0";
      description
        "Configure offload server IP for tech-support ouput";
    }
    leaf tech-support-tftp-offload-client-mac {
      type yang:mac-address;
      default "00:00:00:00:00:00";
      description
        "Offload tech-support client information";
    }
    leaf password-validation-enable {
      type boolean;
      default "false";
      description
        "Configures strong password enforcement options.";
    }
    leaf probe-filter {
      type boolean;
      default "true";
      description
        "Configure filtering of probe requests from AP";
    }
    leaf assisted-roam-floor-bias {
      type uint16 {
        range "5 .. 25";
      }
      default "15";
      description
        "Configures RSSI bias default for same floor APs";
    }
    leaf assisted-roam-max-denial {
      type uint16 {
        range "1 .. 10";
      }
      default "5";
      description
        "Configures maximum number of times for association denial";
    }
    leaf assisted-roam-min-prediction {
      type uint16 {
        range "2 .. 6";
      }
      default "3";
      description
        "Configures minimum number of optimized APs for assisted-roaming prediction to work";
    }
    container sip-pref-call-data-entry {
      description
        "SIP preferred call database";
      list sip-pref-call-data {
        key "call-index";
        description
          "SIP preferred call data";
        uses wireless-apf-cfg:sip-preferred-call-data;
      }
    }
    leaf spam-authorize-aps-mac {
      type boolean;
      default "false";
      description
        "Configures an AP authorization policy with mac";
    }
    leaf spam-authorize-aps-serial-num {
      type boolean;
      default "false";
      description
        "Configures an AP authorization policy with serial number";
    }
    leaf spam-authorize-aps-method-list {
      type string {
        length "0..32";
      }
      default "default";
      description
        "Configures an AP authorization policy with specified method list";
    }
    leaf dot1x-max-login-ignore-identity-response {
      type boolean;
      default "true";
      description
        "Configure to ignore the same username count reaching max in the EAP identity response";
    }
    leaf dedicated-to-xor-rssi-threshold {
      type int8 {
        range "-128 .. 0";
      }
      default "-55";
      description
        "Configures macro to micro transition RSSI";
    }
    leaf xor-to-dedicated-rssi-threshold {
      type int8 {
        range "-128 .. 0";
      }
      default "-65";
      description
        "Configures micro-macro client load balancing window";
    }
    leaf xor-roam-min-client-count {
      type uint16 {
        range "0 .. 65535";
      }
      default "3";
      description
        "Configures macro-micro minimum client count for transition";
    }
    leaf balancing-window {
      type uint16 {
        range "0 .. 65535";
      }
      default "3";
      description
        "Configures micro-macro client load balancing window";
    }
    leaf xor-roam-probe-suppress-op-mode {
      type wireless-enum-types:enm-apf-xor-roam-probe-suppression;
      default "apf-xor-suppress-opmode-disabled";
      description
        "Configures micro-Macro probe suppression arguments";
    }
    leaf xor-roam-probe-suppress-rssi-hysteresis {
      type int8 {
        range "-6 .. -3";
      }
      default "-6";
      description
        "Configures probe cycles to be suppressed[ RSSI in dBm]";
    }
    leaf xor-roam-probe-suppress-transition-aggressiveness {
      type uint8 {
        range "0 .. 255";
      }
      default "3";
      description
        "Configures probe cycles to be suppressed [Number of cycles]";
    }
    leaf spam-fra-state {
      type boolean;
      default "false";
      description
        "Enable/Disable Fra on all Cisco APs";
    }
    leaf spam-fra-interval {
      type uint32 {
        range "1 .. 24";
      }
      default "1";
      description
        "Configure Fra Interval in hours";
    }
    leaf fra-sensitivity {
      type wireless-types:enm-fra-sensitivity;
      default "fra-sensitivity-medium";
      description
        "Configure FRA Coverage Overlap Sensitivity";
    }
    leaf fra-service-priority {
      type wireless-types:enm-fra-service-priority;
      default "fra-service-priority-coverage";
      description
        "Configure FRA Service Priority";
    }
    leaf fra-sensor-threshold {
      type wireless-types:enm-fra-sensor-coverage-profile;
      default "fra-sensor-coverage-best";
      description
        "Configure FRA Sensor Threshold";
    }
    container ports {
      description
        "SIP snooping ports";
      uses wireless-apf-cfg:snooping-ports;
    }
  }

  grouping sip-preferred-call-data {
    description
      "SIP Preferred call database";
    leaf call-index {
      type uint32 {
        range "1 .. 6";
      }
      description
        "Index in database for preferred call number";
    }
    leaf preferred-call-number {
      type string {
        length "0..28";
      }
      default "";
      description
        "SIP preferred call number";
    }
  }

  container apf-cfg-data {
    description
      "AP functionality configuration data";
    container apf {
      presence "apf";
      description
        "AP functionality configuration";
      uses wireless-apf-cfg:st-apf;
    }
  }
}
