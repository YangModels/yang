module Cisco-IOS-XE-wireless-security-cfg {
  yang-version 1;
  namespace "http://cisco.com/ns/yang/Cisco-IOS-XE-wireless-security-cfg";
  prefix wireless-security-cfg;

  import Cisco-IOS-XE-wireless-types {
    prefix wireless-types;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing AP Security configuration.
     Copyright (c) 2016-2018 by Cisco Systems, Inc.
     All rights reserved.";

  revision 2017-12-07 {
    description
      "Initial revision";
    reference "1.0.0";
  }

  grouping lsc-prov-list {
    description
      "AP LSC Provision list";
    leaf ap-mac {
      type yang:mac-address;
      description
        "AP Ethernet Mac address to which LSC Certificates will be provisioned";
    }
  }

  grouping st-lsc-provision {
    description
      "AP LSC provisioning configuration";
    leaf status {
      type wireless-types:lsc-prov-status;
      default "lsc-prov-disable";
      description
        "Setting this to true will make APs to start LSC provisioning. Setting this to false will make APs to fallback to MIC/SSC";
    }
    leaf join-attempt {
      type uint32;
      default "4";
      description
        "Join attempts before AP fallbacks to MIC from LSC.";
    }
    leaf country {
      type string;
      default "";
      description
        "Country name that will be sent as a part of Certificate  Signing Request from the AP";
    }
    leaf state {
      type string;
      default "";
      description
        "State name that will be sent as a part of Certificate  Signing Request from the AP";
    }
    leaf city {
      type string;
      description
        "City name that will be sent as a part of Certificate  Signing Request from the AP";
    }
    leaf domain {
      type string;
      default "";
      description
        "Domain name that will be sent as a part of Certificate  Signing Request from the AP";
    }
    leaf org {
      type string;
      default "";
      description
        "Organisation name that will be sent as a part of Certificate  Signing Request from the AP";
    }
    leaf email-addr {
      type string;
      default "";
      description
        "Email address that will be sent as a part of Certificate  Signing Request from the AP";
    }
    leaf key-size {
      type wireless-types:enum-ewlc-lsc-key-size;
      default "lsc-keysize-2048";
      description
        "Size of the keys: Can only be 1024 or 2048";
    }
    leaf sig-256 {
      type boolean;
      default "false";
      description
        "Enable/Disable 256 bit signature";
    }
    leaf lsc-tp-name {
      type string;
      description
        "Trustpoint corresponding to the CA server through which certificates will be provided to AP and WLC for LSC provisioning";
    }
  }

  container lsc-cfg-data {
    description
      "Wireless security configurations";
    container lsc-prov {
      presence "lsc-prov";
      description
        "LSC Provisioning configurations for Access points";
      uses wireless-security-cfg:st-lsc-provision;
    }
    container lsc-provision-entries {
      description
        "AP LSC provision list configuration";
      list lsc-provision-entry {
        key "ap-mac";
        description
          "This object encompasses the AP LSC provisioning list";
        uses wireless-security-cfg:lsc-prov-list;
      }
    }
  }
}
