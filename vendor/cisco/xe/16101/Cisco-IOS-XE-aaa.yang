module Cisco-IOS-XE-aaa {
  namespace "http://cisco.com/ns/yang/Cisco-IOS-XE-aaa";
  prefix ios-aaa;

  import ietf-inet-types {
    prefix inet;
  }


  import Cisco-IOS-XE-types {
    prefix ios-types;
  }

  import Cisco-IOS-XE-native {
    prefix ios;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Authentication, Authorization and Accouting (AAA) Yang Model.
     Copyright (c) 2016-2018 by Cisco Systems, Inc.
     All rights reserved.";

  // =========================================================================
  // REVISION
  // =========================================================================
  revision 2018-10-16 {
    description
      "Added cli-full-command to handle authorization commands create delete";
  }

  revision 2018-10-09 {
    description
      "Added 'cli-preformatted' for handling special char in aaa server-key";
  }
 
  revision 2018-08-24 {
    description
      "Added options under aaa accounting update *";
  }

  revision 2018-08-03 {
    description
      "Added IPv6 support for radius";
  }

  revision 2018-08-02 {
    description
      "Added IPv6 support for tacacs";
  }

  revision 2018-05-29 {
    description
      "Add default for aaa session common";
  }

  revision 2018-01-15 {
    description
      "Add Support for suppress node under aaa accounting";
  }

  revision 2018-01-11 {
    description
      "Changed aaa group radius ip source-interface to implement correct native interface model";
  }
 
  revision 2017-12-15 {
    description
      "Added aaa server group acct-port leaf";
  }
 
  revision 2017-12-04 {
    description
      "Added support back for aaa accounting dot1x required for DNA-C removed in revision below on 06-01";
  }
 
  revision 2017-11-17 {
    description
      "Added support for named tacacs and radius servers in both aaa groups for radius and tacacs";
  }

  revision 2017-11-16 {
    description
      "Support server-private <ip> key under aaa group server radius";
  }
  revision 2017-10-10 {
    description
      "Support new aaa local authorization auth-proxy";
  }
  revision 2017-10-06 {
    description
      "Add server-private list to radius server group";
  }
  revision 2017-10-05 {
    description
      "Add support for 'subscriber *' and 'mac-delimiter *' commands under aaa group server";
  }
  revision 2017-09-28 {
    description
      "Support wireless aaa misc commands";
  }
  revision 2017-09-05 {
    description
      "Support new aaa login commands and aaa server commands";
  }
  revision 2017-06-05 {
    description
      "Update domain delimeter description to conform to YANG 1.1";
    reference
      "RFC 7950: The YANG 1.1 Data Modeling Language";
  }
  revision 2017-06-01 {
    description
      "Changed aaa accounting dot1x to aaa accounting identity";
  }
  revision 2017-03-24 {
    description
      "Remove banner and fail-message";
  }
  revision 2017-03-08 {
    description
      "Add radius retransmit/automate-tester";
  }
  revision 2017-03-03 {
    description
      "add aaa login support and deadtimer for radius";
  }
  revision 2017-02-28 {
    description
      "Add attribute 31 to radius-server";
  }
  revision 2017-02-07 {
    description
      "Initial revision";
  }

  typedef ipv4-mask-slash-prefix-len-type {
    type string {
      pattern '/(([0-9])|([1-2][0-9])|(3[0-2]))';
    }
  }

  grouping aaa-attribute-type-options {
    leaf mandatory {
      description
        "Specify an AAA attribute as mandatory";
      type empty;
    } 
    leaf tag {
      description
        "Specify an AAA attribute tag";
      type uint8 {
        range "1..31";
      }
    }
  }

  grouping aaa-accounting-identity {
    container start-stop {
      description
        "Record start and stop without waiting";
      leaf broadcast {
        description
          "Use Broadcast for Accounting";
        type empty;
      }
      leaf group {
        description
          "Use Server-group";
        type union {
          type string;
          type enumeration {
            enum "radius";
            enum "tacacs+";
          }
        }
      }
    }
  }

  grouping aaa-accounting-dot1x {
    container start-stop {
      description
        "Record start and stop without waiting";
      leaf broadcast {
        description
          "Use Broadcast for Accounting";
        type empty;
      }
      leaf group {
        description
          "Use Server-group";
        type union {
          type string;
          type enumeration {
            enum "radius";
            enum "tacacs+";
          }
        }
      }
    }
  }

  grouping aaa-authorization-cred-download {
    leaf local {
      description
        "Use local database";
      type empty;
    }
    leaf cache {
      description
        "Use Cached-group";
      type union {
        type string;
        type enumeration {
           enum "ldap";
           enum "radius";
           enum "tacacs+";
         } 
      }
    }
    leaf group {
      description
        "Use server-group";
      type union {
        type string;
        type enumeration {
           enum "ldap";
           enum "radius";
           enum "tacacs+";
         } 
      }
    }
    leaf if-authenticated {
      description
        "Succeed if user has authenticated";
      type empty;
    }
    leaf none {
      description
        "No authorization (always succeeds)";
      type empty;
    }
  }

  grouping aaa-server-radius-key-grouping { 
    container key {
      description
        "Specify a RADIUS client";
      uses aaa-server-radius-key;
    }
  }
 
  grouping aaa-server-proxy-common {
    container accounting {
      description
        "Specify accounting details";
      uses aaa-server-method;
      uses aaa-server-radius-port;
    }
    container authentication {
      description
        "Specify authentication details";
      uses aaa-server-method;
      uses aaa-server-radius-port;
    }
    container calling-station-id {
      description 
        "Specify format of Calling-Station-Id, attribute\
         31.Default format is to expect mac-address in\
         calling-station-id";
      container format {
        description
          "Specify the format as MAC or MSISDN";
        choice type {
          container mac-address {
            description
              "Expect MAC address to be present in CLID";
            choice mac-format {
              container default {
                description
                  "format ex: 0000.4096.3e4a";
                presence "true";
                uses aaa-case-grouping;
              }
              container ietf {
                description
                  "format ex: 00-00-40-96-3E-4A";
                presence "true";
                uses aaa-case-grouping;
              }
              leaf none {
                description
                  "format unspecified";
                type empty;
              }
              container one-byte {
                description
                  "format ex: 00.00.40.96.3e.4a";
                uses aaa-server-delimiter-groupingg;
              }
              container three-byte {
                description
                  "format ex: 000040.963e4a";
                uses aaa-server-delimiter-groupingg;
              }
              container two-byte {
                description
                  "format ex: 0000.4096.3e4a";
                uses aaa-server-delimiter-groupingg;
              }
              container unformatted {
                description
                  "format ex: 000040963e4a";
                presence "true";
                uses aaa-case-grouping;
              }
            }
          }
          leaf msisdn {
            description
              "Expect MSISDN value to be present in CLID";
            type empty;
          } 
        }
      }
    }

    container eap-user {
      description
        "EAP users";
      leaf ignore-open-session {
        description
          "for EAP authenticated users, open-session is not supported";
        type empty;
      }
    }

    container filter {
      description
        "Configure filter";
      container access {
        description
          "For access requests";
        uses aaa-server-filter;
      }
      container accounting {
        description
          "For accounting requests";
      uses aaa-server-filter;
      }
      container attribute {
        description
          "Filter attributes in packets sent to clients";
        choice attr-type {
          leaf allow {
            description
              "Allow only the attributes specified in the list";
            type string;
          }
          leaf block {
            description
              "Block the attributes specified in the list";
            type string;
          }
        }
      }
    }      

    uses aaa-server-radius-key-grouping;

    container message-authenticator {
      description
        "Message Authenticator attribute from Clients";
      container ignore {
        description
          "Ignore checking of Message Authenticator attribute from\
           Clients";
        presence "true";
        leaf accounting {
          description
            "Ignore checking of Message Authenticator attribute from\
            accounting packets";
          type empty;
        }
      }
    }
    container mode {
      description
        "Radius Proxy Pass thru mode";
      leaf pass-through {
        description
          "Enable the pass-through mode for Radius Proxy";
        type empty;
      }
    }
    container pwlan-session {
      description
        "PWLAN Reconnect feature";
      leaf reconnect {
        description
          "Enable the reconnect feature for PWLAN RP sessions";
        type empty;
      }
    }
    container re-authentication {
      description
        "Specify re-authentication details";
      leaf do-not-apply {
        description
          "Do not apply new data during re-authentication";
        type empty;
      }
    }
    container session-identifier { 
      description
        "This attribute will be used to correlate Radius \
         requests of a session and to identify sessions within \
         radius-proxy";
      leaf attribute {
        description
          "Specify an IETF Radius attribute";
        type uint8 {
          range "1..255";
        }
      }
      container vsa {
        description
          "Specify Vendor-Specific Attribute";
        leaf vendor {
          description
            "Specify the vendor type";
          type uint16 {
            range "1..65535";
          }
        }
        leaf type {
          description
            "Give attribute type for vsa";
          type uint8 {
            range "1..255";
          }
        }
      }
    }

    container timer {
      description
        "Configure RADIUS proxy timer values";
      container disconnect {
        description
          "Specify disconnect timer";
        leaf acct-stop {
          description
            "Specify disconnect delay timer for accounting stop";
          type uint16 {
            range "0..43200";
          }
        }
        leaf reauth-fail {
          description
            "Specify disconnect delay timer for reauthentication failure";
          type uint16 {
            range "0..43200";
          }
        }
      }
      leaf ip-address {
        description
          "Specify value of wait for IP timer";
        type uint16 {
          range "0..43200";
        }
      }
      leaf reconnect {
        description
          "Specify value of wait for reconnect timer";
        type uint16 {
          range "0..43200";
        }
      }
      leaf request {
        description
          "Specify value of wait for Access-Request timer";
        type uint16 {
          range "0..43200";
        }
      }
      leaf roaming {
        description
          "Specify value of wait for roaming timer";
        type uint16 {
          range "0..43200";
        }
      }
    }    
  }

  grouping aaa-server-options {
    leaf word1 {
      description
        "Name of the filter to be applied (max 31 chars. \
        (max 31 chars. longer will be ignored)";
      type string;
    } 
    leaf word2 {
      description
        "Name of the filter to be applied (max 31 chars. \
        (max 31 chars. longer will be ignored)";
      type string;
    } 
    leaf word3 {
      description
        "Name of the filter to be applied (max 31 chars. \
        (max 31 chars. longer will be ignored)";
      type string;
    } 
    leaf word4 {
      description
        "Name of the filter to be applied (max 31 chars. \
        (max 31 chars. longer will be ignored)";
      type string;
    } 
  }

  grouping aaa-server-filter {
    choice filter-type {
      container ack {
        description
          "Acknowledge the packet";
        uses aaa-server-options;
      }
      container drop {
        description
          "Drop the packet";
        uses aaa-server-options;
      }
      container ignore {
        description
          "Ignore the packet for applying ISG features";
        uses aaa-server-options;
      }
    }
  }

  grouping aaa-server-radius-port {
    leaf port {
      description
        "Radius server port";
      type uint16;
    }
  }

  grouping aaa-server-radius-key {
    leaf key {
      type enumeration {
        enum "0";
        enum "6";
        enum "7";
      }
    }
    leaf string {
      type string {
        pattern '.*';
      }
    }
  }

  grouping aaa-server-method {
    container method-list {
      description
        "Authentication method list details";
      choice method {
        leaf method-name {
          description
            "Method list name";
          type string;
        }
        leaf default {
          description
            "The default authentication list";
          type empty;
        }
      }
    }
  }

  grouping aaa-case-grouping {
    leaf type {
      type enumeration {
        enum "lower-case";
        enum "upper-case"; 
      }
    }
  }

  grouping aaa-server-delimiter-groupingg {
    container delimiter {
      choice delimeter-type {
        container colon {
          presence "true";
          uses aaa-case-grouping;
        }
        container dot {
          presence "true";
          uses aaa-case-grouping;
        }
        container hyphen {
          presence "true";
          uses aaa-case-grouping;
        }
      }
    } 
  }

  grouping aaa-authentication-dot1x-grouping {
    leaf group {
      description
        "Use Server-group";
      type union {
        type string;
        type enumeration {
          enum "radius";
          enum "ldap";
        }
      }
    }
    leaf local {
      description
        "Use local username authentication";
      type empty;
    }
    leaf cache {
      description
        "Use Cased-group";
      type union {
        type string;
        type enumeration {
          enum "radius";
          enum "ldap";
        }
      }
    }
  }

  grouping aaa-accounting-grouping {
    choice accounting-choice {
      leaf none {
        description
          "No accounting.";
        type empty;
      }
      container start-stop {
        description
          "Record start and stop without waiting";
        leaf broadcast {
          description
            "Use Broadcast for Accounting";
          type empty;
        }
        leaf group {
          description
            "Use Server-group";
          type union {
            type string;
            type enumeration {
              enum "radius";
              enum "tacacs+";
            }
          }
        }
      }
      container stop-only {
        description
          "Record stop when service terminates.";
        leaf broadcast {
          description
            "Use Broadcast for Accounting";
          type empty;
        }
        leaf group {
          description
            "Use Server-group";
          type union {
            type string;
            type enumeration {
              enum "radius";
              enum "tacacs+";
            }
          }
        }
      }
    }
  }

  grouping config-aaa-grouping {
    leaf new-model {
      description
        "Enable NEW access control commands and functions.(Disables OLD commands.)";
        type empty;
    }
    container group {
      description
        "AAA group definitions";
      container server {
        description
          "AAA Server group definitions";
        list tacacsplus {
          description
            "Tacacs+ server-group definition";
          key "name";
          leaf name {
            type string;
          }
          container server {
            description
              "Specify a TACACS server";
            list name {
              description
                "Name of tacacs server";
              key "name";
              leaf name {
                type string;
              }
            }
//added list for multiple tacacs servers in a group
            list direct {
              key "name";
              leaf name {
                type inet:host;
              }
            }
          }
          list server-private {
            description
              "Define a private TACACS server (per group)";
            key "name";
            leaf name {
              type ios-types:host-type;
            }
            leaf port {
              description
                "TCP port for TACACS+ server (default is 49)";
              type uint16 {
                range "1..65535";
              }
            }
            leaf timeout {
              description
                "Time to wait for this TACACS server to reply (overrides default)";
              type uint16 {
                range "1..1000";
              }
            }
            container key {
              description
                "per-server encryption key (overrides default)";
              leaf encryption {
                type enumeration {
                  enum "0";
                  enum "7";
                }
              }
              leaf key {
                type string;
              }
            }
            //nat  To send client's post NAT address to tacacs+ server
            //single-connection Multiplex all packets over a single..
            //..tcp connection to server (for CiscoSecure)
          }
          container ip {
            description
              "Internet Protocol config commands";
            container tacacs {
              description
                "TACACS configuration commands";
              uses config-ip-tacacs-main-grouping;
            }
            container vrf {
              description
                "Set VPN Routing Forwarding to use with the servers";
              leaf forwarding {
                description
                  "Configure forwarding table";
                type string;
              }
            }
          }
        }
        // aaa group server tacacs+
        list tacacs {
          description "Tacacs+ server-group definition";
          key "name";
          leaf name {
            type string; 
          }
        }
        // aaa group server radius *
        list radius {
          description
            "Radius server-group definition";
          key "name";
          leaf name {
            type string;
          }
          container server {
            description
              "Specify a RADIUS server";
            list name {
              description
                "Name of radius server";
              key "name";
              leaf name {
                type string;
                
              }
            }
            list direct {
              key "name";
              leaf name {
                type inet:host;
              }
              leaf auth-port {
                description
                  "UDP port for RADIUS authentication server (default is 1645)";
                type uint16 {
                  range "0..65535";
                }
              }
              leaf acct-port {
                description
                  "UDP port for RADIUS accounting server (default is 1646)";
                type uint16 {
                  range "0..65535";
                }
              }
            }
          }
          container subscriber {
            description
              "Configures MAC Filtering RADIUS Compatibility mode";
            container mac-filtering {
              description
                "MAC Filtering";
              leaf security-mode {
                description
                  "Security Mode";
                type enumeration {
                  enum "mac";
                  enum "none";
                  enum "shared-secret";
                }
              }
            }
          }
          leaf mac-delimiter {
            description
              "MAC Delimiter for Radius Compatibility Mode";
            type enumeration {
              enum "colon";
              enum "hyphen";
              enum "none";
              enum "single-hyphen";
            } 
          }
          list server-private {
            description
              "Define a private RADIUS server (per group)";
            ordered-by user;
            key "name";
            leaf name {
              type ios-types:host-type;
            }
            leaf auth-port {
              description
                "UDP port for RADIUS authentication server (default is 1645)";
              type uint16 {
                range "0..65534";
              }
            }
            leaf acct-port {
              description
                "UDP port for RADIUS accounting server (default is 1646)";
              type uint16 {
                range "0..65534";
              }
            }
            leaf timeout {
              description
                "Time to wait for this RADIUS server to reply (overrides default)";
              type uint16 {
                range "1..1000";
              }
            }
            leaf retransmit {
              description
                "Number of retries to active server (overrides default)";
              type uint8 {
                range "0..100";
              }
            }
            container key {
              description
                "per-server encryption key (overrides default)";
              leaf encryption {
                type enumeration {
                  enum "0";
                  enum "6";
                  enum "7";
                }
              }
              leaf key {
                type string;
              }
            }
          }
          leaf deadtime {
            description
              "Specify time in minutes to ignore an unresponsive server";
            type uint16 {
              range "0..1440";
            }
          }
          container ip {
            description
              "Internet Protocol config commands";
            container radius {
              description
                "RADIUS configuration commands";
              container source-interface {
                description
                  "Specify interface for source address in RADIUS packets";
                uses ios-ifc:interface-grouping;
              }
            }
            container vrf {
              description
                "Set VPN Routing Forwarding to use with the servers";
              leaf forwarding {
                description
                  "Configure forwarding table";
                type string;
              }
            }
          }
          container load-balance {
            description
              "Server group load-balancing options.";
            container method {
              description
                "Method by which the next host will be picked.";
              container least-outstanding {
                description
                  "Pick the server with the least transactions outstanding.";
                presence "true";
                leaf batch-size {
                  description
                    "Size of the transaction batch that should be load-balanced.";
                  type uint32 {
                    range "1..2147483647";
                  }
                }
                leaf ignore-preferred-server {
                  description
                    "Should the preferred-server be ignored.";
                  type empty;
                }
              }
            }
          }
          //  subscriber Configures MAC Filtering RADIUS Compatibility mode
          //  throttle Throttle requests to radius server
        }
      }
    }
    // aaa attribute
    container attribute {
      description
        "AAA attribute definitions";
      list list {
        description
          "AAA attribute list definition";
        key "name";
        leaf name {
         type string;
        }
        container attribute {
          description
            "Specify an AAA attribute";
          container type {
            description
              "Specify an AAA attribute type";
            leaf password {
              description
                "The password of the user to be authenticated \
                 string of hex characters";
              type string;
            }
            uses aaa-attribute-type-options;
          }
        }
      }  
    } 
    // aaa authentication
    container authentication {
      description
        "Authentication configurations parameters.";
       //  arap             Set authentication lists for arap.
      //aaa authentication attempts
      container attempts {
        description
          "Set the maximum number of authentication attempts";
        leaf login {
          description
            "Set the max. number of attempts for login service";
          type uint8 {
            range "1..25";
          }
        }
      }

      // aaa authentication dot1x
      container dot1x {
        description
          "Set authentication lists for IEEE 802.1x.";
        list dot1x-list {
          key "name";
          leaf name {
            type string;
          }
          uses aaa-authentication-dot1x-grouping;
        }
        container default {
          description
            "The default authentication list.";
          uses aaa-authentication-dot1x-grouping;
        }
      }
      // aaa authentication enable
      container enable {
        description
          "Set authentication list for enable.";
        container default {
          description
            "The default authentication list.";
          leaf group {
            description
              "Use Server-group";
            type union {
              type string;
              type enumeration {
                enum "radius";
                enum "tacacs+";
              }
            }
          }
          leaf enable {
            description
              "Use enable password for authentication.";
            type empty;
          }
          leaf line {
            description
              "Use line password for authentication.";
            type empty;
          }
          leaf none {
            description
              "No authentication.";
            type empty;
          }
        }
      }
      // aaa authentication eou
      container eou {
          description "Set authentication lists for EAPoUDP";
          container default {
              description "The default authentication list";
              container group {
                  description "Use Server-group";
                  leaf radius {
                      description "Use list of all Radius hosts.";
                      type empty;
                  }
              }
          }
      }
      //  eou              Set authentication lists for EAPoUDP

      // aaa authentication login *
      list login {
        description
          "Set authentication lists for logins.";
        key "name";
        leaf name {
          type union {
            type enumeration {
              enum "default";
            }
            type string {
              length "1..31";
            }
          }
        }
        container a1 {
          choice auth-login-choice {
            leaf none {
              description
                "NO authentication.";
              type empty;
            }
            leaf krb5 {
              description
                "Use Kerberos 5 authentication.";
              type empty;
            }
            leaf krb5-telnet {
              description
               "Allow logins only if already authenticated via Kerbero";
              type empty;
            }
            leaf line {
              description
                "Use line password for authentication.";
              type empty;
            }
            leaf enable {
              description
                "Use enable password for authentication.";
              type empty;
            }
            leaf local {
              description
                "Use local username authentication.";
              type empty;
            }
            leaf local-case {
              description
                "Use case-sensitive local username authentication.";
              type empty;
            }
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
          }
        }
        container a2 {
          when "not(../a1/none)" {
          }
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet)" {
              }
              type empty;
            }
            leaf krb5-telnet {
              when "not(../../a1/krb5) and not(../../a1/krb5-telnet)" {
              }
            type empty;
            }
            leaf line {
              description
                "Use line password for authentication.";
              type empty;
            }
            leaf enable {
              description
                "Use enable password for authentication.";
              type empty;
            }
            leaf local {
              when "not(../../a1/local) and not(../../a1/local-case)" {
              }
              type empty;
            }
            leaf local-case {
              when "not(../../a1/local) and not(../../a1/local-case)" {
              }
              type empty;
            }
          }
        }
        container a3 {
          when "not(../a2/none) and not (../a1/none)" {
          }
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet) and not(../../a2/krb5) and not(../../a2/krb5-telnet)" {
              }
              type empty;
            }
            leaf krb5-telnet {
              when "not(../../a1/krb5) and not(../../a1/krb5-telnet) and not(../../a2/krb5) and not(../../a2/krb5-telnet)" {
              }
              type empty;
            }
            leaf line {
              description
                "Use line password for authentication.";
              type empty;
            }
            leaf enable {
              description
                "Use enable password for authentication.";
              type empty;
            }
            leaf local {
              when "not(../../a1/local) and not(../../a1/local-case) and not(../../a2/local) and not(../../a2/local-case)" {
              }
              type empty;
            }
            leaf local-case {
              when "not(../../a1/local) and not(../../a1/local-case) and not(../../a2/local) and not(../../a2/local-case)" {
              }
              type empty;
            }
          }
        }
        container a4 {
          when "not(../a2/none) and not(../a1/none) and not(../a3/none)" {
          }
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet) and not(../../a2/krb5) and not(../../a2/krb5-telnet) and not(../../a3/krb5) and not(../../a3/krb5-telnet)" {
              }
              type empty;
            }
            leaf krb5-telnet {
              when "not(../../a1/krb5) and not(../../a1/krb5-telnet) and not(../../a2/krb5) and not(../../a2/krb5-telnet) and not(../../a3/krb5) and not(../../a3/krb5-telnet)" {
              }
              type empty;
            }
            leaf line {
              description
                "Use line password for authentication.";
              type empty;
            }
            leaf enable {
              description
                "Use enable password for authentication.";
              type empty;
            }

            leaf local {
              when "not(../../a1/local) and not(../../a1/local-case) and not(../../a2/local) and not(../../a2/local-case) and not(../../a3/local) and not(../../a3/local-case)" {
              }
              type empty;
            }
            leaf local-case {
              when "not(../../a1/local) and not(../../a1/local-case) and not(../../a2/local) and not(../../a2/local-case) and not(../../a3/local) and not(../../a3/local-case)" {
              }
              type empty;
            }
          }
        }
      }

      // aaa authentication onep *
      container onep {
        description "Set authentication lists for ONEP";
        container default {
          description "The default authentication list.";
          container local {
            description "Use local username authentication.";
            presence true;
          }
        }
      }

      // aaa authentication ppp *
      list ppp {
        description
          "Set authentication lists for ppp.";
        
        key "id";
        leaf id {
          type string {
            length "1..31";
          }
        }
        container a1 {
          choice auth-choice {
            leaf if-needed {
              description
                "Only authenticate if needed.";
              type empty;
            }
            leaf none {
              description
                "NO authentication.";
              type empty;
            }
            leaf krb5 {
              description
                "Use Kerberos 5 authentication.";
              type empty;
            }
            leaf local {
              description
                "Use local username authentication.";
              type empty;
            }
            leaf local-case {
              description
                "Use case-sensitive local username authentication.";
              type empty;
            }
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
          }
        }
        container a2 {
          when "not(../a1/none)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5)" {
              }
              type empty;
            }
            leaf local {
              when "not(../../a1/local) and not(../../a1/local-case)" {
              }
              type empty;
            }
            leaf local-case {
              when "not(../../a1/local) and not(../../a1/local-case)" {
              }
              type empty;
            }
          }
        }
        container a3 {
          when "not(../a2/none) and not (../a1/none)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5) and not(../../a2/krb5)" {
              }
              type empty;
            }
            leaf local {
              when "not(../../a1/local) and not(../../a1/local-case) and not(../../a2/local) and not(../../a2/local-case)" {
              }
              type empty;
            }
            leaf local-case {
              when "not(../../a1/local) and not(../../a1/local-case) and not(../../a2/local) and not(../../a2/local-case)" {
              }
              type empty;
            }
          }
        }
        container a4 {
          when "not(../a2/none) and not(../a1/none) and not(../a3/none)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5) and not(../../a2/krb5) and not(../../a3/krb5)" {
              }
              type empty;
            }
            leaf local {
              when "not(../../a1/local) and not(../../a1/local-case) and not(../../a2/local) and not(../../a2/local-case) and not(../../a3/local) and not(../../a3/local-case)" {
              }
              type empty;
            }
            leaf local-case {
              when "not(../../a1/local) and not(../../a1/local-case) and not(../../a2/local) and not(../../a2/local-case) and not(../../a3/local) and not(../../a3/local-case)" {
              }
              type empty;
            }
          }
        }
      }
    }
    // aaa local 
    container local {
      description
        "AAA Local method options";
      container authentication {
        description
          "Local authentication options";
        container authorization {
          leaf authen-type {
            type union {
              type enumeration {
                enum "default";
              }
              type string;
            }
          }
          leaf authorization {
            type union {
              type enumeration {
                enum "default";
              }
              type string;
            }
          }
        }
        container attempts {
          description
            "Local authentication attempts";
          leaf max-fail {
            description
              "Max failed attempts to lock the user";
            type uint16 {
              range "1..65535";
            }
          }
        }
      } 
    }
    // aaa authorization
    container authorization {
      description
        "Authorization configurations parameters.";
      container auth-type {
          description "For Authentication Proxy Services";
          container default {
              description "The default authorization list.";
              leaf group {
                  description "Use server-group.";
                  type enumeration {
                      enum "radius";
                  }
              }
          }
      }
      list commands {
        description
          "For exec (shell) commands.";
        key "level list-name";
        leaf level {
          description
            "Enable level";
          type uint8 {
            range "0..15";
          }
        }
        leaf list-name {
          type union {
            type enumeration {
              enum "default";
            }
            type string;
          }
        }
        leaf local {
          description
            "Use local database.";
          type empty;
        }
        leaf group {
          description
            "Use server-group.";
          type union {
            type enumeration {
              enum "tacacs+";
            }
            type string;
          }
        }
        leaf if-authenticated {
          description
            "Succeed if user has authenticated.";
          type empty;
        }
        leaf none {
          description
            "No authorization (always succeeds).";
          type empty;
        }
      }
      leaf console {
        type empty;
      }
      leaf config-commands {
        description
          "For configuration mode commands.";
        type empty;
      }
      //  configuration For downloading configurations from AAA server
      container configuration {
        description "For downloading configurations from AAA server";
        container default {
          description "The default authorization list.";
          container group {
            description "Use server-group.";
            list group-name {
              key "group-name";
              leaf group-name {
                description "Server-group name";
                type string;
              }
            }
          }
        }
      }
      //  console For enabling console authorization
      container credential-download {
        description
          "For downloading EAP credential from Local/RADIUS/LDAP";
        container default {
          description
            "The default authorization list";
          uses aaa-authorization-cred-download;
        }
        list authorization-list {
          description
            "Named authorization list (max 31 characters, \
             longer will be rejected)";
          key "name";
          leaf name {
            type string;
          }
          uses aaa-authorization-cred-download;
        }
      }

      // aaa authorization exec *
      list exec {
        description
          "For starting an exec (shell).";
        key "name";
        leaf name {
          type string;
        }
    container a1 {
      choice auth-exec-choice {
        leaf if-authenticated {
      description
        "Succeed if user has authenticated.";
      type empty;
        }
        leaf none {
      description
        "No authorization (always succeeds)";
      type empty;
        }
        leaf krb5-instance {
      description
        "Use Kerberos instance privilege maps";
      type empty;
        }
        leaf local {
      description
        "Use local database";
      type empty;
        }
        leaf group {
      description
        "Use Server-group";
      type union {
        type string;
        type enumeration {
          enum "ldap";
          enum "radius";
          enum "tacacs+";
        }
      }
       }
       leaf cache {
      description
        "Use Cached-group";
      type union {
        type string;
        type enumeration {
          enum "ldap";
          enum "radius";
          enum "tacacs+";
        }
      }
        }
      }
    }
    container a2 {
      when "not(../a1/none) and not(../a1/if-authenticated)" {
      }
      choice auth-exec-choice {
        leaf group {
      description
        "Use Server-group";
      type union {
        type string;
        type enumeration {
          enum "ldap";
          enum "radius";
          enum "tacacs+";
        }
      }
        }
        leaf cache {
      description
        "Use Cached-group";
      type union {
        type string;
        type enumeration {
          enum "ldap";
          enum "radius";
          enum "tacacs+";
        }
      }
        }
            leaf if-authenticated {
      description
        "Succeed if user has authenticated.";
      type empty;
        }
        leaf none {
      description
        "No authorization (always succeeds).";
      type empty;
        }
        leaf krb5-instance {
      when "not (../../a1/krb5-instance)" {
      }
      type empty;
        }
        leaf local {
      when "not(../../a1/local)" {
      }
      type empty;
        }
      }
    }
    container a3 {
      when "not(../a2/none) and not (../a1/none) and not(../a2/if-authenticated) and not(../a1/if-authenticated)" {
      }
      choice auth-exec-choice {
        leaf group {
      description
        "Use Server-group";
      type union {
        type string;
        type enumeration {
          enum "ldap";
          enum "radius";
          enum "tacacs+";
        }
      }
        }
        leaf cache {
      description
        "Use Cached-group";
      type union {
        type string;
        type enumeration {
          enum "ldap";
          enum "radius";
          enum "tacacs+";
        }
      }
        }
        leaf none {
      description
        "No authorization (always succeeds).";
      type empty;
        }
        leaf if-authenticated {
      description
        "Succeed if user has authenticated.";
      type empty;
        }
        leaf krb5-instance {
      when "not (../../a1/krb5-instance) and not (../../a2/krb5-instance)" {
      }
      type empty;
        }
        leaf local {
      when "not(../../a1/local) and not(../../a2/local)" {
      }
      type empty;
        }
      }
    }
    container a4 {
      when "not(../a2/none) and not(../a1/none) and not(../a3/none) and not(../a2/if-authenticated) and not(../a1/if-authenticated) and not(../a3/if-authenticated)" {
      }
      choice auth-exec-choice {
        leaf group {
      description
        "Use Server-group";
      type union {
        type string;
        type enumeration {
          enum "ldap";
          enum "radius";
          enum "tacacs+";
        }
      }
        }
        leaf cache {
      description
        "Use Cached-group";
      type union {
        type string;
        type enumeration {
          enum "ldap";
          enum "radius";
          enum "tacacs+";
        }
      }
        }
        leaf none {
      description
        "No authorization (always succeeds).";
      type empty;
        }
        leaf if-authenticated {
      description
        "Succeed if user has authenticated.";
      type empty;
        }
        leaf krb5-instance {
      when "not (../../a1/krb5-instance) and not (../../a2/krb5-instance) and not (../../a3/krb5-instance)" {
      }
      type empty;
        }
        leaf local {
      when "not(../../a1/local) and not(../../a2/local) and not(../../a3/local)" {
      }
      type empty;
        }
      }
    }
  }
      // aaa authorization eventmanager *
      list eventmanager {
        description
          "For starting an exec (shell).";
        key "name";
        leaf name {
          type string;
        }
        leaf group {
          description
            "Use server-group.";
          type union {
            type string;
            type enumeration {
              enum "ldap";
              enum "radius";
              enum "tacacs";
            }
          }
        }
        leaf local {
          description
            "Use local database.";
          type empty;
        }
        leaf none {
          description
            "No authorization (always succeeds).";
          type empty;
        }
      }
      // aaa authorization network *
      list network {
        description
          "For network services. (PPP, SLIP, ARAP)";
        key "id";
        leaf id {
          type union {
            type enumeration {
              enum "default";
            }
            type string {
              length "1..31";
            }
          }
        }
        container a1 {
          choice auth-choice {
            leaf if-authenticated {
              description
                "Succeed if user has authenticated.";
              type empty;
            }
            leaf none {
              description
                "NO authentication.";
              type empty;
            }
            leaf local {
              description
                "Use local username authentication.";
              type empty;
            }
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
          }
        }
        container a2 {
          when "not(../a1/none) and not(../a1/if-authenticated)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf if-authenticated {
              description
                "Succeed if user has authenticated.";
              type empty;
            }
            leaf none {
              description
                "NO authentication.";
              type empty;
            }
            leaf local {
              when "not(../../a1/local)" {
              }
              type empty;
            }
          }
        }
        container a3 {
          when "not(../a2/none) and not (../a1/none) and not(../a2/if-authenticated) and not(../a1/if-authenticated)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf if-authenticated {
              description
                "Succeed if user has authenticated.";
              type empty;
            }
            leaf local {
              when "not(../../a1/local) and not(../../a2/local)" {
              }
              type empty;
            }
          }
        }
        container a4 {
          when "not(../a2/none) and not(../a1/none) and not(../a3/none) and not(../a2/if-authenticated) and not(../a1/if-authenticated) and not(../a3/if-authenticated)" {
          }
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf if-authenticated {
              description
                "Succeed if user has authenticated.";
              type empty;
            }
            leaf local {
              when "not(../../a1/local) and not(../../a2/local) and not(../../a3/local)" {
              }
              type empty;
            }
          }
        }
      }
      // aaa authorization auth-proxy
      container auth-proxy {
          description "For Authentication Proxy Services";
          container default {
              description "The default authorization list.";
              leaf local {
                description "Local authorization.";
                type empty;
              }
              leaf group {
                description
                  "Use Server-group";
                type union {
                  type string;
                  type enumeration {
                    enum "radius";
                  }
                }
              }            
          }
      }
      // aaa authorization onep *
      container onep {
        description "Set authorization lists for ONEP";
        container default {
          description "The default authorization list.";
          container group {
            description "Use Server-group";
            list group-word {
              key "group-word";
              leaf group-word {
                description "Server-group name";
                type string;
              }
            }
          }
        }
      }
    }
    // aaa accounting
    container accounting {
      description
        "Accounting configurations parameters.";
      list commands {
        description
          "For exec (shell) commands.";
        key "level list-name";
        leaf level {
          description
            "Enable level";
          type uint8 {
            range "0..15";
          }
        }
        leaf list-name {
          type union {
            type enumeration {
              enum "default";
            }
            type string {
              length "1..31";
            }
          }
        }
        leaf action-type {
          type enumeration {
            enum "none";
            enum "start-stop";
            enum "stop-only";
          }
        }
        leaf broadcast {
          description
            "Use Broadcast for Accounting";
          type empty;
        }
        leaf group {
          description
            "Use Server-group";
          type union {
            type string;
            type enumeration {
              enum "tacacs+";
            }
          }
        }
      }
      list connection {
        description
          "For outbound connections. (telnet, rlogin)";
        key "name";
        leaf name {
          type string;
        }
        uses aaa-accounting-grouping;
      }
      container delay-start {
        description "Delay PPP Network start record until peer IP address is known.";
        leaf extended-delay {
          description "";
          type uint8 {
            range "1..2";
          }
        }
        leaf all {
          description
            "Delay start records for all vrf and non-vrf users.";
          type empty;
        }
      }
      container dot1x {
        description
          "For dot1x sessions.";
        container default {
          description
            "The default authorization list";
          uses aaa-accounting-dot1x;
        }
        list accounting-list {
          description
            "Named authorization list (max 31 characters, \
             longer will be rejected)";
          key "name";
          leaf name {
            type string;
          }
          uses aaa-accounting-dot1x;
        }
      }
      container identity {
        description
          "For identity sessions.";
        container default {
          description
            "The default authorization list";
          uses aaa-accounting-identity;
        }
        list accounting-list {
          description
            "Named authorization list (max 31 characters, \
             longer will be rejected)";
          key "name";
          leaf name {
            type string;
          }
          uses aaa-accounting-identity;
        }
      }

      list exec {
        description
          "For starting an exec (shell).";
        key "name";
        leaf name {
          type string;
        }
        uses aaa-accounting-grouping;
      }
      container exec-submode {
        list exec {
          description
            "For starting an exec (shell).";
          key "name";
          leaf name {
            type string;
          }
          container action-type {
            description
              "Type of action to be performed on accounting records";
            uses aaa-accounting-grouping;
          }
        }
      }
      list network {
        description
          "For network services. (PPP, SLIP, ARAP)";
        
        key "id";
        leaf id {
          type union {
            type enumeration {
              enum "default";
            }
            type string {
              length "1..31";
            }
          }
        }
        container start-stop {
          description
            "Record start and stop without waiting";

          leaf group {
            description
              "Use Server-group";
            type union {
              type string;
              type enumeration {
                enum "radius";

              }
            }
          }
        }
        choice network-choice {
          case a {
            leaf none {
              description
                "No accounting.";
              type empty;
            }
          }
          case b {
            leaf mode {
              type enumeration {
                enum "start-stop";
                enum "stop-only";
              }
            }
            leaf broadcast {
              description
                "Use Broadcast for Accounting";
              type empty;
            }
            container a1 {
              leaf group {
                description
                  "Use server-group.";
                type union {
                  type string;
                  type enumeration {
                    enum "ldap";
                    enum "radius";
                    enum "tacacs";
                  }
                }
              }
            }
            container a2 {
              leaf group {
                description
                  "Use server-group.";
                type union {
                  type string;
                  type enumeration {
                    enum "ldap";
                    enum "radius";
                    enum "tacacs";
                  }
                }
              }
            }
            container a3 {
              leaf group {
                description
                  "Use server-group.";
                type union {
                  type string;
                  type enumeration {
                    enum "ldap";
                    enum "radius";
                    enum "tacacs";
                  }
                }
              }
            }
            container a4 {
              leaf group {
                description
                  "Use server-group.";
                type union {
                  type string;
                  type enumeration {
                    enum "ldap";
                    enum "radius";
                    enum "tacacs";
                  }
                }
              }
            }
          }
        }
      }
      container send {
        description
          "Send records to accounting server";
        container counters {
          description
            "Enable specific counters in the Stop record";
          leaf ipv6 {
            description
              "Send IPv6 counters in the Stop Record";
            type empty;
          }
        }
        container stop-record {
          description
            "Generate STOP records for a specified event";
          leaf always {
            description
              "Generate STOP records always, even if the START record is not sent";
            type empty;
          }
          container authentication {
            description
              "Generate STOP records for authentication failures";
            container failure {
              description
                "Generate STOP records for authentication failures";
              presence "true";
              leaf vrf {
                description
                  "VPN Routing/Forwarding parameters";
                type string;
              }
            }
            container success {
              description
                "Generate STOP records for authenticated users";
              container remote-server {
                description
                  "Successfully authenticated, through access-accept, by a remote AAA server";
                presence "true";
                leaf vrf {
                  description
                    "VPN Routing/Forwarding parameters";
                  type string;
                }
              }
            }
          }
        }
      }
      container suppress {
        description
          "Do not generate accounting records for a specific type of user";
        leaf null-username {
          description
            "Do not generate accounting records for users with a null-username";
          type empty;
        }
      }

      container system {
        description
          "For system events.";
        choice default-guarantee-first {
          case default-case {
            container default {
              description
                "The default accounting list.";
              presence "true";
              leaf none {
                description
                  "No accounting.";
                type empty;
              }
              container start-stop {
                description
                  "Record start and stop without waiting";
                leaf broadcast {
                  description
                    "Use Broadcast for Accounting";
                  type empty;
                }
                leaf group {
                  description
                    "Use Server-group";
                  type union {
                    type string;
                    type enumeration {
                      enum "radius";
                      enum "tacacs+";
                    }
                  }
                }
              }
              leaf vrf {
                description
                  "VPN Routing/Forwarding parameters";
                type string;
              }
            }
          }
          case guarantee-first-case {
            leaf guarantee-first {
              description
                "Guarantee system accounting as first record.";
              type boolean;
            }
          }
        }
      }
      container update {
        description "Enable accounting update records";
        choice update-choice {
          leaf periodic {
            description "Periodic intervals to send accounting update records(in minutes)";
            type uint32 {
              range "1..71582";
            }
          }
          container newinfo {
            description "Only send accounting update records when we have new acct info.";
            presence "true";
            leaf periodic {
              description "Periodic intervals to send accounting update records(in minutes)";
              type uint32 {
                range "1..71582";
              }
            }        
          }
        }
      }
      container auth-proxy {
        description
          "For Authentication Proxy Services";
        container default {
          description
            "The default authorization list.";
          container start-stop {
            description
              "Record start and stop without waiting";
            leaf group {
              description
                "Use server-group.";
              type string;
            }
          }
        }
      }
    }
    //aaa server
    container server {
      description
        "Local AAA server";
      container radius {
        description
          "Profile for local radius server";
        container dynamic-author {
          description
            "Local server profile for RFC 3576 support";
          presence true;
          uses aaa-server-radius-port;
          list client {
            description
              "Specify a RADIUS client";
            key ip;
            leaf ip {
              type union {
                type inet:ipv4-address;
                type inet:ipv6-address;
                type string;
              }
            }
            leaf dtls {
              description
                "Enable DTLS for the client";
              type empty;
            }
            list vrf {
              description
                " Virtual Routing/Forwarding parameters";
              key name;
              leaf name {
                type string;
              }
              leaf dtls {
                description
                  "Enable DTLS for the client";
                type empty;
              }
              container server-key {
                description
                  "Specify a RADIUS client server-key";
                uses aaa-server-radius-key;
              }
            }
            container server-key {
              description
                "Specify a RADIUS client server-key";
              uses aaa-server-radius-key;
            }
          }
          container server-key {
            description
              "Specify a RADIUS client server-key";
            uses aaa-server-radius-key;
          }
          container domain {
            description
              "Username domain options";
            leaf delimiter {
              description
                'Domain delimiter, Choose from {@, /, $, %, \, #, -}';
                type string;
            }
            container stripping {
              description
                "Match incoming username left oriented of the @ domain delimiter";
              presence true;
              leaf right-to-left {
                description
                  "Terminate the string at the first delimiter going from right to left";
                type empty;
              }
            }
          }
          leaf auth-type {
            description
              "Specify the server authorization type";
            type enumeration {
              enum "all";
              enum "any";
              enum "session-key";
            }
          }
          container ignore {
            description
              "Override behaviour to ignore certain parameters";
            leaf retransmission {
              description
                "Drop packets using same radius id";
              type empty;
            }
            leaf server-key {
              description
                "Ignore shared secret";
              type empty;
            }
            leaf session-key {
              description
                "Ignore attr 151";
              type empty;
            }
          }
        }
        container policy-device {
          description
            "Local server profile for RADIUS External Policy Delegation client";
          presence true;
          container accounting {
            description
              "Specify accounting details";
            uses aaa-server-radius-port;
          }
          container authentication {
            description
              "Specify authentication details";
            uses aaa-server-radius-port;
          }
          list client {
            description
              "Specify a RADIUS client";
            key ip;
            leaf ip {
              type union {
                type inet:ipv4-address;
                type inet:ipv6-address;
                type string;
              }
            }
            leaf port {
              description
                "Port on which radius client listens for CoA messages (default is 3799)";
              type uint16 {
                range "0..65534";
              }
            }
            list vrf {
              description
                " Virtual Routing/Forwarding parameters";
              key name;
              leaf name {
                type string;
              }
              leaf port {
                description
                  "Port on which radius client listens for CoA messages (default is 3799)";
                type uint16 {
                  range "0..65534";
                }
              }
              uses aaa-server-radius-key-grouping;
            }
            uses aaa-server-radius-key-grouping;
          }
          uses aaa-server-radius-key-grouping;
          container message-authenticator {
            description
              "Message Authenticator attribute from Clients";
            leaf ignore {
              description
                "Ignore checking of Message Authenticator attribute from\
                 Clients";
              type empty;
            }
          }
        }
        container proxy {
          description
            "Local server profile for RADIUS proxy clients";
          presence true;
          uses aaa-server-proxy-common;
          container client-ip {
            list client {
              description
                "Specify a RADIUS client";
              key "ip";
              leaf ip {
                type union {
                  type inet:ipv4-address;
                  type inet:ipv6-address;
                  type string;
                }
              }
              uses aaa-server-proxy-common;
            }
          }
          container client-ip-mask {
            list client {
              description
                "Specify a RADIUS client";
              key "ip mask";
              leaf ip {
                type union {
                  type inet:ipv4-address;
                  type inet:ipv6-address;
                  type string;
                }
              }
              leaf mask {
                description
                  "Network mask or prefix length";
                type union {
                  type ipv4-mask-slash-prefix-len-type;
                  type inet:ipv4-address;
                }
              }
              uses aaa-server-proxy-common;
            }
          }
          container client-ip-vrf {
            list client {
              description
                "Specify a RADIUS client";
              key "ip vrf";
              leaf ip {
                type union {
                  type inet:ipv4-address;
                  type inet:ipv6-address;
                  type string;
                }
              }
              leaf vrf {
                description
                  "Virtual Routing/Forwarding parameters";
                type string;
              }
              uses aaa-server-proxy-common;
            }
          }
          container client-ip-mask-vrf {
            list client {
              description
                "Specify a RADIUS client";
              key "ip mask vrf";
              leaf ip {
                type union {
                  type inet:ipv4-address;
                  type inet:ipv6-address;
                  type string;
                }
              }
              leaf mask {
                description
                  "Network mask or prefix length";
                type union {
                  type ipv4-mask-slash-prefix-len-type;
                  type inet:ipv4-address;
                }
              }
              leaf vrf {
                description
                  "Virtual Routing/Forwarding parameters";
                type string;
              }
              uses aaa-server-proxy-common;
            }
          }

          container send {
            description
              "Send attributes in Radius requests";
            container vsa {
              description
                "Vendor specific attribute configuration";
              container rpclient-source-address {
                description
                  "AP Source Address";
                presence true;
                leaf accounting { 
                  description
                    "send in accounting requests";
                  type empty;
                }
                leaf authentication {
                  description
                    "send in access requests";
                  type empty;
                }
              }
            }                 
          } 
        }

        container sesm {
          description
            "Local server profile for a SESM client";
          presence true;
          list client {
            description
              "Specify a RADIUS client";
            key ip;
            leaf ip {
              type union {
                type inet:ipv4-address;
                type inet:ipv6-address;
                type string;
              }
            }
            list vrf {
              description
                " Virtual Routing/Forwarding parameters";
              key name;
              leaf name {
                type string;
              }
              uses aaa-server-radius-key-grouping;
            }
            uses aaa-server-radius-key-grouping;
          }
          uses aaa-server-radius-key-grouping;
          container message-authenticator {
            description
              "Message Authenticator attribute from Clients";
            leaf ignore {
              description
                "Ignore checking of Message Authenticator attribute from\
                 Clients";
              type empty;
            }
          }
          uses aaa-server-radius-port;
        }
      }
    }

    // aaa session-id
    leaf session-id {
      description
        "AAA Session ID";
      type enumeration {
        enum "common";
        enum "unique";
      }
      default "common";
    }
    // aaa login 
    container login {
      description
        "AAA login enable display";
      leaf display {
        description
          "Display options for login info";
        type enumeration {
          enum "last-failure";
          enum "last-success";
          enum "number-failures";
        }
      }
      leaf success-track-conf-time {
        description
          "Track Successful login attempts occurring during configured
time-period";
        type uint8 {
          range "1..24";
        }
      }
    }

    //aaa max-sessions
    leaf max-sessions {
      description
        "Adjust initial hash size for estimated max sessions";
      type uint16 {
        range "1024..64000";
      }
    }
 
    //aaa memory
    container memory {
       description
         "AAA memory parameters";
       container threshold {
         description 
           "set appropriate thresholds for the AAA process";
         container accounting {
           description
             "AAA accounting low-memory threshold";
           leaf disable {
             description
               "accounting may be disabled, if available memory falls below\
                this percentage";
             type uint8 {
               range "1..15";
             }
           }
         }
         container authentication {
           description
             "AAA authentication low-memory threshold";
           leaf reject {
             description
               "requests will be rejected, if available memory falls below\
                this percentage";
             type uint8 {
               range "2..15";
             }
           }
         }
      }
    } 
 
    //aaa password
    leaf password {
      description
        "Configure password/secret related settings";
      type enumeration {
        enum "restriction";
      }
    }

    //aaa policy
    container policy {
      description
        "AAA policy parameters";
      leaf interface-config {
        description
          "LCP interface config policy parameters";
        type enumeration {
          enum "allow-subinterface";
        }
      }
    }

    //aaa route
    container route {
      description
        "Static route downloading";
      container download {
        description
          "Download from AAA server";
        leaf update-period {
          description
            "Route update period in minutes";
          type uint16 {
             range "1..1440";
          }
        }
        leaf authorization {
          description
            "Method list to use for authorization"; 
          type string;
        }
      }
    }

    //aaa traceback
    leaf traceback {
      description
        "Traceback recording";
      type enumeration {
        enum "recording";
      }
    }
  }

  grouping config-radius-grouping {
    list filter {
      description
        "Packet filter configuration";
      when "/ios:native/ios:aaa/ios-aaa:new-model"; 
      key "id";
      leaf id {
        type string;
      }
      leaf match {
        type enumeration {
          enum "match-all";
          enum "match-any";
        }
      }
    }
    list server {
      description
        "Server configuration";
      when "/ios:native/ios:aaa/ios-aaa:new-model"; 
      key "id";
      leaf id {
        type string;
      }
      container address {
        description
          "Specify the radius server address";
          
        choice radius-host-address {
          leaf ipv4 {
            description
              "IPv4 address or Hostname for radius server";
            type union {
              type inet:ipv4-address;
              type string;
            }
          }
          leaf ipv6 {
            description
              "IPv6 address or Hostname for radius server";
            type union {
              type inet:ipv6-address;
              type string;
            }
          }
        }
        leaf auth-port {
          description
            "UDP port for RADIUS authentication server (default is 1645)";
          default 1645;
          type uint16 {
            range "0..65535";
          }
        }
        leaf acct-port {
          description
            "UDP port for RADIUS accounting server (default is 1646)";
          default 1646;
          type uint16 {
            range "0..65535";
          }
        }
      }
      // radius server timeout
      leaf timeout {
        description
          "Time to wait for a RADIUS server to reply (overrides default)";
        type uint16 {
          range "1..1000";
        }
      }

      container automate-tester {
        description
          "Configure server automated testing.";
        leaf username {
          type string;
        }
        leaf at-option {
          type enumeration {
//          enum "idle-time";
//          enum "ignore-acct-port";
//          enum "ignore-auth-port";
            enum "probe-on";
          }
        }
      }
      container backoff {
        description
          "Retry backoff pattern(Default is retransmits with constant delay)";
        container exponential {
          description
            "Exponential retransmit backoff";
          
          presence "true";
          leaf max-delay {
            description
              "Max delay between retransmits(default is 3 min)";
            type uint8 {
              range "1..120";
            }
          }
          leaf backoff-retry {
            description
              "Exponential backoff retry number(default is 8)";
            type uint8 {
              range "1..50";
            }
          }
        }
      }
      container key {
        description
          "Per-server encryption key";
        
        leaf encryption {
          type enumeration {
            enum "0";
            enum "5";
          }
        }
        leaf key {
          type string;
        }
      }
      container pac {
        description
          "Protected Access Credential key";
        container key {
          description
            "Per-server encryption key";
          
          leaf encryption {
            type enumeration {
              enum "0";
              enum "6";
              enum "7";
            }
          }
          leaf key {
            type string;
          }
        }
      }
      leaf retransmit {
        description
          "Number of retries to active server (overrides default)";
        type uint8 {
          range "0..100";
        }
      }
    }
  }

  grouping lower-upper-case-grouping {
    leaf lu-case {
      type enumeration {
        enum "lower-case";
        enum "upper-case";
      }
    }
  }

  grouping config-radius-server-grouping {
    // radius-server attribute           Customize selected radius attributes
    list attribute {
      description
        "Customize selected radius attributes";
      when "/ios:native/ios:aaa/ios-aaa:new-model"; 
      key "number";
      leaf number {
        type uint32;
      }
      leaf-list send-attribute {
        type enumeration {
          enum "on-for-login-auth";
          enum "include-in-access-req";
          enum "support-multiple";
        }
      }
      container access-request {
        description
          "Access-Request packet";
        when "../number = '25'";
        leaf include {
          description
            "Include attribute";
          type empty;
        }
      }
      container attri31 {
        description
          "Calling Station ID";
        when "../number = '31'";
        list attri31-list {
          key "calling-station-id";
          leaf calling-station-id {
            type enumeration {
//            enum "append-circuit-id";
              enum "mac";
//            enum "remote-id";
              enum "send";
            }
          }
          container id-mac {
            when "../calling-station-id = 'mac'";
            leaf format {
              type enumeration {
//              enum "default";
                enum "ietf";
//              enum "one-byte";
//              enum "three-byte";
//              enum "two-byte";
//              enum "unformatted";
              }
            }
            uses lower-upper-case-grouping;
          }
          container id-send {
            when "../calling-station-id = 'send'";
            leaf nas-port-detail {
              type empty;
            }
            leaf mac-only {
              type empty;
            }
          }
        }
      }
    }
    //  authorization       Authorization processing information
    //  backoff             Retry backoff pattern(Default is retransmits with
    //                      constant delay)
    //  cache               AAA auth cache default server group
    //  challenge-noecho    Data echoing to screen is disabled during
    //                      Access-Challenge
    //  configure-nas       Attempt to upload static routes and IP pools
    //                      at startup
    //  dead-criteria       Set the criteria used to decide when a radius
    // snmp-server dead-criteria       Set the criteria used to decide when a radius
    container dead-criteria {
      description
        "Set the criteria used to decide when a radius server ismarked dead";
      when "/ios:native/ios:aaa/ios-aaa:new-model"; 
      leaf time {
        description
          "The time during which no properly formed response must be recievedfrom the RADIUS server";
        type uint8 {
          range "1..120";
        }
      }
      leaf tries {
        description
          "The number of times the router must fail to recieve a response fromthe radius server to mark it as dead";
        type uint8 {
          range "1..100";
        }
      }
    }
    //                      server is marked dead
    //  deadtime            Time to stop using a server that doesn't respond
    // radius-server deadtime *
    leaf deadtime {
      description
        "Time to stop using a server that doesn't respond";
      when "/ios:native/ios:aaa/ios-aaa:new-model"; 
      type uint32 {
        range "1..1440";
      }
    }
    //  directed-request    Allow user to specify radius server to use
    //                      with `@server'
    //  domain-stripping    Strip the domain from the username
    // radius-server host *
    list host {
      description
        "Specify a RADIUS server";
      when "/ios:native/ios:aaa/ios-aaa:new-model"; 
      key "id";
      leaf id {
        type union {
          type string;
          type inet:ipv4-address;
        }
      }
      // radius-server host * auth-port
      leaf auth-port {
        description
          "UDP port for RADIUS authentication server (default is 1645)";
        type uint16 {
          range "0..65535";
        }
      }
      // radius-server host * acct-port
      leaf acct-port {
        description
          "UDP port for RADIUS accounting server (default is 1646)";
        type uint16 {
          range "0..65535";
        }
      }
      //  alias         1-8 aliases for this server (max. 8)
      //  backoff       Retry backoff pattern (Default is retransmits with
      //                constant delay)
      //  non-standard  Parse attributes that violate the RADIUS standard
      // radius-server host * retransmit
      //  retransmit    Specify the number of retries to active server
      //                (overrides default)
      leaf retransmit {
        description
          "Specify the number of retries to active server";
        type uint8 {
          range "1..100";
        }
      }
      //  test          Configure server automated testing.
      // radius-server host * test
      container test {
        description
          "Configure server automated testing";
        list username {
          description
            "A name (from local database) that should be used to send requests.";
          key "name";
          leaf name {
            type string;
          }
          container key {
            description
              "per-server encryption key (overrides default)";
            leaf encryption {
              type enumeration {
                enum "0";
                enum "7";
              }
            }
            leaf clear-key {
              type string;
            }
          }
        }
      }
      // radius-server host * timeout
      leaf timeout {
        description
          "Time to wait for a RADIUS server to reply (overrides default)";
        type uint16 {
          range "1..1000";
        }
      }
      // radius-server host * key
      leaf key {
        description
          "per-server encryption key (overrides default)";
        type union {
          type enumeration {
            enum "0";
            enum "7";
          }
          type string;
        }
      }
      leaf clear-key {
        when "../key = '0' or ../key = '7'";
        type string;
      }
      //  non-standard  Parse attributes that violate the RADIUS standard
    }
    //  key                 encryption key shared with the radius servers
    container key {
      description
        "encryption key shared with the radius servers";
      when "/ios:native/ios:aaa/ios-aaa:new-model"; 
      leaf encryption {
        type enumeration {
          enum "0";
          enum "7";
        }
      }
      leaf clear-key {
        type string;
      }
    }
    //  load-balance        Radius load-balancing options.
    //  optional-passwords  The first RADIUS request can be made without
    //                      requesting a password
    //  retransmit          Specify the number of retries to active server
    leaf retransmit {
      description
        "Specify the number of retries to active server";
      when "/ios:native/ios:aaa/ios-aaa:new-model"; 
      type uint8 {
        range "1..100";
      }
    }
    //  retry               Specify how the next packet is sent after timeout.
    //  source-ports
    container source-ports {
      description
        "source ports used for sending out RADIUS requests";
      when "/ios:native/ios:aaa/ios-aaa:new-model"; 
      leaf extended {
        description
          "Use 200 source-ports between 21645-21844";
        type empty;
      }
    }
    //  timeout             Time to wait for a RADIUS server to reply
    leaf timeout {
      description
        "Time to wait for a RADIUS server to reply";
      when "/ios:native/ios:aaa/ios-aaa:new-model"; 
      type uint16 {
        range "1..1000";
      }
    }
    //  transaction         Specify per-transaction parameters
    //  unique-ident        Higher order bits of Acct-Session-Id
    // radius-server vsa *                Vendor specific attribute configuration
    container vsa {
      description
        "Vendor specific attribute configuration";
      when "/ios:native/ios:aaa/ios-aaa:new-model"; 
      container disallow {
        description
          "Forbid certain VSA behaviour";
        leaf unknown {
          description
            "Forbid unknown VSAs";
          type empty;
        }
      }
      container send {
        description
          "Send vendor-specific attributes in requests";
        presence "true";
        container accounting {
          description
            "Send in accounting requests";
          presence "true";
          leaf threegpp2 {
            description
              "Send 3GPP2 VSAs in accounting requests";
            type empty;
          }
        }
        container authentication {
          description
            "Send in access requests";
          presence "true";
          leaf threegpp2 {
            description
              "Send 3GPP2 VSAs in accounting requests";
            type empty;
          }
        }
        container cisco-nas-port {
          description
            "Send cisco-nas-port VSA(2)";
          presence "true";
          leaf threegpp2 {
            description
              "Send 3GPP2 VSAs in accounting requests";
            type empty;
          }
        }
      }
    }
  }

  grouping config-ip-radius-grouping {
    container radius {
      description
        "RADIUS configuration commands";
      container source-interface {
        description
          "Specify interface for source address in RADIUS packets";
        uses ios-ifc:interface-grouping;
      }
    }
  }

  grouping config-tacacs-grouping {
    list server {
      description
        "Server configuration";
      key "name";
      leaf name {
        type string;
      }
      container address {
        description
          "Specify ip address for tacacs server";
        choice tacacs-host-address {
          leaf ipv4 {
            description
              "IPv4 address or Hostname for tacacs server";
            type union {
              type inet:ipv4-address;
              type string;
            }
          }
          leaf ipv6 {
            description
              "IPv6 address or Hostname for tacacs server";
            type union {
              type inet:ipv6-address;
              type string;
            }
          }
        }
      }
      leaf port {
        description
          "Configure port for tacacs server";
        type uint16 {
          range "1..65535";
        }
      }
      leaf timeout {
        description
          "Configure timeout for tacacs server";
        type uint16 {
          range "1..1000";
        }
      }
      container key {
        description
          "per-server encryption key (overrides default)";
        leaf encryption {
          type enumeration {
            enum "0";
            enum "7";
          }
        }
        leaf key {
          type string;
        }
      }
    }
  }

  grouping config-tacacs-server-grouping {
    // tacacs-server host *
    list host {
      description
        "Specify a TACACS server";
      key "name";
      leaf name {
        type ios-types:host-type;
      }
      // tacacs-server host * port
      leaf port {
        description
          "TCP port for TACACS+ server (default is 49)";
        type uint16 {
          range "1..65535";
        }
      }
      // tacacs-server host * key
      leaf key {
        description
          "Set TACACS+ encryption key.";
        type union {
          type enumeration {
            enum "0";
            enum "7";
          }
          type string;
        }
      }
      leaf encryption-key {
        when "../key = '0' or ../key = '7'";
        type string;
      }
      // tacacs-server host * timeout
      leaf timeout {
        description
          "Time to wait for this TACACS server to reply (overrides default)";
        type uint16 {
          range "1..1000";
        }
      }
    }
    // tacacs-server timeout
    leaf timeout {
      description
        "Time to wait for a TACACS server to reply";
      type uint16 {
        range "1..1000";
      }
    }
    // tacacs-server directed-request
    container directed-request {
      description
        "Allow user to specify tacacs server to use with `@server'";
      presence "true";
      leaf restricted {
        description
          "restrict queries to directed request servers only";
        type empty;
      }
      leaf no-truncate {
        description
          "Do not truncate the @hostname from username.";
        type empty;
      }
    }
    // tacacs-server key
    container key {
      description
        "Set TACACS+ encryption key.";
      leaf encryption {
        type enumeration {
          enum "0";
          enum "7";
        }
      }
      leaf key {
        type string;
      }
    }
  }

  grouping config-ip-tacacs-main-grouping {
    container source-interface {
      description
        "Specify interface for source address in TACACS packets";
      uses ios-ifc:interface-grouping;
    }
  }

  grouping config-ip-tacacs-grouping {
    container tacacs {
      description
        "TACACS configuration commands";
      uses config-ip-tacacs-main-grouping;
    }
  }

  /////////////////////////////////////////////////////////
  // native / aaa *
  /////////////////////////////////////////////////////////
  augment "/ios:native/ios:aaa" {
      uses config-aaa-grouping;
  }

  /////////////////////////////////////////////////////////
  // native / radius *
  /////////////////////////////////////////////////////////
  augment "/ios:native/ios:radius" {
    uses config-radius-grouping;
  }

  /////////////////////////////////////////////////////////
  // native / radius-server *
  /////////////////////////////////////////////////////////
  augment "/ios:native/ios:radius-server" {
    uses config-radius-server-grouping;
  }

  /////////////////////////////////////////////////////////
  // native / ip / radius *
  /////////////////////////////////////////////////////////
  augment "/ios:native/ios:ip" {
    uses config-ip-radius-grouping;
  }

  /////////////////////////////////////////////////////////
  // native / tacacs *
  /////////////////////////////////////////////////////////
  augment "/ios:native/ios:tacacs" {
    uses config-tacacs-grouping;
  }

  /////////////////////////////////////////////////////////
  // native / tacacs server *
  /////////////////////////////////////////////////////////
  augment "/ios:native/ios:tacacs-server" {
    uses config-tacacs-server-grouping;
  }

  /////////////////////////////////////////////////////////
  // native / ip / tacacs *
  /////////////////////////////////////////////////////////
  augment "/ios:native/ios:ip" {
    uses config-ip-tacacs-grouping;
  }
}
