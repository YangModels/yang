module Cisco-IOS-XE-wireless-events-oper {
  yang-version 1;
  namespace "http://cisco.com/ns/yang/Cisco-IOS-XE-wireless-events-oper";
  prefix wireless-event-oper;

  import Cisco-IOS-XE-wireless-mobility-types {
    prefix wireless-mobility-types;
  }
  import Cisco-IOS-XE-wsa-types {
    prefix wsa-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless operations events generated from the Cisco Wireless
     controller. These models may produce high volume of data.
     Copyright (c) 2018 by Cisco Systems, Inc.
     All rights reserved";

  revision 2018-10-05 {
    description
      "Addition of fabric parameters to wsa client event.";
    reference "1.1.0";
  }
  revision 2018-06-11 {
    description
      "Initial revision";
    reference "1.0.0";
  }

  grouping st-dhcp-ip-addr {
    description
      "List of DHCP server IP addresses";
    leaf server-ip {
      type inet:ip-address;
      description
        "Server IP address";
    }
  }

  grouping wsa-client-eventq-db-elem {
    description
      "Wireless client lifecycle events data model";
    leaf client-mac {
      type yang:mac-address;
      description
        "Wireless Client's MAC Address";
    }
    leaf audit-session-id {
      type string;
      description
        "Audit session id of the session";
    }
    leaf client-event {
      type wsa-types:wsa-client-events;
      description
        "Wireless client event type, indicating the phase a client is in its lifecycle";
    }
    leaf client-event-result {
      type wsa-types:wsa-client-event-result;
      description
        "Wireless client event status, indicating a failure or success in client lifecycle";
    }
    leaf state-transition-timestamp {
      type yang:date-and-time;
      description
        "Timestamp indicating when a client transitioned into the present lifecycle event. Time elapsed since 00:00:00 UTC, Thursday, 1 January 1970";
    }
    leaf ms-ap-slot-id {
      type uint8;
      description
        "AP slot client is associated to";
    }
    leaf wtp-mac {
      type yang:mac-address;
      description
        "AP mac client is associated to";
    }
    leaf ssid {
      type string;
      description
        "SSID client is associated to";
    }
    leaf vlan-id {
      type uint32;
      description
        "Wireless Client layer 2 vlan id";
    }
    leaf mm-client-role {
      type wireless-mobility-types:mm-client-role;
      description
        "Wireless Client's mobility role";
    }
    leaf ipv4-address {
      type inet:ipv4-address;
      description
        "Wireless Client's IPv4 address";
    }
    leaf-list ipv6 {
      type inet:ipv6-address;
      max-elements "8";
      ordered-by user;
      description
        "Wireless Client's IPv6 list of addresses";
    }
    leaf rssi {
      type int8;
      description
        "Last updated Radio Signal Strength indicator, of a Wireless Client";
    }
    leaf snr {
      type uint8;
      description
        "Last updated Signal strength to noise ratio, of a Wireless Client";
    }
    list dhcp-server-ip-addr {
      description
        "DHCP server IP the Wireless client has communicated with";
      uses wireless-event-oper:st-dhcp-ip-addr;
    }
    leaf aaa-server {
      type inet:ip-address;
      description
        "AAA server IP the Wireless client has communicated with";
    }
    leaf is-fabric-client {
      type boolean;
      description
        "Indicates whether the client is a fabric client or not";
    }
    leaf client-vnid {
      type uint32;
      description
        "Fabric client's Virtual Network ID. This informaiton is valid only if client is a fabric client";
    }
    leaf client-sgt {
      type uint16;
      description
        "Fabric client's group tag. This informaiton is valid only if client is a fabric client";
    }
  }

  grouping wsa-client-eventq-db-elem-3p {
    description
      "Wireless client lifecycle third-party events data model enum";
    leaf client-event-reason {
      type wsa-types:wsa-client-event-reason-3p;
      description
        "Wireless client event reason third-party, indicating what is happening with a client in its current lifecycle event";
    }
    leaf client-event-reason-addon {
      type wsa-types:wsa-client-event-reason-addon-3p;
      description
        "Wireless client event reason addon third-party, provides more information about the client_event_reason";
    }
  }

  notification wsa-client-event {
    description
      "Wireless client operational events. Provides an event for each significant activity in the Wireless clients life cycle. It may generate high volume of data, depending on scale";
    uses wireless-event-oper:wsa-client-eventq-db-elem;
    uses wireless-event-oper:wsa-client-eventq-db-elem-3p;
  }
  container wireless-events {
    config false;
    description
      "root container of wireless client operational events";
  }
}
