module Cisco-IOS-XE-wireless-dot11-cfg {
  yang-version 1;
  namespace "http://cisco.com/ns/yang/Cisco-IOS-XE-wireless-dot11-cfg";
  prefix wireless-dot11-cfg;

  import Cisco-IOS-XE-wireless-enum-types {
    prefix wireless-enum-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing configs related to various 802.11 protocols.
     Copyright (c) 2016-2018 by Cisco Systems, Inc.
     All rights reserved.";

  revision 2018-06-13 {
    description
      "- Change TX MCS rate config for dot11ac
       - Remove SIP codec support
       - Add range constraints to integer.";
    reference "4.0.0";
  }
  revision 2018-03-01 {
    description
      "Defaults changed";
    reference "3.0.0";
  }
  revision 2018-01-24 {
    description
      "The first generally available version";
    reference "2.0.0";
  }
  revision 2017-05-05 {
    description
      "Initial revision";
    reference "1.0.0";
  }

  grouping dot11-cfg {
    description
      "This field represents the 802.11 default config";
    leaf fragmentation-threshold {
      type uint16 {
        range "256 .. 2346";
      }
      default "2346";
      description
        "This attribute shall specify the current maximum size, in octets, of the MPDU that may be delivered to the PHY. An MSDU shall be broken into fragments if its size exceeds the value of this attribute after adding MAC headers and trailers. An MSDU or MMPDU shall be fragmented when the resulting frame has individual address in the Address1 field, and the length of the frame is larger than this threshold. The default value for this attribute shall be the lesser of 2346 or the aMPDUMaxLength of the attached PHY and shall never exceed the lesser of 2346 or the aMPDUMaxLength of the attached PHY. The value of this attribute shall never be less than 256.";
    }
    leaf default-tx-power-level {
      type uint16 {
        range "1 .. 5";
      }
      default "1";
      description
        "The TxPowerLevel N currently being used to transmit data. Some PHYs also use this value to determine the receiver sensitivity requirements for CCA.";
    }
  }

  grouping dot11-80211-capability-config {
    description
      "st_dot11_apf_dot11_capability_config";
    leaf apf-beacon-interval {
      type uint16 {
        range "20 .. 1000";
      }
      default "100";
      description
        "This attribute shall specify the number of TU that a AP Radio shall use for scheduling Beacon tranmissions. This value is transmitted in Beacon and Probe Response frames.";
    }
  }

  grouping dot11-ht-config {
    description
      "This object indicates 802.11n related configurations";
    leaf apf-80211n-enabled {
      type boolean;
      default "true";
      description
        "This object is used to enable the controller to manage 802.11n networks. A value of 'true' means the 802.11n network is enabled. A value of 'false' means the 802.11n network is disabled.";
    }
    leaf apf-80211n-rifs-tx-status {
      type boolean;
      default "true";
      description
        "This object is used to indicate the support for RIFS on this band. A value of 'true' indicates that RIFS is enabled for this band. A value of 'false' indicates that RIFS is disabled for this band.";
    }
    leaf apf-80211n-short-guard-enabled {
      type boolean;
      default "true";
      description
        "This object is used to indicate the support for 802.11n guard interval on this band. A value of 'true' indicates that guard interval is enabled for this band. A value of 'false' indicates that guard interval is disabled for this band.";
    }
  }

  grouping dot11-dot11ac-config {
    description
      "This object represents configurations related 802.11ac feature";
    leaf vht-enable {
      type boolean;
      default "true";
      description
        "This object is used to enable the controller to manage 802.11ac networks. A value of 'true' means the 802.11ac network is enabled. A value of 'false' means the 802.11ac network is disabled.";
    }
  }

  grouping dot11h-config {
    description
      "This object represents configurations related 802.11n feature";
    leaf channel-switch-enable {
      type uint8;
      default "1";
      description
        "To enable or disable channel switch. When disabling Channel Switch no need to pass mode and count";
    }
    leaf channel-switch-mode {
      type uint8;
      default "0";
      description
        "The Channel Switch Mode indicates any restriction on transmission until a channel switch. An Channel mode set to 1 means that the STA in a BSS to which the frame containing the element is addressed shall tranmit no further frames with in the BSS until the scheduled channel switch. A Channel switch mode set to 0 does not impose any requirement on the receiving STA.";
    }
    leaf power-constraint {
      type uint8 {
        range "0 .. 30";
      }
      default "0";
      description
        "Local maximum transmit power for a channel is defined as maximum transmit power level specified for the channel in the Country element minus the local power constraint specified for the channel in the Power Constraint element.The power constraint is coded as an unsigned integer in units of decibels. To disable power constraint set Power Constraint to 0.";
    }
    leaf smart-dfs {
      type uint8;
      default "1";
      description
        "This field indicates the use nonoccupancy time for Radar interference channel";
    }
  }

  grouping dot11-80211-qos-pm-config {
    description
      "This object represents configuration related to radio policy";
    leaf qos-pm-name {
      type string;
      default "unknown";
      description
        "This field indicates the radio policy name";
    }
    leaf def-11gn {
      type uint32 {
        range "15000 .. 200000000";
      }
      default "200000000";
      description
        "This field indicates 2.4Ghz radio policy rate";
    }
    leaf def-11an {
      type uint32 {
        range "15000 .. 400000000";
      }
      default "400000000";
      description
        "This field indicates 5Ghz 11n radio policy rate";
    }
    leaf def-11ac {
      type uint32 {
        range "15000 .. 1000000000";
      }
      default "1000000000";
      description
        "This field indicates 11ac radio policy rate";
    }
  }

  grouping mcs-key-80211ac {
    description
      "This object indicates the 802.11ac MCS rates related configuration.";
    leaf spatial-stream {
      type uint32 {
        range "1 .. 4";
      }
      description
        "The object represents the spatial stream number related to MCS data rate settings on the 802.11ac band.";
    }
    leaf index {
      type uint8 {
        range "8 .. 9";
      }
      description
        "Key atribute to the 802.11ac MCS rates table. Key value is the spatial stream value";
    }
  }

  grouping ac-mcs-80211 {
    description
      "This object indicates the configurations related to MCS rates";
    leaf apf-80211ac-mcs-tx-enable {
      type boolean;
      default "true";
      description
        "This object is used to enable or disable the data rate. When this object is set to 'true' the MCS support is enabled. When this object is set to 'false' the MCS support is disabled.";
    }
  }

  grouping ampdu-80211n {
    description
      "This object consists of all the 802.11n MSDU related configurations";
    leaf index {
      type uint8 {
        range "0 .. 7";
      }
      description
        "This is the key atribute to the 802.11n amsdu configuration table.";
    }
    leaf apf-80211n-ampdu-tx-priority {
      type wireless-enum-types:apf-80211n-ampdu;
      default "apf-80211n-ampdu-invalid";
      description
        "This field represents the 802.11n-2.4Ghz transmit A-MPDU
         Possible values:
         0 - Disabled
         1 - Enabled
         2 - Invalid";
    }
  }

  grouping ampdu-tx-scheduler {
    description
      "This object consists of all the 802.11n MSDU scheduler related configurations";
    leaf scheduler-enabled {
      type boolean;
      default "true";
      description
        "This field represents if 802.11n AMPDU scheduler is enabled. A value of True inidcates that the scheduler is enabled. A value of False indicates that the scheduler is disabled";
    }
    leaf rt-timeout {
      type uint32 {
        range "1 .. 1000";
      }
      default "10";
      description
        "Represents A-MPDU transmit aggregation scheduler realtime traffic timeout in msec";
    }
    leaf frame-burst {
      type wireless-enum-types:frame-burst-mode;
      default "frame-burst-automatic";
      description
        "Boolean value that indicates if optimal settings for bursting of 802.11ac A-MPDUs is enabled. A value of True indicates that optimal settings is enabled. A value of False indicates optimal settings is disabled
         Possible values:
         0 - Automatic
         1 - Enabled
         2 - Disabled";
    }
  }

  grouping amsdu-11n {
    description
      "This object represents the configurations related to the 802.11n A-MSDU feature";
    leaf index {
      type uint8 {
        range "0 .. 7";
      }
      description
        "This field indiates the spatial stream index. This is also the key to the A-mpdu configurations table";
    }
    leaf apf-80211n-amsdu-tx-priority {
      type wireless-enum-types:apf-80211n-amsdu;
      default "apf-80211n-amsdu-invalid";
      description
        "This object is used to represent 802.11n A-MSDU transmit priority
         Possible values:
         0 - Disable
         1 - Enable
         2 - Invalid";
    }
  }

  grouping dot11 {
    description
      "This object represents all the 802.11 features";
    leaf band {
      type uint8;
      description
        "This object represents the band to which the configurations belong to.";
    }
    leaf voice-adm-control-support-status {
      type boolean;
      default "false";
      description
        "This object is used to enable or disable admission control for voice traffic flowing through the 802.11a interfaces in the controller.";
    }
    leaf video-adm-control-support-status {
      type boolean;
      default "false";
      description
        "This object is used to enable or disable admission control for video traffic flowing through the 802.11a interfaces in the controller.";
    }
    leaf dot11-sip-cac-voice-sample-size {
      type uint32 {
        range "10 .. 80";
      }
      default "20";
      description
        "This object specifies the configured voice sample size in milliseconds for SIP Cac configuration of the dot11 band for the APs associated with this controller.";
    }
    leaf dot11-sip-cac-config-band-width {
      type uint32 {
        range "8 .. 64";
      }
      default "64";
      description
        "This object specifies the configured bandwidth in kbps for SIP CAC configuration of the dot11 band for the APs associated with this controller.";
    }
    leaf apf-dot11-number-of-channels {
      type uint32;
      default "0";
      description
        "This attribute shall indicate the value of the total number of channels allowed in the subband for the associated domain country string. The default value of this attribute shall be zero.";
    }
    leaf apf-network-state {
      type boolean;
      default "true";
      description
        "802.11 Network Admin Status.";
    }
    leaf apf-dot11g-supported {
      type boolean;
      default "true";
      description
        "This attribute is enabled to also support 802.11g protocol on the 802.11b network. Enabling 802.11g allows additional data rates: 6, 9, 12, 18, 24, 36, 48, 54 Mbps.";
    }
    leaf cac-voice-max-bandwidth {
      type uint8 {
        range "5 .. 85";
      }
      default "75";
      description
        "This represents the maximum bandwidth allocated to 802.11e clients. It is expressed as percentage of the total bandwidth of 802.11b network. The value of this attribute can vary from 0 to 100.";
    }
    leaf apf-dtpc {
      type boolean;
      default "true";
      description
        "This attribute may be used to enable the DTPC support on all 802.11b/g radios. DTPC or Dynamic Transmit Power Control support means that the radio's transmit power will be advertised in the beacons and probe responses.";
    }
    leaf cac-video-max-bandwidth {
      type uint8 {
        range "5 .. 85";
      }
      default "5";
      description
        "This object denotes the maximum bandwidth that can be allocated by controller for video traffic when admission control is enabled for 802.11a interfaces in the controller. When set to 0, all available bandwidth in 802.11a interfaces can be allocated to video traffic.";
    }
    leaf cac-voice-roam-bandwidth {
      type uint8 {
        range "0 .. 25";
      }
      default "6";
      description
        "This object represents the bandwidth relative to the maximum allocated bandwidth indicated by cLQd11aVoiceMaxAdmBandwidth, that can be allocated to roaming clients for voice traffic, when admission control is enabled for 802.11a interfaces in the controller.";
    }
    leaf cac-video-roam-bandwidth {
      type uint8 {
        range "0 .. 25";
      }
      default "0";
      description
        "This object represents the bandwidth relative to the maximum allocated bandwidth indicated by cLQd11aVideoMaxAdmBandwidth, that can be allocated to roaming clients for video traffic, when admission control is enabled for 802.11a interfaces in the controller.";
    }
    leaf tsm-enable {
      type boolean;
      default "false";
      description
        "When this object is set to 'true', the associated APs send the controller, every 90 seconds, statistical data on traffic observed on their 802.11a interfaces. When this object is set to 'false', the APs stop sending statistical data on the 802.11a interfaces to the controller.";
    }
    leaf exp-bandwidth-req-enable {
      type boolean;
      default "false";
      description
        "This object specifies if expedited BW feature is enabled or not. A value of 'true' will ensure that the APs advertise the expedited BW support in their beacons and association responses. A value of 'false' will ensure that the APs do not advertise the expedited BW support in their beacons and association responses.";
    }
    leaf cac-voice-load-based {
      type boolean;
      default "true";
      description
        "This object specifies the parameters that can be modified, when admission control is enabled. loadBased - controller will reserve and manage max-bandwidth and roaming-bandwidth based on the load on the WLAN. static - controller will reserve and manage max-bandwidth (cLQd11aVoiceMaxAdmBandwidth) and roaming-bandwidth (cLQd11aVoiceMaxRoamBandwidth) as per user configured values. When ACM is disabled, admission control will not be enforced. This may delay voice traffic depending on the traffic on the WLAN.";
    }
    leaf cac-voice-tspec-inactivity-timeout-ignore {
      type uint8 {
        range "0 .. 1";
      }
      default "1";
      description
        "This object is to configure TSPEC inactivity timeout processing mode";
    }
    leaf cac-stream-size {
      type uint32 {
        range "84000 .. 92100";
      }
      default "84000";
      description
        "This object is to configure Max data rate of the stream acceptable, between 84000 and 92100 range";
    }
    leaf cac-max-streams {
      type uint8 {
        range "1 .. 5";
      }
      default "2";
      description
        "This object is to configure Max number of streams per TSPEC";
    }
    leaf beamforming {
      type wireless-enum-types:nw-leg-beam-form;
      default "nw-leg-bf-disable";
      description
        "This object indicates the status of legacy beam forming in this AP. This object is applicable only for 11n supported APs. For APs that does not support legacy beam forming, a get request on this attribute will return the value 'notApplicable'. A value of 'enable' indicates that the legacy Beam forming is enabled in this AP. A value of 'false' indicates that the legacy Beam forming is disabled in this AP.
         Possible values:
         0 - Disable
         1 - Enable
         2 - Not applicable";
    }
    leaf world-mode-ie {
      type boolean;
      default "true";
      description
        "Boolean value that inidcates if World mode IE needs to be passed as bart of beacon";
    }
    leaf cac-voice-sip {
      type boolean;
      default "false";
      description
        "This object specifies whether SIP CAC is enabled.";
    }
    leaf apf-dot11b-short-preamble {
      type boolean;
      default "true";
      description
        "802.11b Short Preamble.";
    }
    leaf tx-power-control-threshold {
      type int8 {
        range "-80 .. -50";
      }
      default "-70";
      description
        "This object represents the Global AP Transmit Power Threshold value. The permissible range is -80 dbm to -50 dbm";
    }
    leaf channel-aware-tpc {
      type boolean;
      default "false";
      description
        "Represents if the TPC algorithm is channel aware";
    }
    container apf-dot11-default-cfg {
      description
        "This field contains all the 802.11 default configurations";
      uses wireless-dot11-cfg:dot11-cfg;
    }
    container apf-dot11-capability {
      description
        "This field indicates configurations related to 802.11 capabilities supported by the controller";
      uses wireless-dot11-cfg:dot11-80211-capability-config;
    }
    container ht-cfg {
      description
        "This object represents the 802.11n related configurations";
      uses wireless-dot11-cfg:dot11-ht-config;
    }
    container dot11ac-cfg {
      description
        "This object represents the 802.11ac related configurations";
      uses wireless-dot11-cfg:dot11-dot11ac-config;
    }
    container dot11h-cfg {
      description
        "This object represents the 802.11h related configurations";
      uses wireless-dot11-cfg:dot11h-config;
    }
    container dot11-qos-pm {
      description
        "This object represents configuration related to radio policy";
      uses wireless-dot11-cfg:dot11-80211-qos-pm-config;
    }
    leaf ate-oper-mode {
      type wireless-enum-types:apf-ate-mode;
      default "apf-atf-mode-disable";
      description
        "This object is used to set the mode 1 - Disabled 2 - SSID Mode 3 - Monitor Mode represented by radio type of ATF supported APs joined in the controller.Read operation on this attribute may differ if config is overridden.";
    }
    leaf ate-stealing {
      type wireless-enum-types:apf-ate-stealing-policy;
      default "apf-atf-stealing-policy-disable";
      description
        "This object is used to set the mode1 - Disabled 2 - SSID Mode 3 - Monitor Mode represented by cLApDot11IfType of ATF supported APs joined in the controller.Read operation on this attribute may differ if config is overridden.";
    }
    leaf g-edca {
      type wireless-enum-types:edca-profile;
      default "edca-wmm";
      description
        "This object specifies the EDCA profile to be used in EDCA Parameter set element.";
    }
    leaf medium-occupancy-limit {
      type uint32;
      default "100";
      description
        "This attribute shall indicate the maximum amount of time, in TU, that a point coordinator may control the usage of the wireless medium without relinquishing control for long enough to allow at least one instance of DCF access to the medium. The default value of this attribute shall be 100, and the maximum value shall be 1000.";
    }
    leaf ed-threshold {
      type int32;
      default "-50";
      description
        "The current Energy Detect Threshold being used by the DSSS PHY";
    }
    leaf cfp-period {
      type uint32;
      default "4";
      description
        "The attribute shall describe the number of DTIM intervals between the start of CFPs. It is modified by MLME-START.request primitive.";
    }
    leaf cfp-max-duration {
      type uint32;
      default "60";
      description
        "The attribute shall describe the maximum duration of the CFP in TU that may be generated by the PCF. It is modified by MLME-START.request primitive.";
    }
    leaf rts-threshold {
      type uint32;
      default "2347";
      description
        "This attribute shall indicate the number of octets in an MPDU, below which an RTS/CTS handshake shall not be performed. An RTS/CTS handshake shall be performed at the beginning of any frame exchange sequence where the MPDU is of type Data or Management, the MPDU has an individual address in the Address1 field, and the length of the MPDU is greater than this threshold. (For additional details, refer to Table 21 in 9.7.) Setting this attribute to be larger than the maximum MSDU size shall have the effect of turning off the RTS/CTS handshake for frames of Data or Management type transmitted by this STA. Setting this attribute to zero shall have the effect of turning on the RTS/CTS handshake for all frames of Data or Management type transmitted by this STA. The default value of this attribute shall be 2347.";
    }
    leaf cf-pollable {
      type boolean;
      default "false";
      description
        "When this attribute is true, it shall indicate that the STA is able to respond to a CF-Poll with a data frame within a SIFS time. This attribute shall be false if the STA is not able to respond to a CF-Poll with a data frame within a SIFS time.";
    }
    leaf cf-poll-request {
      type boolean;
      default "false";
      description
        "Specifies wheather CFP is enabled";
    }
    leaf dtim-period {
      type uint32;
      default "1";
      description
        "This attribute shall specify the number of beacon intervals that shall elapse between transmission of Beacons frames containing a TIM element whose DTIM Count field is 0. This value is transmitted in the DTIM Period field of Beacon frames.";
    }
    leaf max-tx-power-level {
      type uint32;
      default "1";
      description
        "This attribute shall indicate the maximum transmit power, in dBm, allowed in the subband for the associated domain country string. The default value of this attribute shall be zero.";
    }
    leaf short-retry-limit {
      type uint32;
      default "7";
      description
        "This attribute shall indicate the maximum number of transmission attempts of a frame, the length of which is less than or equal to bsnGlobalDot11RTSThreshold, that shall be made before a failure condition is indicated. The default value of this attribute shall be 7.";
    }
    leaf long-retry-limit {
      type uint32;
      default "4";
      description
        "This attribute shall indicate the maximum number of transmission attempts of a frame, the length of which is greater than bsnGlobalDot11RTSThreshold, that shall be made before a failure condition is indicated. The default value of this attribute shall be 4.";
    }
    leaf max-tx-msdu-lifetime {
      type uint32;
      default "512";
      description
        "The MaxTransmitMSDULifetime shall be the elapsed time in TU, after the initial transmission of an MSDU, after which further attempts to transmit the MSDU shall be terminated. The default value of this attribute shall be 512.";
    }
    leaf max-rx-lifetime {
      type uint32;
      default "512";
      description
        "The MaxReceiveLifetime shall be the elapsed time in TU, after the initial reception of a fragmented MMPDU or MSDU, after which further attempts to reassemble the MMPDU or MSDU shall be terminated. The default value shall be 512.";
    }
    leaf channel-agility {
      type boolean;
      default "false";
      description
        "This attribute indicates that the PHY channel agility functionality is enabled.";
    }
    container ampdu-entries {
      description
        "Configurations related to 802.11n A-MPDU";
      list ampdu-entry {
        key "index";
        description
          "A list of configuration objects related to 802.11n A-MPDU";
        uses wireless-dot11-cfg:ampdu-80211n;
      }
    }
    container ampdu-tx-scheduler {
      presence "ampdu-tx-scheduler";
      description
        "List of configuration objects related to 802.11n A-MPDU trasmit scheduler";
      uses wireless-dot11-cfg:ampdu-tx-scheduler;
    }
    container amsdu-entries {
      description
        "Configurations related to 802.11n A-MSDU";
      list amsdu-entry {
        key "index";
        description
          "List of configuration objects related to 802.11n A-MSDU";
        uses wireless-dot11-cfg:amsdu-11n;
      }
    }
    container media-stream-band-info-cfg {
      presence "mediaStreamBandInfo";
      description
        "Configurations related to media stram band information";
      uses wireless-dot11-cfg:media-stream-band-info;
    }
    container spectrum-cfg {
      presence "spectrum-cfg";
      description
        "Configurations related to Clean-Air";
      uses wireless-dot11-cfg:spectrum-cfg;
    }
    leaf cac-max-calls {
      type uint32;
      description
        "cac max calls";
    }
  }

  grouping spectrum-cfg {
    description
      "Config related to Clean Air. This node cannot be configured";
    leaf spectrum-admin-state-set {
      type boolean;
      default "false";
      description
        "This object indicates whether Clean Air (CA) is enabled on this band. A value of 'true' indicates CA is enabled. A value of 'false' indicates CA is disabled.";
    }
    leaf si-admin-state-set {
      type boolean;
      default "false";
      description
        "This object indicates whether Spectrum Intelligence (SI) is enabled on this band. A value of 'true' indicates SI is enabled. A value of 'false' indicates SI is disabled.";
    }
    leaf dev-report-state-set {
      type boolean;
      default "true";
      description
        "This object indicates whether device reporting state is enabled on this band. A value of 'true' indicates IDR is enabled. A value of 'false' indicates IDR is disabled.";
    }
    leaf aq-polling-period {
      type uint8;
      default "15";
      description
        "This object represents the Air Quality polling interval.";
    }
    leaf id-report-enable {
      type boolean;
      default "false";
      description
        "This object indicates whether IDR is enabled on this band. A value of 'true' indicates IDR is enabled. A value of 'false' indicates IDR is disabled.";
    }
    leaf id-report-period {
      type uint8;
      default "90";
      description
        "This object indicates the interferer reporting period, this is fixed at 90 seconds";
    }
    leaf aq-report-enable {
      type boolean;
      default "false";
      description
        "This object indicates whether Air Quality Reporting is enabled on this band. A value of 'true' indicates IDR is enabled. A value of 'false' indicates IDR is disabled.";
    }
    leaf aq-alarm-mode {
      type boolean;
      default "false";
      description
        "This object indicates whether AQ notification is enabled on this band. A value of 'true' indicates AQ notification is enabled. A value of 'false' indicates AQ notification is disabled.";
    }
    leaf aq-alarm-threshold {
      type uint8 {
        range "1 .. 100";
      }
      default "10";
      description
        "This object represents the threshold value for the trap.";
    }
    leaf dev-alarm-mode {
      type boolean;
      default "false";
      description
        "This object indicates whether IDR notification is enabled on this band. A value of 'true' indicates IDR notification is enabled. A value of 'false' indicates IDR notification is disabled.";
    }
    leaf rrm-ed-enable {
      type boolean;
      default "false";
      description
        "This object indicates whether event driven RRM is enabled on this band. A value of 'true' indicates event driven RRM is enabled. A value of 'false' indicates event driven RRM is disabled.";
    }
    leaf rrm-ed-threshold-level {
      type wireless-enum-types:rrm-ed-threshold-level;
      default "rrm-cleanair-event-low";
      description
        "This object represents the event driven RRM threshold level.
                 
         'low' - low level event driven RRM threshold value
         'medium' - medium level event driven RRM threshold value
         'high' - high level event driven RRM threshold value
         'custom' - user specified value of even driven RRM threshold";
    }
    leaf rrm-ed-custom-threshold-value {
      type uint32 {
        range "1 .. 99";
      }
      default "1";
      description
        "This object represents the event driven RRM Custom threshold value. This object only takes effect when the value of cLSiD11EventDrivenRrmThresLvl is 'custom'.";
    }
    leaf rrm-ed-rogue-enable {
      type boolean;
      default "false";
      description
        "This object specifies whether event driven RRM rogue contribution is enabled on this band. A value of 'true' indicates rogue contribution is enabled. A value of 'false' indicates rogue contribution is disabled.";
    }
    leaf rrm-ed-rogue {
      type uint8 {
        range "1 .. 99";
      }
      default "80";
      description
        "This object specifies the event driven RRM rogue contribution duty cycle threshold value.";
    }
    leaf idrv-period {
      type uint8;
      default "20";
      description
        "The interferer report period is fixed at 90 seconds";
    }
    leaf aq-alarm2-control {
      type boolean;
      default "false";
      description
        "Config air quality alarm on exceeding unclassified category severity";
    }
    leaf aq-alarm2-threshold {
      type uint8 {
        range "1 .. 100";
      }
      default "35";
      description
        "Config air quality alarm threshold for unclassified category severity, range 1(low) - 100(high)";
    }
    leaf cleanair-dev-all-mode {
      type boolean;
      default "true";
      description
        "This object specifies detection of all given interferer types on CleanAIR capable access points is enabled on this band or not. A value of 'true' indicates that it is enabled. A value of 'false' indicates it is disabled.";
    }
    leaf rrm-pd-propagation {
      type boolean;
      default "false";
      description
        "This object specifies whether Persistent Device Propagation to neighboring access points is enabled on this band or not. A value of 'true' indicates that Persistent Device Propagation is enabled. A value of 'false' indicates Persistent Device Propagation is disabled.";
    }
    leaf cleanair-device-bt-link-mode {
      type boolean;
      default "true";
      description
        "This object specifies detection of bluetooth link device on CleanAIR capable access points is enabled on this band or not. A value of 'true' indicates that it is enabled. A value of 'false' indicates it is disabled.";
    }
    leaf device-bt-link-mode {
      type boolean;
      default "false";
      description
        "This object specifies whether alarm for reporting bluetooth link on CleanAIR capable access points is enabled on this band or not. A value of 'true' indicates that it is enabled. A value of 'false' indicates it is disabled.";
    }
    leaf cleanair-device-mw-oven-mode {
      type boolean;
      default "true";
      description
        "This object specifies detection of micorwave oven interferer device types on CleanAIR capable access points is enabled on this band or not. A value of 'true' indicates that it is enabled. A value of 'false' indicates it is disabled.";
    }
    leaf device-mw-oven-mode {
      type boolean;
      default "false";
      description
        "This object specifies whether alarm for reporting microwave oven on CleanAIR capable access points is enabled on this band or not. A value of 'true' indicates that it is enabled. A value of 'false' indicates it is disabled.";
    }
    leaf cleanair-dev802fh-mode {
      type boolean;
      default "true";
      description
        "This object specifies detection of frequency hopping 802.11 complaint device on CleanAIR capable access points is enabled on this band or not. A value of 'true' indicates that it is enabled. A value of 'false' indicates it is disabled.";
    }
    leaf dev802fh-mode {
      type boolean;
      default "false";
      description
        "This object specifies whether alarm for reporting frequency hopping 802.11 complaint on CleanAIR capable access points is enabled on this band or not. A value of 'true' indicates that it is enabled. A value of 'false' indicates it is disabled.";
    }
    leaf cleanair-device-bt-discovery-mode {
      type boolean;
      default "true";
      description
        "This object specifies detection of bluetooth device on CleanAIR capable access points is enabled on this band or not. A value of 'true' indicates that it is enabled. A value of 'false' indicates it is disabled.";
    }
    leaf device-bt-discovery-mode {
      type boolean;
      default "false";
      description
        "This object specifies whether alarm for reporting bluetooth on CleanAIR capable access points is enabled on this band or not. A value of 'true' indicates that it is enabled. A value of 'false' indicates it is disabled.";
    }
    leaf cleanair-device-tddtx-mode {
      type boolean;
      default "true";
      description
        "This object specifies detection of time division duplex transmitter device on CleanAIR capable access points is enabled on this band or not. A value of 'true' indicates that it is enabled. A value of 'false' indicates it is disabled.";
    }
    leaf device-tddtx-mode {
      type boolean;
      default "false";
      description
        "This object specifies whether alarm for reporting time division duplex transmitter on CleanAIR capable access points is enabled on this band or not. A value of 'true' indicates that it is enabled. A value of 'false' indicates it is disabled.";
    }
    leaf cleanair-device-jammer-mode {
      type boolean;
      default "true";
      description
        "This object specifies detection of jammer device on CleanAIR capable access points is enabled on this band or not. A value of 'true' indicates that it is enabled. A value of 'false' indicates it is disabled.";
    }
    leaf device-jammer-mode {
      type boolean;
      default "false";
      description
        "This object specifies whether alarm for reporting jammer on CleanAIR capable access points is enabled on this band or not. A value of 'true' indicates that it is enabled. A value of 'false' indicates it is disabled.";
    }
    leaf cleanair-device-conttx-mode {
      type boolean;
      default "true";
      description
        "This object specifies detection of continous transmitter device on CleanAIR capable access points is enabled on this band or not. A value of 'true' indicates that it is enabled. A value of 'false' indicates it is disabled.";
    }
    leaf device-conttx-mode {
      type boolean;
      default "false";
      description
        "This object specifies whether alarm for reporting continous transmitter on CleanAIR capable access points is enabled on this band or not. A value of 'true' indicates that it is enabled. A value of 'false' indicates it is disabled.";
    }
    leaf cleanair-device-dect-like-mode {
      type boolean;
      default "true";
      description
        "This object specifies detection of DECT like device on CleanAIR capable access points is enabled on this band or not. A value of 'true' indicates that it is enabled. A value of 'false' indicates it is disabled.";
    }
    leaf device-dect-like-mode {
      type boolean;
      default "false";
      description
        "This object specifies whether alarm for reporting DECT like on CleanAIR capable access points is enabled on this band or not. A value of 'true' indicates that it is enabled. A value of 'false' indicates it is disabled.";
    }
    leaf cleanair-device-video-mode {
      type boolean;
      default "true";
      description
        "This object specifies detection of video camera device on CleanAIR capable access points is enabled on this band or not. A value of 'true' indicates that it is enabled. A value of 'false' indicates it is disabled.";
    }
    leaf device-video-mode {
      type boolean;
      default "false";
      description
        "This object specifies whether alarm for reporting video camera on CleanAIR capable access points is enabled on this band or not. A value of 'true' indicates that it is enabled. A value of 'false' indicates it is disabled.";
    }
    leaf cleanair-device-zig-bee-mode {
      type boolean;
      default "true";
      description
        "This object specifies detection of zigbee device on CleanAIR capable access points is enabled on this band or not. A value of 'true' indicates that it is enabled. A value of 'false' indicates it is disabled.";
    }
    leaf device-zig-bee-mode {
      type boolean;
      default "false";
      description
        "This object specifies whether alarm for reporting zigbee on CleanAIR capable access points is enabled on this band or not. A value of 'true' indicates that it is enabled. A value of 'false' indicates it is disabled.";
    }
    leaf cleanair-device-inv-mode {
      type boolean;
      default "true";
      description
        "This object specifies detection of spectrally inverted wifi signal device on CleanAIR capable access points is enabled on this band or not. A value of 'true' indicates that it is enabled. A value of 'false' indicates it is disabled.";
    }
    leaf device-inv-mode {
      type boolean;
      default "false";
      description
        "This object specifies whether alarm for reporting spectrally inverted wifi signal on CleanAIR capable access points is enabled on this band or not. A value of 'true' indicates that it is enabled. A value of 'false' indicates it is disabled.";
    }
    leaf cleanair-device-nonstd-mode {
      type boolean;
      default "true";
      description
        "This object specifies detection of device using non standard wifi channels on CleanAIR capable access points is enabled on this band or not. A value of 'true' indicates that it is enabled. A value of 'false' indicates it is disabled.";
    }
    leaf device-nonstd-mode {
      type boolean;
      default "false";
      description
        "This object specifies whether alarm for reporting device using non standard wifi channels";
    }
    leaf cleanair-device-superag-mode {
      type boolean;
      default "true";
      description
        "This object specifies detection of superAG device on CleanAIR capable access points is enabled on this band or not. A value of 'true' indicates that it is enabled. A value of 'false' indicates it is disabled.";
    }
    leaf device-superag-mode {
      type boolean;
      default "false";
      description
        "This object specifies whether alarm for reporting superAG on CleanAIR capable access points is enabled on this band or not. A value of 'true' indicates that it is enabled. A value of 'false' indicates it is disabled.";
    }
    leaf cleanair-device-canopy-mode {
      type boolean;
      default "true";
      description
        "This object specifies detection of canopy device on CleanAIR capable access points is enabled on this band or not. A value of 'true' indicates that it is enabled. A value of 'false' indicates it is disabled.";
    }
    leaf device-canopy-mode {
      type boolean;
      default "false";
      description
        "This object specifies whether alarm for reporting canopy on CleanAIR capable access points is enabled on this band or not. A value of 'true' indicates that it is enabled. A value of 'false' indicates it is disabled.";
    }
    leaf cleanair-device-xbox-mode {
      type boolean;
      default "true";
      description
        "This object specifies detection of xbox device on CleanAIR capable access points is enabled on this band or not. A value of 'true' indicates that it is enabled. A value of 'false' indicates it is disabled.";
    }
    leaf device-xbox-mode {
      type boolean;
      default "false";
      description
        "This object specifies whether alarm for reporting xbox on CleanAIR capable access points is enabled on this band or not. A value of 'true' indicates that it is enabled. A value of 'false' indicates it is disabled.";
    }
    leaf cleanair-device-wimax-mobile-mode {
      type boolean;
      default "true";
      description
        "This object specifies detection of wimax mobile device on CleanAIR capable access points is enabled on this band or not. A value of 'true' indicates that it is enabled. A value of 'false' indicates it is disabled.";
    }
    leaf device-wimax-mobile-mode {
      type boolean;
      default "false";
      description
        "This object specifies whether alarm for reporting wimax mobile on CleanAIR capable access points is enabled on this band or not. A value of 'true' indicates that it is enabled. A value of 'false' indicates it is disabled.";
    }
    leaf cleanair-device-wimax-fixed-mode {
      type boolean;
      default "true";
      description
        "This object specifies detection of wimax fixed device on CleanAIR capable access points is enabled on this band or not. A value of 'true' indicates that it is enabled. A value of 'false' indicates it is disabled.";
    }
    leaf device-wimax-fixed-mode {
      type boolean;
      default "false";
      description
        "This object specifies whether alarm for reporting wimax fixed on CleanAIR capable access points is enabled on this band or not. A value of 'true' indicates that it is enabled. A value of 'false' indicates it is disabled.";
    }
    leaf cleanair-device-ble-beacon-mode {
      type boolean;
      default "false";
      description
        "This object specifies detection of BLE beacon device on CleanAIR capable access points is enabled on this band or not. A value of 'true' indicates that it is enabled. A value of 'false' indicates it is disabled.";
    }
    leaf device-ble-beacon-mode {
      type boolean;
      default "false";
      description
        "This object specifies whether alarm for reporting ble beacon on CleanAIR capable access points is enabled on this band or not. A value of 'true' indicates that it is enabled. A value of 'false' indicates it is disabled.";
    }
    leaf si-device-fhss-mode {
      type boolean;
      default "true";
      description
        "This object specifies detection of FHSS device on SI capable access points is enabled on this band or not. A value of 'true' indicates that it is enabled. A value of 'false' indicates it is disabled.";
    }
    leaf device-fhss-mode {
      type boolean;
      default "false";
      description
        "This object specifies whether alarm for reporting FHSS on SI capable access points is enabled on this band or not. A value of 'true' indicates that it is enabled. A value of 'false' indicates it is disabled.";
    }
  }

  grouping media-stream-band-info {
    description
      "st_mediaStream_bandInfo";
    leaf multicast-direct {
      type boolean;
      default "false";
      description
        "This object specifies the decision flag to allow multicast direct stream on radio.";
    }
    leaf multicast-direct-adm-best-effort {
      type boolean;
      default "false";
      description
        "This object specifies whether to admit a media stream in best effort queue.";
    }
    leaf video-redirect {
      type boolean;
      default "false";
      description
        "This object specifies whether a unicast or multicast only video stream can be redirected to best effort.";
    }
    leaf cac-mmedia-max-bandwidth {
      type uint32 {
        range "5 .. 85";
      }
      default "85";
      description
        "This object specifies the maximum allowed bandwidth for media traffic.";
    }
    leaf cac-mstream-mdirect-min-client-rate {
      type wireless-enum-types:dot11-min-phy-rate;
      default "six";
      description
        "cacMStreamMDirectMinClientRate";
    }
    leaf cac-mstream-mdirect-max-retry-percent {
      type uint32 {
        range "0 .. 100";
      }
      default "80";
      description
        "cacMStreamMDirectMaxRetryPercent";
    }
    leaf mult-direct-max-stream-per-radio-val {
      type uint32 {
        range "0 .. 20";
      }
      default "0";
      description
        "This object specifies the maximum number of allowed streams per radio for a 802.11 band.";
    }
    leaf mult-direct-max-stream-per-client-val {
      type uint32 {
        range "0 .. 15";
      }
      default "0";
      description
        "This object specifies the maximum number of allowed streams per client for a 802.11 band.";
    }
  }

  container dot11-cfg-data {
    description
      "Configuration objects related to 802.11 feature";
    container dot11ac-mcs-entries {
      description
        "Configurations related to 802.11ac MCS rates";
      list dot11ac-mcs-entry {
        key "spatial-stream index";
        description
          "Configurations related to 802.11ac MCS rates";
        uses wireless-dot11-cfg:ac-mcs-80211;
        uses wireless-dot11-cfg:mcs-key-80211ac;
      }
    }
    container dot11-entries {
      description
        "Configuration related to 802.11 protocol";
      list dot11-entry {
        key "band";
        description
          "List of configuration objects related to 802.11 protocol";
        uses wireless-dot11-cfg:dot11;
      }
    }
  }
}
