module Cisco-IOS-XE-transceiver-oper {
  yang-version 1;
  namespace "http://cisco.com/ns/yang/Cisco-IOS-XE-transceiver-oper";
  prefix xcvr-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring transceivers in a Network Element.
     Copyright (c) 2017-2018 by Cisco Systems, Inc.
     All rights reserved.";

  revision 2018-01-18 {
    description
      "Initial revision";
    reference "1.0.0";
  }

  typedef xcvr-sonet-code {
    type enumeration {
      enum "oc-48-short-reach" {
        value 0;
      }
      enum "oc-48-intermediate-reach" {
        value 1;
      }
      enum "oc-48-long-reach" {
        value 2;
      }
      enum "sonet-sr-compliant" {
        value 3;
      }
      enum "sonet-lr-compliant" {
        value 4;
      }
      enum "oc-192-short-reach" {
        value 5;
      }
      enum "escon-smf-1310-laser" {
        value 6;
      }
      enum "escon-mmf-1310-led" {
        value 7;
      }
      enum "unknown" {
        value 8;
      }
    }
    description
      "SONET/SDH application code supported by the port";
  }

  typedef xcvr-otn-code {
    type enumeration {
      enum "p1l1-2d1" {
        value 0;
      }
      enum "p1s1-2d2" {
        value 1;
      }
      enum "p1l1-2d2" {
        value 2;
      }
      enum "otn-undefined" {
        value 3;
      }
    }
    description
      "OTN application code supported by the port";
  }

  grouping statistics-values {
    description
      "Statistics values for power and current";
    leaf instant {
      type decimal64 {
        fraction-digits 2;
      }
      description
        "Instant value";
    }
    leaf avg {
      type decimal64 {
        fraction-digits 2;
      }
      description
        "Average value";
    }
    leaf max {
      type decimal64 {
        fraction-digits 2;
      }
      description
        "Maximum value";
    }
    leaf min {
      type decimal64 {
        fraction-digits 2;
      }
      description
        "Minimum value";
    }
  }

  grouping xcvr-physical-channel {
    description
      "List of physical channel for transceiver";
    leaf index {
      type uint16;
      description
        "Index of the physical channnel";
    }
    leaf description {
      type string;
      description
        "Text description for the client physical channel";
    }
    leaf tx-laser {
      type boolean;
      description
        "Enable (true) or disable (false) the transmit label for the channel";
    }
    leaf target-output-power {
      type decimal64 {
        fraction-digits 2;
      }
      description
        "Target output optical power level of the optical channel(dBm)";
    }
    leaf output-frequency {
      type uint64;
      description
        "The frequency in MHz of the individual physical channel";
    }
    container output-power {
      description
        "The output optical power of a physical channel(dBm)";
      uses xcvr-ios-xe-oper:statistics-values;
    }
    container input-power {
      description
        "The input optical power of a physical channel(dBm)";
      uses xcvr-ios-xe-oper:statistics-values;
    }
    container laser-bias-current {
      description
        "The current applied by the system to the transmit laser to achieve the output power(mA)";
      uses xcvr-ios-xe-oper:statistics-values;
    }
  }

  grouping xcvr {
    description
      "Attributes of transceiver";
    leaf name {
      type string;
      description
        "Port name";
    }
    leaf enabled {
      type boolean;
      description
        "Turns power on/off to the transceiver";
    }
    leaf present {
      type boolean;
      description
        "Transceiver is present on the port";
    }
    leaf identifier {
      type string;
      description
        "Indicates the type of optical transceiver used on this port";
    }
    leaf connector {
      type string;
      description
        "Connector type used on this port";
    }
    leaf ethernet-pmd {
      type string;
      description
        "Ethernet PMD (physical medium dependent sublayer) that the transceiver supports. The SFF/QSFP MSAs have registers for this and CFP MSA has similar.";
    }
    leaf vendor {
      type string;
      description
        "Full name of transceiver vendor";
    }
    leaf vendor-part {
      type string;
      description
        "Transceiver vendor's part number";
    }
    leaf vendor-rev {
      type string;
      description
        "Transceiver vendor's revision number";
    }
    leaf serial-no {
      type string;
      description
        "Transceiver serial number";
    }
    leaf fault-condition {
      type boolean;
      description
        "Indicates if a fault condition exists in the transceiver";
    }
    leaf date {
      type string;
      description
        "Representation of the transceiver date";
    }
    leaf sonet {
      type xcvr-ios-xe-oper:xcvr-sonet-code;
      description
        "SONET/SDH application code supported by the port";
    }
    leaf otn {
      type xcvr-ios-xe-oper:xcvr-otn-code;
      description
        "OTN application code supported by the port";
    }
    leaf internal-temp {
      type decimal64 {
        fraction-digits 2;
      }
      description
        "Internally measured temperature in degrees Celsius";
    }
    container output-power {
      description
        "The output optical power of overall transceiver(dBm)";
      uses xcvr-ios-xe-oper:statistics-values;
    }
    container input-power {
      description
        "The input optical power of overall transceiver(dBm)";
      uses xcvr-ios-xe-oper:statistics-values;
    }
    container laser-bias-current {
      description
        "The current applied by the system to the transmit laser to achieve the output power(mA)";
      uses xcvr-ios-xe-oper:statistics-values;
    }
    list xcvr-physical-channel {
      key "index";
      description
        "List of physical channel for transceiver";
      uses xcvr-ios-xe-oper:xcvr-physical-channel;
    }
  }

  container transceiver-oper-data {
    config false;
    description
      "Top-level container for transceiver operational data";
    list transceiver {
      key "name";
      description
        "List of transceiver instance, keyed by name";
      uses xcvr-ios-xe-oper:xcvr;
    }
  }
}
