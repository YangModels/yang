module Cisco-IOS-XE-wireless-ap-types {
  yang-version 1;
  namespace "http://cisco.com/ns/yang/Cisco-IOS-XE-wireless-ap-types";
  prefix wireless-ap-types;

  import Cisco-IOS-XE-wireless-enum-types {
    prefix wireless-enum-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless ap data types.
     Copyright (c) 2016-2018 by Cisco Systems, Inc.
     All rights reserved.";

  revision 2018-06-15 {
    description
      "AIRsense feature renamed to Intelligent Capture";
    reference "4.0.0";
  }
  revision 2018-03-22 {
    description
      "Leaf name changes";
    reference "3.0.0";
  }
  revision 2018-01-24 {
    description
      "The first generally available version";
    reference "2.0.0";
  }
  revision 2017-05-05 {
    description
      "Initial revision";
    reference "1.0.0";
  }

  typedef enm-link-latency-type {
    type enumeration {
      enum "link-auditing-disable" {
        value 0;
        description
          "option for link auditing disable";
      }
      enum "link-auditing-enable" {
        value 1;
        description
          "option for link auditing enable";
      }
      enum "link-auditing-data" {
        value 2;
        description
          "option for link auditing data";
      }
      enum "link-auditing-reset" {
        value 4;
        description
          "option for link auditing reset";
      }
    }
    description
      "enum for capturing the link auditing configurations";
  }

  typedef enm-ap-tag-source {
    type enumeration {
      enum "tag-source-none" {
        value 0;
        description
          "This value specifies that the tag 
           source is empty";
      }
      enum "tag-source-static" {
        value 1;
        description
          "This value specifies that the tags for ap 
           are configured at controller";
      }
      enum "tag-source-filter" {
        value 2;
        description
          "This value specifies that the tag for ap
           are configured at controller by filter engine";
      }
      enum "tag-source-ap-pnp" {
        value 3;
        description
          "This value specifies that the tags for ap
           are coming from ap with help of PNP server";
      }
      enum "tag-source-default" {
        value 4;
        description
          "This value specifies that the tags for ap
           configured to be default";
      }
      enum "tag-source-location" {
        value 5;
        description
          "This value specifies that the tag for ap
           are configured at controller under location";
      }
    }
    description
      "Enum to store the tag source for the AP tags";
  }

  typedef syslog-facility-value {
    type enumeration {
      enum "facility-kern" {
        value 0;
        description
          "Syslog value of type FACILITY_KERN";
      }
      enum "facility-user" {
        value 1;
        description
          "Syslog value of type FACILITY_USER";
      }
      enum "facility-mail" {
        value 2;
        description
          "Syslog value of type FACILITY_MAIL";
      }
      enum "facility-daemon" {
        value 3;
        description
          "Syslog value of type FACILITY_DAEMON";
      }
      enum "facility-auth" {
        value 4;
        description
          "Syslog value of type FACILITY_AUTH";
      }
      enum "facility-syslog" {
        value 5;
        description
          "Syslog value of type FACILITY_SYSLOG";
      }
      enum "facility-lpr" {
        value 6;
        description
          "Syslog value of type FACILITY_LPR";
      }
      enum "facility-news" {
        value 7;
        description
          "Syslog value of type FACILITY_NEWS";
      }
      enum "facility-uucp" {
        value 8;
        description
          "Syslog value of type FACILITY_UUCP";
      }
      enum "facility-sys9" {
        value 9;
        description
          "Syslog value of type FACILITY_SYS9";
      }
      enum "facility-sys10" {
        value 10;
        description
          "Syslog value of type FACILITY_SYS10";
      }
      enum "facility-sys11" {
        value 11;
        description
          "Syslog value of type FACILITY_SYS11";
      }
      enum "facility-sys12" {
        value 12;
        description
          "Syslog value of type FACILITY_SYS12";
      }
      enum "facility-sys13" {
        value 13;
        description
          "Syslog value of type FACILITY_SYS13";
      }
      enum "facility-sys14" {
        value 14;
        description
          "Syslog value of type FACILITY_SYS14";
      }
      enum "facility-cron" {
        value 15;
        description
          "Syslog value of type FACILITY_CRON";
      }
      enum "facility-local0" {
        value 16;
        description
          "Syslog value of type FACILITY_LOCAL0";
      }
      enum "facility-local1" {
        value 17;
        description
          "Syslog value of type FACILITY_LOCAL1";
      }
      enum "facility-local2" {
        value 18;
        description
          "Syslog value of type FACILITY_LOCAL2";
      }
      enum "facility-local3" {
        value 19;
        description
          "Syslog value of type FACILITY_LOCAL3";
      }
      enum "facility-local4" {
        value 20;
        description
          "Syslog value of type FACILITY_LOCAL4";
      }
      enum "facility-local5" {
        value 21;
        description
          "Syslog value of type FACILITY_LOCAL5";
      }
      enum "facility-local6" {
        value 22;
        description
          "Syslog value of type FACILITY_LOCAL6";
      }
      enum "facility-local7" {
        value 23;
        description
          "Syslog value of type FACILITY_LOCAL7";
      }
    }
    description
      "enum for capturing the syslog facility options";
  }

  typedef ap-mode-type {
    type enumeration {
      enum "mode-local" {
        value 0;
        description
          "option to denote that the AP is working in local mode";
      }
      enum "flex-connect" {
        value 1;
        description
          "option to denote that the AP is working in flex mode";
      }
      enum "monitor" {
        value 2;
        description
          "option to denote that the AP is working in monitor mode";
      }
      enum "rogue-detector" {
        value 3;
        description
          "option to denote that the AP is working as a rogue detector";
      }
      enum "sniffer" {
        value 4;
        description
          "option to denote that the AP is in sniffer mode";
      }
      enum "bridge" {
        value 5;
        description
          "option to denote that the AP is working as a bridge AP";
      }
      enum "flex-and-bridge" {
        value 6;
        description
          "option to denote that the AP is in flex and bridge mode";
      }
      enum "se-connect" {
        value 7;
        description
          "ap mode of type SE_CONNECT";
      }
    }
    description
      "enum for capturing the mode of operation of AP";
  }

  typedef ap-sub-mode-type {
    type enumeration {
      enum "ap-sub-mode-none" {
        value 0;
        description
          "AP sub mode None";
      }
      enum "wips-mode" {
        value 1;
        description
          "AP sub mode Wips";
      }
      enum "pppoe" {
        value 2;
        description
          "PPPoE";
      }
      enum "pppoe-wips" {
        value 3;
        description
          "PPPoE Wips";
      }
      enum "dot11b" {
        value 4;
        description
          "Dot11b";
      }
      enum "tracking-mode" {
        value 5;
        description
          "Tracking";
      }
    }
    description
      "enum to denote the submode of the AP";
  }

  typedef power-injector-sel-type {
    type enumeration {
      enum "pwrinj-unknown" {
        value 0;
        description
          "Unknown";
      }
      enum "pwrinj-installed" {
        value 1;
        description
          "Installed";
      }
      enum "pwrinj-override" {
        value 2;
        description
          "Override";
      }
    }
    description
      "enum to denote the power injector selection for the AP";
  }

  typedef cdp-interface-type {
    type enumeration {
      enum "ethernet" {
        value 0;
        description
          "option to denote that the cdp interface is ethernet";
      }
      enum "radio" {
        value 1;
        description
          "option to denote that the cdp interface is radio";
      }
    }
    description
      "enum to denote cisco discovery protocol interface type";
  }

  typedef cipher-type {
    type enumeration {
      enum "aes256-sha1" {
        value 1;
        description
          "option to denote that the cipher type being used is 256 bit AES SHA1";
      }
      enum "aes256-sha2" {
        value 2;
        description
          "option to denote that the cipher type being used is 256 bit AES SHA2";
      }
    }
    description
      "enum to denote the cipher type that is being enforced";
  }

  typedef crash-or-radio-type {
    type enumeration {
      enum "crash-data" {
        value 0;
        description
          "Crash type of dump";
      }
      enum "radio-core-dupm" {
        value 1;
        description
          "Radio core type dump";
      }
    }
    description
      "enum to denote the crash type";
  }

  typedef duplex-setting-type {
    type enumeration {
      enum "ether-duplex-full" {
        value 5;
        description
          "ethernet is in full duplex mode";
      }
      enum "ether-duplex-half" {
        value 6;
        description
          "ethenet is in half duplex mode";
      }
      enum "ether-duplex-auto" {
        value 7;
        description
          "automatically select the duplex mode";
      }
    }
    description
      "enum to denote ethernet duplex settings";
  }

  typedef speed-type {
    type enumeration {
      enum "ether-speed-10" {
        value 1;
        description
          "option used to set the speed of the interface to 10 Gigabit";
      }
      enum "ether-speed-100" {
        value 2;
        description
          "option used to set the speed of the interface to 100 Gigabit";
      }
      enum "ether-speed-1000" {
        value 3;
        description
          "option used to set the speed of the interface to 1000 Gigabit";
      }
      enum "ether-speed-auto" {
        value 4;
        description
          "option used to automatically detect and selet the speed of the ethernet interface";
      }
    }
    description
      "enum to denote the ethernet link speed";
  }

  typedef port-mode-type {
    type enumeration {
      enum "access" {
        value 0;
        description
          "option to denote that the ethernet interface is an access interface";
      }
      enum "trunk" {
        value 1;
        description
          "option to denote that the ethernet interface is a trunk interface";
      }
    }
    description
      "enum to denote the mode of operation of the switched interface";
  }

  typedef vlan-opertion-type {
    type enumeration {
      enum "add-vlan" {
        value 0;
        description
          "option to denote the operation is add vlan";
      }
      enum "delete-vlan" {
        value 1;
        description
          "option to denote the operation is delete vlan";
      }
      enum "native-vlan" {
        value 2;
        description
          "option to denote the interface uses native vlan";
      }
    }
    description
      "enum to denote the vlan operation type";
  }

  typedef enm-ap-dot1x-eap-type {
    type enumeration {
      enum "dot1x-eap-none" {
        value 0;
        description
          "option to denote the authentication EAP-NONE";
      }
      enum "dot1x-eap-fast" {
        value 43;
        description
          "option to denote the authentication EAP-FAST";
      }
      enum "dot1x-eap-tls" {
        value 13;
        description
          "option to denote the authentication EAP-TLS";
      }
      enum "dot1x-eap-peap" {
        value 25;
        description
          "option to denote the authentication EAP-PEAP";
      }
    }
    description
      "enum to denote the authentication EAP type";
  }

  typedef enm-lsc-ap-auth-state-type {
    type enumeration {
      enum "lsc-ap-auth-none" {
        value 0;
        description
          "option to denote the LSC AP auth for none";
      }
      enum "lsc-ap-auth-capwap-dtls" {
        value 1;
        description
          "option to denote the LSC AP auth for capwap dtls";
      }
      enum "lsc-ap-auth-dot1x-port-auth" {
        value 2;
        description
          "option to denote the LSC AP auth for dot1x port auth";
      }
      enum "lsc-ap-auth-both" {
        value 3;
        description
          "option to denote the LSC AP auth for both";
      }
    }
    description
      "enum to denote the LSC AP auth state type";
  }

  grouping st-capwap-timer-cfg {
    description
      "capwap timer configurations";
    leaf heart-beat-timeout {
      type uint8 {
        range "1 .. 30";
      }
      default "30";
      description
        "This object represents the Heartbeattimeout for the AP discovery";
    }
    leaf discovery-timeout {
      type uint8 {
        range "1 .. 10";
      }
      default "10";
      description
        "This object represents the timeout for the AP discovery";
    }
    leaf fast-heart-beat-timeout {
      type uint8 {
        range "0 .. 10";
      }
      default "0";
      description
        "This object represents the timeout value for the heart beat timer.";
    }
    leaf primary-discovery-timeout {
      type uint16 {
        range "30 .. 3000";
      }
      default "120";
      description
        "This object represents the timeout for the primary AP discovery";
    }
    leaf primed-join-timeout {
      type uint32 {
        range "0 .. 43200";
      }
      default "0";
      description
        "This object represents the primed timeout for the AP discovery";
    }
  }

  grouping st-capwap-retransmit-timer-cfg {
    description
      "capwap retransmit timer configuration";
    leaf count {
      type uint8 {
        range "3 .. 8";
      }
      default "5";
      description
        "retransmit timer count";
    }
    leaf interval {
      type uint8 {
        range "2 .. 5";
      }
      default "3";
      description
        "retransmit timer interval";
    }
  }

  grouping st-backup-controllers-cfg {
    description
      "backup controller configurations";
    leaf fallback-enabled {
      type boolean;
      default "true";
      description
        "Backup Controllers fallback enabled";
    }
    leaf primary-controller-name {
      type string;
      default "";
      description
        "the AP's primary controller name";
    }
    leaf secondary-controller-name {
      type string;
      default "";
      description
        "the AP's secondary controller name";
    }
    leaf primary-controller-ip {
      type inet:ip-address;
      default "0.0.0.0";
      description
        "the AP's primary controller ip address";
    }
    leaf secondary-controller-ip {
      type inet:ip-address;
      default "0.0.0.0";
      description
        "the AP's secondary controller ip address";
    }
  }

  grouping st-static-domain-nameserver-cfg {
    description
      "static domain name server configurations";
    leaf nameserver-address {
      type inet:ip-address;
      default "0.0.0.0";
      description
        "domain name server address";
    }
    leaf domain-name {
      type string;
      default "default";
      description
        "domain name";
    }
  }

  grouping st-tcp-mss-cfg {
    description
      "ipv4 TCP MSS configurations";
    leaf adjust-mss {
      type boolean;
      default "true";
      description
        "adjust mss";
    }
    leaf tcp-adjust-mss {
      type uint16 {
        range "536 .. 1363";
      }
      default "1250";
      description
        "This object represents the Global AP TCP MSS value";
    }
  }

  grouping st-ipv6-tcp-mss-cfg {
    description
      "ipv6 TCP MSS configurations";
    leaf adjust-mss-enable {
      type boolean;
      default "true";
      description
        "adjust mss enable";
    }
    leaf tcp-adjust-mss-size {
      type uint16 {
        range "1220 .. 1331";
      }
      default "1220";
      description
        "tcp mss adjust size";
    }
  }

  grouping st-device-mgmt-cfg {
    description
      "device management configurations";
    leaf telnet {
      type boolean;
      default "false";
      description
        "This object specifies whether Telnet session can be established to the AP";
    }
    leaf ssh {
      type boolean;
      default "false";
      description
        "This object specifies whether SSH session can be established to the AP";
    }
  }

  grouping st-user-mgmt-cfg {
    description
      "user management configuration";
    leaf username {
      type string;
      default "";
      description
        "user management username";
    }
    leaf password-type {
      type wireless-enum-types:crypt-type;
      default "clear";
      description
        "user management password type";
    }
    leaf secret-type {
      type wireless-enum-types:crypt-type;
      default "clear";
      description
        "user management secret type";
    }
    leaf enabled {
      type boolean;
      default "false";
      description
        "status of user management";
    }
  }

  grouping st-lawful-interception-cfg {
    description
      "Lawful Interception configurations per AP profile";
    leaf enable {
      type boolean;
      default "false";
      description
        "This object specifies whether Lawful Interception is enabled or not";
    }
    leaf timer-interval {
      type uint32 {
        range "60 .. 600";
      }
      default "60";
      description
        "This object represents the timer interval in seconds for periodic Lawful Interception updates";
    }
  }

  grouping st-ext-module-cfg {
    description
      "AP external module configurations";
    leaf enable {
      type boolean;
      default "false";
      description
        "This object specifies whether AP External Module is enabled or not";
    }
  }

  grouping st-persistent-ssid-broadcast-cfg {
    description
      "persistent SSID broadcast configurations";
    leaf enable {
      type boolean;
      default "false";
      description
        "This object specifies whether Persistent SSID Broadcast is enabled or not";
    }
  }

  grouping st-poe-cfg {
    description
      "power over ethernet configuration";
    leaf pre-standard8023af-switch-flag {
      type boolean;
      default "false";
      description
        "PreStandard 802.3af Switch";
    }
    leaf power-injector-state {
      type boolean;
      default "false";
      description
        "Power Injector State";
    }
    leaf power-injector-selection {
      type wireless-ap-types:power-injector-sel-type;
      default "pwrinj-unknown";
      description
        "power injector selection";
    }
    leaf injector-switch-mac {
      type yang:mac-address;
      default "00:00:00:00:00:00";
      description
        "mac address of the power injector switch";
    }
  }

  grouping st-coredump-cfg {
    description
      "coredump related configuration";
    leaf coredump-flag {
      type wireless-enum-types:memory-core-dump-flag;
      default "tftp-coredump-disable";
      description
        "coredump flag indicate if coredump is enabled and whether its compress or uncompress";
    }
    leaf tftp-server-address {
      type inet:ip-address;
      default "0.0.0.0";
      description
        "tftp server address to be used to move the core dump";
    }
    leaf corefile-name {
      type string;
      default "default";
      description
        "core file name";
    }
  }

  grouping st-tunnel-cfg {
    description
      "tunnel configurations";
    leaf preferred-mode {
      type wireless-enum-types:preferred-mode-type;
      default "preferred-mode-unconfig";
      description
        "This object represents the capwap prefer-mode";
    }
    leaf dtls-cipher {
      type wireless-ap-types:cipher-type;
      description
        "the cipher used for dtls";
    }
  }

  grouping st-crash-data-radio-cfg {
    description
      "configurations for radio data";
    leaf crash-type {
      type wireless-ap-types:crash-or-radio-type;
      description
        "crash type of the radio";
    }
    leaf slot {
      type uint8;
      description
        "slot number of the radio";
    }
  }

  grouping st-login-credentials-cfg {
    description
      "authentiation credentials";
    leaf local-credentials-flag {
      type boolean;
      description
        "local credentials flag";
    }
    leaf dot1x-credentials-flag {
      type boolean;
      description
        "dot1x credential flag";
    }
    leaf local-username {
      type string;
      default "";
      description
        "local authentication user name";
    }
    leaf local-password-type {
      type wireless-enum-types:crypt-type;
      default "clear";
      description
        "local password type";
    }
    leaf dot1x-username {
      type string;
      default "";
      description
        "dot1x user name";
    }
    leaf dot1x-password-type {
      type wireless-enum-types:crypt-type;
      default "clear";
      description
        "dot1x password type";
    }
    leaf max1x-session-limit-per-ap {
      type uint32 {
        range "0 .. 255";
      }
      default "0";
      description
        "maximum dot1x session limits allowed per AP";
    }
  }

  grouping st-dot1x-eap-auth-info {
    description
      "Dot1x EAP auth info";
    leaf dot1x-eap-type {
      type wireless-ap-types:enm-ap-dot1x-eap-type;
      default "dot1x-eap-fast";
      description
        "Dot1x EAP auth type";
    }
  }

  grouping st-lsc-ap-auth-type-info {
    description
      "Dot1x LSC AP auth info";
    leaf lsc-ap-auth-type {
      type wireless-ap-types:enm-lsc-ap-auth-state-type;
      default "lsc-ap-auth-capwap-dtls";
      description
        "LSC AP auth type";
    }
  }

  grouping st-capwap-lag-info {
    description
      "lag configurations";
    leaf ap-lag-enabled {
      type boolean;
      default "false";
      description
        "boolean to indicate whether ap lag enabled is used";
    }
  }

  grouping st-syslog-facility-cfg {
    description
      "syslog facitlity related configurations";
    leaf facility-value {
      type wireless-ap-types:syslog-facility-value;
      default "facility-kern";
      description
        "facility value";
    }
    leaf host {
      type inet:ip-address;
      default "255.255.255.255";
      description
        "host name";
    }
    leaf log-level {
      type wireless-types:syslog-trap-level;
      default "syslog-level-information";
      description
        "log level";
    }
  }

  grouping st-mode {
    description
      "Defines the type of AP mode";
    leaf ap-mode {
      type wireless-ap-types:ap-mode-type;
      description
        "Defines the AP mode";
    }
    leaf ap-sub-mode {
      type wireless-ap-types:ap-sub-mode-type;
      description
        "Defines the AP sub mode";
    }
    leaf fast-channel {
      type uint32;
      description
        "Fast channel mode";
    }
  }

  grouping st-ethernet-port-cfg {
    description
      "ethernet port configurations";
    leaf interface-number {
      type uint8;
      description
        "interface numbe of the ethernet port";
    }
    leaf port-mode {
      type wireless-ap-types:port-mode-type;
      description
        "Defines Ethernet is port mode type";
    }
    leaf operation {
      type wireless-ap-types:vlan-opertion-type;
      description
        "operation mode of the port";
    }
    leaf vlan {
      type uint16;
      description
        "vlan id of the port";
    }
    leaf duplex-type {
      type wireless-ap-types:duplex-setting-type;
      default "ether-duplex-auto";
      description
        "duplex type of the ethernet port";
    }
    leaf speed {
      type wireless-ap-types:speed-type;
      default "ether-speed-auto";
      description
        "speed supported by the ethernet port";
    }
  }

  grouping st-rogue-params {
    description
      "rogue configuration parameters";
    leaf profile-name {
      type string;
      description
        "rogue profile name";
    }
    leaf rogue-detection-monitor-mode-report-interval {
      type uint32 {
        range "10 .. 300";
      }
      default "10";
      description
        "time interval at which monitor mode report for AP rogue detection is generated";
    }
    leaf ap-rogue-detection-min-rssi {
      type int32 {
        range "-128 .. -70";
      }
      default "-90";
      description
        "minmum RSSI for AP rogue detection";
    }
    leaf ap-rogue-detection-transient-interval {
      type uint32 {
        range "0 .. 1800";
      }
      default "0";
      description
        "transient interval for AP rogue detection";
    }
    leaf rogue-containment-flexconnect {
      type boolean;
      default "false";
      description
        "rogue Containment in flexconnect";
    }
    leaf rogue-containment-autorate {
      type boolean;
      default "false";
      description
        "rogue Containment autorate";
    }
    leaf ap-rogue-detection {
      type boolean;
      default "true";
      description
        "rogue AP detection";
    }
  }

  grouping st-hyperlocation {
    description
      "hyperloaction related configurations";
    leaf hyperlocation-enable {
      type boolean;
      default "false";
      description
        "enable hyperlocation";
    }
    leaf pak-rssi-threshold-detection {
      type int32 {
        range "-100 .. -50";
      }
      default "-100";
      description
        "pak rssi threshold detection";
    }
    leaf pak-rssi-threshold-trigger {
      type uint8 {
        range "1 .. 100";
      }
      must "../pak-rssi-threshold-reset < ../pak-rssi-threshold-trigger" {
        error-message "pak-rssi-threshold-trigger must be greater than pak-rssi-threshold-reset";
        error-app-tag "must-violation";
      }
      default "10";
      description
        "pak rssi threshold trigger";
    }
    leaf pak-rssi-threshold-reset {
      type uint8 {
        range "0 .. 99";
      }
      default "8";
      description
        "pak rssi threshold reset";
    }
  }

  grouping st-qing-config-entry {
    description
      "qing config entry configurations";
    leaf traffic-qinq-enabled {
      type boolean;
      default "false";
      description
        "indicate that traffic qinq enabled";
    }
    leaf dhcp-qinq-enabled {
      type boolean;
      default "false";
      description
        "dhcp qinq enable flag";
    }
    leaf qinq-service-vlan-id {
      type int32;
      default "0";
      description
        "qinq service vlan identifier";
    }
  }

  grouping st-tftp-downgrade {
    description
      "tftp downgrade configuration";
    leaf tftp-downgrade-ip-address {
      type inet:ip-address;
      default "0.0.0.0";
      description
        "tftp downgrade ip address";
    }
    leaf tftp-downgrade-filename {
      type string;
      default "";
      description
        "tftp downgrade file name";
    }
  }

  grouping st-traffic-limit-cfg {
    description
      "configuration related to traffic limit";
    leaf max1x-session-limit-per-ap {
      type uint8;
      default "0";
      description
        "maximum dot1x session limits allowed per AP";
    }
  }

  grouping st-report-interval {
    description
      "Report interval at which the AP sends client stats to Controller";
    leaf radio-24ghz {
      type uint32 {
        range "5 .. 90";
      }
      default "90";
      description
        "Report Interval at which AP sends Client Stats 
         for all the clients connected to 24ghz radio in seconds";
    }
    leaf radio-5ghz {
      type uint32 {
        range "5 .. 90";
      }
      default "90";
      description
        "Report Interval at which AP sends Client Stats 
         for all the clients connected to 5ghz radio in seconds";
    }
  }

  grouping st-icap {
    description
      "Configuration of ICap subscriptions";
    leaf full-trace-enabled {
      type boolean;
      default "false";
      description
        "Full packet trace subscription enabled";
    }
    leaf partial-trace-enabled {
      type boolean;
      default "false";
      description
        "Partial packet trace subscription enabled";
    }
    leaf partial-trace-proto-all {
      type boolean;
      default "false";
      description
        "Collect partial packet traces for all protocols";
    }
    leaf partial-trace-proto-mgmt-all {
      type boolean;
      default "false";
      description
        "Collect partial packet traces for all management protocols";
    }
    leaf partial-trace-proto-mgmt-assoc {
      type boolean;
      default "false";
      description
        "Collect partial packet traces for association management protocols";
    }
    leaf partial-trace-proto-mgmt-auth {
      type boolean;
      default "false";
      description
        "Collect partial packet traces for authentication management protocols";
    }
    leaf partial-trace-proto-mgmt-probe {
      type boolean;
      default "false";
      description
        "Collect partial packet traces for probing management protocols";
    }
    leaf partial-trace-proto-data-all {
      type boolean;
      default "false";
      description
        "Collect partial packet traces for all data protocols";
    }
    leaf partial-trace-proto-data-arp {
      type boolean;
      default "false";
      description
        "Collect partial packet traces for the ARP protocol";
    }
    leaf partial-trace-proto-data-dhcp {
      type boolean;
      default "false";
      description
        "Collect partial packet traces for the DHCP protocol";
    }
    leaf partial-trace-proto-data-dhcpv6 {
      type boolean;
      default "false";
      description
        "Collect partial packet traces for the DHCPv6 protocol";
    }
    leaf partial-trace-proto-data-dns {
      type boolean;
      default "false";
      description
        "Collect partial packet traces for the DNS protocol";
    }
    leaf partial-trace-proto-data-eap {
      type boolean;
      default "false";
      description
        "Collect partial packet traces for the EAP protocol";
    }
    leaf partial-trace-proto-data-icmp {
      type boolean;
      default "false";
      description
        "Collect partial packet traces for the ICMP protocol";
    }
    leaf partial-trace-proto-data-icmpv6 {
      type boolean;
      default "false";
      description
        "Collect partial packet traces for the ICMPv6 protocol";
    }
    leaf partial-trace-proto-cisco-all {
      type boolean;
      default "false";
      description
        "Collect partial packet traces for all Cisco proprietary protocol";
    }
    leaf partial-trace-proto-cisco-ndp {
      type boolean;
      default "false";
      description
        "Collect partial packet traces for the NDP protocol";
    }
    leaf anomaly-det-enabled {
      type boolean;
      default "false";
      description
        "Anomaly detection subscription enabled";
    }
    leaf anomaly-det-trigger-trace-ap {
      type boolean;
      default "false";
      description
        "Trigger AP packet trace on anomaly detection";
    }
    leaf anomaly-det-dhcp-timeout {
      type uint32 {
        range "1 .. 120";
      }
      default "5";
      description
        "DHCP timeout for anomaly detection";
    }
    leaf anomaly-det-dot1x-timeout {
      type uint32 {
        range "1 .. 60";
      }
      default "3";
      description
        "802.1X timeout for anomaly detection";
    }
    leaf client-stats-enabled {
      type boolean;
      default "false";
      description
        "Client statistics subscription enabled";
    }
    leaf client-stats-freq {
      type uint32 {
        range "30 .. 3600";
      }
      default "30";
      description
        "Frequency for client statistics collection, in seconds";
    }
    leaf ap-stats-system-enabled {
      type boolean;
      default "false";
      description
        "AP system statistics subscription enabled";
    }
    leaf ap-stats-system-freq {
      type uint32 {
        range "30 .. 3600";
      }
      default "30";
      description
        "Frequency for AP system statistics collection, in seconds";
    }
    leaf ap-stats-memory-enabled {
      type boolean;
      default "false";
      description
        "AP memory statistics subscription enabled";
    }
    leaf ap-stats-memory-freq {
      type uint32 {
        range "30 .. 3600";
      }
      default "30";
      description
        "Frequency for AP memory statistics collection, in seconds";
    }
    leaf ap-stats-interface-enabled {
      type boolean;
      default "false";
      description
        "AP interface statistics subscription enabled";
    }
    leaf ap-stats-interface-freq {
      type uint32 {
        range "30 .. 3600";
      }
      default "30";
      description
        "Frequency for AP interface statistics collection, in seconds";
    }
    leaf ap-stats-routing-enabled {
      type boolean;
      default "false";
      description
        "AP routing statistics subscription enabled";
    }
    leaf ap-stats-routing-freq {
      type uint32 {
        range "30 .. 3600";
      }
      default "30";
      description
        "Frequency for AP routing statistics collection, in seconds";
    }
    leaf ap-stats-radio-enabled {
      type boolean;
      default "false";
      description
        "AP radio statistics subscription enabled";
    }
    leaf ap-stats-radio-freq {
      type uint32 {
        range "30 .. 3600";
      }
      default "30";
      description
        "Frequency for AP radio statistics collection, in seconds";
    }
    leaf ap-stats-wlan-enabled {
      type boolean;
      default "false";
      description
        "AP WLAN statistics subscription enabled";
    }
    leaf ap-stats-wlan-freq {
      type uint32 {
        range "30 .. 3600";
      }
      default "30";
      description
        "Frequency for AP WLAN statistics collection, in seconds";
    }
    leaf ap-stats-dns-enabled {
      type boolean;
      default "false";
      description
        "AP DNS statistics subscription enabled";
    }
    leaf ap-stats-dns-freq {
      type uint32 {
        range "30 .. 3600";
      }
      default "30";
      description
        "Frequency for AP DNS statistics collection, in seconds";
    }
    leaf rf-spectrum-enabled {
      type boolean;
      default "false";
      description
        "Radiofrequency spectrum subscription enabled";
    }
    leaf rf-spectrum-slot0-enabled {
      type boolean;
      default "false";
      description
        "Radio slot 0 used for radiofrequency spectrum measurements";
    }
    leaf rf-spectrum-slot1-enabled {
      type boolean;
      default "false";
      description
        "Radio slot 1 used for radiofrequency spectrum measurements";
    }
    leaf rf-spectrum-slot2-enabled {
      type boolean;
      default "false";
      description
        "Radio slot 2 used for radiofrequency spectrum measurements";
    }
  }

  grouping st-usb-module-cfg {
    description
      "AP USB status Structure";
    leaf enable {
      type boolean;
      default "true";
      description
        "Boolean to represent if USB is enabled/disabled";
    }
  }
}
