module Cisco-IOS-XE-wireless-site-cfg {
  yang-version 1;
  namespace "http://cisco.com/ns/yang/Cisco-IOS-XE-wireless-site-cfg";
  prefix wireless-site-cfg;

  import Cisco-IOS-XE-wireless-ap-types {
    prefix wireless-ap-types;
  }
  import Cisco-IOS-XE-wireless-enum-types {
    prefix wireless-enum-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing site configurations
     Copyright (c) 2016-2018 by Cisco Systems, Inc.
     All rights reserved.";

  revision 2018-06-15 {
    description
      "AIRsense feature renamed to Intelligent Capture";
    reference "4.0.0";
  }
  revision 2018-03-21 {
    description
      "Leaf removal and default changes";
    reference "3.0.0";
  }
  revision 2018-01-24 {
    description
      "The first generally available version";
    reference "2.0.0";
  }
  revision 2017-05-05 {
    description
      "Initial revision";
    reference "1.0.0";
  }

  grouping site-tag-config {
    description
      "This structure stores the site tag configurations for an AP";
    leaf site-tag-name {
      type string;
      description
        "Each entry represents a conceptual row in cLSiteTagConfigTable and corresponds to an Site Tag in a Elastic Wireless Controller.";
    }
    leaf description {
      type string;
      default "";
      description
        "This object is used to specify the description of the Site Tag";
    }
    leaf flex-profile {
      type string;
      default "default-flex-profile";
      description
        "This object identifies the flex profile which is part of the Site tag";
    }
    leaf ap-join-profile {
      type string;
      default "default-ap-profile";
      description
        "This object identifies the Ap Join profile which is part of the Site tag";
    }
    leaf is-local-site {
      type boolean;
      default "true";
      description
        "This parameter is set to enable local site";
    }
    leaf fabric-control-plane-name {
      type string;
      description
        "Fabric Control Plane Name";
    }
    leaf image-download-profile-name {
      type string;
      default "default-me-image-download-profile";
      description
        "Image Download Profile Name";
    }
    container site-master-ap-config-entries {
      description
        "This object stores the master AP configurations in a site";
      list site-master-ap-config-entry {
        key "ap-model";
        description
          "List of master AP configurations in a site";
        uses wireless-site-cfg:site-master-ap-config;
      }
    }
  }

  grouping site-master-ap-config {
    description
      "This structure stores the master AP configurations in a site";
    leaf ap-model {
      type string;
      description
        "This attribute represents the AP model name";
    }
    leaf ap-name {
      type string;
      description
        "This attribute represents the AP name";
    }
    leaf ap-mac-address {
      type yang:mac-address;
      description
        "This attribute represents the AP name";
    }
  }

  grouping halo-ble {
    description
      "This object represents BLE global configuration.It lists the ibeacon's identification number and attenuation value which is common to HALO enabled AP's that have joined the controller.";
    leaf beacon-id {
      type uint8 {
        range "0 .. 4";
      }
      description
        "This object represents BLE ibeacon ID for which gloabl BLE configurations to be applied.";
    }
    leaf txpower {
      type uint8 {
        range "0 .. 52";
      }
      default "0";
      description
        "This object represents TX power of particular ibeacon for HALO enabled APs that have joined the controller.The TX power is based on size of proximity zone needed.";
    }
    leaf enabled {
      type boolean;
      default "false";
      description
        "This object specifies the status of the BLE beacons. enable(1) - enable the BLE beacon disable(2) - disable the BLE beacon.";
    }
    leaf uuid {
      type string;
      default "00000000-0000-0000-0000-000000000000";
      description
        "This object represents the UUID (universally unique identifier) which is a 128-bit value";
    }
  }

  grouping st-icap-full-trace-client {
    description
      "Stores the client MAC address used in the ICap full packet trace subscription client filter";
    leaf addr {
      type yang:mac-address;
      description
        "MAC address";
    }
  }

  grouping st-icap-partial-trace-client {
    description
      "Stores the client MAC address used in the ICap partial packet trace subscription client filter";
    leaf addr {
      type yang:mac-address;
      description
        "MAC address";
    }
  }

  grouping st-icap-anomaly-det-client {
    description
      "Stores the client MAC address used in the ICap anomaly detection subscription client filter";
    leaf addr {
      type yang:mac-address;
      description
        "MAC address";
    }
  }

  grouping st-icap-client-stats-client {
    description
      "Stores the client MAC address used in the ICap client statistics subscription client filter";
    leaf addr {
      type yang:mac-address;
      description
        "MAC address";
    }
  }

  grouping ap-cfg-profile {
    description
      "This object represents the ap join profile configurations";
    leaf profile-name {
      type string;
      description
        "This object specifies the ap configuration profile name";
    }
    leaf description {
      type string;
      default "";
      description
        "This object specifies the description for the ap configuration profile";
    }
    leaf generation-id {
      type uint32;
      description
        "This object specifies the generation id for the ap configuration profile";
    }
    leaf stats-timer {
      type uint32 {
        range "0 .. 65535";
      }
      default "180";
      description
        "This object specifies the stats timer fort the AP";
    }
    leaf vlan-tagging {
      type boolean;
      default "false";
      description
        "This object specifies if vlan tagging is enabled for the AP";
    }
    leaf data-encryption-flag {
      type boolean;
      default "false";
      description
        "This object specifies the data encryption status of AP";
    }
    leaf led-state {
      type boolean;
      default "true";
      description
        "This object specifies whether the LED state of all the access points should be enabled or disabled.";
    }
    leaf shutdown {
      type boolean;
      description
        "This object allows the user to enable or disable AP radio Interface";
    }
    leaf reset-button {
      type boolean;
      default "false";
      description
        "This object specifies if reset button is enabled for the AP";
    }
    leaf console-redirect {
      type boolean;
      description
        "This object specifies if console redirect is enabled for the AP";
    }
    leaf jumbo-mtu {
      type boolean;
      default "false";
      description
        "This object specifies if jumbo mtu is enabled for the AP";
    }
    leaf link-latency-flag {
      type wireless-ap-types:enm-link-latency-type;
      default "link-auditing-disable";
      description
        "This object specifies the link auditing options";
    }
    container ap-mode {
      description
        "This object specifies the mode of operation of the AP";
      uses wireless-ap-types:st-mode;
    }
    container poe {
      description
        "This object specifies the power over ethernet configurations";
      uses wireless-ap-types:st-poe-cfg;
    }
    container device-mgmt {
      description
        "This object specifies the device management related configurations";
      uses wireless-ap-types:st-device-mgmt-cfg;
    }
    container user-mgmt {
      description
        "This object specifies the user management related configurations";
      uses wireless-ap-types:st-user-mgmt-cfg;
    }
    container tcp-mss {
      description
        "This object specifies the ipv4 tcp mss related configurations";
      uses wireless-ap-types:st-tcp-mss-cfg;
    }
    container ipv6-tcp-mss {
      description
        "This object specifies the ipv6 tcp mss configurations";
      uses wireless-ap-types:st-ipv6-tcp-mss-cfg;
    }
    container tunnel {
      description
        "This object represents the global capwap prefer-mode";
      uses wireless-ap-types:st-tunnel-cfg;
    }
    container capwap-timer {
      description
        "This object represents the capwap timer related configurations";
      uses wireless-ap-types:st-capwap-timer-cfg;
    }
    container retransmit-timer {
      description
        "This object represents the retransmit timer";
      uses wireless-ap-types:st-capwap-retransmit-timer-cfg;
    }
    container login-credentials {
      description
        "This object represents the Global AP 802.1x Supplicant Authentication login credentials";
      uses wireless-ap-types:st-login-credentials-cfg;
    }
    container dot1x-eap-type-info {
      description
        "This object represents the Global AP 802.1x EAP type info";
      uses wireless-ap-types:st-dot1x-eap-auth-info;
    }
    container lsc-ap-auth-type-info {
      description
        "This object represents the Global AP 802.1x LSC AP auth type info";
      uses wireless-ap-types:st-lsc-ap-auth-type-info;
    }
    container coredump {
      description
        "This object represents the AP core dump related configurations";
      uses wireless-ap-types:st-coredump-cfg;
    }
    container syslog {
      description
        "This object represents the AP sys log related configurations";
      uses wireless-ap-types:st-syslog-facility-cfg;
    }
    container static-config {
      description
        "This object represents the static domain name server related configurations";
      uses wireless-ap-types:st-static-domain-nameserver-cfg;
    }
    container backup-controllers {
      must "not((string-length(primary-controller-name) = 0) and (primary-controller-ip != '0.0.0.0')) " {
        error-message "Primary Controller IP can not be configured without Primary controller name";
        error-app-tag "must-violation";
      }
      must "not((string-length(secondary-controller-name) = 0) and (secondary-controller-ip != '0.0.0.0')) " {
        error-message "Secondary Controller IP can not be configured without Secondary controller name";
        error-app-tag "must-violation";
      }
      description
        "Backup controller configuration for the AP";
      uses wireless-ap-types:st-backup-controllers-cfg;
    }
    container crash-data {
      description
        "This object represents the crash data configurations for the AP";
      uses wireless-ap-types:st-crash-data-radio-cfg;
    }
    container hyperlocation {
      description
        "This object represents the hyperlocation configuration for the AP";
      uses wireless-ap-types:st-hyperlocation;
    }
    container rogue-detection {
      description
        "This object represents the rogue detection related paramters";
      uses wireless-ap-types:st-rogue-params;
    }
    leaf ntp-server {
      type inet:ip-address;
      default "0.0.0.0";
      description
        "This object represents the NTP server related configuration";
    }
    leaf oeap-disable-local-access {
      type boolean;
      default "false";
      description
        "This object specifies whether the local access is supported for all the Office Extended Access Points, joined to this controller";
    }
    container lag-info {
      description
        "This object specifies whether the ap-lag status of all the access points in the profile whether enabled or disabled.";
      uses wireless-ap-types:st-capwap-lag-info;
    }
    container qing-config {
      description
        "This object specifies the quing configurations of the AP";
      uses wireless-ap-types:st-qing-config-entry;
    }
    leaf group-nas-id {
      type string;
      default "";
      description
        "This object specifies the group NAS identifier of the AP";
    }
    leaf radio-interface-shutdown-enabled {
      type boolean;
      default "false";
      description
        "This object allows the user to enable or disable AP radio Interface";
    }
    leaf ethernet-interface-down-time {
      type uint32;
      default "0";
      description
        "This object specifies the Ethernet interface down time after which the AP radio interface will be shut down";
    }
    leaf cdp-enable {
      type boolean;
      default "true";
      description
        "This object specifies if cdp is enabled for the AP";
    }
    leaf bridging-enable {
      type boolean;
      default "false";
      description
        "This object specifies if bridging is enabled or not";
    }
    container tftp-down-grade {
      description
        "This object specifies tftp downgrade related configurations";
      uses wireless-ap-types:st-tftp-downgrade;
    }
    container traffic-limit {
      description
        "This object specifies the maximum dot1x session limit for the AP";
      uses wireless-ap-types:st-traffic-limit-cfg;
    }
    leaf ap-country-code {
      type string;
      description
        "This object specifies the country code name for the AP";
    }
    leaf ble-beacon-interval {
      type uint8 {
        range "1 .. 10";
      }
      default "1";
      description
        "This attribute specifies the BLE beacon interval for the AP";
    }
    leaf ble-beacon-advpwr {
      type uint8 {
        range "40 .. 100";
      }
      default "59";
      description
        "This attribute specifies the BLE beacon power";
    }
    leaf ap-packet-capture-profile {
      type string;
      default "";
      description
        "This attribute specifies the BLE beacon interval for the AP";
    }
    leaf ap-trace-profile {
      type string;
      default "";
      description
        "Specifies the AP trace profile name applied on the AP";
    }
    leaf mesh-profile-name {
      type string;
      default "default-mesh-profile";
      description
        "This attribute specifies the mesh profile name for the AP";
    }
    container reporting-interval {
      description
        "This attribute specifies the interval at which AP should send client stats";
      uses wireless-ap-types:st-report-interval;
    }
    leaf window-size {
      type uint16;
      default "1";
      description
        "This object specifies capwap queue window size for the AP";
    }
    container ethernet-cdp-cfgs {
      description
        "This object specifies the cdp related configurations of the AP";
      list ethernet-cdp-cfg {
        key "slot-id";
        description
          "List of cdp related configurations of the AP";
        uses wireless-site-cfg:ethernet-cdp-cfg;
      }
    }
    container dot11-cdp-cfgs {
      description
        "This object specifies the dot11 cdp related configurations of the AP";
      list dot11-cdp-cfg {
        key "slot-id";
        description
          "List of dot11 cdp related configurations of the AP";
        uses wireless-site-cfg:dot11-cdp-cfg;
      }
    }
    container halo-ble-entries {
      description
        "This object encompasses the halo ble configurations";
      list halo-ble-entry {
        key "beacon-id";
        description
          "This object encompasses the halo ble configurations";
        uses wireless-site-cfg:halo-ble;
      }
    }
    container remote-lan-ports {
      description
        "This object specifies the remote lan ports of the AP";
      list remote-lan-port {
        key "port-id";
        description
          "List of remote lan ports of the AP";
        uses wireless-site-cfg:remote-lan-port-entry;
      }
    }
    container ext-module {
      description
        "This object specifies the AP External Module related configurations";
      uses wireless-ap-types:st-ext-module-cfg;
    }
    container icap {
      description
        "Configuration of ICap subscriptions";
      uses wireless-ap-types:st-icap;
    }
    container icap-full-packet-trace-client-mac-address-entries {
      description
        "Selects the clients for which to collect traces, by client MAC address.";
      list icap-full-packet-trace-client-mac-address-entry {
        key "addr";
        description
          "Specifies the client MAC address.";
        uses wireless-site-cfg:st-icap-full-trace-client;
      }
    }
    container icap-partial-packet-trace-client-mac-address-entries {
      description
        "Selects the clients for which to collect traces, by client MAC address.";
      list icap-partial-packet-trace-client-mac-address-entry {
        key "addr";
        description
          "Specifies the client MAC address.";
        uses wireless-site-cfg:st-icap-partial-trace-client;
      }
    }
    container icap-anomaly-detection-client-mac-address-entries {
      description
        "Selects the clients for which to collect traces, by client MAC address.";
      list icap-anomaly-detection-client-mac-address-entry {
        key "addr";
        description
          "Specifies the client MAC address.";
        uses wireless-site-cfg:st-icap-anomaly-det-client;
      }
    }
    container icap-client-statistics-client-mac-address-entries {
      description
        "Selects the clients for which to collect statistics, by client MAC address.";
      list icap-client-statistics-client-mac-address-entry {
        key "addr";
        description
          "Specifies the client MAC address.";
        uses wireless-site-cfg:st-icap-client-stats-client;
      }
    }
    container lawful-interception {
      description
        "This object specifies the Lawful Interception related configurations";
      uses wireless-ap-types:st-lawful-interception-cfg;
    }
    container persistent-ssid-broadcast {
      description
        "This object specifies whether pesistent SSID broadcast is enabled on the AP";
      uses wireless-ap-types:st-persistent-ssid-broadcast-cfg;
    }
    container usb-module-status {
      description
        "Status of USB configuration if disabled/enabled";
      uses wireless-ap-types:st-usb-module-cfg;
    }
  }

  grouping remote-lan-port-entry {
    description
      "This attribute specifies the remote lan port entry of the AP";
    leaf port-id {
      type uint32;
      description
        "This attribute specifies the port id of the AP";
    }
    leaf poe {
      type boolean;
      default "false";
      description
        "This attribute specifies the power over ethernet specifications of the AP";
    }
    leaf shutdown {
      type boolean;
      default "false";
      description
        "This object allows the user to enable or disable AP radio Interface";
    }
    leaf remote-lan-name {
      type string;
      default "None";
      description
        "This attribute specifies the remote LAN name of the AP";
    }
  }

  grouping ethernet-cdp-cfg {
    description
      "This object specifies the ethernet cdp configuration";
    leaf generation-id {
      type uint32;
      description
        "This object specifies the generation id";
    }
    leaf slot-id {
      type wireless-enum-types:slot-id-type;
      description
        "This attribute specifies the slot id of the ethernet cdp configuration";
    }
    leaf cdp-flag {
      type boolean;
      default "false";
      description
        "This attribute specifies the cdp flag of the ethernet cdp configuration";
    }
  }

  grouping dot11-cdp-cfg {
    description
      "This object specifies the dot11 cdp configuration";
    leaf generation-id {
      type uint32;
      description
        "This object specifies the dot11 generation id";
    }
    leaf slot-id {
      type wireless-enum-types:slot-id-type;
      description
        "This attribute specifies the slot id of the dot11 cdp configuration";
    }
    leaf cdp-flag {
      type boolean;
      default "false";
      description
        "This attribute specifies the cdp flag of the dot11 cdp configuration";
    }
  }

  grouping ap-packet-capture-profile {
    description
      "This object encompasses the packet capture profile configurations of an AP";
    leaf profile-name {
      type string;
      description
        "This attrbute represent the profile name of the packet capture profile";
    }
    leaf description {
      type string;
      description
        "This attrbute represent the description of the packet capture profile";
    }
    leaf buffer-size {
      type uint16 {
        range "1024 .. 4096";
      }
      default "2048";
      description
        "This object specifies the size of the buffer Access Point should use to copy the captured packets for client and dump it to the FTP server. Default value is 2048 kilobytes";
    }
    leaf duration {
      type uint16 {
        range "1 .. 60";
      }
      default "10";
      description
        "This object specifies the duration for which the Access Point should capture packets for specified client. Default value is 10";
    }
    leaf truncate-len {
      type uint16 {
        range "0 .. 1500";
      }
      default "0";
      description
        "This object specifies the length of the packet after truncation while capturing packets on the Access Point. Default value is 0 which indictaes captured packet should contain the full payload length";
    }
    leaf ftp-server-ip {
      type inet:ip-address;
      default "0.0.0.0";
      description
        "This object specifies the IP Address of the FTP server. Access Point will dump the captured packets to a file in this ftp server";
    }
    leaf ftp-path {
      type string;
      default "";
      description
        "This object specifies the directory path in the ftp server for storing the file which contains the captured packets in the Access Point.";
    }
    leaf ftp-username {
      type string;
      default "";
      description
        "This object specifies the username to login into the ftp server in order to transfer the captured packets from the Access Point.";
    }
    leaf ftp-password {
      type string;
      default "";
      description
        "This object specifies the password to login into the ftp server in order to transfer the captured packets from the Access Point.";
    }
    leaf ftp-password-type {
      type wireless-enum-types:crypt-type;
      default "clear";
      description
        "This object specifies the password type to login into the ftp server in order to transfer the captured packets from the Access Point.";
    }
    leaf classifier-control {
      type boolean;
      default "true";
      description
        "This object specifies the filters for 802.11 control packets, while capturing packets on the Access Point. A value of 'true' indicates 802.11 control packets should be captured. A value of 'false' indicates 802.11 control packets should not be captured. Default value is true";
    }
    leaf classifier-management {
      type boolean;
      default "true";
      description
        "This object specifies the filters for 802.11 Management packets, while capturing packets on the Access Point. A value of 'true' indicates 802.11 Management packets should be captured. A value of 'false' indicates 802.11 Management packets should not be captured. Default value is true";
    }
    leaf classifier-data {
      type boolean;
      default "false";
      description
        "This object specifies the filters for 802.11 Data packets, while capturing packets on the Access Point. A value of 'true' indicates 802.11 Data packets should be captured. A value of 'false' indicates 802.11 Data packets should not be captured. Default value is false";
    }
    leaf classifier-dot1x {
      type boolean;
      default "false";
      description
        "This object specifies the filters for 802.11 Dot1x packets, while capturing packets on the Access Point. A value of 'true' indicates 802.11 Dot1x packets should be captured. A value of 'false' indicates 802.11 Dot1x packets should not be captured. Default value is false";
    }
    leaf classifier-arp {
      type boolean;
      default "false";
      description
        "This object specifies the filters for ARP packets while capturing packets on the Access Point. A value of 'true' indicates ARP packets should be captured. A value of 'false' indicates ARP packets should not be captured.Default value is false";
    }
    leaf classifier-iapp {
      type boolean;
      default "false";
      description
        "This object specifies the filters for 802.11 IAPP packets, while capturing packets on the Access Point. A value of 'true' indicates IAPP packets should be captured. A value of 'false' indicates IAPP packets should not be captured. Default value is false";
    }
    leaf classifier-ip {
      type boolean;
      default "false";
      description
        "This object specifies the filters for IP packets, while capturing packets on the Access Point. A value of ' true' indicates IP packets should be captured. A value of false' indicates IP packets should not be captured. Default value is false";
    }
    leaf classifier-tcp {
      type boolean;
      default "false";
      description
        "This object specifies the filters for TCP packets while capturing packets on the Access Point. Value of 'true' indicates IP packets should be captured. Value of 'false' indicates IP packets should not be captured. Default value is false";
    }
    leaf classifier-tcp-port {
      type uint16 {
        range "0 .. 65535";
      }
      default "0";
      description
        "This object specifies the filters for TCP packets, while capturing packets on the Access Point Value of 'true' indicates IP packets should be captured. Value of 'false' indicates IP packets should not be captured. Default value is false";
    }
    leaf classifier-udp {
      type boolean;
      default "false";
      description
        "This object specifies the filters for TCP packets, while capturing packets on the Access Point. Value of 'true' indicates IP packets should be captured. Value of 'false' indicates IP packets should not be captured. Default value is fals";
    }
    leaf classifier-udp-port {
      type uint16 {
        range "0 .. 65535";
      }
      default "0";
      description
        "This object specifies the filter value port number for UDP packets, while capturing packets on the Access Point. Default value is 0 which indicates all UDP packets should be captured";
    }
    leaf classifier-broadcast {
      type boolean;
      default "false";
      description
        "This object specifies the filters for 802.11 Broadcast packets, while capturing packets on the Access Point. A value of 'true' indicates Broadcast packets should be captured.A value of 'false' indicates Broadcast packets should not be captured. Default value is false";
    }
    leaf classifier-multicast {
      type boolean;
      default "false";
      description
        "This object specifies the filters for 802.11 Multicast packets, while capturing packets on the Access Point. A value of 'true' indicates Multicast packets should be captured. A value of 'false' indicates Multicast packets should not be captured. Default value is false";
    }
  }

  grouping ap-trace-profile {
    description
      "Trace profile configuration of the AP";
    leaf profile-name {
      type string;
      description
        "Trace profile name of the AP";
    }
    leaf description {
      type string;
      description
        "Description of the AP trace profile";
    }
    leaf ap-trace-client-console-log {
      type boolean;
      default "false";
      description
        "Flag to enable console logs at the AP";
    }
    leaf ap-trace-client-filter-arp {
      type boolean;
      default "false";
      description
        "Trace filter to enable client's ARP packets tracing at the AP";
    }
    leaf ap-trace-client-filter-assoc {
      type boolean;
      default "false";
      description
        "Trace filter to enable client's association packets tracing at the AP";
    }
    leaf ap-trace-client-filter-auth {
      type boolean;
      default "false";
      description
        "Trace filter to enable client's authentication packets at the AP";
    }
    leaf ap-trace-client-filter-dhcp {
      type boolean;
      default "false";
      description
        "Trace filter to enable client's DHCP packets tracing at the AP";
    }
    leaf ap-trace-client-filter-eap {
      type boolean;
      default "false";
      description
        "Trace filter to enable client's EAP packets tracing at the AP";
    }
    leaf ap-trace-client-filter-icmp {
      type boolean;
      default "false";
      description
        "Trace filter to enable client's ICMP packets tracing at the AP";
    }
    leaf ap-trace-client-filter-ndp {
      type boolean;
      default "false";
      description
        "Trace filter to enable client's NDP packets tracing at the AP";
    }
    leaf ap-trace-client-filter-probe {
      type boolean;
      default "false";
      description
        "Trace filter to enable client's probe packets tracing at the AP";
    }
  }

  container site-cfg-data {
    description
      "Yang model for site related config";
    container ap-cfg-profiles {
      description
        "This object encompasses the ap config profile";
      list ap-cfg-profile {
        key "profile-name";
        description
          "List of AP config profiles";
        uses wireless-site-cfg:ap-cfg-profile;
      }
    }
    container ap-packet-capture-profiles {
      description
        "AP packet capture profile configuration";
      list ap-packet-capture-profile {
        key "profile-name";
        description
          "List of AP packet capture profiles";
        uses wireless-site-cfg:ap-packet-capture-profile;
      }
    }
    container ap-trace-profiles {
      description
        "AP trace profile configuration";
      list ap-trace-profile {
        key "profile-name";
        description
          "List of AP trace capture profiles";
        uses wireless-site-cfg:ap-trace-profile;
      }
    }
    container site-tag-configs {
      description
        "Site tag configuration";
      list site-tag-config {
        key "site-tag-name";
        description
          "List of site tag configurations";
        uses wireless-site-cfg:site-tag-config;
      }
    }
  }
}
