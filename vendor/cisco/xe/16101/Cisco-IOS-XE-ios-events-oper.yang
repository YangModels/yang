module Cisco-IOS-XE-ios-events-oper {
  yang-version 1;
  namespace "http://cisco.com/ns/yang/Cisco-IOS-XE-ios-events-oper";
  prefix ios-events-ios-xe-oper;

  import Cisco-IOS-XE-utd-common-oper {
    prefix utd-common-ios-xe-oper;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for asynchronous events from network element.
     Copyright (c) 2016-2018 by Cisco Systems, Inc.
     All rights reserved.";

  revision 2018-07-03 {
    description
      "- Added new notification for Radius sever state event
       - Change of notification names";
    reference "2.0.0";
  }
  revision 2017-10-10 {
    description
      "Initial revision";
    reference "1.0.0";
  }

  typedef notification-severity {
    type enumeration {
      enum "critical" {
        value 0;
      }
      enum "major" {
        value 1;
      }
      enum "minor" {
        value 2;
      }
    }
    description
      "Notification severity";
  }

  typedef bgp-pstate {
    type enumeration {
      enum "bgp-state-idle" {
        value 0;
      }
      enum "bgp-state-connect" {
        value 1;
      }
      enum "bgp-state-active" {
        value 2;
      }
      enum "bgp-state-opensent" {
        value 3;
      }
      enum "bgp-state-openconfirm" {
        value 4;
      }
      enum "bgp-state-established" {
        value 5;
      }
      enum "bgp-state-clearing" {
        value 6;
      }
      enum "bgp-state-deleted" {
        value 7;
      }
    }
    description
      "GGP state";
  }

  typedef notification-failure-state {
    type enumeration {
      enum "notf-failure-state-ok" {
        value 0;
        description
          "Notification failure state ok";
      }
      enum "notf-failure-state-failed" {
        value 1;
        description
          "Notification failure state failed";
      }
    }
    description
      "Notification failure state";
  }

  typedef hardware-sensor-type {
    type enumeration {
      enum "hw-sensor-board" {
        value 0;
        description
          "Hardware sensor board";
      }
      enum "hw-sensor-cpu-junction" {
        value 1;
        description
          "Hardware sensor CPU junction";
      }
      enum "hw-sensor-dram" {
        value 2;
        description
          "Hardware sensor DRAM";
      }
      enum "hw-sensor-pim" {
        value 3;
        description
          "Hardware sensor PIM";
      }
    }
    description
      "Hardware Sensor Type";
  }

  typedef notification-sensor-state {
    type enumeration {
      enum "sensor-state-green" {
        value 0;
        description
          "Sensor state green";
      }
      enum "sensor-state-yellow" {
        value 1;
        description
          "Sensor state yellow";
      }
      enum "sensor-state-red" {
        value 2;
        description
          "Sensor state red";
      }
    }
    description
      "Notification sensor state";
  }

  typedef notification-module-state {
    type enumeration {
      enum "notf-module-state-inserted" {
        value 0;
        description
          "Notification module inserted state";
      }
      enum "notf-module-state-removed" {
        value 1;
        description
          "Notification module removed state";
      }
    }
    description
      "Notification module state";
  }

  typedef interface-notif-state {
    type enumeration {
      enum "interface-notif-state-up" {
        value 0;
      }
      enum "interface-notif-state-down" {
        value 1;
      }
    }
    description
      "Interface Notification state";
  }

  typedef ospf-nbr-state {
    type enumeration {
      enum "ospf-nbr-down" {
        value 0;
      }
      enum "ospf-nbr-attempt" {
        value 1;
      }
      enum "ospf-nbr-init" {
        value 2;
      }
      enum "ospf-nbr-two-way" {
        value 3;
      }
      enum "ospf-nbr-exstart" {
        value 4;
      }
      enum "ospf-nbr-exchange" {
        value 5;
      }
      enum "ospf-nbr-loading" {
        value 6;
      }
      enum "ospf-nbr-full" {
        value 7;
      }
      enum "ospf-nbr-deleted" {
        value 8;
      }
      enum "ospf-nbr-depend-upon" {
        value 9;
      }
    }
    description
      "OSPF neighbor states";
  }

  typedef ospf-intf-state {
    type enumeration {
      enum "ospf-ifs-down" {
        value 0;
      }
      enum "ospf-ifs-loopback" {
        value 1;
      }
      enum "ospf-ifs-waiting" {
        value 2;
      }
      enum "ospf-ifs-point-to-m-point" {
        value 3;
      }
      enum "ospf-ifs-point-to-point" {
        value 4;
      }
      enum "ospf-ifs-dr" {
        value 5;
      }
      enum "ospf-ifs-backup" {
        value 6;
      }
      enum "ospf-ifs-dr-other" {
        value 7;
      }
      enum "ospf-ifs-depend-upon" {
        value 8;
      }
    }
    description
      "OSPF interface states";
  }

  typedef intf-admin-state {
    type enumeration {
      enum "up" {
        value 0;
      }
      enum "down" {
        value 1;
      }
    }
    description
      "Interface admin state";
  }

  typedef dhcp-server-state-val {
    type enumeration {
      enum "dhcp-server-state-up" {
        value 0;
      }
      enum "dhcp-server-state-down" {
        value 1;
      }
    }
    description
      "DHCP Server state";
  }

  typedef vrrp-ip-addr-type {
    type enumeration {
      enum "vrrp-undefined" {
        value 0;
      }
      enum "vrrp-ipv4-address" {
        value 1;
      }
      enum "vrrp-ipv6-address" {
        value 2;
      }
    }
    description
      "IP Address type";
  }

  typedef vrrp-notif-proto-state {
    type enumeration {
      enum "vrrp-notif-init" {
        value 1;
      }
      enum "vrrp-notif-backup" {
        value 2;
      }
      enum "vrrp-notif-master" {
        value 3;
      }
      enum "vrrp-notif-recover" {
        value 4;
      }
    }
    description
      "VRRP protocol state";
  }

  typedef fib-updates-af-type {
    type enumeration {
      enum "fib-updates-af-unknown" {
        value 0;
      }
      enum "fib-updates-af-ipv4" {
        value 1;
      }
      enum "fib-updates-af-ipv6" {
        value 2;
      }
    }
    description
      "FIB updates AF type";
  }

  typedef utd-ips-alert-action-val {
    type enumeration {
      enum "utd-ips-alert-action-unknown" {
        value 0;
        description
          "Unified Threat Defense (UTD) Intrusion Prevention System (IPS) alert action is unknown";
      }
      enum "utd-ips-alert-action-alert" {
        value 1;
        description
          "Unified Threat Defense (UTD) Intrusion Prevention System (IPS) alert action generated an alert";
      }
      enum "utd-ips-alert-action-drop" {
        value 2;
        description
          "Unified Threat Defense (UTD) Intrusion Prevention System (IPS) alert action resulted in a drop";
      }
      enum "utd-ips-alert-action-wdrop" {
        value 3;
        description
          "Unified Threat Defense (UTD) Intrusion Prevention System (IPS) alert action would have resulted in a drop if running in IPS mode";
      }
    }
    description
      "Unified Threat Defense (UTD) Intrusion Prevention System (IPS) alert action";
  }

  typedef utd-ips-alert-classification-val {
    type enumeration {
      enum "utd-ips-alert-classification-none" {
        value 0;
        description
          "Unified Threat Defense (UTD) Intrusion Prevention System (IPS) alert classification is not set";
      }
      enum "utd-ips-alert-classification-not-suspicious" {
        value 1;
        description
          "Unified Threat Defense (UTD) Intrusion Prevention System (IPS) alert classification is not suspicious traffic";
      }
      enum "utd-ips-alert-classification-unknown" {
        value 2;
        description
          "Unified Threat Defense (UTD) Intrusion Prevention System (IPS) alert classification is unknown traffic";
      }
      enum "utd-ips-alert-classification-bad-unknown" {
        value 3;
        description
          "Unified Threat Defense (UTD) Intrusion Prevention System (IPS) alert classification is potentially bad traffic";
      }
      enum "utd-ips-alert-classification-attempted-recon" {
        value 4;
        description
          "Unified Threat Defense (UTD) Intrusion Prevention System (IPS) alert classification is attempted information leak";
      }
      enum "utd-ips-alert-classification-successful-recon-limited" {
        value 5;
        description
          "Unified Threat Defense (UTD) Intrusion Prevention System (IPS) alert classification is information leak";
      }
      enum "utd-ips-alert-classification-successful-recon-largescale" {
        value 6;
        description
          "Unified Threat Defense (UTD) Intrusion Prevention System (IPS) alert classification is large scale information leak";
      }
      enum "utd-ips-alert-classification-attempted-dos" {
        value 7;
        description
          "Unified Threat Defense (UTD) Intrusion Prevention System (IPS) alert classification is attempted denial of service";
      }
      enum "utd-ips-alert-classification-successful-dos" {
        value 8;
        description
          "Unified Threat Defense (UTD) Intrusion Prevention System (IPS) alert classification is denial of service";
      }
      enum "utd-ips-alert-classification-attempted-user" {
        value 9;
        description
          "Unified Threat Defense (UTD) Intrusion Prevention System (IPS) alert classification is attempted user privilege gain";
      }
      enum "utd-ips-alert-classification-unsuccessful-user" {
        value 10;
        description
          "Unified Threat Defense (UTD) Intrusion Prevention System (IPS) alert classification is unsuccessful user privilege gain";
      }
      enum "utd-ips-alert-classification-successful-user" {
        value 11;
        description
          "Unified Threat Defense (UTD) Intrusion Prevention System (IPS) alert classification is successful user privilege gain";
      }
      enum "utd-ips-alert-classification-attempted-admin" {
        value 12;
        description
          "Unified Threat Defense (UTD) Intrusion Prevention System (IPS) alert classification is attempted administrator privilege gain";
      }
      enum "utd-ips-alert-classification-successful-admin" {
        value 13;
        description
          "Unified Threat Defense (UTD) Intrusion Prevention System (IPS) alert classification is successful administrator privilege gain";
      }
      enum "utd-ips-alert-classification-rpc-portmap-decode" {
        value 14;
        description
          "Unified Threat Defense (UTD) Intrusion Prevention System (IPS) alert classification is decode of an rpc query";
      }
      enum "utd-ips-alert-classification-shellcode-detect" {
        value 15;
        description
          "Unified Threat Defense (UTD) Intrusion Prevention System (IPS) alert classification is executable code was detected";
      }
      enum "utd-ips-alert-classification-string-detect" {
        value 16;
        description
          "Unified Threat Defense (UTD) Intrusion Prevention System (IPS) alert classification is a suspicious string was detected";
      }
      enum "utd-ips-alert-classification-suspicious-filename-detect" {
        value 17;
        description
          "Unified Threat Defense (UTD) Intrusion Prevention System (IPS) alert classification is a suspicious filename was detected";
      }
      enum "utd-ips-alert-classification-suspicious-login" {
        value 18;
        description
          "Unified Threat Defense (UTD) Intrusion Prevention System (IPS) alert classification is an attempted login using a suspicious username was detected";
      }
      enum "utd-ips-alert-classification-system-call-detect" {
        value 19;
        description
          "Unified Threat Defense (UTD) Intrusion Prevention System (IPS) alert classification is a system call was detected";
      }
      enum "utd-ips-alert-classification-tcp-connection" {
        value 20;
        description
          "Unified Threat Defense (UTD) Intrusion Prevention System (IPS) alert classification is a tcp connection was detected";
      }
      enum "utd-ips-alert-classification-trojan-activity" {
        value 21;
        description
          "Unified Threat Defense (UTD) Intrusion Prevention System (IPS) alert classification is a network trojan was detected";
      }
      enum "utd-ips-alert-classification-unusual-client-port-connection" {
        value 22;
        description
          "Unified Threat Defense (UTD) Intrusion Prevention System (IPS) alert classification is a client was using an unusual port";
      }
      enum "utd-ips-alert-classification-network-scan" {
        value 23;
        description
          "Unified Threat Defense (UTD) Intrusion Prevention System (IPS) alert classification is detection of a network scan";
      }
      enum "utd-ips-alert-classification-denial-of-service" {
        value 24;
        description
          "Unified Threat Defense (UTD) Intrusion Prevention System (IPS) alert classification is detection of a denial of service attack";
      }
      enum "utd-ips-alert-classification-non-standard-protocol" {
        value 25;
        description
          "Unified Threat Defense (UTD) Intrusion Prevention System (IPS) alert classification is detection of a non-standard protocol or event";
      }
      enum "utd-ips-alert-classification-protocol-command-decode" {
        value 26;
        description
          "Unified Threat Defense (UTD) Intrusion Prevention System (IPS) alert classification is generic protocol command decode";
      }
      enum "utd-ips-alert-classification-web-application-activity" {
        value 27;
        description
          "Unified Threat Defense (UTD) Intrusion Prevention System (IPS) alert classification is access to a potentially vulnerable web application";
      }
      enum "utd-ips-alert-classification-web-application-attack" {
        value 28;
        description
          "Unified Threat Defense (UTD) Intrusion Prevention System (IPS) alert classification is web application attack";
      }
      enum "utd-ips-alert-classification-misc-activity" {
        value 29;
        description
          "Unified Threat Defense (UTD) Intrusion Prevention System (IPS) alert classification is misc activity";
      }
      enum "utd-ips-alert-classification-misc-attack" {
        value 30;
        description
          "Unified Threat Defense (UTD) Intrusion Prevention System (IPS) alert classification is misc attack";
      }
      enum "utd-ips-alert-classification-icmp-event" {
        value 31;
        description
          "Unified Threat Defense (UTD) Intrusion Prevention System (IPS) alert classification is generic icmp event";
      }
      enum "utd-ips-alert-classification-inappropriate-content" {
        value 32;
        description
          "Unified Threat Defense (UTD) Intrusion Prevention System (IPS) alert classification is inappropriate content was detected";
      }
      enum "utd-ips-alert-classification-policy-violation" {
        value 33;
        description
          "Unified Threat Defense (UTD) Intrusion Prevention System (IPS) alert classification is potential corporate privacy violation";
      }
      enum "utd-ips-alert-classification-default-login-attempt" {
        value 34;
        description
          "Unified Threat Defense (UTD) Intrusion Prevention System (IPS) alert classification is attempt to login by a default username and password";
      }
      enum "utd-ips-alert-classification-sdf" {
        value 35;
        description
          "Unified Threat Defense (UTD) Intrusion Prevention System (IPS) alert classification is senstive data";
      }
      enum "utd-ips-alert-classification-file-format" {
        value 36;
        description
          "Unified Threat Defense (UTD) Intrusion Prevention System (IPS) alert classification is known malicious file or file based exploit";
      }
      enum "utd-ips-alert-classification-malware-cnc" {
        value 37;
        description
          "Unified Threat Defense (UTD) Intrusion Prevention System (IPS) alert classification is known malware command and control traffic";
      }
      enum "utd-ips-alert-classification-client-side-exploit" {
        value 38;
        description
          "Unified Threat Defense (UTD) Intrusion Prevention System (IPS) alert classification is known client side exploit attempt";
      }
    }
    description
      "Unified Threat Defense (UTD) Intrusion Prevention System (IPS) alert classification";
  }

  typedef utd-ips-alert-priority-val {
    type enumeration {
      enum "utd-ips-alert-priority-unknown" {
        value 0;
        description
          "Unified Threat Defense (UTD) Intrusion Prevention System (IPS) alert priority is unknown";
      }
      enum "utd-ips-alert-priority-emerg" {
        value 1;
        description
          "Unified Threat Defense (UTD) Intrusion Prevention System (IPS) alert priority is emergency";
      }
      enum "utd-ips-alert-priority-alert" {
        value 2;
        description
          "Unified Threat Defense (UTD) Intrusion Prevention System (IPS) alert priority is alert";
      }
      enum "utd-ips-alert-priority-crit" {
        value 3;
        description
          "Unified Threat Defense (UTD) Intrusion Prevention System (IPS) alert priority is critical";
      }
      enum "utd-ips-alert-priority-error" {
        value 4;
        description
          "Unified Threat Defense (UTD) Intrusion Prevention System (IPS) alert priority is error";
      }
      enum "utd-ips-alert-priority-warn" {
        value 5;
        description
          "Unified Threat Defense (UTD) Intrusion Prevention System (IPS) alert priority is warning";
      }
      enum "utd-ips-alert-priority-notice" {
        value 6;
        description
          "Unified Threat Defense (UTD) Intrusion Prevention System (IPS) alert priority is notice";
      }
      enum "utd-ips-alert-priority-info" {
        value 7;
        description
          "Unified Threat Defense (UTD) Intrusion Prevention System (IPS) alert priority is info";
      }
      enum "utd-ips-alert-priority-debug" {
        value 8;
        description
          "Unified Threat Defense (UTD) Intrusion Prevention System (IPS) alert priority is debug";
      }
    }
    description
      "Unified Threat Defense (UTD) Intrusion Prevention System (IPS) alert priority";
  }

  typedef utd-update-type-val {
    type enumeration {
      enum "utd-update-type-unknown" {
        value 0;
        description
          "Unified Threat Defense (UTD) update type is unknown";
      }
      enum "utd-update-type-ips" {
        value 1;
        description
          "Unified Threat Defense (UTD) update is an IPS signature package update";
      }
      enum "utd-update-type-urlf" {
        value 2;
        description
          "Unified Threat Defense (UTD) update is a URL-Filtering DB update";
      }
    }
    description
      "Unified Threat Defense (UTD) update type";
  }

  typedef bridge-state-val {
    type enumeration {
      enum "bridge-creation" {
        value 0;
        description
          "Bridge is created";
      }
      enum "bridge-deletion" {
        value 1;
        description
          "Bridge is deleted";
      }
    }
    description
      "Bridge state update";
  }

  grouping bgp-peer-state {
    description
      "BGP peer state";
    leaf severity-level {
      type ios-events-ios-xe-oper:notification-severity;
      description
        "Event severity";
    }
    leaf host-name {
      type string;
      description
        "Host name";
    }
    leaf system-ip {
      type inet:ip-address;
      description
        "IP address";
    }
    leaf vrf-name {
      type string;
      description
        "VRF name";
    }
    leaf peer {
      type inet:ip-address;
      description
        "Peer IP address";
    }
    leaf bgp-new-state {
      type ios-events-ios-xe-oper:bgp-pstate;
      description
        "New BGP state";
    }
    leaf local-address {
      type inet:ip-address;
      description
        "Local IP address";
    }
    leaf local-routerid {
      type inet:ip-address;
      description
        "Local router ID";
    }
    leaf peer-routerid {
      type inet:ip-address;
      description
        "Peer router ID";
    }
  }

  grouping ospf-neighbor-state {
    description
      "OSPF neighbor state";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF Name";
    }
    leaf neighbor {
      type inet:ip-address;
      description
        "Neighbor IP address";
    }
    leaf router-id {
      type inet:ip-address;
      description
        "Router ID";
    }
    leaf if-addr {
      type inet:ip-address;
      description
        "Interface address";
    }
    leaf ospf-new-state {
      type ios-events-ios-xe-oper:ospf-nbr-state;
      description
        "New OSPF state";
    }
  }

  grouping ospf-interface-state {
    description
      "OSPF interface state";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf interface {
      type string;
      description
        "Interface name";
    }
    leaf ospf-interface-new-state {
      type ios-events-ios-xe-oper:ospf-intf-state;
      description
        "New OSPF interface state";
    }
  }

  grouping interface-oper-state {
    description
      "Interface operational state";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "Interface name";
    }
    leaf new-state {
      type ios-events-ios-xe-oper:interface-notif-state;
      description
        "Is the new state up or down";
    }
  }

  grouping memory-usage {
    description
      "Memory usage";
    leaf severity-level {
      type ios-events-ios-xe-oper:notification-severity;
      description
        "Event severity";
    }
    leaf host-name {
      type string;
      description
        "Host name";
    }
    leaf system-ip {
      type inet:ip-address;
      description
        "System IP address";
    }
    leaf warning {
      type string;
      description
        "Memory usage level warning";
    }
    leaf total-mb {
      type uint32;
      description
        "Total memory in megabytes";
    }
    leaf free-mb {
      type uint32;
      description
        "Free memory in megabytes";
    }
  }

  grouping cpu-usage {
    description
      "CPU usage";
    leaf severity-level {
      type ios-events-ios-xe-oper:notification-severity;
      description
        "Event severity";
    }
    leaf host-name {
      type string;
      description
        "Host name";
    }
    leaf system-ip {
      type inet:ip-address;
      description
        "System IP address";
    }
    leaf warning {
      type string;
      description
        "CPU usage warning";
    }
    leaf one-min {
      type uint32;
      description
        "CPU average load (one min)";
    }
    leaf five-min {
      type uint32;
      description
        "CPU average load (five min)";
    }
    leaf fifteen-min {
      type uint32;
      description
        "CPU average load (fifteen min)";
    }
  }

  grouping interface-admin-state {
    description
      "Interface admin state";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "Interface name";
    }
    leaf new-admin-state {
      type ios-events-ios-xe-oper:intf-admin-state;
      description
        "New interface admin state";
    }
  }

  grouping dhcp-server-state {
    description
      "DHCP server state";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "Interface name";
    }
    leaf state {
      type ios-events-ios-xe-oper:dhcp-server-state-val;
      description
        "Is the new state up (true for UP)";
    }
  }

  grouping dhcp-address-assigned {
    description
      "DHCP address assigned";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "interface name";
    }
    leaf client-mac {
      type string;
      description
        "Client mac";
    }
    leaf ip {
      type inet:ip-address;
      description
        "Client ip address assigned";
    }
  }

  grouping dhcp-address-renewed {
    description
      "DHCP address renewed";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "interface name";
    }
    leaf client-mac {
      type string;
      description
        "Client mac";
    }
    leaf ip {
      type inet:ip-address;
      description
        "Client ip address renewed";
    }
  }

  grouping dhcp-address-released {
    description
      "DHCP address released";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "interface name";
    }
    leaf client-mac {
      type string;
      description
        "Client mac";
    }
    leaf ip {
      type inet:ip-address;
      description
        "Client ip address released";
    }
    leaf reason {
      type string;
      description
        "Reason for release";
    }
  }

  grouping dhcp-address-rejected {
    description
      "DHCP address rejected";
    leaf severity-level {
      type ios-events-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf if-name {
      type string;
      description
        "interface name";
    }
    leaf client-mac {
      type string;
      description
        "Client mac";
    }
    leaf ip {
      type inet:ip-address;
      description
        "Client ip address rejected";
    }
    leaf reason {
      type string;
      description
        "Reason for rejection";
    }
  }

  grouping system-reboot-issued {
    description
      "System reboot issued";
    leaf severity-level {
      type ios-events-ios-xe-oper:notification-severity;
      description
        "Event severity";
    }
    leaf host-name {
      type string;
      description
        "Host name";
    }
    leaf system-ip {
      type inet:ip-address;
      description
        "System IP address";
    }
    leaf reboot-reason {
      type string;
      description
        "System reboot reason";
    }
  }

  grouping system-reboot-complete {
    description
      "System reboot complete";
    leaf severity-level {
      type ios-events-ios-xe-oper:notification-severity;
      description
        "Event severity";
    }
    leaf host-name {
      type string;
      description
        "Host name";
    }
    leaf system-ip {
      type inet:ip-address;
      description
        "System IP address";
    }
  }

  grouping disk-usage {
    description
      "Disk usage";
    leaf severity-level {
      type ios-events-ios-xe-oper:notification-severity;
      description
        "Event severity";
    }
    leaf host-name {
      type string;
      description
        "Host name";
    }
    leaf system-ip {
      type inet:ip-address;
      description
        "System IP address";
    }
    leaf warning {
      type string;
      description
        "Disk usage level warning";
    }
    leaf total-mb {
      type uint32;
      description
        "Total memory in megabytes";
    }
    leaf free-mb {
      type uint32;
      description
        "Free memory in megabytes";
    }
  }

  grouping flash-fault {
    description
      "Flash fault";
    leaf severity-level {
      type ios-events-ios-xe-oper:notification-severity;
      description
        "Event severity";
    }
    leaf host-name {
      type string;
      description
        "Host name";
    }
    leaf system-ip {
      type inet:ip-address;
      description
        "System IP address";
    }
    leaf new-state {
      type ios-events-ios-xe-oper:notification-failure-state;
      description
        "New flash fault state";
    }
  }

  grouping emmc-fault {
    description
      "Emmc fault";
    leaf severity-level {
      type ios-events-ios-xe-oper:notification-severity;
      description
        "Event severity";
    }
    leaf host-name {
      type string;
      description
        "Host name";
    }
    leaf system-ip {
      type inet:ip-address;
      description
        "System IP address";
    }
    leaf new-state {
      type ios-events-ios-xe-oper:notification-failure-state;
      description
        "New emmc fault state";
    }
  }

  grouping sdcard-fault {
    description
      "SD card fault";
    leaf severity-level {
      type ios-events-ios-xe-oper:notification-severity;
      description
        "Event severity";
    }
    leaf host-name {
      type string;
      description
        "Host name";
    }
    leaf system-ip {
      type inet:ip-address;
      description
        "System IP address";
    }
    leaf new-state {
      type ios-events-ios-xe-oper:notification-failure-state;
      description
        "New sdcard fault state";
    }
  }

  grouping tempsensor-fault {
    description
      "Tempsensor fault";
    leaf severity-level {
      type ios-events-ios-xe-oper:notification-severity;
      description
        "Event severity";
    }
    leaf host-name {
      type string;
      description
        "Host name";
    }
    leaf system-ip {
      type inet:ip-address;
      description
        "System IP address";
    }
    leaf hw-sensor-type {
      type ios-events-ios-xe-oper:hardware-sensor-type;
      description
        "HW sensor type";
    }
    leaf hw-dev-index {
      type uint32;
      description
        "HW device index";
    }
    leaf name {
      type string;
      description
        "Temp sensor fault";
    }
    leaf new-state {
      type ios-events-ios-xe-oper:notification-failure-state;
      description
        "New temp sensor state";
    }
  }

  grouping tempsensor-state {
    description
      "Tempsensor state";
    leaf severity-level {
      type ios-events-ios-xe-oper:notification-severity;
      description
        "Event severity";
    }
    leaf host-name {
      type string;
      description
        "Host name";
    }
    leaf system-ip {
      type inet:ip-address;
      description
        "System IP address";
    }
    leaf hw-sensor-type {
      type ios-events-ios-xe-oper:hardware-sensor-type;
      description
        "HW sensor type";
    }
    leaf hw-dev-index {
      type uint32;
      description
        "HW device index";
    }
    leaf name {
      type string;
      description
        "Tempsensor state";
    }
    leaf temp {
      type uint32;
      description
        "temprature";
    }
    leaf sensor-new-state {
      type ios-events-ios-xe-oper:notification-sensor-state;
      description
        "Sensor new state";
    }
  }

  grouping fan-fault {
    description
      "Fan fault";
    leaf severity-level {
      type ios-events-ios-xe-oper:notification-severity;
      description
        "Event severity";
    }
    leaf host-name {
      type string;
      description
        "Host name";
    }
    leaf system-ip {
      type inet:ip-address;
      description
        "System IP address";
    }
    leaf fantray-id {
      type uint32;
      description
        "Fan tray id";
    }
    leaf fan-id {
      type uint32;
      description
        "Fan id";
    }
    leaf new-state {
      type ios-events-ios-xe-oper:notification-failure-state;
      description
        "New fan fault state";
    }
  }

  grouping fantray-fault {
    description
      "Fan tray fault";
    leaf severity-level {
      type ios-events-ios-xe-oper:notification-severity;
      description
        "Event severity";
    }
    leaf host-name {
      type string;
      description
        "Host name";
    }
    leaf system-ip {
      type inet:ip-address;
      description
        "System IP address";
    }
    leaf fantray-id {
      type uint32;
      description
        "Fan tray id";
    }
    leaf new-state {
      type ios-events-ios-xe-oper:notification-module-state;
      description
        "New fan tray fault state";
    }
  }

  grouping pem-fault {
    description
      "PEM fault";
    leaf severity-level {
      type ios-events-ios-xe-oper:notification-severity;
      description
        "Event severity";
    }
    leaf host-name {
      type string;
      description
        "Host name";
    }
    leaf system-ip {
      type inet:ip-address;
      description
        "System IP address";
    }
    leaf pem-id {
      type uint32;
      description
        "PEM id";
    }
    leaf new-state {
      type ios-events-ios-xe-oper:notification-failure-state;
      description
        "New pem fault state";
    }
  }

  grouping pem-state-change {
    description
      "PEM state change";
    leaf severity-level {
      type ios-events-ios-xe-oper:notification-severity;
      description
        "Event severity";
    }
    leaf host-name {
      type string;
      description
        "Host name";
    }
    leaf system-ip {
      type inet:ip-address;
      description
        "System IP address";
    }
    leaf pem-id {
      type uint32;
      description
        "PEM id";
    }
    leaf new-state {
      type ios-events-ios-xe-oper:notification-module-state;
      description
        "New pem state";
    }
  }

  grouping pim-fault {
    description
      "PIM fault";
    leaf severity-level {
      type ios-events-ios-xe-oper:notification-severity;
      description
        "Event severity";
    }
    leaf host-name {
      type string;
      description
        "Host name";
    }
    leaf system-ip {
      type inet:ip-address;
      description
        "System IP address";
    }
    leaf pim-id {
      type uint32;
      description
        "PIM id";
    }
    leaf new-state {
      type ios-events-ios-xe-oper:notification-failure-state;
      description
        "New pim fault state";
    }
  }

  grouping pim-state-change {
    description
      "PIM state change notification";
    leaf severity-level {
      type ios-events-ios-xe-oper:notification-severity;
      description
        "Event severity";
    }
    leaf host-name {
      type string;
      description
        "Host name";
    }
    leaf system-ip {
      type inet:ip-address;
      description
        "System IP address";
    }
    leaf pim-id {
      type uint32;
      description
        "PIM id";
    }
    leaf new-state {
      type ios-events-ios-xe-oper:notification-module-state;
      description
        "New pim state";
    }
  }

  grouping sfp-state-change {
    description
      "SFP state change";
    leaf severity-level {
      type ios-events-ios-xe-oper:notification-severity;
      description
        "Event severity";
    }
    leaf host-name {
      type string;
      description
        "Host name";
    }
    leaf system-ip {
      type inet:ip-address;
      description
        "System IP address";
    }
    leaf sfp-name {
      type string;
      description
        "SFP name";
    }
    leaf new-state {
      type ios-events-ios-xe-oper:notification-module-state;
      description
        "New SFP state";
    }
  }

  grouping sfp-support-state {
    description
      "SFP support state";
    leaf severity-level {
      type ios-events-ios-xe-oper:notification-severity;
      description
        "Event severity";
    }
    leaf host-name {
      type string;
      description
        "Host name";
    }
    leaf system-ip {
      type inet:ip-address;
      description
        "System IP address";
    }
    leaf sfp-name {
      type string;
      description
        "SFP name";
    }
    leaf new-state {
      type ios-events-ios-xe-oper:notification-module-state;
      description
        "New SFP support state";
    }
  }

  grouping usb-state-change {
    description
      "USB state change";
    leaf severity-level {
      type ios-events-ios-xe-oper:notification-severity;
      description
        "Event severity";
    }
    leaf host-name {
      type string;
      description
        "Host name";
    }
    leaf system-ip {
      type inet:ip-address;
      description
        "System IP address";
    }
    leaf usb-slot {
      type uint32;
      description
        "USB slot";
    }
    leaf new-state {
      type ios-events-ios-xe-oper:notification-module-state;
      description
        "New USB state";
    }
  }

  grouping vrrp-group-state-change {
    description
      "VRRP group state change";
    leaf severity-level {
      type ios-events-ios-xe-oper:notification-severity;
      description
        "Event severity";
    }
    leaf host-name {
      type string;
      description
        "Host name";
    }
    leaf system-ip {
      type inet:ip-address;
      description
        "IP address";
    }
    leaf vrf-name {
      type string;
      description
        "VRF name";
    }
    leaf if-number {
      type uint32;
      description
        "SNMP if index";
    }
    leaf grp-id {
      type uint32;
      description
        "Group Number";
    }
    leaf addr-type {
      type ios-events-ios-xe-oper:vrrp-ip-addr-type;
      description
        "Address Type";
    }
    leaf if-name {
      type string;
      description
        "Interface Name";
    }
    leaf vrrp-group-state {
      type ios-events-ios-xe-oper:vrrp-notif-proto-state;
      description
        "VRRP state";
    }
  }

  grouping fib-update {
    description
      "FIB update notifications";
    leaf severity-level {
      type ios-events-ios-xe-oper:notification-severity;
      description
        "Event severity";
    }
    leaf host-name {
      type string;
      description
        "Host name";
    }
    leaf system-ip {
      type inet:ip-address;
      description
        "IP address";
    }
    leaf vrf-name {
      type string;
      description
        "Last updated VRF";
    }
    leaf address-family-type {
      type ios-events-ios-xe-oper:fib-updates-af-type;
      description
        "Last updated address family";
    }
    leaf fib-last-update-time {
      type yang:date-and-time;
      description
        "Last update time";
    }
  }

  grouping system-login-change {
    description
      "Notification that a login to the system has occurred";
    leaf severity-level {
      type ios-events-ios-xe-oper:notification-severity;
      description
        "Event severity";
    }
    leaf host-name {
      type string;
      description
        "Host name";
    }
    leaf system-ip {
      type inet:ip-address;
      description
        "System IP address";
    }
    leaf user-name {
      type string;
      description
        "User name";
    }
    leaf user-id {
      type uint32;
      description
        "User ID";
    }
  }

  grouping system-logout-change {
    description
      "Notification that a user has logged out";
    leaf severity-level {
      type ios-events-ios-xe-oper:notification-severity;
      description
        "Event severity";
    }
    leaf host-name {
      type string;
      description
        "Host name";
    }
    leaf system-ip {
      type inet:ip-address;
      description
        "System IP address";
    }
    leaf user-name {
      type string;
      description
        "User name";
    }
    leaf user-id {
      type uint32;
      description
        "User ID";
    }
  }

  grouping system-aaa-login-fail {
    description
      "Notification that a login attempt has failed";
    leaf severity-level {
      type ios-events-ios-xe-oper:notification-severity;
      description
        "Event severity";
    }
    leaf host-name {
      type string;
      description
        "Host name";
    }
    leaf system-ip {
      type inet:ip-address;
      description
        "System IP address";
    }
    leaf user-name {
      type string;
      description
        "User name";
    }
    leaf remote-host {
      type string;
      description
        "Remote host";
    }
  }

  grouping aaa-admin-pwd-change {
    description
      "The administration password has been changed";
    leaf severity-level {
      type ios-events-ios-xe-oper:notification-severity;
      description
        "Event severity";
    }
    leaf host-name {
      type string;
      description
        "Host name";
    }
    leaf system-ip {
      type inet:ip-address;
      description
        "System IP address";
    }
  }

  grouping cellular-sim-status-change {
    description
      "Cellular SIM Status Change";
    leaf severity-level {
      type ios-events-ios-xe-oper:notification-severity;
      description
        "Event severity";
    }
    leaf host-name {
      type string;
      description
        "Host name";
    }
    leaf system-ip {
      type inet:ip-address;
      description
        "System IP address";
    }
    leaf if-name {
      type string;
      description
        "interface name";
    }
    leaf reason {
      type string;
      description
        "Reason for SIM status change";
    }
  }

  grouping cellular-modem-status-change {
    description
      "Cellular Modem Status Change";
    leaf severity-level {
      type ios-events-ios-xe-oper:notification-severity;
      description
        "Event severity";
    }
    leaf host-name {
      type string;
      description
        "Host name";
    }
    leaf system-ip {
      type inet:ip-address;
      description
        "System IP address";
    }
    leaf if-name {
      type string;
      description
        "interface name";
    }
    leaf reason {
      type string;
      description
        "Reason for modem status change";
    }
  }

  grouping cellular-network-status-change {
    description
      "Cellular Network Status Change";
    leaf severity-level {
      type ios-events-ios-xe-oper:notification-severity;
      description
        "Event severity";
    }
    leaf host-name {
      type string;
      description
        "Host name";
    }
    leaf system-ip {
      type inet:ip-address;
      description
        "System IP address";
    }
    leaf if-name {
      type string;
      description
        "interface name";
    }
    leaf reason {
      type string;
      description
        "Reason for cellular network status change";
    }
  }

  grouping app-dpi-flows-out-of-memory {
    description
      "Traffic exceeds number of flows or memory limit supported by DPI";
    leaf severity-level {
      type ios-events-ios-xe-oper:notification-severity;
      description
        "Event severity";
    }
    leaf host-name {
      type string;
      description
        "Host name";
    }
    leaf system-ip {
      type inet:ip-address;
      description
        "System IP address";
    }
    leaf dpi-out-of-memory-state {
      type boolean;
      description
        "DPI flows out-of-memory new failure state";
    }
  }

  grouping utd-ips-alert {
    description
      "Unified Threat Defense (UTD) Intrusion Prevention System (IPS) alert";
    leaf severity-level {
      type ios-events-ios-xe-oper:notification-severity;
      description
        "Event severity";
    }
    leaf host-name {
      type string;
      description
        "Host name";
    }
    leaf system-ip {
      type inet:ip-address;
      description
        "System IP address";
    }
    leaf timestamp {
      type yang:date-and-time;
      description
        "Alert timestamp";
    }
    leaf action {
      type ios-events-ios-xe-oper:utd-ips-alert-action-val;
      description
        "Alert action";
    }
    leaf sid {
      type uint32;
      description
        "Alert signature ID";
    }
    leaf gid {
      type uint32;
      description
        "Alert generator ID";
    }
    leaf rev {
      type uint32;
      description
        "Alert signature revision ID";
    }
    leaf classification {
      type ios-events-ios-xe-oper:utd-ips-alert-classification-val;
      description
        "Alert classification ID";
    }
    leaf message {
      type string;
      description
        "Alert message";
    }
    leaf priority {
      type ios-events-ios-xe-oper:utd-ips-alert-priority-val;
      description
        "Alert priority";
    }
    leaf src-ip {
      type inet:ip-address;
      description
        "Alert source IP";
    }
    leaf dst-ip {
      type inet:ip-address;
      description
        "Alert destination IP";
    }
    leaf src-port {
      type uint16;
      description
        "Alert source port";
    }
    leaf dst-port {
      type uint16;
      description
        "Alert destination port";
    }
    leaf protocol {
      type uint8;
      description
        "Alert protocol";
    }
    leaf vrf {
      type string;
      description
        "Alert VRF";
    }
  }

  grouping utd-update {
    description
      "Unified Threat Defense (UTD) update";
    leaf severity-level {
      type ios-events-ios-xe-oper:notification-severity;
      description
        "Event severity";
    }
    leaf host-name {
      type string;
      description
        "Host name";
    }
    leaf system-ip {
      type inet:ip-address;
      description
        "System IP address";
    }
    leaf type {
      type ios-events-ios-xe-oper:utd-update-type-val;
      description
        "Update type";
    }
    leaf timestamp {
      type yang:date-and-time;
      description
        "Update timestamp";
    }
    leaf version {
      type string;
      description
        "Current version";
    }
    leaf status {
      type utd-common-ios-xe-oper:utd-update-status-val;
      description
        "Update status";
    }
    leaf reason {
      type string;
      description
        "Update failure reason";
    }
  }

  grouping utd-version-mismatch {
    description
      "Unified Threat Defense (UTD) version mismatch";
    leaf severity-level {
      type ios-events-ios-xe-oper:notification-severity;
      description
        "Event severity";
    }
    leaf host-name {
      type string;
      description
        "Host name";
    }
    leaf system-ip {
      type inet:ip-address;
      description
        "System IP address";
    }
    leaf current-version {
      type string;
      description
        "Current Unified Threat Defense (UTD) package version";
    }
    leaf recommended-version {
      type string;
      description
        "Recommended Unified Threat Defense (UTD) package version";
    }
    leaf supported {
      type boolean;
      description
        "Indicates if the current Unified Threat Defense (UTD) package version is supported";
    }
  }

  grouping aaa-event-server-state {
    description
      "Notification of AAA Server State";
    leaf severity-level {
      type ios-events-ios-xe-oper:notification-severity;
      description
        "Event severity";
    }
    leaf host-name {
      type string;
      description
        "Host name";
    }
    leaf system-ip {
      type inet:ip-address;
      description
        "System IP address";
    }
    leaf server-ip {
      type inet:ip-address;
      description
        "Server IP Address";
    }
    leaf auth-port {
      type uint16;
      description
        "Server Authetication Port";
    }
    leaf acct-port {
      type uint16;
      description
        "Server Accounting Port";
    }
    leaf timestamp {
      type yang:date-and-time;
      description
        "Timestamp for server UP/DOWN event";
    }
    leaf server-state {
      type boolean;
      description
        "Server State";
    }
  }

  grouping bridge-state {
    description
      "Bridge state notification";
    leaf severity-level {
      type ios-events-ios-xe-oper:notification-severity;
      description
        "Event severity";
    }
    leaf bridge-id {
      type uint32;
      description
        "Bridge ID <1..4094>";
    }
    leaf bridge-state {
      type ios-events-ios-xe-oper:bridge-state-val;
      description
        "Bridge state";
    }
  }

  grouping bridge-intf-state {
    description
      "Bridge interface operational state notification";
    leaf severity-level {
      type ios-events-ios-xe-oper:notification-severity;
      description
        "Event severity";
    }
    leaf bridge-id {
      type uint32;
      description
        "Bridge ID <1..4094>";
    }
    leaf if-name {
      type string;
      description
        "Switch port name belong to the bridge";
    }
    leaf bridge-intf-oper-state {
      type ios-events-ios-xe-oper:interface-notif-state;
      description
        "Bridge interface operational state";
    }
  }

  notification bgp-peer-state-change {
    description
      "BGP peer state change notification";
    uses ios-events-ios-xe-oper:bgp-peer-state;
  }
  notification ospf-neighbor-state-change {
    description
      "OSPF neighbor state change notification";
    uses ios-events-ios-xe-oper:ospf-neighbor-state;
  }
  notification ospf-interface-state-change {
    description
      "OSPF interface state change notification";
    uses ios-events-ios-xe-oper:ospf-interface-state;
  }
  notification interface-state-change {
    description
      "Interafce operational state change notification";
    uses ios-events-ios-xe-oper:interface-oper-state;
  }
  notification memory-usage {
    description
      "Memory usage notification";
    uses ios-events-ios-xe-oper:memory-usage;
  }
  notification cpu-usage {
    description
      "CPU usage notification";
    uses ios-events-ios-xe-oper:cpu-usage;
  }
  notification interface-admin-state-change {
    description
      "Interafce admin state change notification";
    uses ios-events-ios-xe-oper:interface-admin-state;
  }
  notification dhcp-server-state-change {
    description
      "DHCP server state change notification";
    uses ios-events-ios-xe-oper:dhcp-server-state;
  }
  notification dhcp-address-assigned {
    description
      "DHCP address assigned change notification";
    uses ios-events-ios-xe-oper:dhcp-address-assigned;
  }
  notification dhcp-address-renewed {
    description
      "DHCP server address renewed change notification";
    uses ios-events-ios-xe-oper:dhcp-address-renewed;
  }
  notification dhcp-address-released {
    description
      "DHCP address released change notification";
    uses ios-events-ios-xe-oper:dhcp-address-released;
  }
  notification dhcp-address-rejected {
    description
      "DHCP address rejected change notification";
    uses ios-events-ios-xe-oper:dhcp-address-rejected;
  }
  notification system-reboot-complete {
    description
      "System reboot complete notification";
    uses ios-events-ios-xe-oper:system-reboot-complete;
  }
  notification flash-fault {
    description
      "Flash fault notification";
    uses ios-events-ios-xe-oper:flash-fault;
  }
  notification emmc-fault {
    description
      "Emmc fault notification";
    uses ios-events-ios-xe-oper:emmc-fault;
  }
  notification sdcard-fault {
    description
      "SD card fault notification";
    uses ios-events-ios-xe-oper:sdcard-fault;
  }
  notification tempsensor-fault {
    description
      "Tempsensor fault notification";
    uses ios-events-ios-xe-oper:tempsensor-fault;
  }
  notification tempsensor-state {
    description
      "Tempsensor state notification";
    uses ios-events-ios-xe-oper:tempsensor-state;
  }
  notification fan-fault {
    description
      "Fan fault notification";
    uses ios-events-ios-xe-oper:fan-fault;
  }
  notification fantray-fault {
    description
      "Fan tray notification";
    uses ios-events-ios-xe-oper:fantray-fault;
  }
  notification pem-fault {
    description
      "PEM fault notification";
    uses ios-events-ios-xe-oper:pem-fault;
  }
  notification pem-state-change {
    description
      "PEM state change notification";
    uses ios-events-ios-xe-oper:pem-state-change;
  }
  notification pim-fault {
    description
      "PIM fault notification";
    uses ios-events-ios-xe-oper:pim-fault;
  }
  notification pim-state-change {
    description
      "PIM state change notification";
    uses ios-events-ios-xe-oper:pim-state-change;
  }
  notification sfp-state-change {
    description
      "SFP state change notification";
    uses ios-events-ios-xe-oper:sfp-state-change;
  }
  notification sfp-support-state {
    description
      "SFP support state notification";
    uses ios-events-ios-xe-oper:sfp-support-state;
  }
  notification usb-state-change {
    description
      "USB state change notification";
    uses ios-events-ios-xe-oper:usb-state-change;
  }
  notification vrrp-group-state-change {
    description
      "VRRP group state change";
    uses ios-events-ios-xe-oper:vrrp-group-state-change;
  }
  notification system-reboot-issued {
    description
      "System reboot issued notification";
    uses ios-events-ios-xe-oper:system-reboot-issued;
  }
  notification disk-usage {
    description
      "Disk usage notification";
    uses ios-events-ios-xe-oper:disk-usage;
  }
  notification fib-updates {
    description
      "FIB update notification";
    uses ios-events-ios-xe-oper:fib-update;
  }
  notification system-login-change {
    description
      "System login notification";
    uses ios-events-ios-xe-oper:system-login-change;
  }
  notification system-logout-change {
    description
      "System logout notification";
    uses ios-events-ios-xe-oper:system-logout-change;
  }
  notification system-aaa-login-fail {
    description
      "System login fail notification";
    uses ios-events-ios-xe-oper:system-aaa-login-fail;
  }
  notification aaa-admin-pwd-change {
    description
      "Administration password change notification";
    uses ios-events-ios-xe-oper:aaa-admin-pwd-change;
  }
  notification cellular-sim-status-change {
    description
      "Cellular SIM status change notification";
    uses ios-events-ios-xe-oper:cellular-sim-status-change;
  }
  notification cellular-modem-status-change {
    description
      "Cellular Modem status change notification";
    uses ios-events-ios-xe-oper:cellular-modem-status-change;
  }
  notification cellular-network-status-change {
    description
      "Cellular Network status change notification";
    uses ios-events-ios-xe-oper:cellular-network-status-change;
  }
  notification app-dpi-flows-out-of-memory {
    description
      "app_dpi_flows_out_of_memory";
    uses ios-events-ios-xe-oper:app-dpi-flows-out-of-memory;
  }
  notification utd-ips-alert {
    description
      "Unified Threat Defense (UTD) Intrusion Prevention System (IPS) alert notification";
    uses ios-events-ios-xe-oper:utd-ips-alert;
  }
  notification utd-update {
    description
      "Unified Threat Defense (UTD) update notification";
    uses ios-events-ios-xe-oper:utd-update;
  }
  notification utd-version-mismatch {
    description
      "Unified Threat Defense (UTD) version mismatch notification";
    uses ios-events-ios-xe-oper:utd-version-mismatch;
  }
  notification aaa-event-server-state {
    description
      "AAA Server State Notification";
    uses ios-events-ios-xe-oper:aaa-event-server-state;
  }
  notification bridge-state-change {
    description
      "Bridge state notification";
    uses ios-events-ios-xe-oper:bridge-state;
  }
  notification bridge-interface-state-change {
    description
      "Bridge interface operational state notification";
    uses ios-events-ios-xe-oper:bridge-intf-state;
  }
  container ios-events {
    config false;
    description
      "Events generated from IOS features";
  }
}
