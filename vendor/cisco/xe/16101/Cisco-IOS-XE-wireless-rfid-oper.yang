module Cisco-IOS-XE-wireless-rfid-oper {
  yang-version 1;
  namespace "http://cisco.com/ns/yang/Cisco-IOS-XE-wireless-rfid-oper";
  prefix wireless-rfid-ios-oper;

  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Wireless rfid Operational Data
     Copyright (c) 2016-2018 by Cisco Systems, Inc.
     All rights reserved.";

  revision 2018-01-24 {
    description
      "Changes done in ptl code for time format";
    reference "2.0.0";
  }
  revision 2017-12-22 {
    description
      "Initial revision";
    reference "1.0.0";
  }

  typedef enm-rfid-data-type {
    type enumeration {
      enum "bluesoft-rfid-data" {
        value 0;
        description
          "This enum value represents type of bluesoft rfid tag.";
      }
      enum "cisco-rfid-data" {
        value 1;
        description
          "This enum value represents type of cisco rfid tag.";
      }
    }
    description
      "This enum has all the RFID
       tags supported types.";
  }

  grouping st-apf-seq-control {
    description
      "sequence control represents sequence and fragmentation number.";
    leaf seq-num {
      type uint16;
      description
        "seq_num represents sequence number of rfid tag packet.";
    }
    leaf frag-num {
      type uint16;
      description
        "frag_num represents fragmentation number of rfid tag packet.";
    }
  }

  grouping st-rfid-cisco-cont-hdr {
    description
      "CTX content header contains attributes of ctx header of rfid.";
    leaf ccx-version {
      type uint8;
      description
        "ccx_version represents ccx verison of rfid.";
    }
    leaf tx-power {
      type int8;
      description
        "tx_power represents tx power of rfid.";
    }
    leaf channel {
      type uint8;
      description
        "channel represents channel id of rfid.";
    }
    leaf reg-class {
      type uint8;
      description
        "reg_class represents reg_class of rfid.";
    }
    leaf burst-len {
      type uint8;
      description
        "burst_len represents burst length of rfid.";
    }
  }

  grouping st-bluesoft-rfid-data {
    description
      "Bluesoft rfid data represents data of bluesoft rfid tag.";
    leaf last-seq-num {
      type uint8;
      description
        "last_seq_num represents last sequence number of rfid tag.";
    }
    leaf tag-type {
      type uint8;
      description
        "tag_type represents type of bluesoft rfid tag.";
    }
    leaf batt-status {
      type uint8;
      description
        "batt_status represents support of bluesoft rfid tag or not.";
    }
  }

  grouping st-ccx-payload-list {
    description
      "ccx payload contains ccx payload data of rfid.";
    leaf-list data {
      type uint8;
      max-elements "500";
      ordered-by user;
      description
        "Data contains one byte of ccx payload data.";
    }
  }

  grouping st-cisco-rfid-data {
    description
      "cisco rfid data represents data of cisco rfid tag.";
    container rfid-cisco-hdr {
      description
        "cisco header represents cisco tag header.";
      uses wireless-rfid-ios-oper:st-rfid-cisco-cont-hdr;
    }
    container seq-control {
      description
        "sequence control represents sequence control number of rfid tag.";
      uses wireless-rfid-ios-oper:st-apf-seq-control;
    }
    leaf payload-len {
      type uint16;
      description
        "payload_len represents payload length of rfid packet.";
    }
    container ccx-payload {
      description
        "ccx_payload represents ccx payload length of rfid packet.";
      uses wireless-rfid-ios-oper:st-ccx-payload-list;
    }
  }

  grouping st-vendor-spec-data {
    description
      "vendor specific data of rfid packet.";
    choice type-choice {
      description
        "type choice represents type of rfid tag supported.";
      case bluesoft-rfid-data {
        container bluesoft {
          description
            "bluesoft represents updation of bluesoft rfid information.";
          uses wireless-rfid-ios-oper:st-bluesoft-rfid-data;
        }
      }
      case cisco-rfid-data {
        container cisco {
          description
            "cisco represents cisco rfid tag information.";
          uses wireless-rfid-ios-oper:st-cisco-rfid-data;
        }
      }
    }
  }

  grouping st-rfid-avg-rssi {
    description
      "rfid avg rssi represents AP rssi information.";
    leaf num {
      type int16;
      description
        "num represents rssi num.";
    }
    leaf denom {
      type uint16;
      description
        "denom represents rssi denom.";
    }
    leaf value {
      type int8;
      description
        "value represents value of rssi.";
    }
    leaf last-sent {
      type int8;
      description
        "last_sent represents last sent rssi.";
    }
  }

  grouping st-rfid-avg-snr {
    description
      "rfid avg snr represents snr of AP.";
    leaf num {
      type int16;
      description
        "num of snr.";
    }
    leaf denom {
      type uint16;
      description
        "denom of snr.";
    }
    leaf value {
      type int8;
      description
        "value of snr.";
    }
  }

  grouping rfid-ap-entry-list {
    description
      "ap entry list is list of ap data, max count of list is 16.";
    container rssi {
      description
        "rssi represents rssi parameters of rfid.";
      uses wireless-rfid-ios-oper:st-rfid-avg-rssi;
    }
    leaf slot {
      type uint8;
      description
        "slot represents AP slot.";
    }
    leaf band {
      type uint8;
      description
        "band represents radio band of AP.";
    }
    container snr {
      description
        "snr represents value of snr.";
      uses wireless-rfid-ios-oper:st-rfid-avg-snr;
    }
    leaf time-stamp-ms {
      type uint32;
      description
        "time stamp represents time stamp of rfid packet received by the AP.";
    }
    leaf in-use {
      type int8;
      description
        "in_use represents stale ap data or not.";
    }
    leaf expired {
      type int8;
      description
        "expired represents stale node in the list, true if time stamp time expired.";
    }
    leaf ap-mac-addr {
      type yang:mac-address;
      description
        "ap_mac_addr represents ap mac address of AP.";
    }
  }

  grouping st-rfid-ap-highest-rssi {
    description
      "ap highest rssi represents stores mac address of highest AP address.";
    leaf ap-mac-addr {
      type yang:mac-address;
      description
        "ap mac address represents ap mac address of highest rssi AP.";
    }
    container rssi {
      description
        "rssi represents rssi value of highest rssi AP.";
      uses wireless-rfid-ios-oper:st-rfid-avg-rssi;
    }
  }

  grouping st-rfid-data {
    description
      "rfid data represents rfid parameters.";
    leaf rfid-mac-addr {
      type yang:mac-address;
      description
        "rfid mac address represents mac address of the rfid device.";
    }
    leaf rfid-type {
      type wireless-rfid-ios-oper:enm-rfid-data-type;
      description
        "rfid type represents type of rfid tag.";
    }
    leaf rfid-auto-interval {
      type uint16;
      description
        "rfid auto interval represents rfid packet interval.";
    }
    leaf rfid-bytes-rx {
      type uint32;
      description
        "rfid bytes rx represents number of bytes received in rfid packet.";
    }
    leaf rfid-packets-rx {
      type uint32;
      description
        "rfid packets rx represents number of rfid packets received for same rfid.";
    }
    leaf rfid-last-heard {
      type uint64;
      description
        "last heard represents time stamp of last rfid packet received.";
    }
    container rfid-vendor {
      description
        "rfid vendor represents vendor type of rfid received like cisco tag or bluesoft.";
      uses wireless-rfid-ios-oper:st-vendor-spec-data;
    }
    leaf locp-dirty-bit {
      type boolean;
      description
        "local dirty bit represents record already sent to nmsp or not.";
    }
    container ap-high-rssi {
      description
        "ap high rssi represents parameters of highest rssi AP";
      uses wireless-rfid-ios-oper:st-rfid-ap-highest-rssi;
    }
    list ap-data {
      description
        "ap data represents ap information of rfid packet received.";
      uses wireless-rfid-ios-oper:rfid-ap-entry-list;
    }
    leaf tx-power {
      type int8;
      description
        "tx_power represents tx power of AP which send rfid packet.";
    }
    leaf timer-handle {
      type uint64;
      description
        "timer_handle represents timer handle of the record.";
    }
  }

  grouping st-rfid-stats {
    description
      "rfid stats represents statsitics of rfid packet.";
    leaf rfid-error-db-full {
      type uint32;
      description
        "rfid error full db represents counter increment when DB is full.";
    }
    leaf rfid-error-invalid-payload {
      type uint32;
      description
        "rfid error invalid payload represents counter increment if rfid payload is NULL.";
    }
    leaf rfid-error-invalid-tag {
      type uint32;
      description
        "rfid error invalid tag represents counter increment if ccx version is incorrect.";
    }
    leaf rfid-error-dot11-hdr {
      type uint32;
      description
        "rfid error dot11 hdr represents counter increment if dot11 header is null.";
    }
    leaf rfid-error-pkt-len {
      type uint32;
      description
        "rfid error packet length represents counter increment for invalid rfid packet length.";
    }
    leaf rfid-error-state-drop {
      type uint32;
      description
        "ccx_payload represents ccx payload length of rfid packet.";
    }
    leaf rfid-packet-received {
      type uint32;
      description
        "rfid packet received represents counter increment when rfid packet received.";
    }
    leaf rfid-error-populate-value {
      type uint32;
      description
        "rfid error populate value represents counter increment when failed to populate rfid values into DB.";
    }
    leaf rfid-error-insert-record {
      type uint32;
      description
        "rfid error insert record represents counter increments if failed insert rfid record.";
    }
    leaf rfid-error-update-record {
      type uint32;
      description
        "rfid error update record represents counter increment when update fails.";
    }
    leaf rfid-insert-record {
      type uint32;
      description
        "rfid insert record represents counter increment when record inserted successfully in DB";
    }
    leaf rfid-error-ccx-payload {
      type uint32;
      description
        "rfid ccx payload error represents counter increment if ccx payload is null.";
    }
    leaf rfid-delete-record {
      type uint32;
      description
        "rfid delete record represents failed to rfid delete record.";
    }
    leaf rfid-error-exceed-ap-count {
      type uint32;
      description
        "rfid error exceed ap count represents counter increment failed to insert
         AP data when list max count exceeds.";
    }
    leaf rfid-error-record-remove {
      type uint32;
      description
        "rfid error record remove represents counter increment when 
         fail to remove ap node in list.";
    }
    leaf rfid-oldest-rssi-expired {
      type uint32;
      description
        "rfid oldest rssi expired represents counter increment when oldest rssi expired.";
    }
    leaf rfid-smallest-rssi-expired {
      type uint32;
      description
        "rfid smallest rssi expired represents counter increment when smallest rssi expired.";
    }
    leaf rfid-query-insert {
      type uint32;
      description
        "rfid query insert represents counter increment when query request received.";
    }
    leaf rfid-error-invalid-rssi {
      type uint32;
      description
        "rfid error invalid rssi represents counter increment if rssi value is not 
         in accepted range.";
    }
  }

  container rfid-oper-data {
    config false;
    description
      "wireless rfid oper data contains all rfid operational data informaiton";
    list rfid-data {
      key "rfid-mac-addr";
      description
        "rfid data represents parameter of rfid packet.";
      uses wireless-rfid-ios-oper:st-rfid-data;
    }
    container rfid-stats {
      presence "rfid-stats";
      description
        "rfid stats represents counters of rfid stats.";
      uses wireless-rfid-ios-oper:st-rfid-stats;
    }
  }
}
