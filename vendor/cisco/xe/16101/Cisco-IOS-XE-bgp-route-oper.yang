module Cisco-IOS-XE-bgp-route-oper {
  yang-version 1;
  namespace "http://cisco.com/ns/yang/Cisco-IOS-XE-bgp-route-oper";
  prefix bgp-route-ios-xe-oper;

  import Cisco-IOS-XE-bgp-common-oper {
    prefix bgp-common-ios-xe-oper;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     route for bgp route operational data.
     Copyright (c) 2016-2018 by Cisco Systems, Inc.
     All rights reserved.";

  revision 2018-04-09 {
    description
      "Added enum type for bgp path internal/external
       status";
    reference "1.4.0";
  }
  revision 2017-09-25 {
    description
      "Properly indicated leaf-list ordering";
    reference "1.3.0";
  }
  revision 2017-05-22 {
    description
      "Added the BGP Peer Group Elements";
    reference "1.2.0";
  }
  revision 2017-05-12 {
    description
      "Added the BGP RD and Neighbor routes";
    reference "1.1.0";
  }
  revision 2017-02-07 {
    description
      "Initial revision";
    reference "1.0.0";
  }

  typedef bgp-origin-code {
    type enumeration {
      enum "origin-igp" {
        value 0;
        description
          "BGP origin code IGP";
      }
      enum "origin-egp" {
        value 1;
        description
          "BGP origin code EGP";
      }
      enum "origin-incomplete" {
        value 2;
        description
          "BGP origin code incomplete";
      }
    }
    description
      "BGP origin code";
  }

  typedef bgp-rpki-status {
    type enumeration {
      enum "rpki-valid" {
        value 0;
      }
      enum "rpki-invalid" {
        value 1;
      }
      enum "rpki-not-found" {
        value 2;
      }
      enum "rpki-not-enabled" {
        value 3;
      }
      enum "rpki-illegal" {
        value 4;
      }
    }
    description
      "BGP RPKI status";
  }

  typedef bgp-path-origin {
    type enumeration {
      enum "internal-path" {
        value 0;
        description
          "BGP origin internal";
      }
      enum "external-path" {
        value 1;
        description
          "BGP origin external";
      }
    }
    description
      "BGP path internal/external origin";
  }

  typedef bgp-route-filters {
    type enumeration {
      enum "bgp-rf-all" {
        value 0;
        description
          "BGP all route filter";
      }
      enum "bgp-rf-cidr-only" {
        value 1;
        description
          "BGP CIDR only route filter";
      }
      enum "bgp-rf-label" {
        value 2;
        description
          "BGP label route filter";
      }
      enum "bgp-rf-rib-failure" {
        value 3;
        description
          "BGP RIB failure route filter";
      }
      enum "bgp-rf-injected" {
        value 4;
        description
          "BGP injected route filter";
      }
      enum "bgp-rf-inconsistent" {
        value 5;
        description
          "BGP inconsistent route filter";
      }
      enum "bgp-rf-community" {
        value 6;
        description
          "BGP community route filter";
      }
      enum "bgp-rf-extcommunity" {
        value 7;
        description
          "BGP extcommunity route filter";
      }
      enum "bgp-rf-oer-controlled" {
        value 8;
        description
          "BGP OER controlled route filter";
      }
      enum "bgp-rf-pending" {
        value 9;
        description
          "BGP pending route filter";
      }
    }
    description
      "BGP route filters";
  }

  typedef bgp-neighbor-route-filters {
    type enumeration {
      enum "bgp-nrf-post-received" {
        value 0;
        description
          "BGP received routes post policy";
      }
      enum "bgp-nrf-pre-received" {
        value 1;
        description
          "BGP received routes pre policy";
      }
      enum "bgp-nrf-pre-advertised" {
        value 2;
        description
          "BGP pre advertised pre policy";
      }
      enum "bgp-nrf-post-advertised" {
        value 3;
        description
          "BGP post advertised post policy";
      }
    }
    description
      "BGP neighbor route filters";
  }

  grouping peer-group {
    description
      "BGP peer groups";
    leaf name {
      type string;
      description
        "BGP peer group name";
    }
    leaf description {
      type string;
      description
        "Peer Group description string";
    }
    leaf remote-as {
      type uint32;
      description
        "Peer Group Remote AS value";
    }
    leaf bgp-version {
      type uint16;
      description
        "BGP version being used to communicate
         with the remote router";
    }
    leaf min-time {
      type uint16;
      description
        "Peer Group minimum time";
    }
    leaf num-of-sessions {
      type uint32;
      description
        "Number of Sessions for peer group";
    }
    leaf num-estab-sessions {
      type uint32;
      description
        "Number of established sessions 
         for peer group";
    }
    leaf num-sso-sessions {
      type uint32;
      description
        "Number of SSO sesssions for peer group";
    }
    leaf-list peer-members {
      type string;
      ordered-by user;
      description
        "BGP peer group members";
    }
    leaf fmt-grp-ix {
      type uint16;
      description
        "BGP peer group Formatted Group Index value";
    }
    leaf adv-ix {
      type uint16;
      description
        "BGP peer group Advertised Index value";
    }
    leaf aspath-in {
      type uint32;
      description
        "BGP peer group AS Path filter in value";
    }
    leaf aspath-out {
      type uint32;
      description
        "BGP peer group AS Path filter out value";
    }
    leaf routemap-in {
      type string;
      description
        "BGP peer group Route Map in value";
    }
    leaf routemap-out {
      type string;
      description
        "BGP peer group Route Map out value";
    }
    leaf updated-messages {
      type uint64;
      description
        "BGP peer group Updated Messages value";
    }
    leaf rep-count {
      type uint32;
      description
        "BGP peer group Replicated Count value";
    }
    leaf slowpeer-detection-value {
      type uint16;
      description
        "BGP peer group slow peer Threshold value";
    }
    leaf weight {
      type uint16;
      description
        "BGP weight value";
    }
    leaf send-community {
      type boolean;
      description
        "BGP Send Community status";
    }
    leaf extended-community {
      type boolean;
      description
        "BGP Extended Community status";
    }
    leaf remove-private-as {
      type boolean;
      description
        "BGP Remove Private AS status";
    }
  }

  grouping path-status {
    description
      "BGP path status";
    leaf suppressed {
      type empty;
      description
        "Suppressed path";
    }
    leaf damped {
      type empty;
      description
        "Damped path";
    }
    leaf history {
      type empty;
      description
        "History path";
    }
    leaf valid {
      type empty;
      description
        "Valid path";
    }
    leaf sourced {
      type empty;
      description
        "Sourced path";
    }
    leaf bestpath {
      type empty;
      description
        "Best path";
    }
    leaf internal {
      type empty;
      description
        "Internal path";
    }
    leaf rib-fail {
      type empty;
      description
        "RIB-fail path";
    }
    leaf stale {
      type empty;
      description
        "Stale path";
    }
    leaf multipath {
      type empty;
      description
        "Multipath path";
    }
    leaf backup-path {
      type empty;
      description
        "Backup path";
    }
    leaf rt-filter {
      type empty;
      description
        "RT filter path";
    }
    leaf best-external {
      type empty;
      description
        "Best external path";
    }
    leaf additional-path {
      type empty;
      description
        "Additional path";
    }
    leaf rib-compressed {
      type empty;
      description
        "RIB compressed path";
    }
  }

  grouping path-type {
    description
      "BGP path type";
    leaf nexthop {
      type string;
      description
        "Next hop for this path";
    }
    leaf metric {
      type uint32;
      description
        "Metric associated with the path";
    }
    leaf local-pref {
      type uint32;
      description
        "Local preference for this path";
    }
    leaf weight {
      type uint32;
      description
        "Path weight";
    }
    leaf as-path {
      type string;
      description
        "AS path";
    }
    leaf origin {
      type bgp-route-ios-xe-oper:bgp-origin-code;
      description
        "Path origin";
    }
    container path-status {
      description
        "Path status";
      uses bgp-route-ios-xe-oper:path-status;
    }
    leaf rpki-status {
      type bgp-route-ios-xe-oper:bgp-rpki-status;
      description
        "RPKI path status";
    }
    leaf community {
      type string;
      description
        "Community label for the path";
    }
    leaf mpls-in {
      type string;
      description
        "MPLS label in for the path";
    }
    leaf mpls-out {
      type string;
      description
        "MPLS label out for the path";
    }
    leaf sr-profile-name {
      type string;
      description
        "SR profile name for the path";
    }
    leaf sr-binding-sid {
      type uint32;
      description
        "SR binding sid for the path";
    }
    leaf sr-label-indx {
      type uint32;
      description
        "SR label index for the path";
    }
    leaf as4-path {
      type string;
      description
        "path using 4-octet AS numbers";
    }
    leaf atomic-aggregate {
      type boolean;
      description
        "attribute indicating whether or not the prefix is an atomic aggregate";
    }
    leaf aggr-as-number {
      type uint32;
      description
        "AS number of autonomous system them performed the aggregation";
    }
    leaf aggr-as4-number {
      type uint32;
      description
        "AS4 number of autonomous system them performed the aggregation";
    }
    leaf aggr-address {
      type string;
      description
        "IP address of the router that performed the aggregation";
    }
    leaf originator-id {
      type string;
      description
        "the router ID of the originator of the route in the local AS";
    }
    leaf cluster-list {
      type string;
      description
        "the reflection path the route has passed";
    }
    leaf extended-community {
      type string;
      description
        "BGP extended community attribute";
    }
    leaf ext-aigp-metric {
      type uint64;
      description
        "the accumulated IGP metric for the path";
    }
    leaf path-id {
      type uint32;
      description
        "path identifier used to uniquely identify a route";
    }
    leaf path-origin {
      type bgp-route-ios-xe-oper:bgp-path-origin;
      description
        "Internal/External path";
    }
  }

  grouping route-entry {
    description
      "Routing table entry details";
    leaf prefix {
      type string;
      description
        "Routing table entry prefix";
    }
    leaf version {
      type uint32;
      description
        "Routing table version";
    }
    leaf available-paths {
      type uint32;
      description
        "Number of paths available for BGP prefix";
    }
    leaf advertised-to {
      type string;
      description
        "Whom the prefix is advertised to";
    }
    container bgp-path-entries {
      description
        "Prefix next hop details";
      list bgp-path-entry {
        key "nexthop";
        description
          "List of prefix next hop details";
        uses bgp-route-ios-xe-oper:path-type;
      }
    }
  }

  grouping route-filter {
    description
      "BGP route filter";
    leaf route-filter {
      type bgp-route-ios-xe-oper:bgp-route-filters;
      description
        "BGP route filter";
    }
    container bgp-route-entries {
      description
        "BGP route entries";
      list bgp-route-entry {
        key "prefix";
        description
          "List of BGP route entries";
        uses bgp-route-ios-xe-oper:route-entry;
      }
    }
  }

  grouping neighbor-route-entry {
    description
      "Neighbor routing table entry details";
    leaf prefix {
      type string;
      description
        "Neighbor routing table entry prefix";
    }
    leaf version {
      type uint32;
      description
        "Neighbor routing table version";
    }
    leaf available-paths {
      type uint32;
      description
        "Number of paths available for BGP prefix";
    }
    leaf advertised-to {
      type string;
      description
        "Whom the prefix is advertised to";
    }
    container bgp-neighbor-path-entries {
      description
        "Prefix next hop details";
      list bgp-neighbor-path-entry {
        key "nexthop";
        description
          "List of prefix next hop details";
        uses bgp-route-ios-xe-oper:path-type;
      }
    }
  }

  grouping neighbor-route-filter {
    description
      "BGP neighbor route filter";
    leaf nbr-fltr {
      type bgp-route-ios-xe-oper:bgp-neighbor-route-filters;
      description
        "BGP neighbor route filter";
    }
    container bgp-neighbor-route-entries {
      description
        "BGP neighbor route entries";
      list bgp-neighbor-route-entry {
        key "prefix";
        description
          "List of BGP neighbor route entries";
        uses bgp-route-ios-xe-oper:neighbor-route-entry;
      }
    }
  }

  grouping bgp-route-neighbor {
    description
      "BGP route neighbor";
    leaf nbr-id {
      type string;
      description
        "BGP neighbor ID";
    }
    container bgp-neighbor-route-filters {
      description
        "BGP neighbor route filters";
      list bgp-neighbor-route-filter {
        key "nbr-fltr";
        description
          "List of BGP neighbor route filters";
        uses bgp-route-ios-xe-oper:neighbor-route-filter;
      }
    }
  }

  grouping af-record {
    description
      "BGP AF record";
    leaf afi-safi {
      type bgp-common-ios-xe-oper:afi-safi;
      description
        "BGP address family";
    }
    container bgp-route-filters {
      description
        "BGP route filters";
      list bgp-route-filter {
        key "route-filter";
        description
          "List of BGP route filters";
        uses bgp-route-ios-xe-oper:route-filter;
      }
    }
    container bgp-route-neighbors {
      description
        "BGP route neighbors";
      list bgp-route-neighbor {
        key "nbr-id";
        description
          "List of BGP route neighbors";
        uses bgp-route-ios-xe-oper:bgp-route-neighbor;
      }
    }
    container bgp-peer-groups {
      description
        "BGP peer groups";
      list bgp-peer-group {
        key "name";
        description
          "List of BGP peer groups";
        uses bgp-route-ios-xe-oper:peer-group;
      }
    }
  }

  grouping vrf-record {
    description
      "VRF record";
    leaf vrf {
      type string;
      description
        "BGP VRF";
    }
    container bgp-route-afs {
      description
        "BGP address families";
      list bgp-route-af {
        key "afi-safi";
        description
          "List of BGP address families";
        uses bgp-route-ios-xe-oper:af-record;
      }
    }
  }

  grouping bgp-rd-neighbor-route-entry {
    description
      "RD neighbor routing table entry details";
    leaf prefix {
      type string;
      description
        "RD neighbor routing table entry prefix";
    }
    leaf version {
      type uint32;
      description
        "RD neighbor routing table version";
    }
    leaf available-paths {
      type uint32;
      description
        "Number of  paths available for BGP prefix";
    }
    leaf advertised-to {
      type string;
      description
        "Whom the prefix is advertised to";
    }
    container bgp-rd-neighbor-path-entries {
      description
        "Prefix next hop details";
      list bgp-rd-neighbor-path-entry {
        key "nexthop";
        description
          "List of prefix next hop details";
        uses bgp-route-ios-xe-oper:path-type;
      }
    }
  }

  grouping bgp-rd-neighbor-route-filter {
    description
      "BGP RD neighbor route filter";
    leaf neighbor-filter {
      type bgp-route-ios-xe-oper:bgp-neighbor-route-filters;
      description
        "BGP RD neighbor route filter";
    }
    container bgp-rd-neighbor-route-entries {
      description
        "BGP RD neighbor route entries";
      list bgp-rd-neighbor-route-entry {
        key "prefix";
        description
          "List of BGP RD neighbor route entries";
        uses bgp-route-ios-xe-oper:bgp-rd-neighbor-route-entry;
      }
    }
  }

  grouping bgp-rd-route-neighbor {
    description
      "BGP RD route neighbor";
    leaf neighbor-id {
      type string;
      description
        "BGP RD neighbor ID";
    }
    container bgp-rd-neighbor-route-filters {
      description
        "BGP RD neighbor route filters";
      list bgp-rd-neighbor-route-filter {
        key "neighbor-filter";
        description
          "List of BGP RD neighbor route filters";
        uses bgp-route-ios-xe-oper:bgp-rd-neighbor-route-filter;
      }
    }
  }

  grouping bgp-rd-route-entry {
    description
      "RD Routing table entry details";
    leaf prefix {
      type string;
      description
        "RD Routing table entry prefix";
    }
    leaf version {
      type uint32;
      description
        "RD Routing table version";
    }
    leaf available-paths {
      type uint32;
      description
        "Number of  paths available for BGP prefix";
    }
    leaf advertised-to {
      type string;
      description
        "Whom the prefix is advertised to";
    }
    container bgp-rd-path-entries {
      description
        "Prefix next hop details";
      list bgp-rd-path-entry {
        key "nexthop";
        description
          "List of prefix next hop details";
        uses bgp-route-ios-xe-oper:path-type;
      }
    }
  }

  grouping bgp-rd-route-filter {
    description
      "BGP RD route filter";
    leaf route-filter {
      type bgp-route-ios-xe-oper:bgp-route-filters;
      description
        "BGP RD route filter";
    }
    container bgp-rd-route-entries {
      description
        "BGP RD route entries";
      list bgp-rd-route-entry {
        key "prefix";
        description
          "List of BGP RD route entries";
        uses bgp-route-ios-xe-oper:bgp-rd-route-entry;
      }
    }
  }

  grouping bgp-rd-route-af {
    description
      "BGP RD AF record";
    leaf afi-safi {
      type bgp-common-ios-xe-oper:afi-safi;
      description
        "BGP address family";
    }
    container bgp-rd-route-filters {
      description
        "BGP RD route filters";
      list bgp-rd-route-filter {
        key "route-filter";
        description
          "List of BGP RD route filters";
        uses bgp-route-ios-xe-oper:bgp-rd-route-filter;
      }
    }
    container bgp-rd-route-neighbors {
      description
        "BGP RD route neighbors";
      list bgp-rd-route-neighbor {
        key "neighbor-id";
        description
          "List of BGP RD route neighbors";
        uses bgp-route-ios-xe-oper:bgp-rd-route-neighbor;
      }
    }
  }

  grouping bgp-rd-record {
    description
      "RD record";
    leaf rd-value {
      type string;
      description
        "BGP rd value";
    }
    container bgp-rd-route-afs {
      description
        "BGP rd address families";
      list bgp-rd-route-af {
        key "afi-safi";
        description
          "List of BGP RD address families";
        uses bgp-route-ios-xe-oper:bgp-rd-route-af;
      }
    }
  }
}
