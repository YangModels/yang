module Cisco-IOS-XE-wireless-wlan-cfg {
  yang-version 1;
  namespace "http://cisco.com/ns/yang/Cisco-IOS-XE-wireless-wlan-cfg";
  prefix wireless-wlan-cfg;

  import Cisco-IOS-XE-wireless-enum-types {
    prefix wireless-enum-types;
  }
  import Cisco-IOS-XE-wireless-types {
    prefix wireless-types;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing wlan configurations
     Copyright (c) 2016-2018 by Cisco Systems, Inc.
     All rights reserved.";

  revision 2018-07-04 {
    description
      "- Added constraints for call-snoop
       - CTS CLI support";
    reference "4.0.0";
  }
  revision 2018-03-09 {
    description
      "Seperate ATF policy from WLAN policy.
       Move accounting-list from wlan to policy profile.";
    reference "3.0.0";
  }
  revision 2018-01-24 {
    description
      "The first generally available version";
    reference "2.0.0";
  }
  revision 2017-05-05 {
    description
      "Initial revision";
    reference "1.0.0";
  }

  grouping wlan-data-config-file {
    description
      "Contains global wlan configuration params";
    leaf profile-name {
      type string;
      default "";
      description
        "WLAN Profile Name";
    }
    leaf id {
      type int32;
      default "0";
      description
        "wlan ID";
    }
    leaf broadcast-ssid {
      type boolean;
      default "true";
      description
        "broadcast SSID on a WLAN";
    }
    leaf ccx-aironet-ie {
      type boolean;
      default "true";
      description
        "This object indicates the support for the Cisco Compatible Extensions Aironet information element on this WLAN.";
    }
    leaf p2p-blocking-action {
      type wireless-enum-types:apf-vap-p2p-blocking-action;
      default "p2p-blocking-action-none";
      description
        "This object represents the name of the ACL applied to this WLAN. If it is required to remove the ACL";
    }
    leaf acl-name {
      type string;
      default "";
      description
        "This object represents the name of the ACL applied to this WLAN. If it is required to remove the ACL name for a";
    }
    leaf ssid {
      type string;
      default "";
      description
        "This object represents the SSID assigned to this WLAN. The access points will broadcast this SSID on this WLAN.";
    }
    leaf dtim80211a {
      type uint8 {
        range "1 .. 255";
      }
      default "1";
      description
        "This object represents DTIM configuration per WLAN for each 802.11 network.";
    }
    leaf dtim80211b {
      type uint8 {
        range "1 .. 255";
      }
      default "1";
      description
        "This object represents DTIM configuration per WLAN for each 802.11 network.";
    }
    leaf chd-per-wlan {
      type boolean;
      default "true";
      description
        "This object indicates whether Coverage Hole Detection (CHD) is enabled on the controller. A value of 'true' indicates CHD is on and a value of 'false' indicates CHD is turned off for this WLAN.";
    }
    leaf status {
      type boolean;
      default "false";
      description
        "Administrative Status of ESS(WLAN). By disabling an ESS the corresponding SSID is no longer broadcasted in AP beacons.";
    }
  }

  grouping st-mpsk-keys {
    description
      "MPSK Key parameters";
    leaf priority {
      type uint8 {
        range "0 .. 4";
      }
      description
        "MPSK priority";
    }
    leaf mpsk-key {
      type string;
      default "";
      description
        "MPSK key";
    }
    leaf mpsk-key-type {
      type wireless-enum-types:crypt-type;
      default "clear";
      description
        "MPSK key Type";
    }
    leaf mpsk-key-format {
      type wireless-enum-types:apf-vap-key-type;
      must "(../mpsk-key-format = 'key-hex' and  string-length(../mpsk-key) = 64) or  (../mpsk-key-format = 'key-ascii' and  string-length(../mpsk-key) < 64)" {
        error-message "Hex keys need to be 64 characters. ASCII keys need to be less than 64 characters";
        error-app-tag "must-violation";
      }
      description
        "MPSK key format";
    }
  }

  grouping bss-802-11v {
    description
      "IEEE 802.11v Parameters";
    leaf dot11v-dms {
      type boolean;
      default "false";
      description
        "Configure DMS processing per WLAN";
    }
    leaf dot11v-bss-max-idle {
      type boolean;
      default "false";
      description
        "Configure BSS max idle processing per WLAN";
    }
    leaf dot11v-bss-max-idle-protected {
      type boolean;
      default "false";
      description
        "Configure protected mode for BSS max idle processing per WLAN";
    }
    leaf dot11v-tfs {
      type boolean;
      default "false";
      description
        "Configure tfs processing per WLAN";
    }
    leaf dot11v-bss-transition {
      type boolean;
      default "true";
      description
        "Configure BSS transition per WLAN";
    }
    leaf dot11v-wnm-sleep-mode {
      type boolean;
      default "false";
      description
        "Configure wnm sleep mode per WLAN";
    }
    leaf dot11v-disassoc-imminent {
      type boolean;
      default "false";
      description
        "Configure BSS transition disassociation Imminent per WLAN";
    }
    leaf dot11v-disassoc-timer {
      type uint16 {
        range "0 .. 3000";
      }
      default "200";
      description
        "Configure BSS transition disassociation imminent timer per WLAN";
    }
    leaf dot11v-disassoc-timer-opt-roam {
      type uint16 {
        range "0 .. 40";
      }
      default "40";
      description
        "Configure BSS transition disassociation imminent optimized-roaming timer per WLAN";
    }
  }

  grouping st-et-analytics {
    description
      "Provides Encrypted Traffic Analytics feature details";
    leaf is-tvi-enabled {
      type boolean;
      default "false";
      description
        "This flag enables/disables Encrypted Traffic Analytics feature on this WLAN";
    }
  }

  grouping wlan-profile {
    description
      "Contains apfvap config params";
    leaf vap-id {
      type uint32 {
        range "1 .. 4096";
      }
      description
        "wlan ID";
    }
    leaf profile-name {
      type string;
      description
        "profileName";
    }
    leaf security-wifi-sec {
      type boolean;
      default "true";
      description
        "Configures WPA/WPA2 Support for a WLAN";
    }
    leaf security8021-x {
      type boolean;
      default "false";
      description
        "Configures 802.1X";
    }
    leaf security-wep {
      type boolean;
      default "false";
      description
        "Configures static WEP keys on a WLAN";
    }
    leaf security-web {
      type boolean;
      default "false";
      description
        "Configures Web authentication";
    }
    leaf security-web-redir {
      type boolean;
      default "false";
      description
        "Set Conditional Web Redirect on a WLAN";
    }
    leaf security-splashpg-web-redir {
      type boolean;
      default "false";
      description
        "Set Splash-Page Web Redirect";
    }
    leaf auth-80211 {
      type wireless-enum-types:apf-vap-80211-authentication;
      default "apf-vap-80211-auth-open";
      description
        "Configures 802.11 authentication";
    }
    leaf key-index {
      type uint8 {
        range "1 .. 4";
      }
      description
        "This index is for informing Mobile Station which key it should use for Static WEP Authentication";
    }
    leaf encr-80211 {
      type wireless-enum-types:apf-vap-80211-encryption;
      default "apf-vap-80211-encryp-wep104";
      description
        "Type of Static WEP Encryption. Length of key specified in default Key depends on this attribute.";
    }
    leaf default-wep-key {
      type string;
      default "";
      description
        "Static WEP Default Key";
    }
    leaf default-wep-key-type {
      type wireless-enum-types:crypt-type;
      default "clear";
      description
        "Key Input is in ascii";
    }
    leaf encr-8021x {
      type wireless-enum-types:apf-vap-8021x-encryption;
      default "apf-vap-8021x-encryp-wep104";
      description
        "Type of 802.1X Encryption";
    }
    leaf wep-ascii {
      type wireless-enum-types:apf-vap-key-type;
      default "key-hex";
      description
        "The format of the wep key";
    }
    leaf ssn-ie-enabled {
      type boolean;
      default "false";
      description
        "Configures WPA support";
    }
    leaf ssn-cipher-suite-tkip {
      type boolean;
      default "false";
      description
        "WPA/TKIP Cipher support";
    }
    leaf ssn-cipher-suite-aes {
      type boolean;
      default "false";
      description
        "AES Cipher support";
    }
    leaf auth-key-mgmt-suite-psk {
      type boolean;
      default "false";
      description
        "This object specifies the authentication pre-shared key in the hex format that is applicable only when";
    }
    leaf psk-ascii {
      type wireless-enum-types:apf-vap-key-type;
      default "key-ascii";
      description
        "This object specifies the type of the authentication preshared key configured through the object cLWSecDot11EssCckmPsk.";
    }
    leaf rsn-ie-enabled {
      type boolean;
      default "true";
      description
        "This object specifies cckmwpa2 security is enabled or not";
    }
    leaf ssn-cipher-suite-enabled {
      type uint32;
      default "0";
      description
        "Configures WPA ciphers";
    }
    leaf rsn-cipher-suite-enabled {
      type uint32;
      default "0";
      description
        "Configures WPA2 ciphers";
    }
    leaf rsn-cipher-suite-aes {
      type boolean;
      default "true";
      description
        "WPA2/CCMP128 support";
    }
    leaf rsn-cipher-suite-gcmp128 {
      type boolean;
      default "false";
      description
        "WPA2/GCMP128 support";
    }
    leaf rsn-cipher-suite-gcmp256 {
      type boolean;
      default "false";
      description
        "WPA2/GCMP256 support";
    }
    leaf rsn-cipher-suite-ccmp256 {
      type boolean;
      default "false";
      description
        "WPA2/CCMP256 support";
    }
    leaf auth-key-status {
      type uint16;
      default "0";
      description
        "Configures Auth Key Management";
    }
    leaf auth-key-mgmt-suite8021x {
      type boolean;
      default "true";
      description
        "802.1x support";
    }
    leaf auth-key-mgmt-suite-cckm {
      type boolean;
      default "false";
      description
        "This object specifies the type of authentication key management";
    }
    leaf auth-key-mgmt-suite-ft {
      type boolean;
      default "false";
      description
        "Configures 802.1x support";
    }
    leaf auth-key-mgmt-suite-ft-psk {
      type boolean;
      default "false";
      description
        "Configures PSK support";
    }
    leaf auth-key-mgmt-dot1x-sha256 {
      type boolean;
      default "false";
      description
        "Configures 802.1x SHA256 AKM";
    }
    leaf auth-key-mgmt-psk-sha256 {
      type boolean;
      default "false";
      description
        "Configures PSK SHA256 AKM";
    }
    leaf psk {
      type string;
      default "";
      description
        "This object specifies the authentication pre-shared key in the hex format";
    }
    leaf psk-type {
      type wireless-enum-types:crypt-type;
      default "clear";
      description
        "Key format";
    }
    leaf mac-filtering {
      type string;
      default "";
      description
        "Set MAC filtering support on WLAN";
    }
    leaf authorization-override-list-name {
      type string;
      default "";
      description
        "Set override MAC filtering support on WLAN";
    }
    leaf set-mac-filter {
      type boolean;
      default "false";
      description
        "A type of security policy for Mobile Stations (Clients). Select to filter clients by MAC address";
    }
    leaf blacklist-disabled {
      type boolean;
      default "true";
      description
        "This is the flag that can enable or disable the client backlisting feature for a WLAN";
    }
    leaf allow-radius-override {
      type boolean;
      default "false";
      description
        "Enable or Disable AAA override for the global WLAN parameters.";
    }
    leaf mfp-protection-enabled {
      type boolean;
      default "true";
      description
        "This object specifies whether the MFP protection on this WLAN be enabled or not";
    }
    leaf client-blacklist-timeout {
      type uint32 {
        range "0 .. 2147483647";
      }
      default "60";
      description
        "Set the timeout for blacklisted Mobile Stations after which the mobile station will be automatically";
    }
    leaf wlan-interface-name {
      type string;
      default "default";
      description
        "Name of the interface used by this WLAN";
    }
    leaf web-acl-name {
      type string;
      default "";
      description
        "Name of IPv4 ACL for the WLAN";
    }
    leaf ipv6-acl-name {
      type string;
      default "none";
      description
        "Name of IPv6 ACL for the WLAN";
    }
    leaf web-ipv6-acl-name {
      type string;
      default "none";
      description
        "Configure IPv6 WLAN Web ACL";
    }
    leaf radio-policy {
      type wireless-enum-types:apf-vap-radio-policies;
      must
        "(../radio-policy = 'apf-vap-radio-all' or
          ../radio-policy = 'apf-vap-radio-80211a-only' or
          ../radio-policy = 'apf-vap-radio-80211ag-only' or
          ../radio-policy = 'apf-vap-radio-80211bg-only' or
          ../radio-policy = 'apf-vap-radio-80211g-only')" {
        error-message
          "Radio policy must be one of the following:
           1. apf-vap-radio-all 
           2. apf-vap-radio-80211a-only 
           3. apf-vap-radio-80211ag-only 
           4. apf-vap-radio-80211bg-only 
           5. apf-vap-radio-80211g-only";
        error-app-tag "must-violation";
      }
      default "apf-vap-radio-all";
      description
        "Configures the Radio Policy";
    }
    leaf wme-policy {
      type wireless-enum-types:apf-vap-wme-policies;
      default "apf-vap-wme-allowed";
      description
        "Configures WMM (WME)";
    }
    leaf wfd-policy {
      type wireless-enum-types:apf-vap-wifi-direct-policies;
      default "apf-vap-wifidirect-disable";
      description
        "Configure WiFi Direct related attributes on WLAN";
    }
    leaf http-profiling {
      type boolean;
      default "false";
      description
        "Configures Client local profiling on a WLAN, based on HTTP attributes";
    }
    leaf radius-http-prof {
      type boolean;
      default "false";
      description
        "Configures Client radius profiling on a WLAN, based on HTTP attributes";
    }
    leaf tkip-hold-down-timer {
      type uint8 {
        range "0 .. 60";
      }
      default "60";
      description
        "TKIP MIC countermeasures hold-down timer";
    }
    leaf dot11r-ft-capabilities-ds {
      type boolean;
      default "true";
      description
        "Configures Fast Transition over the DS";
    }
    leaf dot11r-ft-reassoc-deadtime {
      type uint32 {
        range "1 .. 100";
      }
      default "20";
      description
        "Enter the Reassociation timeout in seconds";
    }
    leaf dot11r-ft-mode {
      type wireless-enum-types:ft-dot11r-mode;
      default "dot11r-adaptive-enabled";
      description
        "Configures Fast Transition Adaptive support";
    }
    leaf dot11w-pmf-enabled {
      type wireless-enum-types:apf-vap-pmf-policies;
      default "apf-vap-pmf-disabled";
      description
        "Configures PMF as optional/required";
    }
    leaf dot11w-pmf-assoc-come-back-time {
      type uint32 {
        range "1 .. 20";
      }
      default "1";
      description
        "Enter the Association Comeback Time in seconds";
    }
    leaf dot11w-pmf-sa-query-retry-time {
      type uint32 {
        range "100 .. 500";
      }
      default "200";
      description
        "Configures SA Query Retry TimeOut";
    }
    leaf auto-qos-policy {
      type wireless-enum-types:apf-vap-auto-qos-profile;
      default "apf-vap-auto-qos-disabled";
      description
        "Enable AutoQos Wireless Enterprise Policy";
    }
    leaf local-eap-profile-name {
      type string;
      default "";
      description
        "Configure the EAP profile on a WLAN";
    }
    leaf local-eap-flag {
      type boolean;
      default "false";
      description
        "This object indicates if the EAP Profile on a WLAN is set or not";
    }
    leaf band-steering-allow-set {
      type boolean;
      default "false";
      description
        "Allow/Disallow Band Select on a WLAN.";
    }
    leaf load-balancing-allow-set {
      type boolean;
      default "false";
      description
        "Allow/Disallow Load Balance on a WLAN.";
    }
    leaf passive-client-set {
      type boolean;
      default "false";
      description
        "Configures passive client feature";
    }
    leaf universal-admin-set {
      type boolean;
      default "false";
      description
        "This object allows universal admin mode to be enabled on a 802.1X/WPA/WPA2 secured WLAN.";
    }
    leaf mu-mimo-set {
      type boolean;
      default "false";
      description
        "Configures 802.11ac MU-MIMO on a WLAN";
    }
    leaf mstream-mc-direct-set {
      type boolean;
      default "false";
      description
        "Configures multicast direct for WLAN";
    }
    leaf scan-defer-time-set {
      type uint16 {
        range "0 .. 60000";
      }
      default "100";
      description
        "Configures minimum allowable elapsed time";
    }
    leaf scan-defer-priority0 {
      type boolean;
      default "false";
      description
        "Configures priority markings for packets - Enable priority 0";
    }
    leaf scan-defer-priority1 {
      type boolean;
      default "false";
      description
        "Configures priority markings for packets - Enable priority 1";
    }
    leaf scan-defer-priority2 {
      type boolean;
      default "false";
      description
        "Configures priority markings for packets - Enable priority 2";
    }
    leaf scan-defer-priority3 {
      type boolean;
      default "false";
      description
        "Configures priority markings for packets - Enable priority 3";
    }
    leaf scan-defer-priority4 {
      type boolean;
      default "false";
      description
        "Configures priority markings for packets - Enable priority 4";
    }
    leaf scan-defer-priority5 {
      type boolean;
      default "true";
      description
        "Configures priority markings for packets - Enable priority 5";
    }
    leaf scan-defer-priority6 {
      type boolean;
      default "true";
      description
        "Configures priority markings for packets - Enable priority 6";
    }
    leaf scan-defer-priority7 {
      type boolean;
      default "false";
      description
        "Configures priority markings for packets - Enable priority 7";
    }
    leaf dot1x-mlist {
      type string;
      default "";
      description
        "Enter the Authentication list name";
    }
    leaf dot1x-authorization-list {
      type string;
      default "";
      description
        "Enter the Authorization list name";
    }
    leaf multicast-interface {
      type boolean;
      default "false";
      description
        "This object specifies whether multicast interface is enabled on the controller";
    }
    leaf multicast-interface-name {
      type string;
      default "default";
      description
        "This object specifies the interface, which would be used for the multicast traffic for all the clients that are associated to this WLAN.";
    }
    leaf max-associated-clients {
      type uint32;
      default "0";
      description
        "Configure maximum client connections per WLAN";
    }
    leaf max-clients-per-ap-per-wlan {
      type uint32 {
        range "0 .. 400";
      }
      default "0";
      description
        "Configure maximum client connections per AP per WLAN";
    }
    leaf max-clients-per-ap-radio-per-wlan {
      type uint32 {
        range "0 .. 200";
      }
      default "200";
      description
        "Configure maximum client connections per AP Radio per WLAN";
    }
    leaf static-ip-tunneling {
      type boolean;
      default "false";
      description
        "Configures static IP client tunneling support on a WLAN.";
    }
    leaf non-cisco-wgb {
      type boolean;
      default "false";
      description
        "Configures Non-Cisco WGB support";
    }
    leaf web-auth-on-mac-filter-failure {
      type boolean;
      default "false";
      description
        "Enables Web authentication on MAC filter failure.";
    }
    leaf webauth-mlist {
      type string;
      default "";
      description
        "Enter the Authentication list name";
    }
    leaf webauth-authorization-list {
      type string;
      default "";
      description
        "Enter the Authorization list name";
    }
    leaf webauth-parametermap {
      type string;
      default "";
      description
        "Enter the parameter-map name";
    }
    leaf ap-subscriber-policy-name {
      type string;
      default "";
      description
        "comfigures the Service policy name";
    }
    leaf ip-source-guard {
      type boolean;
      default "false";
      description
        "MAC verification";
    }
    leaf uapsd-compliant-client {
      type boolean;
      default "false";
      description
        "Configure WMM UAPSD Compliant Client support for Wlan";
    }
    leaf re-anchor-policy {
      type boolean;
      default "false";
      description
        "Confgure Re-Anchor Policy for Roamng Voice Clients";
    }
    leaf client-session-timeout {
      type uint32;
      default "2";
      description
        "The duration of client session in seconds";
    }
    leaf assisted-roaming-80211k {
      type boolean;
      default "false";
      description
        "This object indicates whether 11k Assisted Roaming Prediction Optimization is enabled on the controller for this WLAN.";
    }
    leaf dualband-neig-list-80211k {
      type boolean;
      default "false";
      description
        "This object indicates whether 11k Neighbor List Dual Band is enabled on the controller for this WLAN.";
    }
    leaf neighbor-list-80211k {
      type boolean;
      default "false";
      description
        "This object indicates whether 11k Neighbor List is enabled on the controller for this WLAN.";
    }
    leaf multicast-buffer {
      type uint8 {
        range "30 .. 60";
      }
      description
        "Configure Multicast Buffer Tuning for 802.11a radio for the WLAN";
    }
    leaf multicast-buffer-mode {
      type boolean;
      default "false";
      description
        "Configure Multicast Buffer Tuning mode for 802.11a radio for the WLAN";
    }
    container id-data {
      description
        "No need to expose in yang";
      uses wireless-wlan-cfg:wlan-data-config-file;
    }
    leaf is-remote-lan {
      type boolean;
      description
        "No need to expose in yang";
    }
    leaf cckm-tsf-tolerance {
      type uint16 {
        range "1000 .. 5000";
      }
      default "1000";
      description
        "CCKM timestamp tolerance";
    }
    leaf lan-sub-type {
      type wireless-enum-types:apf-vap-lan-sub-type;
      description
        "This object indicates whether its a wireless, guest or remote LAN";
    }
    leaf wep-key-change {
      type uint32;
      description
        "This object represents the time when the static WEP key was changed by the user.";
    }
    leaf wlan-mac-auth-over-dot1x-enabled {
      type boolean;
      description
        "This object specifies the configuration state of authentication failover to Dot1x for the WLAN.";
    }
    leaf wlan-kts-cac-support-enabled {
      type boolean;
      description
        "This object is used to configure the KTS CAC support for the WLAN";
    }
    container dot11v-data {
      description
        "No need to expose in yang";
      uses wireless-wlan-cfg:bss-802-11v;
    }
    leaf mpsk-enable {
      type boolean;
      must "(../mpsk-enable = 'false') or (../mpsk-enable = 'true' and  ../auth-key-mgmt-suite-psk = 'true')" {
        error-message "AKM PSK needs to be enabled to enable MPSK";
        error-app-tag "must-violation";
      }
      default "false";
      description
        "MPSK enabled";
    }
    container mpsk-keys {
      description
        "MPSK keys";
      list mpsk-key {
        key "priority";
        description
          "MPSK keys";
        uses wireless-wlan-cfg:st-mpsk-keys;
      }
    }
  }

  grouping policy-tag {
    description
      "Contain policy tag details";
    leaf tag-name {
      type string;
      description
        "This object uniquely identifies the policy tag";
    }
    leaf description {
      type string;
      default "";
      description
        "description for the policy tag";
    }
    container wlan-policies {
      description
        "WLAN policy configuration";
      list wlan-policy {
        key "wlan-profile-name";
        description
          "No need to expose in yang";
        uses wireless-wlan-cfg:policy-profile;
      }
    }
    container tag-child-rlan-policy-configs {
      description
        "RLAN policy configuration";
      list tag-child-rlan-policy-config {
        key "port-id";
        description
          "Configure remote lan profile and policy profile for policy tag";
        uses wireless-wlan-cfg:st-tag-child-rlan-policy-config;
      }
    }
  }

  grouping policy-profile {
    description
      "Contains policy profile details";
    leaf wlan-profile-name {
      type string;
      description
        "Name of the WLAN profile";
    }
    leaf policy-profile-name {
      type string;
      default "";
      description
        "Name of the policy profile";
    }
  }

  grouping st-user-qos-service-policy {
    description
      "Specifies information of ingress and egress service-policy names";
    leaf ingress-service-name {
      type string {
        length "0..80";
      }
      default "";
      description
        "This object specifies the ingress service-policy name. It can be system generated policy name or user-defined policy name.";
    }
    leaf egress-service-name {
      type string {
        length "0..80";
      }
      default "";
      description
        "This object specifies the egress service-policy name. It can be system generated policy name or user-defined policy name.";
    }
  }

  grouping st-user-autoqos-mode {
    description
      "This object specifies the user the status of Auto QoS";
    leaf mode {
      type wireless-enum-types:autoqos-profile;
      default "autoqos-disabled";
      description
        "This object specifies the user to enable or disable Auto QoS mode in wireless policy profile.";
    }
  }

  grouping st-wlan-mobility-settings-policy {
    description
      "This is structure to specifies wlan mobility settings.";
    leaf anchor {
      type boolean;
      default "false";
      description
        "This objects specifies that wlan mapped to the policy is an anchor wlan";
    }
  }

  grouping st-user-flow-monitor {
    description
      "This object describes traffic monitoring types and its information.";
    leaf flow-monitor-ingress-name {
      type string {
        length "0..32";
      }
      default "";
      description
        "This object represents the ingress Netflow Monitor name assigned to this profile. An empty flow monitor name should be used to de-associate the monitor from the profile.";
    }
    leaf flow-monitor-egress-name {
      type string {
        length "0..32";
      }
      default "";
      description
        "This object represents the egress Netflow Monitor name assigned to this profile. An empty flow monitor name should be used to de-associate the monitor from the profile.";
    }
  }

  grouping st-wlan-local-profiling-policy {
    description
      "This is structure to specifies wlan local profiling policy.";
    leaf device-classification {
      type boolean;
      default "false";
      description
        "This object specfies to enable or disable client device classification.A value of 'true' indicates native profiling is enabled.A value of 'false' indicates native profiling is disabled.";
    }
    leaf subscriber-policy-name {
      type string;
      default "";
      description
        "This object uniquely identifies a native profiling classification policy       configured on the Wireless LAN Controller.";
    }
    leaf radius-profiling {
      type boolean;
      default "false";
      description
        "Radius profiling";
    }
    leaf http-tlv-caching {
      type boolean;
      default "false";
      description
        "HTTP TLV caching";
    }
    leaf dhcp-tlv-caching {
      type boolean;
      default "false";
      description
        "DHCP TLV caching";
    }
  }

  grouping wlan-timeout-settings-policy {
    description
      "Contains timeout related details for wlan";
    leaf session-timeout {
      type uint32 {
        range "20 .. 86400";
      }
      default "1800";
      description
        "Configures client Session timeout";
    }
    leaf idle-timeout {
      type uint32 {
        range "15 .. 100000";
      }
      default "300";
      description
        "The duration of idle timeout in seconds";
    }
    leaf idle-threshold {
      type uint32;
      default "0";
      description
        "Configures the idle thresold";
    }
  }

  grouping wlan-data-acl-policy {
    description
      "Conatians wlan ACL config detials";
    leaf ipv4-acl {
      type string;
      default "";
      description
        "Name of IPV4 ACL";
    }
    leaf ipv6-acl {
      type string;
      default "";
      description
        "Configure the name of IPV6 ACL";
    }
    leaf layer2-acl {
      type string;
      default "";
      description
        "Configure the name of layer2 ACL";
    }
    leaf pre-auth-urlfilter-list {
      type string;
      description
        "Configure the name of pre-auth URL filter list";
    }
    leaf post-auth-urlfilter-list {
      type string;
      description
        "Configure the name of post-auth URL filter list";
    }
  }

  grouping cts-policy {
    description
      "Configuration of CTS policy";
    leaf sgacl-enforcement {
      type boolean;
      default "false";
      description
        "Configuration to enable SGACL enforcement of cts policies on the device";
    }
  }

  grouping st-wlan-aaa-policy {
    description
      "This is structure to specifies wlan aaa policy.";
    leaf aaa-override {
      type boolean;
      default "false";
      description
        "This flag is set when aaa override is enabled";
    }
    leaf nac {
      type boolean;
      default "false";
      description
        "This flag is set when NAC is enabled";
    }
    leaf aaa-policy-name {
      type string;
      default "default-aaa-policy";
      description
        "This is the name of the aaa policy name.";
    }
  }

  grouping st-wlan-wgb-policy {
    description
      "WGB Policy";
    leaf broadcast-tagging {
      type boolean;
      default "false";
      description
        "WGB Broadcast tagging";
    }
    leaf wgb-vlan {
      type boolean;
      default "false";
      description
        "Client Vlan Support";
    }
  }

  grouping wlan-flex-policy {
    description
      "Configuration of flex policy";
    leaf split-mac-acl {
      type string;
      default "";
      description
        "Configuration of split mac acl";
    }
    leaf vlan-central-switching {
      type boolean;
      default "false";
      description
        "Configuration of vlan central switching";
    }
  }

  grouping st-wlan-static-ip-mobility {
    description
      "Configuration of static IP mobility";
    leaf is-static-ip-mobility {
      type boolean;
      default "false";
      description
        "Configuration of static IP mobility";
    }
  }

  grouping wlan-switching-policy {
    description
      "Conatains wlan swtiching policy details";
    leaf central-switching {
      type boolean;
      default "true";
      description
        "Enable/disable central switching";
    }
    leaf central-authentication {
      type boolean;
      default "true";
      description
        "Enable/disable central authentication";
    }
    leaf central-dhcp {
      type boolean;
      default "true";
      description
        "Central dhcp for locally switched clients";
    }
    leaf override-nat-pat {
      type boolean;
      default "false";
      description
        "This object specifies whether Network Address Translation (NAT) and Port Address Trnaslation (PAT) are enabled on this WLAN";
    }
    leaf central-assoc-enable {
      type boolean;
      default "true";
      description
        "This object indicates the behavior of the REAP when handling the (re-)association management frames from associated to it through the WLAN policy identified";
    }
  }

  grouping st-umbrella-params {
    description
      "This table include the umbrella params for a wlan";
    leaf param-map-name {
      type string;
      default "";
      description
        "Umbrella's open dns param map name";
    }
  }

  grouping dhcp-params {
    description
      "This table include the DHCP params for a wlan";
    leaf is-dhcp-enabled {
      type boolean;
      default "false";
      description
        "DHCP required for all clients on this WLAN";
    }
    leaf dhcp-server-address {
      type inet:ip-address;
      default "0.0.0.0";
      description
        "Configures the WLAN's IPv4 DHCP Server";
    }
    leaf dhcp-opt82-enable {
      type boolean;
      default "false";
      description
        "This object represents the DHCP Option82 state";
    }
    leaf dhcp-opt82-ascii {
      type boolean;
      default "false";
      description
        "This object represents the DHCP Option82 Ascii option";
    }
    leaf dhcp-opt82-rid {
      type boolean;
      default "false";
      description
        "This object represents the DHCP Option82 Rid option";
    }
    leaf apmac {
      type boolean;
      default "false";
      description
        "This object represents the DHCP Option82 format Ap mac option";
    }
    leaf ssid {
      type boolean;
      default "false";
      description
        "This object represents the DHCP Option82 format SSID option";
    }
    leaf ap-ethmac {
      type boolean;
      default "false";
      description
        "This object represents the DHCP Option82 format Ap ethmac option";
    }
    leaf apname {
      type boolean;
      default "false";
      description
        "This object represents the DHCP Option82 format Ap name option";
    }
    leaf policy-tag {
      type boolean;
      default "false";
      description
        "This object represents the DHCP Option82 format Policy tag option";
    }
    leaf ap-location {
      type boolean;
      default "false";
      description
        "This object represents the DHCP Option82 format Ap location option";
    }
    leaf vlan-id {
      type boolean;
      default "false";
      description
        "This object represents the DHCP Option82 format Vlan_id option";
    }
    leaf dhcp-option-none {
      type boolean;
      description
        "No dhcp options are set";
    }
  }

  grouping blacklist-params {
    description
      "Set client blacklisting listing on WLAN";
    leaf is-blacklist-enabled {
      type boolean;
      default "true";
      description
        "This is the flag that can enable or disable the client backlisting feature for a WLAN.";
    }
    leaf blacklist-timeout {
      type uint32 {
        range "0 .. 2147483647";
      }
      default "60";
      description
        "Set time the client will be excluded";
    }
  }

  grouping st-atf-policy-map {
    description
      "This object encompasses the parameters for guest mobility manager database export ";
    leaf band-id {
      type uint8 {
        range "0 .. 1";
      }
      description
        "Band ID of the ATF Policy";
    }
    leaf atf-policy-name {
      type string {
        length "0..31";
      }
      default "default-atf-policy";
      description
        "Air Time Fairness policy name";
    }
  }

  grouping st-wlan-policies {
    description
      "This is structure to specifies wlan policies information.";
    leaf policy-profile-name {
      type string;
      description
        "This object specifies one instance of a WLAN policy on the controller.";
    }
    leaf description {
      type string;
      default "";
      description
        "This object specifies the description associated to this WLAN policy.This can be any user defined string";
    }
    leaf status {
      type boolean;
      default "false";
      description
        "This object specifies whether the policy profile is shutdown or active";
    }
    leaf passive-client {
      type boolean;
      default "false";
      description
        "This object specifies whether passive-client support is enabled or not on a policy";
    }
    leaf interface-name {
      type string;
      default "1";
      description
        "This object represents the interface attached to the wireless lan.";
    }
    leaf mcast-vlan-id {
      type uint32 {
        range "1 .. 4094";
      }
      description
        "Multicast Vlan Id attached to the wireless lan.";
    }
    container wlan-switching-policy {
      description
        "This is structure to specifies wlan switching policy";
      uses wireless-wlan-cfg:wlan-switching-policy;
    }
    container wlan-flex-policy {
      description
        "This structure specifies wlan flex policies";
      uses wireless-wlan-cfg:wlan-flex-policy;
    }
    container static-ip-mobility {
      description
        "This structure specifies whether static ip mobility support is enabled or disabled.";
      uses wireless-wlan-cfg:st-wlan-static-ip-mobility;
    }
    container wlan-acl {
      description
        "This structure specifies ipv4 and ipv6 and layer2 acl name mapped to the policies.";
      uses wireless-wlan-cfg:wlan-data-acl-policy;
    }
    container wlan-timeout {
      description
        "This structure encompases of timeout related details for the wlan policy profile. ";
      uses wireless-wlan-cfg:wlan-timeout-settings-policy;
    }
    container wlan-local-profiling {
      description
        "This encompasses of wlan local policy profile details.";
      uses wireless-wlan-cfg:st-wlan-local-profiling-policy;
    }
    container wlan-mobility {
      description
        "This encompasses of wlan mobility related configuiration for the policy profile. ";
      uses wireless-wlan-cfg:st-wlan-mobility-settings-policy;
    }
    container flow-monitor-ipv4 {
      description
        "This structure specifies ipv4 ingress and egress flow monitor.";
      uses wireless-wlan-cfg:st-user-flow-monitor;
    }
    container flow-monitor-ipv6 {
      must "../wlan-switching-policy/central-switching = 'true' or (string-length(flow-monitor-ingress-name) = 0 and string-length(flow-monitor-egress-name) = 0)" {
        error-message "WLAN switching policy central-switching should be enabled when using IPv6 flow monitors";
        error-app-tag "must-violation";
      }
      description
        "This structure specifies ipv6 ingress and egress flow monitor.";
      uses wireless-wlan-cfg:st-user-flow-monitor;
    }
    container flow-monitor-datalink {
      description
        "This structure specifies datalink ingress and egress flow monitor.";
      uses wireless-wlan-cfg:st-user-flow-monitor;
    }
    leaf nbar-protocol-discovery {
      type boolean;
      must "../wlan-switching-policy/central-switching = 'true' or current() = 'false'" {
        error-message "WLAN switching policy central-switching should be enabled when NBAR Protocol Discovery is enabled.";
        error-app-tag "must-violation";
      }
      default "false";
      description
        "This object allows the user to enable or disable NBAR Protocol Discovery for a wlan. A value of 'true' indicates NBAR protocol discovery is active, a 'false' value indicates NBAR protocol discovery is disabled";
    }
    leaf reanchor-classmap-name {
      type string;
      must "../wlan-switching-policy/central-switching = 'true' or string-length() = 0" {
        error-message "WLAN switching policy central-switching should be enabled when using selective reanchoring feature";
        error-app-tag "must-violation";
      }
      must "string-length(../flow-monitor-ipv4/flow-monitor-ingress-name) > 0 or string-length(../flow-monitor-ipv4/flow-monitor-egress-name) > 0 or string-length(../flow-monitor-ipv6/flow-monitor-ingress-name) > 0  or string-length(../flow-monitor-ipv6/flow-monitor-egress-name) > 0 or string-length() = 0" {
        error-message "At least one flow monitor should be enabled when using selective reanchoring feature";
        error-app-tag "must-violation";
      }
      must "string-length() = 0 or current() = 'AVC-Reanchor-Class'" {
        error-message "The value of classmap used for selective reanchoring feature must be either empty (disabled) or 'AVC-Reanchor-Class'";
        error-app-tag "must-violation";
      }
      default "";
      description
        "This object specifies the classmap containing protocols to decide on selective reanchoring";
    }
    container per-ssid-qos {
      description
        "This object keeps ingress and egress service names.";
      uses wireless-wlan-cfg:st-user-qos-service-policy;
    }
    container per-client-qos {
      description
        "This object specifies the per client ingress and egress service names";
      uses wireless-wlan-cfg:st-user-qos-service-policy;
    }
    container autoqos-mode {
      description
        "Specifies the mode of autoqos.";
      uses wireless-wlan-cfg:st-user-autoqos-mode;
    }
    container dhcp-params {
      description
        "Keeps various information of Dhcp such as is_dhcp_enabled,dhcp_server_address etc.";
      uses wireless-wlan-cfg:dhcp-params;
    }
    container cts-policy {
      description
        "This structure specifies CTS policy for the wireless profile.";
      uses wireless-wlan-cfg:cts-policy;
    }
    leaf inline-tagging {
      type boolean;
      default "false";
      description
        "Configuration to enable inline tagging for client";
    }
    leaf sgt {
      type uint16 {
        range "2 .. 65519";
      }
      description
        "Configuration of default SGT value";
    }
    container umbrella-params {
      description
        "Keeps information of policies that can be enforced via umbrella.";
      uses wireless-wlan-cfg:st-umbrella-params;
    }
    container blacklist-params {
      description
        "This object keeps information for client backlisting feature for a WLAN.";
      uses wireless-wlan-cfg:blacklist-params;
    }
    container aaa-policy-params {
      description
        "This object specifies various attributes of WLAN policy. such as polici profile name etc.";
      uses wireless-wlan-cfg:st-wlan-aaa-policy;
    }
    container et-analytics-params {
      description
        "This object specifies whether encrption enabled or disabled.";
      uses wireless-wlan-cfg:st-et-analytics;
    }
    container wgb-policy-params {
      description
        "WGB Policy Params";
      uses wireless-wlan-cfg:st-wlan-wgb-policy;
    }
    leaf fabric-profile-name {
      type string;
      default "";
      description
        "Specifies the fabric profile name configured on the policy profile.";
    }
    leaf accounting-list {
      type string;
      default "";
      description
        "Specifies the accounting list configured on the policy profile.";
    }
    leaf client-count {
      type uint32 {
        range "0 .. 200";
      }
      description
        "Maximum client that can join the wlan mapped to policy profile.";
    }
    container atf-policy-map-entries {
      description
        "ATF Policy Mapping configuration";
      list atf-policy-map-entry {
        key "band-id";
        description
          "ATF Policies associated to policy profile";
        uses wireless-wlan-cfg:st-atf-policy-map;
      }
    }
    container guest-mm-db-export-entries {
      description
        "Guest mm DB configuration";
      list guest-mm-db-export-entry {
        key "ip";
        description
          "Guest mm DB associated to policy profile";
        uses wireless-wlan-cfg:st-guest-mm-db-export;
      }
    }
    leaf call-snoop {
      type boolean;
      must "(../call-snoop = 'true' and ../per-ssid-qos/ingress-service-name = 'platinum-up' and ../per-ssid-qos/egress-service-name = 'platinum') or (../call-snoop = 'false' and (../per-ssid-qos/ingress-service-name = 'platinum-up' and ../per-ssid-qos/egress-service-name = 'platinum')) or (../call-snoop = 'false' and (../per-ssid-qos/ingress-service-name != 'platinum-up' or ../per-ssid-qos/egress-service-name != 'platinum'))" {
        error-message "SSID policies should be configured with Platinum when Call Snoop is enabled";
        error-app-tag "must-violation";
      }
      default "false";
      description
        "Enable or Disable call snoop for the wlan mapped to policy profile.";
    }
    leaf sip-cac-send-dis-assoc {
      type boolean;
      default "false";
      description
        "Enable or Disable SIP CAC send disassociate.";
    }
    leaf sip-cac-send-486-busy {
      type boolean;
      default "false";
      description
        "Enable or Disable SIP CAC send 486 busy.";
    }
    leaf tunnel-profile-name {
      type string {
        length "0..128";
      }
      default "";
      description
        "Tunnel profile name";
    }
  }

  grouping st-guest-mm-db-export {
    description
      "This object encompasses the parameters for guest mobility manager database export ";
    leaf ip {
      type inet:ip-address;
      description
        "IP address of the mobility anchor";
    }
    leaf anchor-priority {
      type wireless-enum-types:enm-export-anchor-priority-type;
      default "export-anchor-tertiary";
      description
        "Priority of the mobility anchor";
    }
  }

  grouping st-nas-id-aaa-config {
    description
      "These are the different NAS-ID options";
    leaf option1 {
      type wireless-types:enm-nas-id-options;
      default "nas-id-sys-name";
      description
        "Radius NAS-ID option1";
    }
    leaf option2 {
      type wireless-types:enm-nas-id-options;
      default "nas-id-not-configured";
      description
        "Radius NAS-ID option2";
    }
    leaf option3 {
      type wireless-types:enm-nas-id-options;
      default "nas-id-not-configured";
      description
        "Radius NAS-ID option3";
    }
  }

  grouping st-wireless-aaa-policy-config {
    description
      "This is the Wireless AAA policy conifguration";
    leaf policy-name {
      type string;
      description
        "This is the policy name";
    }
    container nas-id {
      description
        "Different NAS-ID options";
      uses wireless-wlan-cfg:st-nas-id-aaa-config;
    }
    leaf aaa-realm {
      type boolean;
      description
        "Indicates if AAA-REALM is enabled/disabled";
    }
  }

  grouping st-tag-child-rlan-policy-config {
    description
      "RLAN policy Child table structure";
    leaf port-id {
      type uint16 {
        range "1 .. 4";
      }
      description
        "This is port id where policy should be applied";
    }
    leaf rlan-profile-name {
      type string;
      description
        "This is the name of the RLAN config ";
    }
    leaf rlan-policy-profile-name {
      type string;
      description
        "This is the name of the RLAN policy config ";
    }
  }

  container wlan-cfg-data {
    description
      "This yang file includes the configuration of wlan param and policies";
    container wlan-cfg-entries {
      description
        "WLAN config params";
      list wlan-cfg-entry {
        key "profile-name";
        unique "vap-id";
        description
          "List of WLAN config params";
        uses wireless-wlan-cfg:wlan-profile {
          refine "vap-id" {
            mandatory true;
          }
        }
      }
    }
    container wlan-policies {
      description
        "WLAN policy configuration";
      list wlan-policy {
        key "policy-profile-name";
        description
          "List of WLAN policy configurations";
        uses wireless-wlan-cfg:st-wlan-policies;
      }
    }
    container policy-list-entries {
      description
        "Policy list configuration";
      list policy-list-entry {
        key "tag-name";
        description
          "This object specifies the policy tag name and 
           also hosts the mapping between a Wlan and policy profile";
        uses wireless-wlan-cfg:policy-tag;
      }
    }
    container wireless-aaa-policy-configs {
      description
        "Wireless AAA policy Configurations";
      list wireless-aaa-policy-config {
        key "policy-name";
        description
          "The wireless AAA policy configurations";
        uses wireless-wlan-cfg:st-wireless-aaa-policy-config;
      }
    }
  }
}
