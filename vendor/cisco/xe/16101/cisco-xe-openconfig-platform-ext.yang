module cisco-xe-openconfig-platform-ext {
    namespace "http://cisco.com/ns/yang/cisco-xe-openconfig-platform-ext";
    
    prefix oc-platform-ext;

    import openconfig-platform {
       prefix oc-platform;
    }

    import openconfig-platform-types {
       prefix oc-platform-types;
    }

    import openconfig-transport-types {
       prefix oc-opt-types;
    }

    organization "Cisco Systems";

    description
       "Augmentation for oc-platform";

////////////////////////////////////////////////////////////////////////////
// REVISION
///////////////////////////////////////////////////////////////////////////

 revision 2018-02-05 {
   description "Add UNKNOWN for connector type";
 }

 revision 2017-05-11 {
   description "Initial Draft to add type CONTAINER";
 }

////////////////////////////////////////////////////////////////////////////
// IDENTITY
///////////////////////////////////////////////////////////////////////////

  identity CONTAINER {
    base oc-platform-types:OPENCONFIG_HARDWARE_COMPONENT;
    description
      "Cisco added type CONTAINER";
  }

  identity UNKNOWN_CONNECTOR {
    base oc-opt-types:FIBER_CONNECTOR_TYPE;
    description
      "unknown type connector";
  }
}
