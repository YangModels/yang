module Cisco-IOS-XE-wsa-types {
  yang-version 1;
  namespace "http://cisco.com/ns/yang/Cisco-IOS-XE-wsa-types";
  prefix wsa-types;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wsa data types.
     Copyright (c) 2018 by Cisco Systems, Inc.
     All rights reserved.";

  revision 2018-10-08 {
    description
      "Addition of event reason enums";
    reference "1.1.0";
  }
  revision 2018-06-11 {
    description
      "Initial revision";
    reference "1.0.0";
  }

  typedef wsa-client-event-result {
    type enumeration {
      enum "wsa-cl-event-success" {
        value 0;
        description
          "WSA client event success";
      }
      enum "wsa-cl-event-failure" {
        value 1;
        description
          "WSA client event failure";
      }
    }
    description
      "Enumeration for wsa client event result";
  }

  typedef wsa-client-events {
    type enumeration {
      enum "wsa-cl-event-invalid" {
        value 0;
        description
          "WSA client event type invalid";
      }
      enum "wsa-cl-event-idle" {
        value 1;
        description
          "WSA client event type idle. Represents the client has transitioned into idle state";
      }
      enum "wsa-cl-event-associating" {
        value 2;
        description
          "WSA client event type associating. Used to indicate that the client is trying to associate";
      }
      enum "wsa-cl-event-associated" {
        value 3;
        description
          "WSA client event type associated. Used to indicate that the client has associated to the Access point";
      }
      enum "wsa-cl-event-authenticating" {
        value 4;
        description
          "WSA client event type authenticating. Used to indicate that the client is in the the process of authenticating";
      }
      enum "wsa-cl-event-authenticated" {
        value 5;
        description
          "WSA client event type authenticated. Used to indicate that the client has been Authenticated";
      }
      enum "wsa-cl-event-mobility-discovery" {
        value 6;
        description
          "WSA client event type mobility discovery. Used to indicate that the client is in mobility discovery phase";
      }
      enum "wsa-cl-event-mobility-complete" {
        value 7;
        description
          "WSA client event type mobility complete. Used to indicate that the client is in mobility complete phase";
      }
      enum "wsa-cl-event-ip-learning" {
        value 8;
        description
          "WSA client event type ip learning. Used to indicate that the client is in the process of learning the IP";
      }
      enum "wsa-cl-event-ip-learn-complete" {
        value 9;
        description
          "WSA client event type ip learn complete. Used to indicate that the client has completed the IP learn process";
      }
      enum "wsa-cl-event-webauth-required" {
        value 10;
        description
          "WSA client event type web authentication required. Used to indicate that the client web authentication is pending";
      }
      enum "wsa-cl-event-webauth-complete" {
        value 11;
        description
          "WSA client event type web authentication complete. Used to indicate that the client has completed web authentication";
      }
      enum "wsa-cl-event-dpath-plumb-in-progress" {
        value 12;
        description
          "WSA client event type datapath plumb in progress. Used indicate that the datapath is being programmed for the client";
      }
      enum "wsa-cl-event-dpath-plumb-complete" {
        value 13;
        description
          "WSA client event type datapath plumb complete. Used indicate that the datapath programming for the client has completed";
      }
      enum "wsa-cl-event-run" {
        value 14;
        description
          "WSA client event type run. Used to indicate that the client has moved to run state";
      }
      enum "wsa-cl-event-delete-in-progress" {
        value 15;
        description
          "WSA client event type delete in progress. Used to indicate that the client delete is in progress";
      }
      enum "wsa-cl-event-deleted" {
        value 16;
        description
          "WSA client event type deleted. Used to indicate that the client has been deleted";
      }
      enum "wsa-cl-event-blacklisted" {
        value 17;
        description
          "WSA client event type blacklisted. Used to indicate that the client has been blacklisted";
      }
    }
    description
      "Enumeration for wsa client event type";
  }

  typedef wsa-client-event-reason-3p {
    type enumeration {
      enum "wsa-cl-evt-reason-none" {
        value 0;
        description
          "WSA client event reason none";
      }
      enum "wsa-cl-evt-reason-co-client-connect-timeout" {
        value 1;
        description
          "WSA client event reason client connect timed out";
      }
      enum "wsa-cl-evt-reason-authif-authen-result" {
        value 2;
        description
          "WSA client event reason when authentication result is available";
      }
      enum "wsa-cl-evt-reason-exclusion-assoc-fail" {
        value 3;
        description
          "WSA client event reason when association failed for exclusion";
      }
      enum "wsa-cl-evt-reason-dot11-reassoc-no-assoc" {
        value 4;
        description
          "WSA client event reason dot11 reassociation found without preexisting association";
      }
      enum "wsa-cl-evt-reason-iplearn-dhcp-decline" {
        value 5;
        description
          "WSA client event reason iplearn dhcp offer was declined";
      }
      enum "wsa-cl-evt-reason-iplearn-dhcp-nack" {
        value 6;
        description
          "WSA client event reason iplearn dhcp nack by DHCP server";
      }
      enum "wsa-cl-evt-reason-exclusion-dot11-auth-fail" {
        value 7;
        description
          "WSA client event reason exclusion dot11 authentication fail";
      }
      enum "wsa-cl-evt-reason-exclude-dot11-auth-fail" {
        value 8;
        description
          "WSA client event reason exclude dot11 authentication fail";
      }
      enum "wsa-cl-evt-reason-dot11-denied-rates" {
        value 9;
        description
          "WSA client event reason when provided dot11 rates are denied";
      }
      enum "wsa-cl-evt-reason-dot11-not-supported-auth-alg" {
        value 10;
        description
          "WSA client event reason dot11 authentication algorithm is not supported";
      }
      enum "wsa-cl-evt-reason-exclude-ip-theft" {
        value 11;
        description
          "WSA client event reason excluded because of ip theft";
      }
      enum "wsa-cl-evt-reason-exclusion-ip-theft" {
        value 12;
        description
          "WSA client event reason exclusion because of ip theft";
      }
      enum "wsa-cl-evt-reason-dot11-cipher-suite-rejected" {
        value 13;
        description
          "WSA client event reason dot11 cipher suite rejected";
      }
      enum "wsa-cl-evt-reason-session-timeout" {
        value 14;
        description
          "WSA client event reason session timeout - occurs only for openauth and MAB (mac-filter) security";
      }
      enum "wsa-cl-evt-reason-idle-timeout" {
        value 15;
        description
          "WSA client event reason idle timeout - client was idle for too long";
      }
      enum "wsa-cl-evt-reason-connect-timeout" {
        value 16;
        description
          "WSA client event reason connect timeout - client took too long to connect";
      }
      enum "wsa-cl-evt-reason-dot11-assoc-denied-unspec" {
        value 17;
        description
          "WSA client event reason dot11 association denied unspec";
      }
      enum "wsa-cl-evt-reason-dot11-poor-channel-conditions" {
        value 18;
        description
          "WSA client event reason dot11 poor channel conditions";
      }
      enum "wsa-cl-evt-reason-exclusion-vlan-fail" {
        value 19;
        description
          "WSA client event reason exclusion vlan fail";
      }
      enum "wsa-cl-evt-reason-exclude-vlan-fail" {
        value 20;
        description
          "WSA client event reason exclude vlan fail";
      }
      enum "wsa-cl-evt-reason-dot11-ccx-non-optimal-association-choice" {
        value 21;
        description
          "WSA client event reason dot11 ccx non optimal association choice";
      }
      enum "wsa-cl-evt-reason-dot11-invalid-rsn-ie-capabilities" {
        value 22;
        description
          "WSA client event reason dot11 invalid rsn ie capabilities";
      }
      enum "wsa-cl-evt-reason-group-key-update-timeout" {
        value 23;
        description
          "WSA client event reason group key update timeout";
      }
      enum "wsa-cl-evt-reason-exclusion-web-auth-fail" {
        value 24;
        description
          "WSA client event reason exclusion web authentication fail";
      }
      enum "wsa-cl-evt-reason-exclude-web-auth-fail" {
        value 25;
        description
          "WSA client event reason exclude web authentication fail";
      }
      enum "wsa-cl-evt-reason-key-xchng-timeout" {
        value 26;
        description
          "WSA client event reason key xchng timeout";
      }
      enum "wsa-cl-evt-reason-deauth-or-disassoc-req" {
        value 27;
        description
          "WSA client event reason deauthentication or disassociation request";
      }
      enum "wsa-cl-evt-reason-client-user-triggered-disassoc" {
        value 28;
        description
          "WSA client event reason client user triggered disassoc";
      }
      enum "wsa-cl-evt-reason-client-eap-id-timeout" {
        value 29;
        description
          "WSA client event reason client eap id timeout";
      }
      enum "wsa-cl-evt-reason-mab-failed" {
        value 30;
        description
          "WSA client event reason mab failed";
      }
      enum "wsa-cl-evt-reason-key-mgmt-invalid-key" {
        value 31;
        description
          "WSA client event reason key mgmt invalid key";
      }
      enum "wsa-cl-evt-reason-key-mgmt-key-desc-ver" {
        value 32;
        description
          "WSA client event reason key mgmt key desc ver";
      }
      enum "wsa-cl-evt-reason-key-mgmt-mic-validation" {
        value 33;
        description
          "WSA client event reason key mgmt mic validation";
      }
      enum "wsa-cl-evt-reason-key-mgmt-invalid-frame" {
        value 34;
        description
          "WSA client event reason key mgmt invalid frame";
      }
      enum "wsa-cl-evt-reason-key-mgmt-no-mic-bit" {
        value 35;
        description
          "WSA client event reason key mgmt no mic bit";
      }
      enum "wsa-cl-evt-reason-wlan-change" {
        value 36;
        description
          "WSA client event reason wlan change";
      }
      enum "wsa-cl-evt-reason-client-dot1x-timeout" {
        value 37;
        description
          "WSA client event reason client dot1x timeout";
      }
      enum "wsa-cl-evt-reason-exclude-dot1x-timeout" {
        value 38;
        description
          "WSA client event reason exclude dot1x timeout";
      }
      enum "wsa-cl-evt-reason-exclusion-dot1x-timeout" {
        value 39;
        description
          "WSA client event reason exclusion dot1x timeout";
      }
      enum "wsa-cl-evt-reason-exclusion-dot1x-auth-fail" {
        value 40;
        description
          "WSA client event reason exclusion dot1x authentication fail";
      }
      enum "wsa-cl-evt-reason-exclude-dot1x-auth-fail" {
        value 41;
        description
          "WSA client event reason exclude dot1x authentication fail";
      }
      enum "wsa-cl-evt-reason-iplearn-dhcp-discovery" {
        value 42;
        description
          "WSA client event reason iplearn dhcp discovery";
      }
      enum "wsa-cl-evt-reason-iplearn-dhcp-offer" {
        value 43;
        description
          "WSA client event reason iplearn dhcp offer";
      }
      enum "wsa-cl-evt-reason-iplearn-dhcp-request" {
        value 44;
        description
          "WSA client event reason iplearn dhcp request";
      }
      enum "wsa-cl-evt-reason-iplearn-dhcp-ack" {
        value 45;
        description
          "WSA client event reason iplearn dhcp ack";
      }
      enum "wsa-cl-evt-reason-iplearn-rcv-client-ip" {
        value 46;
        description
          "WSA client event reason iplearn rcv client ip";
      }
      enum "wsa-cl-evt-reason-dot11-invalid-mdie" {
        value 47;
        description
          "WSA client event reason dot11 invalid mdie";
      }
      enum "wsa-cl-evt-reason-dot11-invalid-pmkid" {
        value 48;
        description
          "WSA client event reason dot11 invalid Paire Wise Master Key ID";
      }
      enum "wsa-cl-evt-reason-dot11-invalid-ftie" {
        value 49;
        description
          "WSA client event reason dot11 invalid Fast Transition dot11 IE";
      }
      enum "wsa-cl-evt-reason-inter-ctrl-roam-success" {
        value 50;
        description
          "WSA client event reason inter controller roam success";
      }
      enum "wsa-cl-evt-reason-intra-ctrl-roam-success" {
        value 51;
        description
          "WSA client event reason intra controller roam success";
      }
      enum "wsa-cl-evt-reason-intra-ctrl-roam-failure" {
        value 52;
        description
          "WSA client event reason intra controller roam failure";
      }
      enum "wsa-cl-evt-reason-ap-delete-mn" {
        value 53;
        description
          "WSA client event reason ap deleting mobile";
      }
      enum "wsa-cl-evt-reason-dot11-challenge-fail" {
        value 54;
        description
          "WSA client event reason dot11 challenge fail";
      }
      enum "wsa-cl-evt-reason-key-mgmt-wrong-replay-counter" {
        value 55;
        description
          "WSA client event reason key mgmt wrong replay counter";
      }
      enum "wsa-cl-evt-reason-missing-context" {
        value 56;
        description
          "WSA client event reason missing context";
      }
      enum "wsa-cl-evt-reason-dot11-max-sta" {
        value 57;
        description
          "WSA client event reason dot11 maximum wireless client reached";
      }
      enum "wsa-cl-evt-reason-dot11-invalid-ftie-mic" {
        value 58;
        description
          "WSA client event reason dot11 invalid FT IE message integrity check";
      }
      enum "wsa-cl-evt-reason-co-macauth-result" {
        value 59;
        description
          "WSA client event reason mac authentication result is being provided";
      }
      enum "wsa-cl-evt-reason-co-macauth-reqd" {
        value 60;
        description
          "WSA client event reason mac authentication requested";
      }
      enum "wsa-cl-evt-reason-eap-key-retry-timeout" {
        value 61;
        description
          "WSA client event reason eap key retry timeout";
      }
      enum "wsa-cl-evt-reason-exclusion-policy-failure" {
        value 62;
        description
          "WSA client event reason exclusion policy failure";
      }
      enum "wsa-cl-evt-reason-exclude-policy-failure" {
        value 63;
        description
          "WSA client event reason exclude policy failure";
      }
      enum "wsa-cl-evt-reason-exclude-policy-bind-fail" {
        value 64;
        description
          "WSA client event reason exclude policy bind fail";
      }
      enum "wsa-cl-evt-reason-exclusion-policy-bind-fail" {
        value 65;
        description
          "WSA client event reason exclusion policy bind fail";
      }
      enum "wsa-cl-evt-reason-abort-received" {
        value 66;
        description
          "WSA client event reason internal transaction abort";
      }
      enum "wsa-cl-evt-reason-radio-down" {
        value 67;
        description
          "WSA client event reason AP radio down";
      }
      enum "wsa-cl-evt-reason-assoc-connect-timeout" {
        value 68;
        description
          "WSA client event reason association timed out";
      }
      enum "wsa-cl-evt-reason-macauth-connect-timeout" {
        value 69;
        description
          "WSA client event reason macauth timed out";
      }
      enum "wsa-cl-evt-reason-l2auth-connect-timeout" {
        value 70;
        description
          "WSA client event reason l2 authentication timed out";
      }
      enum "wsa-cl-evt-reason-l3auth-connect-timeout" {
        value 71;
        description
          "WSA client event reason l3 authentication timed out";
      }
      enum "wsa-cl-evt-reason-mobility-connect-timeout" {
        value 72;
        description
          "WSA client event reason mobility timed out";
      }
      enum "wsa-cl-evt-reason-static-ip-anchor-connect-timeout" {
        value 73;
        description
          "WSA client event reason static IP anchor discovery timed out";
      }
      enum "wsa-cl-evt-reason-session-connect-timeout" {
        value 74;
        description
          "WSA client event reason wieless session timed out";
      }
      enum "wsa-cl-evt-reason-iplearn-connect-timeout" {
        value 75;
        description
          "WSA client event reason iplearn timed out";
      }
    }
    description
      "Enumeration for wsa client event reason";
  }

  typedef wsa-client-event-reason-addon-3p {
    type enumeration {
      enum "wsa-cl-evt-reason-addon-none" {
        value 0;
        description
          "WSA client event reason addon none";
      }
      enum "wsa-cl-evt-reason-addon-iplearn-dhcp-discovery-timeout" {
        value 1;
        description
          "WSA client event reason addon iplearn dhcp discovery timeout";
      }
      enum "wsa-cl-evt-reason-addon-iplearn-dhcp-request-timeout" {
        value 2;
        description
          "WSA client event reason addon iplearn dhcp request timeout";
      }
      enum "wsa-cl-evt-reason-addon-iplearn-dhcp-offer-timeout" {
        value 3;
        description
          "WSA client event reason addon iplearn dhcp offer timeout";
      }
      enum "wsa-cl-evt-reason-addon-sm-auth-event-fail-authc" {
        value 4;
        description
          "WSA client event reason addon authentication event fail authc";
      }
      enum "wsa-cl-evt-reason-addon-sm-auth-event-fail-timeout" {
        value 5;
        description
          "WSA client event reason addon authentication event fail timeout";
      }
      enum "wsa-cl-evt-reason-addon-sm-auth-event-fail-aaa-server" {
        value 6;
        description
          "WSA client event reason addon authentication event fail aaa server";
      }
      enum "wsa-cl-evt-reason-addon-sm-auth-event-fail-no-resp" {
        value 7;
        description
          "WSA client event reason addon authentication event fail no resp";
      }
      enum "wsa-cl-evt-reason-addon-client-acl-mismatch" {
        value 8;
        description
          "WSA client event reason addon client acl mismatch";
      }
      enum "wsa-cl-evt-reason-addon-exclusion-max-mac-auth-failures" {
        value 9;
        description
          "WSA client event reason addon exclusion max mac authentication failures";
      }
      enum "wsa-cl-evt-reason-addon-exclusion-max-invalid-assoc-attempts" {
        value 10;
        description
          "WSA client event reason addon exclusion max invalid assoc attempts";
      }
      enum "wsa-cl-evt-reason-addon-mob-timeout" {
        value 11;
        description
          "WSA client event reason addon mobility timeout";
      }
      enum "wsa-cl-evt-reason-addon-mob-client-handoff-success" {
        value 12;
        description
          "WSA client event reason addon mobility client handoff success";
      }
      enum "wsa-cl-evt-reason-addon-mob-client-handoff-failure" {
        value 13;
        description
          "WSA client event reason addon mobility client handoff failure";
      }
      enum "wsa-cl-evt-reason-addon-intra-ap-roam" {
        value 14;
        description
          "WSA client event reason addon intra ap roam";
      }
      enum "wsa-cl-evt-reason-addon-idle-timeout" {
        value 15;
        description
          "WSA client event reason addon idle timeout";
      }
      enum "wsa-cl-evt-reason-addon-sa-query-timeout" {
        value 16;
        description
          "WSA client event reason addon sa query timeout";
      }
      enum "wsa-cl-evt-reason-addon-reassoc-timeout" {
        value 17;
        description
          "WSA client event reason addon reassoc timeout";
      }
      enum "wsa-cl-evt-reason-addon-dhcp-timeout" {
        value 18;
        description
          "WSA client event reason addon dhcp timeout";
      }
    }
    description
      "Enumeration for wsa client event reason addon";
  }
}
