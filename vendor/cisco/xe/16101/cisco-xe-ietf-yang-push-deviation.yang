module cisco-xe-ietf-yang-push-deviation {
  namespace "http://cisco.com/ns/yang/cisco-xe-ietf-yang-push-deviation";

  prefix yp-devs;

  import ietf-yang-types {
    prefix yang;
  }

  import ietf-event-notifications {
    prefix notif-bis;
  }

  import ietf-yang-push {
    prefix yp;
  }

  import cisco-xe-ietf-yang-push-ext {
    prefix cyp;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for ietf-yang-push
     module.
     Copyright (c) 2017 by Cisco Systems, Inc.
     All rights reserved.";

  revision 2017-08-22 {
    description
      "Suppressed unsupported elements of establish-subscription";
  }

  revision 2017-02-22 {
    description
      "Initial Revision";

    reference
      "RFC 6020: YANG - A Data Modeling Language for the
       Network Configuration Protocol (NETCONF)";

  }

  deviation "/notif-bis:modify-subscription" {
    deviate not-supported;
    description  "Currently not supported.";
  }

  /*
   *
  deviation "/notif-bis:establish-subscription/notif-bis:input" +
            "/notif-bis:filter-type/yp:update-filter/yp:update-filter/yp:subtree" {
    deviate not-supported;
    description  "Currently not supported.";
  }
  */

  deviation "/notif-bis:establish-subscription/notif-bis:input" +
            "/yp:update-trigger/yp:periodic/yp:anchor-time" {
    deviate not-supported;
    description  "Currently not supported.";
  }

  deviation "/notif-bis:establish-subscription/notif-bis:input" +
            "/yp:update-trigger/yp:on-change/yp:dampening-period" {
    deviate replace {
      type yang:timeticks {
        range "0";
      }
    }
    description  "Currently only accepts 0.";
  }

  deviation "/notif-bis:establish-subscription/notif-bis:input" +
            "/yp:update-trigger/yp:on-change/yp:excluded-change" {
    deviate not-supported;
    description  "Currently not supported.";
  }

  deviation "/notif-bis:establish-subscription/notif-bis:input" +
            "/yp:dscp" {
    deviate not-supported;
    description  "Currently not supported.";
  }

  deviation "/notif-bis:establish-subscription/notif-bis:input" +
            "/yp:subscription-priority" {
    deviate not-supported;
    description  "Currently not supported.";
  }

  deviation "/notif-bis:establish-subscription/notif-bis:input" +
            "/yp:subscription-dependency" {
    deviate not-supported;
    description  "Currently not supported.";
  }

  /*
   * ==============================
   * subscription-config
   * ==============================
   */

  /*
   *
  deviation "/notif-bis:subscription-config/notif-bis:subscription" +
            "/notif-bis:filter-type/yp:update-filter/yp:update-filter/yp:subtree" {
    deviate not-supported;
    description  "Currently not supported.";
  }
   */

  deviation "/notif-bis:subscription-config/notif-bis:subscription" +
            "/yp:update-trigger/yp:periodic/yp:anchor-time" {
    deviate not-supported;
    description  "Currently not supported.";
  }

  deviation "/notif-bis:subscription-config/notif-bis:subscription" +
            "/yp:update-trigger/yp:on-change/yp:dampening-period" {
    deviate not-supported;
    description  "Currently not supported.";
  }

  deviation "/notif-bis:subscription-config/notif-bis:subscription" +
            "/yp:update-trigger/yp:on-change/yp:excluded-change" {
    deviate not-supported;
    description  "Currently not supported.";
  }

  deviation "/notif-bis:subscription-config/notif-bis:subscription" +
            "/yp:dscp" {
    deviate not-supported;
    description  "Currently not supported.";
  }

  deviation "/notif-bis:subscription-config/notif-bis:subscription" +
            "/yp:subscription-priority" {
    deviate not-supported;
    description  "Currently not supported.";
  }

  deviation "/notif-bis:subscription-config/notif-bis:subscription" +
            "/yp:subscription-dependency" {
    deviate not-supported;
    description  "Currently not supported.";
  }

  /*
   * ==============================
   * subscriptions
   * ==============================
   */

  /*
   *
  deviation "/notif-bis:subscriptions/notif-bis:subscription" +
            "/notif-bis:filter-type/yp:update-filter/yp:update-filter/yp:subtree" {
    deviate not-supported;
    description  "Currently not supported.";
  }
   */

  deviation "/notif-bis:subscriptions/notif-bis:subscription" +
            "/yp:update-trigger/yp:periodic/yp:anchor-time" {
    deviate not-supported;
    description  "Currently not supported.";
  }

  deviation "/notif-bis:subscriptions/notif-bis:subscription" +
            "/yp:update-trigger/yp:on-change/yp:dampening-period" {
    deviate not-supported;
    description  "Currently not supported.";
  }

  deviation "/notif-bis:subscriptions/notif-bis:subscription" +
            "/yp:update-trigger/yp:on-change/yp:excluded-change" {
    deviate not-supported;
    description  "Currently not supported.";
  }

  deviation "/notif-bis:subscriptions/notif-bis:subscription" +
            "/yp:dscp" {
    deviate not-supported;
    description  "Currently not supported.";
  }

  deviation "/notif-bis:subscriptions/notif-bis:subscription" +
            "/yp:subscription-priority" {
    deviate not-supported;
    description  "Currently not supported.";
  }

  deviation "/notif-bis:subscriptions/notif-bis:subscription" +
            "/yp:subscription-dependency" {
    deviate not-supported;
    description  "Currently not supported.";
  }



}
