module Cisco-IOS-XE-wireless-rf-profile-oper {
  yang-version 1;
  namespace "http://cisco.com/ns/yang/Cisco-IOS-XE-wireless-rf-profile-oper";
  prefix wireless-rf-profile-oper;

  import Cisco-IOS-XE-wireless-rrm-types {
    prefix wireless-rrm-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Wireless RF(Radio-Frequency) profile operational data
     Copyright (c) 2016-2018 by Cisco Systems, Inc.
     All rights reserved.";

  revision 2018-02-08 {
    description
      "Initial revision";
    reference "1.0.0";
  }

  grouping st-rf-profile-oper {
    description
      "Contains all the attributes of Radio-Frequency(RF) profile operational data";
    leaf rf-profile-name {
      type string;
      description
        "Name of the RF profile configuration applied on Access-Point(AP)";
    }
    leaf band {
      type uint8;
      description
        "Current radio frequency type Access-Point(AP) is operating";
    }
    container dca-channels-list {
      description
        "Dynamic Channel Assignment(DCA) channel list available for assigning to AP(Access-Point). 
         Any channel is removed from Dynamic Channel Assignment(DCA) list, it will be added to unused list";
      uses wireless-rrm-types:st-rrm-channel-list;
    }
    container unused-channels-list {
      description
        "List of channels configured as unused. 
         These channels will not be consumed by Dynamic Channel Assignment(DCA) algorithm";
      uses wireless-rrm-types:st-rrm-channel-list;
    }
  }

  container rf-oper-data {
    config false;
    description
      "Wireless Radio-Frequency(RF) profile oper data contains all the RF profiles operational information";
    list rf-profile-oper {
      key "rf-profile-name";
      description
        "Contains defination of data structures and tables related
         to RF profile operational data";
      uses wireless-rf-profile-oper:st-rf-profile-oper;
    }
  }
}
