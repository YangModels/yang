module Cisco-IOS-XE-wireless-client-oper {
  yang-version 1;
  namespace "http://cisco.com/ns/yang/Cisco-IOS-XE-wireless-client-oper";
  prefix wireless-client-oper;

  import Cisco-IOS-XE-common-types {
    prefix common-types-ios-xe;
  }
  import Cisco-IOS-XE-event-history-types {
    prefix event-history-types;
  }
  import Cisco-IOS-XE-wireless-client-types {
    prefix wireless-client-types;
  }
  import Cisco-IOS-XE-wireless-enum-types {
    prefix wireless-enum-types;
  }
  import Cisco-IOS-XE-wireless-mobility-types {
    prefix wireless-mobility-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless client operational data.
     Copyright (c) 2016-2018 by Cisco Systems, Inc.
     All rights reserved.";

  revision 2018-09-06 {
    description
      "- Remove leaf client-active
       - Add Units for mm-complete-timestamp
       - Remove binary encoded buffers
       - Add HE capable client flag
       - Add MMIF internal error statistics";
    reference "5.0.0";
  }
  revision 2018-03-22 {
    description
      "Addition of location-info node. Enum value changes";
    reference "4.0.0";
  }
  revision 2018-03-21 {
    description
      "Removal of location-info node";
    reference "3.0.0";
  }
  revision 2018-01-24 {
    description
      "The first generally available version";
    reference "2.0.0";
  }
  revision 2017-09-25 {
    description
      "Properly indicated leaf-list ordering";
    reference "1.1.0";
  }
  revision 2017-05-05 {
    description
      "Initial revision";
    reference "1.0.0";
  }

  typedef dot11i-auth-key-mgmt-type {
    type enumeration {
      enum "akm-unknown" {
        value 0;
        description
          "The client's AKM type is Unknown";
      }
      enum "8021x" {
        value 1;
        description
          "The client's AKM type is Dot1x";
      }
      enum "psk" {
        value 2;
        description
          "The client's AKM type is PSK";
      }
      enum "ft-8021x" {
        value 3;
        description
          "The client's AKM type is FT-802.1x";
      }
      enum "ft-psk" {
        value 4;
        description
          "The client's AKM type is FT-PSK";
      }
      enum "8021x-sha256" {
        value 5;
        description
          "The client's AKM type is Dot1x SHA256";
      }
      enum "psk-sha256" {
        value 6;
        description
          "The client's AKM type is PSK SHA256";
      }
      enum "sae" {
        value 8;
        description
          "The client's AKM type is SAE";
      }
      enum "ft-sae" {
        value 9;
        description
          "The client's AKM type is FT-SAE";
      }
      enum "suiteb-1x" {
        value 11;
        description
          "The client's AKM type is SUITEB-1X";
      }
      enum "suiteb192-1x" {
        value 12;
        description
          "The client's AKM type is SUITEB192-1X";
      }
    }
    description
      "Enum for the Authentication key management (AKM) types for the client";
  }

  typedef dot11-assoc-mode {
    type enumeration {
      enum "assoc-mode-unknown" {
        value 1;
        description
          "The security mode of the client association is Unknown";
      }
      enum "assoc-mode-wep" {
        value 2;
        description
          "The security mode of the client association is WEP";
      }
      enum "assoc-mode-wpa" {
        value 3;
        description
          "The security mode of the client association is WPA1";
      }
      enum "assoc-mode-wpa2" {
        value 4;
        description
          "The security mode of the client association is WPA2";
      }
    }
    description
      "Enum for the security modes that a client association can have";
  }

  typedef encrypt-policy {
    type enumeration {
      enum "encryp-policy-wep104" {
        value 0;
        description
          "The Encryption policy type for the client is WEP (104 bits)";
      }
      enum "encryp-policy-none" {
        value 1;
        description
          "There is no Encryption policy type for the client";
      }
      enum "encryp-policy-wep40" {
        value 2;
        description
          "The Encryption policy type for the client is WEP (40 bits)";
      }
      enum "encryp-policy-wep128" {
        value 3;
        description
          "The Encryption policy type for the client is WEP (128 bits)";
      }
      enum "encryp-policy-aes-ccm128" {
        value 4;
        description
          "The Encryption policy type for the client is AES-CCMP (128 bits)";
      }
      enum "encryp-policy-tkip-mic" {
        value 5;
        description
          "The Encryption policy type for the client is TKIP-MIC";
      }
      enum "encryp-policy-cisco-tkip-wep40" {
        value 6;
        description
          "The Encryption policy type for the client is CKIP-WEP (40 bits)";
      }
      enum "encryp-policy-cisco-tkip-wep104" {
        value 7;
        description
          "The Encryption policy type for the client is CKIP-WEP (104 bits)";
      }
      enum "encryp-policy-cisco-tkip-wep128" {
        value 8;
        description
          "The Encryption policy type for the client is CKIP-WEP (128 bits)";
      }
      enum "encryp-policy-ckip-kp-40" {
        value 9;
        description
          "The Encryption policy type for the client is CKIP-KeyPermutation (40 bits)";
      }
      enum "encryp-policy-ckip-kp-104" {
        value 10;
        description
          "The Encryption policy type for the client is CKIP-KeyPermutation (104 bits)";
      }
      enum "encryp-policy-ckip-mmh-40" {
        value 11;
        description
          "The Encryption policy type for the client is CKIP-MMH (40 bits)";
      }
      enum "encryp-policy-ckip-mmh-104" {
        value 12;
        description
          "The Encryption policy type for the client is CKIP-MMH (104 bits)";
      }
      enum "encryp-policy-ckip-kp-mmh-40" {
        value 13;
        description
          "The Encryption policy type for the client is CKIP-KeyPermutation with MMH (40 bits)";
      }
      enum "encryp-policy-ckip-kp-mmh-104" {
        value 14;
        description
          "The Encryption policy type for the client is CKIP-KeyPermutation with MMH (104 bits)";
      }
      enum "encryp-policy-wapi-sms4" {
        value 15;
        description
          "The Encryption policy type for the client is WAPI";
      }
      enum "encryp-policy-aes-gcmp128" {
        value 20;
        description
          "The Encryption policy type for the client is GCMP128";
      }
      enum "encryp-policy-aes-gcmp256" {
        value 21;
        description
          "The Encryption policy type for the client is GCMP256";
      }
      enum "encryp-policy-aes-ccmp256" {
        value 22;
        description
          "The Encryption policy type for the client is CCMP256";
      }
    }
    description
      "Enum for the encryption policy types for the client, which will be used in add mobile.";
  }

  typedef ccx-capability-enum {
    type enumeration {
      enum "ccx-capability-none" {
        value 0;
        description
          "The client is CCX incapable";
      }
      enum "ccx-plm-capable" {
        value 1;
        description
          "The client is CCX PLM capable";
      }
      enum "ccx-plm-incapable" {
        value 2;
        description
          "The client is CCX PLM incapable";
      }
      enum "ccx-s69-capable" {
        value 4;
        description
          "The client is CCX S69 Capable";
      }
      enum "ccx-plm-refused" {
        value 16;
        description
          "The client CCX capability is PLM refused";
      }
    }
    description
      "Enum for the CCX Capabilities";
  }

  typedef client-dpath-fsm-state {
    type enumeration {
      enum "client-dpath-init" {
        value 0;
        description
          "The Datapath FSM client state is Initialized";
      }
      enum "client-dpath-created" {
        value 1;
        description
          "The Datapath FSM client state is Created";
      }
    }
    description
      "Enum for the Datapath FSM client states";
  }

  typedef client-iplearn-fsm-state {
    type enumeration {
      enum "client-iplearn-init" {
        value 0;
        description
          "The IP learn FSM client state is Initialized";
      }
      enum "client-iplearn-complete" {
        value 1;
        description
          "The IP learn FSM client state is in complete";
      }
    }
    description
      "Enum for the various IP learn FSM client states";
  }

  typedef client-authentication-type {
    type enumeration {
      enum "client-authentication-type-local" {
        value 0;
        description
          "The Client is Locally authenticated";
      }
      enum "client-authentication-type-central" {
        value 1;
        description
          "The Client is Centrally authenticated";
      }
      enum "client-is-non-hreap" {
        value 2;
        description
          "AP to which the client is connected is in local mode. Authentication type is supported only when the AP is Flex-Connect Mode";
      }
    }
    description
      "This data type indicates whether the client is centrally (on Controller) or locally (on AP) authenticated";
  }

  typedef client-switching-mode {
    type enumeration {
      enum "client-switching-mode-unknown" {
        value 0;
        description
          "The switching mode of the client traffic is unknown";
      }
      enum "local" {
        value 1;
        description
          "The client traffic is locally switched from the AP";
      }
      enum "central" {
        value 2;
        description
          "The client traffic is centrally switched from the controller";
      }
    }
    description
      "This data type indicates whether the data from the client is centrally (on Controller) or locally (on AP) switched";
  }

  typedef webauth-on-mac-failure {
    type enumeration {
      enum "client-mac-auth-disabled" {
        value 0;
        description
          "Webauth on MAC failure: not configured.";
      }
      enum "client-mac-auth-passed" {
        value 1;
        description
          "Webauth on MAC failure: L2 passed";
      }
      enum "client-mac-auth-failed" {
        value 2;
        description
          "Webauth on MAC failure: L2 failed";
      }
    }
    description
      "Client L2 state for webauth on MAC Failure feature";
  }

  typedef aaa-req-status {
    type enumeration {
      enum "aaa-req-status-begin" {
        value 0;
        description
          "Aaa Request Status Begin";
      }
      enum "aaa-req-status-sent" {
        value 1;
        description
          "Aaa Request Status Sent";
      }
      enum "aaa-req-status-pass" {
        value 2;
        description
          "Aaa Request Status Pass";
      }
      enum "aaa-req-status-fail" {
        value 3;
        description
          "Aaa Request Fail";
      }
      enum "aaa-req-status-fail-no-retries" {
        value 4;
        description
          "Aaa Request Status Fail No Retries";
      }
      enum "aaa-req-status-failover-retry" {
        value 5;
        description
          "Aaa Request Status Failover Retry";
      }
      enum "aaa-req-status-user-nopassword" {
        value 6;
        description
          "Aaa Request Status User Nopassword";
      }
      enum "aaa-req-status-get-user" {
        value 7;
        description
          "Aaa Request Status Get User";
      }
      enum "aaa-req-status-get-password" {
        value 8;
        description
          "Aaa Request Status Get Password";
      }
      enum "aaa-req-status-get-data" {
        value 9;
        description
          "Aaa Request Status Get Data";
      }
      enum "aaa-req-status-cancelled" {
        value 10;
        description
          "Aaa Request Status Cancelled";
      }
      enum "aaa-req-status-get-challenge-response" {
        value 11;
        description
          "Aaa Request Status Get Challenge Response";
      }
      enum "aaa-req-status-get-new-password" {
        value 12;
        description
          "Aaa Request Status Get New Password";
      }
      enum "aaa-req-status-get-challenge-resp-noecho" {
        value 13;
        description
          "Aaa Request Status Get Challenge Resp Noecho";
      }
    }
    description
      "Aaa Request Status";
  }

  typedef sm-auth-method-id {
    type enumeration {
      enum "invalid-method-id" {
        value 0;
        description
          "Denotes an Invalid method ID";
      }
      enum "dot1x-auth-id" {
        value 1;
        description
          "IEEE 802.1X Authenticator ID";
      }
      enum "mab-type" {
        value 2;
        description
          "Mac-Auth-Bypass Method";
      }
      enum "web-auth-method" {
        value 3;
        description
          "Web Authentication";
      }
      enum "static-method-id" {
        value 4;
        description
          "Static method Identifier";
      }
      enum "eou" {
        value 5;
        description
          "Eap Over UDP Method identifier";
      }
      enum "dot1x-supp-id" {
        value 6;
        description
          "IEEE 802.1X Supplicant ID";
      }
    }
    description
      "IDs representing various authentication";
  }

  typedef sm-ctx-state {
    type enumeration {
      enum "sm-ctx-state-idle" {
        value 0;
        description
          "Session Idle State";
      }
      enum "sm-ctx-state-running" {
        value 1;
        description
          "Session Authc Running State";
      }
      enum "sm-ctx-state-no-more-methods" {
        value 2;
        description
          "Session No more authc methods";
      }
      enum "sm-ctx-state-authc-success" {
        value 3;
        description
          "Session Authentication Success State";
      }
      enum "sm-ctx-state-authc-failed" {
        value 4;
        description
          "Session Authentication Fail State";
      }
      enum "sm-ctx-state-authz-success" {
        value 5;
        description
          "Session Authorization Success State";
      }
      enum "sm-ctx-state-authz-failed" {
        value 6;
        description
          "Session authorixatin failed state";
      }
    }
    description
      "Session Manager Session State";
  }

  typedef sm-domain {
    type enumeration {
      enum "domain-unknown" {
        value 0;
        description
          "Unknown Domain";
      }
      enum "data" {
        value 1;
        description
          "Data Domain";
      }
      enum "voice" {
        value 2;
        description
          "Voice Domain";
      }
    }
    description
      "Session's domain";
  }

  typedef sm-target-scope {
    type enumeration {
      enum "sm-target-scope-unknown" {
        value 0;
        description
          "Session's scope Unknown";
      }
      enum "sm-target-scope-client" {
        value 1;
        description
          "Session's Scope : Client";
      }
      enum "sm-target-scope-interface" {
        value 2;
        description
          "Interface Scope";
      }
    }
    description
      "Session's scope";
  }

  typedef sm-host-mode {
    type enumeration {
      enum "sm-host-mode-unknown" {
        value 0;
        description
          "SM's interface host-mode";
      }
      enum "sm-host-mode-single-host" {
        value 1;
        description
          "Single-host interface configuration";
      }
      enum "sm-host-mode-multi-host" {
        value 2;
        description
          "Multi-Host interface configuration";
      }
      enum "sm-host-mode-multi-auth" {
        value 3;
        description
          "Multi-Auth interface configuration";
      }
      enum "sm-host-mode-multi-domain" {
        value 4;
        description
          "Multi-Domain interface configuration";
      }
    }
    description
      "Interface's host-mode configuration";
  }

  typedef sm-control-direction {
    type enumeration {
      enum "sm-control-direcion-unknown" {
        value 0;
        description
          "Intf config, Control-direction: Unknown";
      }
      enum "sm-control-dir-both" {
        value 1;
        description
          "Intf config, Control-direction: Both";
      }
      enum "sm-control-dir-in" {
        value 2;
        description
          "Intf config, Control-direction: In";
      }
    }
    description
      "Interface Configuration: control-direction";
  }

  typedef sm-port-type {
    type enumeration {
      enum "sm-port-type-unknown" {
        value 0;
        description
          "Intf config, Port-type: Unknown";
      }
      enum "sm-port-type-l2" {
        value 1;
        description
          "Intf config, Port-type: L2 Port";
      }
      enum "sm-port-type-l3" {
        value 2;
        description
          "Intf config, Port-type: L3 Port";
      }
      enum "sm-port-type-dot11" {
        value 4;
        description
          "Intf config, Port-type: Dot11 port";
      }
    }
    description
      "Intf config, Port-type";
  }

  typedef sm-webauth-method {
    type enumeration {
      enum "min" {
        value 0;
        description
          "Auth-Proxy Application ID_MIN";
      }
      enum "easy-vpn" {
        value 1;
        description
          "will be updated";
      }
      enum "webauth" {
        value 2;
        description
          "Parameter map is configured with auth-proxy";
      }
      enum "consent" {
        value 3;
        description
          "parameter map is configured with web consent";
      }
      enum "webconsent" {
        value 4;
        description
          "Parameter map is configured with auth-proxy consent";
      }
      enum "auth-bypass" {
        value 5;
        description
          "Parameter map is configured with webauth";
      }
      enum "max" {
        value 6;
        description
          "will be updated";
      }
    }
    description
      "Webauth Method data";
  }

  typedef sm-webauth-state {
    type enumeration {
      enum "init" {
        value 0;
        description
          "Webauth Init State";
      }
      enum "http-wait-next-password" {
        value 1;
        description
          "will be updated";
      }
      enum "get-redirect" {
        value 2;
        description
          "will be updated";
      }
      enum "login" {
        value 3;
        description
          "Webauth information is in login state";
      }
      enum "webauth-authenticating" {
        value 4;
        description
          "webauth information is in authentication state";
      }
      enum "authc-fail" {
        value 5;
        description
          "webauth information is in failed state";
      }
      enum "nrh-fail" {
        value 6;
        description
          "webauth information is in authc fail state";
      }
      enum "authc-success" {
        value 7;
        description
          "webauth information is in authc success state";
      }
      enum "nrh-success" {
        value 8;
        description
          "webauth information is in authc success state and the client is non responsive host";
      }
      enum "authz" {
        value 9;
        description
          "webauth information is in authz success state";
      }
    }
    description
      "Webauth State";
  }

  typedef sm-protocol-type {
    type enumeration {
      enum "sm-proto-type-cdp" {
        value 0;
        description
          "Protocol Type CDP";
      }
      enum "sm-proto-type-lldp" {
        value 1;
        description
          "Protocol Type LLDP";
      }
      enum "sm-proto-type-dhcp" {
        value 2;
        description
          "Protocol Type DHCP";
      }
      enum "sm-proto-type-mdns" {
        value 3;
        description
          "Protocol Type MDNS";
      }
      enum "sm-proto-type-sip" {
        value 4;
        description
          "Protocol Type SIP";
      }
      enum "sm-proto-type-h323" {
        value 5;
        description
          "Protocol Type H323";
      }
      enum "sm-proto-type-http" {
        value 6;
        description
          "Protocol Type HTTP";
      }
    }
    description
      "Protocol Type";
  }

  typedef epm-svc-source {
    type enumeration {
      enum "epm-svc-source-none" {
        value 0;
        description
          "EPM policy authz source - none";
      }
      enum "epm-svc-source-local" {
        value 1;
        description
          "EPM policy authz source - Local";
      }
      enum "epm-svc-source-pmap" {
        value 2;
        description
          "EPM policy authz source - pmap";
      }
      enum "epm-svc-source-aaa" {
        value 3;
        description
          "EPM policy authz source - AAA";
      }
      enum "epm-svc-source-local-wlan" {
        value 4;
        description
          "EPM policy authz source - WLAN";
      }
    }
    description
      "EPM Authorization policy source";
  }

  typedef epm-svc-status {
    type enumeration {
      enum "epm-svc-status-unknown" {
        value 0;
        description
          "EPM service status - unknown";
      }
      enum "epm-svc-status-error" {
        value 1;
        description
          "EPM service status - error";
      }
      enum "epm-svc-status-new" {
        value 2;
        description
          "EPM service status - new";
      }
      enum "epm-svc-status-loading" {
        value 3;
        description
          "EPM service status - loading";
      }
      enum "epm-svc-status-req-apply" {
        value 4;
        description
          "EPM service status - Request apply";
      }
      enum "epm-svc-status-applied" {
        value 5;
        description
          "EPM service status - applied";
      }
      enum "epm-svc-status-req-unapply" {
        value 6;
        description
          "EPM service status - unapply";
      }
      enum "epm-svc-status-unapplied" {
        value 7;
        description
          "EPM service status - unapplied";
      }
      enum "epm-svc-status-failure" {
        value 8;
        description
          "EPM service status - failure";
      }
      enum "epm-svc-status-max" {
        value 9;
        description
          "EPM service status - MAX";
      }
    }
    description
      "EPM policy application status";
  }

  typedef exclude-reason {
    type enumeration {
      enum "manually-excluded" {
        value 0;
        description
          "The client has been excluded as it has been configured to the exclusionlist";
      }
      enum "80211-association-failure" {
        value 1;
        description
          "The client has been excluded due to association failure";
      }
      enum "80211-authentication-failure" {
        value 2;
        description
          "The client has been excluded due to a 802.11 Authentication failure";
      }
      enum "8021x-authentication-timeout" {
        value 3;
        description
          "The client has been excluded due to a 802.1x Authentication timeout failure";
      }
      enum "8021x-authentication-failure" {
        value 4;
        description
          "The client has been excluded due to a 802.1x Authentication failure";
      }
      enum "web-authentication-failure" {
        value 5;
        description
          "The client has been excluded due to a webauth faiulre";
      }
      enum "client-policy-bind-fail" {
        value 6;
        description
          "The client has been excluded due to a policy bind failure";
      }
      enum "ip-address-theft" {
        value 7;
        description
          "The client has been excluded due to IP Theft";
      }
      enum "client-exclusion-mac-theft" {
        value 8;
        description
          "The client has been excluded due to MAC theft";
      }
      enum "client-exclusion-mac-and-ip-theft" {
        value 9;
        description
          "The client has been excluded due to MAC and IP theft";
      }
      enum "client-qos-policy-failure" {
        value 10;
        description
          "The client has been excluded due to a QOS Policy failure";
      }
      enum "client-qos-policy-send-to-ap" {
        value 11;
        description
          "s value indicates that the client has been excluded due to failure in sending QOS policy to AP";
      }
      enum "client-qos-policy-bind-on-ap" {
        value 12;
        description
          "The client has been excluded due to failure in binding AP with QOS policy";
      }
      enum "client-qos-policy-unbind-on-ap" {
        value 13;
        description
          "The client has been excluded due to failure in unbinding AP from a QOS policy";
      }
      enum "client-static-ip-anchor-failure" {
        value 14;
        description
          "The client has been excluded due to failure in static ip anchor discovery";
      }
      enum "client-exclusion-vlan-fail" {
        value 15;
        description
          "The client has been excluded due to VLAN failure";
      }
      enum "client-exclusion-acl-fail" {
        value 16;
        description
          "The client has been excluded due to ACL failure";
      }
      enum "client-exclusion-punt-acl-fail" {
        value 17;
        description
          "The client has been excluded due to redirect ACL failure";
      }
      enum "client-exclusion-accounting-fail" {
        value 18;
        description
          "The client has been excluded due to radius accounting failure";
      }
      enum "client-exclusion-cts-fail" {
        value 19;
        description
          "The client has been excluded due to cts sgt configuration failed";
      }
      enum "client-exclusion-fqdn-no-def-fail" {
        value 20;
        description
          "The client have been excluded due to missing definition for FQDN filter";
      }
      enum "client-exclusion-fqdn-postauth-mismatch-fail" {
        value 21;
        description
          "The client have been excluded due to mismatch in postauth FQDN filter";
      }
      enum "client-exclusion-fqdn-preauth-mismatch-fail" {
        value 22;
        description
          "The client have been excluded due to mismatch in preauth FQDN filter";
      }
      enum "client-exclusion-fqdn-zero-gid-fail" {
        value 23;
        description
          "The client have been excluded due to zero groupid for FQDN filter";
      }
      enum "client-exclusion-misc-fail" {
        value 24;
        description
          "The client has been excluded due to policy parameter mismatch";
      }
      enum "client-exclusion-reauth-failure" {
        value 25;
        description
          "The client has been excluded due to reauthentication timer policy configuration apply failure";
      }
      enum "client-exclusion-wrong-psk" {
        value 26;
        description
          "The client has been excluded due to wrong PSK";
      }
      enum "client-exclusion-policy-failure" {
        value 27;
        description
          "The client has been excluded due to client policy failure";
      }
    }
    description
      "This enum indicates the reason why the client has been excluded";
  }

  typedef exclusion-client-auth-method-id {
    type enumeration {
      enum "no-auth-type-excluded-client" {
        value 0;
        description
          "Authentication type of the excluded client is NA";
      }
      enum "dot1x-type-excluded-client" {
        value 1;
        description
          "Authentication type of the excluded client is 802.1x";
      }
      enum "mab-excluded-client" {
        value 2;
        description
          "Authentication type of the excluded client is MAB";
      }
      enum "web-auth-method-excluded-client" {
        value 3;
        description
          "Authentication type of the excluded client is Webauth";
      }
      enum "static-excluded-id" {
        value 4;
        description
          "Authentication type of the excluded client is Static";
      }
      enum "eou-excluded-client" {
        value 5;
        description
          "Authentication type of the excluded client is EOU";
      }
      enum "dot1x-supp" {
        value 6;
        description
          "Authentication type of the excluded client is supplicant 802.1x";
      }
    }
    description
      "Authentication type of the excluded client";
  }

  typedef dot11-client-type {
    type enumeration {
      enum "dot11-client-none" {
        value 0;
        description
          "DOT11 client role is not local or mobile";
      }
      enum "dot11-client-local" {
        value 1;
        description
          "DOT11 client role is local";
      }
      enum "dot11-client-mobile" {
        value 2;
        description
          "DOT11 client role is mobile";
      }
      enum "dot11-client-max" {
        value 3;
        description
          "DOT11 client role is MAX";
      }
    }
    description
      "This enum defines DOT11 client role";
  }

  typedef pmkcache-type {
    type enumeration {
      enum "pmk-rsn" {
        value 0;
        description
          "Pmk for Rsn type";
      }
      enum "pmk-cckm" {
        value 1;
        description
          "Pmk for Cckm type";
      }
      enum "pmk-dot11r" {
        value 2;
        description
          "Pmk for Dot11r type";
      }
      enum "pmk-11-w" {
        value 3;
        description
          "Pmk for 11w type";
      }
      enum "pmk-11-ac" {
        value 4;
        description
          "Pmk for 11ac type";
      }
      enum "pmk-open" {
        value 5;
        description
          "Pmk for Mab type";
      }
    }
    description
      "This enum defines the Pmk cache type";
  }

  grouping ms-wifi {
    description
      "WiFi security details of the Client";
    leaf wpa-version {
      type wireless-client-types:dot11-eap-wpa-version;
      description
        "WPA version of the client";
    }
    container ie-data {
      description
        "RSN, WPA Information element data";
      uses common-types-ios-xe:mcp-bytestr;
    }
    leaf rsn-ie-len {
      type uint8;
      description
        "RSN information element length";
    }
    leaf wpa-ie-len {
      type uint8;
      description
        "WPA information element length";
    }
    leaf cipher-suite {
      type wireless-client-types:dot11i-cipher-suite;
      description
        "802.11i Cipher Suite type";
    }
    leaf auth-key-mgmt {
      type wireless-client-oper:dot11i-auth-key-mgmt-type;
      description
        "802.11i authentication key management information";
    }
  }

  grouping ewlc-client-wpa2-security-oper-data {
    description
      "WPA2 security opearational data of the client";
    leaf rsn-ie-enabled {
      type boolean;
      description
        "boolean to indicate whether RSN Information element is enabled";
    }
    leaf rsn-cipher-suite {
      type uint16;
      description
        "RSN Information Element Cipher Suite";
    }
    leaf auth-key-mgmt-suite {
      type uint16;
      description
        "RSN Authentication management type";
    }
    leaf rsn-ie-len {
      type uint32;
      description
        "RSN information element length";
    }
  }

  grouping wmm-data {
    description
      "WiFi Multimedia data of the client";
    leaf tid {
      type uint8;
      description
        "Traffic Stream Id for the WMM data of the client";
    }
    leaf ac {
      type uint8;
      description
        "Access Category for the WMM data of the client";
    }
    leaf up {
      type uint8;
      description
        "User Priority for the WMM data for the client";
    }
    leaf upsd {
      type uint8;
      description
        "Unscheduled Automatic Power Save Delivery";
    }
    leaf call-state {
      type uint8;
      description
        "Voice Call State";
    }
    leaf roam-call {
      type uint8;
      description
        "Roaming call state";
    }
    leaf bandwidth-allocated {
      type uint16;
      description
        "Bandwidth Allocated";
    }
    leaf kbps-bw {
      type uint32;
      description
        "Bandwidth in Kbps";
    }
    leaf got-exp-bw-req {
      type boolean;
      description
        "Expedited Bandwidth required";
    }
    leaf exp-bw-req-tsid {
      type uint8;
      description
        "Expedited Bandwidth Required for traffic id";
    }
    leaf direction {
      type uint8;
      description
        "Direction";
    }
    leaf inactivity-time {
      type uint32;
      description
        "Inactivity time";
    }
  }

  grouping wfd-client-config-detail {
    description
      "Wifi Direct Client Configuration Details";
    leaf wfd-capable {
      type boolean;
      description
        "WiFi Direct Capability";
    }
    leaf managed-wfd-capable {
      type boolean;
      description
        "Managed WiFi Direct Capability";
    }
    leaf cross-connection-capable {
      type boolean;
      description
        "Cross Connection Capability";
    }
    leaf support-concurrent-operation {
      type boolean;
      description
        "Concurrent Operation Support";
    }
    leaf reserve {
      type uint8;
      description
        "Reserve Field";
    }
    leaf p2p-interface-add-count {
      type uint8;
      description
        "P2P Interface Address count";
    }
  }

  grouping tgr-ms-data {
    description
      "Persistent data maintained for 802.11r clients";
    container pmkr0-name {
      description
        "PMK-R0 Name";
      uses common-types-ios-xe:mcp-bytestr;
    }
    container pmkr1-name {
      description
        "PMK-R1 Name";
      uses common-types-ios-xe:mcp-bytestr;
    }
    container ftie-data {
      description
        "FT information Element data";
      uses common-types-ios-xe:mcp-bytestr;
    }
  }

  grouping dot11v-timer-params {
    description
      "802.11v Persistent Timer Parameters";
    leaf trans-bssid-mac {
      type yang:mac-address;
      description
        "Bssid on which a bss transition query was sent";
    }
  }

  grouping sess-timestamp {
    description
      "Time taken for the Client's Association";
    leaf tv-sec {
      type uint32;
      description
        "Seconds in the client's Association time";
    }
    leaf tv-usec {
      type uint32;
      description
        "MicroSeconds in the client's Association time";
    }
  }

  grouping ewlc-eogre-client {
    description
      "EoGRE Client";
    leaf is-eogre {
      type boolean;
      description
        "is EoGRE client";
    }
    leaf match-reason {
      type wireless-enum-types:enm-eogre-client-match;
      description
        "output of the match process of client to eogre client";
    }
    leaf is-aaa-data {
      type boolean;
      description
        "is AAA override received for this client";
    }
    leaf realm {
      type string;
      description
        "client realm";
    }
    leaf vlan {
      type uint16 {
        range "1 .. 4094";
      }
      description
        "EoGRE vlan";
    }
    leaf domain {
      type string;
      description
        "EoGRE domain";
    }
    leaf primary-gw {
      type inet:ip-address;
      description
        "IP address of the primary gateway";
    }
    leaf secondary-gw {
      type inet:ip-address;
      description
        "IP address of the secondary gateway";
    }
  }

  grouping ewlc-client-dot11-oper-data {
    description
      "Table Definition of the 802.11 operational data of the Client";
    leaf ms-mac-address {
      type yang:mac-address;
      description
        "Mac Address of the Client";
    }
    leaf dot11-state {
      type wireless-client-types:dot11-state;
      description
        "DOT11 status for the Client";
    }
    leaf dot11-sm-state {
      type uint32;
      description
        "802.11 FSM state";
    }
    leaf num-wgb-clients {
      type uint32;
      description
        "Number of clients in Workgroup Bridge configuration";
    }
    leaf ms-bssid {
      type yang:mac-address;
      description
        "BSSID of the client";
    }
    leaf ap-mac-address {
      type yang:mac-address;
      description
        "Mac Address of the AP to which the client has joined";
    }
    leaf old-ap-bssid-mac {
      type yang:mac-address;
      description
        "old AP bssid mac address for roamed client";
    }
    leaf current-channel {
      type uint8;
      description
        "Current Channel of the client";
    }
    leaf ms-entry-type {
      type wireless-client-types:ms-type;
      description
        "Client Entry type";
    }
    leaf ms-wlan-id {
      type uint32;
      description
        "WLAN ID to which the client is connected";
    }
    leaf ms-vap-id {
      type uint32;
      description
        "VAP ID to which the client is connected";
    }
    leaf vap-ssid {
      type string;
      description
        "SSID of the WLAN to which the client is connected";
    }
    leaf policy-profile {
      type string;
      description
        "Policy profile applied on the WLAN to which the client is connected";
    }
    leaf ms-assoc-type-flags {
      type uint16;
      description
        "Client Association type flag";
    }
    leaf ms-ap-slot-id {
      type uint8;
      description
        "Slot ID of the AP";
    }
    leaf radio-type {
      type wireless-client-types:ms-radio-type;
      description
        "Type of the Radio of the AP to which the client is associated";
    }
    leaf ms-short-preamble {
      type uint8;
      description
        "Client Short Preamble";
    }
    leaf ms-association-id {
      type uint16;
      description
        "Association Id of the client";
    }
    leaf ms-old-association-id {
      type uint16;
      description
        "Previous association ID of the client";
    }
    leaf ms-auth-seq-num {
      type uint16;
      description
        "Authentication Request Sequence Number";
    }
    leaf ms-auth-alg-num {
      type wireless-client-types:auth-algo;
      description
        "Authentication Algorithm Number";
    }
    leaf ms-reason-code {
      type wireless-client-types:reason-code;
      description
        "Updated when the client sends an unsolicited deauthdisassoc frame";
    }
    leaf ms-preset-reason-code {
      type uint16;
      description
        "Preset the reason code in case the timer kicks";
    }
    leaf ms-capability {
      type uint16;
      description
        "Client's capability Bit Map";
    }
    leaf ms-listen-interval {
      type uint16;
      description
        "Listen Interval of the client for Association";
    }
    leaf ms-cf-pollable {
      type uint8;
      description
        "Client's CF-Pollable";
    }
    leaf ms-cf-poll-request {
      type uint8;
      description
        "Client's CF-Poll Request";
    }
    leaf ms-pbcc {
      type uint8;
      description
        "Client's Packet Binary Convolutional Code";
    }
    leaf ms-channel-agility {
      type uint8;
      description
        "Client's Channel Agility";
    }
    container ms-assoc-time {
      description
        "Client's Association Time";
      uses wireless-client-oper:sess-timestamp;
    }
    leaf assoc-time-at-ap {
      type uint32;
      description
        "Association time at AP in case of FT and auth at AP";
    }
    leaf ms-ft-reassoc-timeout {
      type uint32;
      description
        "Client's reassocitaion timeout";
    }
    leaf ms-session-start-time {
      type uint32;
      description
        "session start timestamp for the Client";
    }
    leaf ms-session-epoch {
      type uint32;
      description
        "Actual global session start time";
    }
    leaf is-11g-client {
      type boolean;
      description
        "Boolean indicating whether the client is connected throught 802.11g protocol";
    }
    leaf port-id {
      type uint16;
      description
        "Port id of associated RLAN clients";
    }
    leaf ms-ht-capabilities-info {
      type uint16;
      description
        "802.11n capabilities indicator";
    }
    leaf ms-ht-ampdu-param {
      type uint8;
      description
        "Aggregate-Mac protocol data unit parameters";
    }
    leaf ms-ht-extended-capabilities-info {
      type uint16;
      description
        "HT Extended Capabilities";
    }
    leaf ms-ht-tx-beam-forming-capabilities {
      type uint32;
      description
        "HT Tx Beamforming Capabilities";
    }
    leaf ms-ht-asel-capabilities {
      type uint8;
      description
        "HT Antenna Selection Capablities";
    }
    leaf ms-ht-capable {
      type boolean;
      description
        "Indicator whether client is 802.11n capable";
    }
    leaf ms-vht-capable {
      type boolean;
      description
        "Indicator whether client is 802.11ac capable";
    }
    leaf ms-he-capable {
      type boolean;
      description
        "Indicator whether client is 802.11ax capable";
    }
    leaf ms-load-balancing-timestamp {
      type uint32;
      description
        "Load Balancing Timestamp";
    }
    leaf ms-load-balancing-retry-count {
      type uint32;
      description
        "Load Balancing Retry count";
    }
    leaf ms-is-calibrating {
      type int8;
      description
        "Location calibration fields, Can take 0(no) 1(yes) and -1(deleted due to session timeout) as values";
    }
    leaf lrad-jumbo {
      type boolean;
      description
        "Jumbo frame flag for 1596 size";
    }
    leaf ms-create-time {
      type uint64;
      description
        "Time stamp when client record is created, again used for client diagnosis";
    }
    leaf invalid-80211-assoc-attempts {
      type uint32;
      description
        "Association request validation, MAB failure counter";
    }
    container ms-wifi {
      description
        "WiFi security of Client";
      uses wireless-client-oper:ms-wifi;
    }
    leaf dot11-assoc-start-ts {
      type uint32;
      description
        "Time at which 802.11 association process started";
    }
    leaf ms-wme-enabled {
      type boolean;
      description
        "Indicator whether Wireless Multimedia Extentions is enabled, or not";
    }
    list wmm-data {
      max-elements "8";
      description
        "Wireless Multimedia data of Client";
      uses wireless-client-oper:wmm-data;
    }
    container wifi-direct-client {
      description
        "Wifi Direct Client Details";
      uses wireless-client-oper:wfd-client-config-detail;
    }
    leaf ms-qos-capability {
      type uint8;
      description
        "QOS capability of Client";
    }
    leaf ms-80211e-enabled {
      type boolean;
      description
        "Indicator whether 802.11e is enabled, or not";
    }
    leaf ms-upsd-status {
      type uint8;
      description
        "Unscheduled Automatic Power Save Delivery Status";
    }
    leaf ms-upsd-bronze-dir {
      type wireless-enum-types:apf-ms-data-upsd-bronze;
      description
        "Client's APSD level Bronze";
    }
    leaf ms-upsd-silver-dir {
      type wireless-enum-types:apf-ms-data-upsd-silver;
      description
        "Client's APSD QOS level Silver";
    }
    leaf ms-upsd-gold-dir {
      type wireless-enum-types:apf-ms-data-upsd-gold;
      description
        "Client's APSD QOS level Gold";
    }
    leaf ms-upsd-platinum-dir {
      type wireless-enum-types:apf-ms-data-upsd-platinum;
      description
        "Client's APSD QOS level Platinum";
    }
    leaf sfa-cap {
      type uint8;
      description
        "Supported Features Advertisement capability";
    }
    leaf mfp-enabled {
      type boolean;
      description
        "Management Frame Protection Enabled";
    }
    leaf dot11w-enabled {
      type boolean;
      description
        "Flag for 802.11w enabled";
    }
    leaf sa-query-retrans-count {
      type uint8;
      description
        "SA Query retransmission count";
    }
    leaf exp-bw-req-enabled {
      type boolean;
      description
        "Flag for Expedited Bandwidth Requirement enabled";
    }
    leaf aironet-ie {
      type boolean;
      description
        "Flag for Aironet Information Element enabled";
    }
    leaf diag-channel {
      type boolean;
      description
        "Flag for WLAN diagnosis (S64) enabled, or not";
    }
    leaf s69-capable {
      type boolean;
      description
        "Flag for S69 enabled, or not";
    }
    leaf diag-capable {
      type boolean;
      description
        "Indicator whether the client is capable of diagnosis";
    }
    leaf diag-reason {
      type uint8;
      description
        "S64 Diagnosis Reason";
    }
    leaf got-tspec-ie {
      type boolean;
      description
        "Flag for whether Tspec ie received, or not";
    }
    leaf locp-info-dirty-bit {
      type uint8;
      description
        "locp info Dirty bit value";
    }
    leaf num-of-neighbors {
      type uint8;
      description
        "Valid number of neighbors in assisted neighbor list";
    }
    leaf-list neighbor-list-11k {
      type yang:mac-address;
      max-elements "9";
      ordered-by user;
      description
        "Neighbor list per Radio Id";
    }
    leaf assisted-roam-denial {
      type uint16;
      description
        "Assisted Roam Denial Counter";
    }
    leaf reassociation-count {
      type uint8;
      description
        "Counter for the Dirty Vlan Feature";
    }
    leaf ms-mac-auth-passed {
      type uint16;
      description
        "Web Authentication on Mac filter failure";
    }
    leaf ewlc-ms-phy-type {
      type wireless-client-types:ms-phy-radio-type;
      description
        "Radio type to which the Client is connected";
    }
    leaf ewlc-ms-flags {
      type uint32;
      description
        "flag indicates when a reassoc request has a Traffic Classification";
    }
    container wpa2-security-oper-data {
      description
        "This structure contains the operational information of the RSN security";
      uses wireless-client-oper:ewlc-client-wpa2-security-oper-data;
    }
    container tgr-ms-data {
      description
        "Persistent data maintained for 802.11r clients";
      uses wireless-client-oper:tgr-ms-data;
    }
    leaf encryption-type {
      type wireless-client-oper:encrypt-policy;
      description
        "Encryption policy for the client used in the add mobile";
    }
    leaf status-code {
      type uint32;
      description
        "802.11 stattus of the client during Association";
    }
    leaf wgb-state {
      type uint8;
      description
        "Work Group Bridge State";
    }
    leaf wgb-mac {
      type yang:mac-address;
      description
        "Mac address of the associated Work group Bridge";
    }
    leaf security-mode {
      type wireless-client-oper:dot11-assoc-mode;
      description
        "Security mode for the client association";
    }
    leaf rm-ie {
      type boolean;
      description
        "Indicator of whether Radio Management Information Element is recieved in Association Request";
    }
    leaf rm-cap-ie {
      type boolean;
      description
        "Radio Management capability Information Element";
    }
    leaf wtp-mac {
      type yang:mac-address;
      description
        "Base BSSID of the client";
    }
    leaf client-wep-policy-type {
      type wireless-client-types:client-wep-policy-type;
      description
        "Client WEP policy type";
    }
    leaf bss-trans-capable {
      type boolean;
      description
        "Indicator whether the client is 802.11v capable";
    }
    container dot11v-timer-params {
      description
        "802.11v Persistent Timer Parameters";
      uses wireless-client-oper:dot11v-timer-params;
    }
    leaf ms-apple-capable {
      type boolean;
      description
        "Indicator whether Client has Fastlane Support";
    }
    leaf is-mesh {
      type boolean;
      description
        "Client record is for the mesh child AP or regular client";
    }
    leaf is-mbssid {
      type boolean;
      description
        "Mobility BSSID or Regular BSSID";
    }
    leaf vlan-central-switching-enabled {
      type boolean;
      description
        "Flag to enable/disable vlan central switching";
    }
    leaf wlan-profile {
      type string;
      description
        "Profile applied on the WLAN/RLAN to which the client is connected";
    }
    leaf-list pmk {
      type uint8;
      max-elements "32";
      ordered-by user;
      description
        "PMK for the client, currently used for SAE";
    }
    leaf-list pmkid {
      type uint8;
      max-elements "32";
      ordered-by user;
      description
        "PMKID for the client, currently used for SAE";
    }
    leaf dms-capable {
      type boolean;
      description
        "Client DMS Capability";
    }
    leaf dms-id-mask {
      type uint64;
      description
        "DMS ID bit mask";
    }
    container eogre-client {
      description
        "Eogre Client";
      uses wireless-client-oper:ewlc-eogre-client;
    }
  }

  grouping protocol-type-num-clients {
    description
      "Number of clients per protocol type";
    leaf-list buffer {
      type uint32;
      max-elements "11";
      ordered-by user;
      description
        "buffer-value";
    }
  }

  grouping st-client-dot11-stats {
    description
      "Client 802.11 statistics";
    leaf total-assoc-attempt {
      type uint32;
      description
        "Total number of Association Attempts";
    }
    leaf total-assoc-failure {
      type uint32;
      description
        "Total number of Association Failures";
    }
    leaf total-assoc-resp-accept {
      type uint32;
      description
        "Total number of Association Response Acceptances";
    }
    leaf total-assoc-resp-reject {
      type uint32;
      description
        "Total number of Association Response Rejects";
    }
    leaf total-assoc-resp-error {
      type uint32;
      description
        "Total number of Association Response Errors";
    }
    leaf dms-action-frame-req {
      type uint32;
      description
        "Number of DMS requests received in action frame";
    }
    leaf dms-action-frame-resp {
      type uint32;
      description
        "Number of DMS response sent in action frame";
    }
    leaf dms-reassoc-req {
      type uint32;
      description
        "Number of DMS requests received in Re-association request";
    }
    leaf dms-reassoc-resp {
      type uint32;
      description
        "Number of DMS response sent in Re-association response";
    }
    leaf total-roam-attempts {
      type uint32;
      description
        "Total number of Roam attempts by the client";
    }
    leaf total-cckm-roam-attempts {
      type uint32;
      description
        "Total number of CCKM roam attempts";
    }
    leaf total-11r-roam-attempts {
      type uint32;
      description
        "Total number of 802.11r roam attempts";
    }
    leaf total-11i-fast-roam-attempts {
      type uint32;
      description
        "Total number of 802.11i fast roam attempts";
    }
    leaf total-11i-slow-roam-attempts {
      type uint32;
      description
        "Total number of 802.11i slow roam attempts";
    }
    leaf total-roam-failures {
      type uint32;
      description
        "Total number of roam failures in 802.11";
    }
    leaf total-ap-roam-attempts {
      type uint32;
      description
        "Total number of AP roam attempts";
    }
    leaf total-ap-11i-fast-roam-attempts {
      type uint32;
      description
        "Total number of AP 802.11i fast roam attempts";
    }
    leaf total-ap-11i-slow-roam-attempts {
      type uint32;
      description
        "Total number of AP 802.11i slow roam attempts";
    }
    leaf lb-total-denied-count {
      type uint32;
      description
        "Total number of denials in Client Load Balancing";
    }
    leaf lb-total-denied-sent {
      type uint32;
      description
        "Total number of denials sent in Client Load Balancing";
    }
    leaf lb-exceeded-denial-max-limit-count {
      type uint32;
      description
        "Total number of times the denial count exceeded the Max Denial Limit Count";
    }
    leaf lb-candiate-5g-count {
      type uint32;
      description
        "None 5G Candidate Count";
    }
    leaf lb-candiate-24g-count {
      type uint32;
      description
        "None 2.4G Candidate Count";
    }
    container protocol-type-num-clients {
      description
        "Number of clients per protocol type";
      uses wireless-client-oper:protocol-type-num-clients;
    }
    leaf-list total-11k-roam-counts {
      type uint32;
      max-elements "10";
      ordered-by user;
      description
        "Total number of 802.11k roam attempts";
    }
    leaf total-other-roam-attempts {
      type uint32;
      description
        "Total other type of roam attempts";
    }
    leaf total-aid-allocation-failure {
      type uint32;
      description
        "Total AID allocation failures";
    }
    leaf total-aid-free-failure {
      type uint32;
      description
        "Total AID free failures";
    }
    leaf total-11r-ft-auth-req-received {
      type uint32;
      description
        "Total 11r ft authentication requests received";
    }
    leaf total-11r-ft-auth-rsp-success {
      type uint32;
      description
        "Total 11r ft authentication response success";
    }
    leaf total-11r-ft-auth-rsp-failure {
      type uint32;
      description
        "Total 11r ft authentication response failure";
    }
    leaf total-11r-ft-action-req-received {
      type uint32;
      description
        "Total 11r ft action requests received";
    }
    leaf total-11r-ft-action-rsp-success {
      type uint32;
      description
        "Total 11r ft action response success";
    }
    leaf total-11r-ft-action-rsp-failure {
      type uint32;
      description
        "Total 11r ft action response failure";
    }
    leaf num-client-radio-type-24ghz {
      type uint32;
      description
        "Number of clients connected to 2.4ghz radio.";
    }
    leaf num-client-radio-type-5ghz {
      type uint32;
      description
        "Number of clients connected to 5ghz radio.";
    }
    leaf wpa3-sae-attempts {
      type uint32;
      description
        "Total number of WPA3 SAE client attempts.";
    }
    leaf wpa3-sae-protocol-incomplete {
      type uint32;
      description
        "Total number of WPA3 SAE clients protocol incomplete.";
    }
    leaf wpa3-sae-commit-received {
      type uint32;
      description
        "Total number of WPA3 SAE commit received.";
    }
    leaf wpa3-sae-commit-rejected {
      type uint32;
      description
        "Total number of WPA3 SAE commit rejected.";
    }
    leaf wpa3-sae-commit-unsupported-group {
      type uint32;
      description
        "Total number of WPA3 SAE commit with unsupported group.";
    }
    leaf wpa3-sae-commit-sent {
      type uint32;
      description
        "Total number of WPA3 SAE commit sent.";
    }
    leaf wpa3-sae-confirm-received {
      type uint32;
      description
        "Total number of WPA3 SAE confirm received.";
    }
    leaf wpa3-sae-confirm-rejected {
      type uint32;
      description
        "Total number of WPA3 SAE confirm rejected.";
    }
    leaf wpa3-sae-confirm-field-mismatch {
      type uint32;
      description
        "Total number of WPA3 SAE confirm field mismatch.";
    }
    leaf wpa3-sae-confirm-message-invalid-length {
      type uint32;
      description
        "Total number of WPA3 SAE confirm message length invalid.";
    }
    leaf wpa3-sae-confirm-sent {
      type uint32;
      description
        "Total number of WPA3 SAE confirm sent.";
    }
    leaf sae-open-sessions {
      type uint32;
      description
        "Number of SAE open sessions.";
    }
  }

  grouping mmif-client-mobility-history-entry {
    description
      "Entry for the roaming client's association history";
    leaf instance-id {
      type uint32;
      description
        "WNCD instance ID from which it has roamed";
    }
    leaf ms-ap-slot-id {
      type uint32;
      description
        "AP Slot ID to which it was connected previously";
    }
    leaf ms-assoc-time {
      type yang:date-and-time;
      description
        "Time for which the client has been associated, before roaming";
    }
    leaf role {
      type wireless-mobility-types:mm-client-role;
      description
        "Mobility Client's role";
    }
    leaf bssid {
      type yang:mac-address;
      description
        "BSSID of the client before roaming";
    }
    leaf ap-name {
      type string;
      description
        "Name of the AP from which it has roamed";
    }
  }

  grouping mmif-client-mobility-history {
    description
      "List of the complete client's mobility history i.e information about the devicesWNCD it was connected to";
    list entry {
      description
        "An entry of a client's mobility history";
      uses wireless-client-oper:mmif-client-mobility-history-entry;
    }
  }

  grouping mmif-mobility-stats {
    description
      "Client's Mobility Statistics";
    leaf mmif-fsm-invalid-events {
      type uint32;
      description
        "Total number of invalid events received in the mobility FSM";
    }
    leaf mmif-fsm-unknown-events {
      type uint32;
      description
        "Total number of unknown events received in the mobility FSM";
    }
    leaf mmif-internal-errors {
      type uint32;
      description
        "Total number of internal errors";
    }
    leaf mmif-ipc-failure {
      type uint32;
      description
        "Total number of IPC failures";
    }
    leaf mmif-db-failure {
      type uint32;
      description
        "Total number of database failures";
    }
    leaf mmif-invalid-params-failure {
      type uint32;
      description
        "Total number of invalid parameter failures";
    }
    leaf mmif-mm-msg-decode-failure {
      type uint32;
      description
        "Total number of mobility message decode failures";
    }
    leaf mmif-fsm-failure {
      type uint32;
      description
        "Total number of FSM failures";
    }
    leaf mmif-client-handoff-success {
      type uint32;
      description
        "Total number of client handoff successes";
    }
    leaf mmif-client-handoff-failure {
      type uint32;
      description
        "Total number of client handoff failures";
    }
    leaf mmif-anchor-deny {
      type uint32;
      description
        "Total number of anchor deny errors";
    }
    leaf mmif-timeout {
      type uint32;
      description
        "Total number of timeout errors";
    }
    leaf mmif-remote-delete {
      type uint32;
      description
        "Total number of remote delete errors";
    }
    leaf mmif-tunnel-down-delete {
      type uint32;
      description
        "Total number of mobility tunnel down delete errors";
    }
    leaf mmif-mbssid-down-event {
      type uint32;
      description
        "Total number of MBSSID down event errors";
    }
    leaf mmif-unknown-failure {
      type uint32;
      description
        "Total number of unknown failures";
    }
    leaf mmif-schedule-errors {
      type uint32;
      description
        "Total number of scheduled errors";
    }
    leaf event-data-frees {
      type uint32;
      description
        "Total number of event data frees done";
    }
    leaf event-data-allocs {
      type uint32;
      description
        "Total number of data allocations done";
    }
    leaf intra-wncd-roam-count {
      type uint32;
      description
        "Total number of intra wncd roaming done";
    }
    leaf remote-inter-controller-roam-count {
      type uint32;
      description
        "Total number of remote inter_controller roam count done";
    }
    leaf remote-webauth-pending-roam-count {
      type uint32;
      description
        "Total number of remote roam in webauth pending";
    }
    leaf anchor-request-sent {
      type uint32;
      description
        "Total number of anchor requests sent";
    }
    leaf anchor-request-grant-received {
      type uint32;
      description
        "Total number of anchor request grants received";
    }
    leaf anchor-request-deny-received {
      type uint32;
      description
        "Total number of anchor request denies received";
    }
    leaf anchor-request-received {
      type uint32;
      description
        "Total number of anchor requests received";
    }
    leaf anchor-request-grant-sent {
      type uint32;
      description
        "Total number of anchor request grants sent";
    }
    leaf anchor-request-deny-sent {
      type uint32;
      description
        "Total number of anchor request denies sent";
    }
    leaf handoff-received-ok {
      type uint32;
      description
        "Total number of handoff status OK received";
    }
    leaf handoff-received-grp-mismatch {
      type uint32;
      description
        "Total number of handoff status group mismatches received";
    }
    leaf handoff-received-ms-unknown {
      type uint32;
      description
        "Total number of handoff status unknown client received";
    }
    leaf handoff-received-ms-ssid {
      type uint32;
      description
        "Total number of handoff status client SSID received";
    }
    leaf handoff-received-deny {
      type uint32;
      description
        "Total number of handoff status deny received";
    }
    leaf handoff-sent-ok {
      type uint32;
      description
        "Total number of handoff status OK sent";
    }
    leaf handoff-sent-grp-mismatch {
      type uint32;
      description
        "Total number of handoff status group mismatches sent";
    }
    leaf handoff-sent-ms-unknown {
      type uint32;
      description
        "Total number of handoff status unknown client sent";
    }
    leaf handoff-sent-ms-ssid {
      type uint32;
      description
        "Total number of handoff status client SSID sent";
    }
    leaf handoff-sent-deny {
      type uint32;
      description
        "Total number of handoff status deny sent";
    }
  }

  grouping mmif-client-history {
    description
      "mmif client history";
    leaf client-mac {
      type yang:mac-address;
      description
        "client mac address";
    }
    container mobility-history {
      description
        "association and mobility history of the client";
      uses wireless-client-oper:mmif-client-mobility-history;
    }
    container evt-history {
      description
        "MMIF FSM event history";
      uses event-history-types:event-history;
    }
  }

  grouping mmif-client-stats {
    description
      "MMIF client statistics";
    leaf client-mac {
      type yang:mac-address;
      description
        "client mac address";
    }
    container mblty-stats {
      description
        "MMIF mobility event statistics";
      uses wireless-client-oper:mmif-mobility-stats;
    }
    list ipc-stats {
      max-elements "255";
      description
        "MM IPC message statistics";
      uses wireless-mobility-types:mm-msg-stats;
    }
  }

  grouping ewlc-mafsm-oper-data {
    description
      "Client Mobility Data";
    leaf ms-mac-addr {
      type yang:mac-address;
      description
        "Client mac-address";
    }
    leaf mm-client-role {
      type wireless-mobility-types:mm-client-role;
      description
        "Mobility Role";
    }
    leaf mm-client-roam-type {
      type wireless-mobility-types:mm-client-roam-type;
      description
        "Client Roam Type";
    }
    leaf mm-announce-collision {
      type uint8;
      description
        "Announce Collisions";
    }
    leaf mm-access-vlan {
      type uint16;
      description
        "Client VLAN Id";
    }
    leaf mm-anchor-bridge-domain-id {
      type uint32;
      description
        "Anchor Bridge Id";
    }
    leaf mm-instance {
      type uint32;
      description
        "Incremental Count for Handoff Instance";
    }
    leaf mm-complete-timestamp {
      type yang:date-and-time;
      units "seconds";
      description
        "Time at which Mobility complete happens";
    }
    leaf mm-remote-tunnel-ip {
      type inet:ip-address;
      description
        "Mobility Remote Tunnel IP Address";
    }
    leaf mm-remote-tunnel-sec-ip {
      type inet:ip-address;
      description
        "Mobility Remote Secondary Tunnel Address";
    }
    leaf mm-remote-platform-id {
      type uint8;
      description
        "Remote Node's platform ID";
    }
    leaf mm-remote-tunnel-id {
      type uint32;
      description
        "Mobility Remote Tunnel Id";
    }
    leaf authc-status {
      type boolean;
      description
        "authc status of the client used by cts";
    }
    leaf mm-anchor-ip {
      type inet:ip-address;
      description
        "Mobility Anchor IP Address";
    }
  }

  grouping ewlc-client-ccx-oper-data {
    description
      "Client's CCX data";
    leaf ms-mac-address {
      type yang:mac-address;
      description
        "Mac Address of the client";
    }
    leaf ccx-version {
      type uint8;
      description
        "CCX version";
    }
    leaf ccx-e2e-version {
      type uint8;
      description
        "CCX End-to-End version";
    }
    leaf ccx-refresh-rate {
      type uint8;
      description
        "CCX Refresh Rate sent by the client in Aironet IE";
    }
    leaf radio-type {
      type uint16;
      description
        "Radio Type";
    }
    leaf no-of-radio-channels {
      type uint8;
      description
        "Number of Radio channels";
    }
    leaf ssid {
      type string;
      description
        "SSID of the WLAN";
    }
    leaf ccx-capability {
      type wireless-client-oper:ccx-capability-enum;
      description
        "CCX S60PLM Capability";
    }
  }

  grouping ewlc-client-wlan-policy {
    description
      "Client WLAN policy";
    leaf current-switching-mode {
      type wireless-client-oper:client-switching-mode;
      description
        "Current switching mode of the client";
    }
    leaf wlan-switching-mode {
      type wireless-client-oper:client-switching-mode;
      description
        "Wlan switching mode, which is initialized based on the WLAN properties";
    }
    leaf central-authentication {
      type wireless-client-oper:client-authentication-type;
      description
        "Indicator of whether the client is centrallylocally authenticated. NA for clients connected to Local Mode APs";
    }
    leaf central-dhcp {
      type boolean;
      description
        "Flag for central DHCP";
    }
    leaf central-assoc-enable {
      type boolean;
      description
        "Flag for central association (Association done at the controller)";
    }
    leaf vlan-central-switching {
      type boolean;
      description
        "VLAN based central switching";
    }
    leaf is-fabric-client {
      type boolean;
      description
        "Indicator of whether the client is an Enterprise client or not";
    }
    leaf is-guest-fabric-client {
      type boolean;
      description
        "Indicator of whether the client is a Guest client or not";
    }
  }

  grouping wgb-data {
    description
      "wgb data";
    leaf wired-client-count {
      type uint8;
      description
        "Number of wired clients joined in this WGB";
    }
  }

  grouping wired-client-data {
    description
      "wired client data";
    leaf primary-wgb-mac {
      type yang:mac-address;
      description
        "Primary Mac address of the associated Work group Bridge";
    }
    leaf secondary-wgb {
      type yang:mac-address;
      description
        "Secondary Mac address of the associated secondary Work group Bridge";
    }
    leaf wgb-create-time {
      type uint64;
      description
        "Work Group Bridge association identifier";
    }
  }

  grouping ewlc-client-common-oper-data {
    description
      "Client Common Operational Data";
    leaf client-mac {
      type yang:mac-address;
      description
        "Client's Mac Address";
    }
    leaf ap-name {
      type string;
      description
        "Name of the AP to which the Client is connected";
    }
    leaf ms-ap-slot-id {
      type uint8;
      description
        "Associated AP's radio slot id";
    }
    leaf ms-radio-type {
      type wireless-client-types:ms-phy-radio-type;
      description
        "Physical radio type of client";
    }
    leaf wlan-id {
      type uint32;
      description
        "WLAN Id";
    }
    leaf configured-lan-id {
      type uint32;
      description
        "Configured WLAN/RLAN Id";
    }
    leaf ms-client-iif-id {
      type uint32;
      description
        "Client IIF ID";
    }
    leaf co-timer-handle {
      type uint32;
      description
        "CO timer to reap incomplete associations";
    }
    leaf client-type {
      type wireless-client-types:ms-client-type;
      description
        "Client Type to distinguish between local and hreap mode";
    }
    leaf co-state {
      type wireless-client-types:client-co-state;
      description
        "Status of client";
    }
    leaf co-fsm-state {
      type uint32;
      description
        "State of CO FSM";
    }
    leaf aaa-override-passphrase {
      type boolean;
      description
        "AAA override passphrase enabled";
    }
    leaf is-tvi-enabled {
      type boolean;
      description
        "Encrypted Traffic Analytics enabled";
    }
    leaf prev-co-state {
      type wireless-client-types:client-co-state;
      description
        "Previous state of the client";
    }
    leaf iplearn-fsm-state {
      type wireless-client-oper:client-iplearn-fsm-state;
      description
        "IP learn fsm client states";
    }
    leaf dpath-fsm-state {
      type wireless-client-oper:client-dpath-fsm-state;
      description
        "Dpath fsm client states";
    }
    leaf-list co-state-transition-timestamp {
      type uint64;
      max-elements "13";
      ordered-by user;
      description
        "Client Orchestrator state transition timestamp";
    }
    leaf fast-path-status {
      type uint8;
      description
        "Fast path status";
    }
    leaf ip-learn-type {
      type wireless-client-types:ip-binding-learn-type;
      description
        "IP learn method";
    }
    container wlan-policy {
      description
        "Client wlan policy";
      uses wireless-client-oper:ewlc-client-wlan-policy;
    }
    leaf device-type {
      type string;
      description
        "Device Type";
    }
    leaf username {
      type string;
      description
        "Username of the client";
    }
    container wired-client-data {
      description
        "wired client data";
      uses wireless-client-oper:wired-client-data;
    }
    container wgb-data {
      description
        "wgb data";
      uses wireless-client-oper:wgb-data;
    }
    leaf atf-policy-name {
      type string;
      description
        "Profile name which supports ATF [Air Time Fairness] policy";
    }
    leaf mac-auth-passed {
      type wireless-client-oper:webauth-on-mac-failure;
      description
        "WebAuth On MAC Failure: L2 Auth";
    }
  }

  grouping st-cac-stats {
    description
      "Wireless Call admission control throttle stats";
    leaf instance-id {
      type uint32;
      description
        "Instance ID";
    }
    leaf iplearn-throttle {
      type uint32;
      description
        "Number of times CAC throttling applied due to IP Learn queue exceeding threshold";
    }
    leaf ipc-throttle {
      type uint32;
      description
        "Number of times CAC throttling applied due to IPC queues exceeding threshold";
    }
    leaf aaa-throttle {
      type uint32;
      description
        "Number of times CAC throttling applied due to AAA queues exceeding threshold";
    }
  }

  grouping st-client-state-stats {
    description
      "Structure for storing the Client State Statistics";
    leaf avg-client-state-duration {
      type uint64;
      description
        "Average time taken over total number of sessions in the state";
    }
    leaf total-sessions {
      type uint64;
      description
        "Total number of sessions in the state";
    }
  }

  grouping run-state-latency-buckets {
    description
      "Distribution of latency in the buckets";
    leaf-list buffer {
      type uint64;
      max-elements "6";
      ordered-by user;
      description
        "Holds the value of latency of each bucket";
    }
  }

  grouping st-tbl-client-latency-stats {
    description
      "Structure for storing the Client Latency Statistics";
    list client-states-stats {
      max-elements "13";
      description
        "Client State Statistics";
      uses wireless-client-oper:st-client-state-stats;
    }
    leaf avg-client-run-state-latency {
      type uint64;
      description
        "Average Latency for the Client to reach the Run state";
    }
    leaf avg-client-run-state-latency-sans-user-delay {
      type uint64;
      description
        "Average Latency for the Client to reach the Run state, without user delay";
    }
    container run-state-latency-buckets {
      description
        "Distribution of latency in the buckets";
      uses wireless-client-oper:run-state-latency-buckets;
    }
    leaf rolling-run-state-hptr {
      type uint32;
      description
        "Rolling latency of clients in RUN state";
    }
    leaf peak-run-state-rate {
      type uint32;
      description
        "Peak rate of clients in RUN state";
    }
  }

  grouping ewlc-wgb-wired-key {
    description
      "WGB wired client table key";
    leaf wgb-mac {
      type yang:mac-address;
      description
        "WGB mac address";
    }
    leaf wired-client-mac {
      type yang:mac-address;
      description
        "Wired client mac";
    }
  }

  grouping ewlc-client-stats-oper-data {
    description
      "Client Statistical Operational data";
    leaf ms-mac-address {
      type yang:mac-address;
      description
        "Client's Mac Address";
    }
    leaf bytes-rx {
      type uint64;
      description
        "Bytes Received";
    }
    leaf bytes-tx {
      type uint64;
      description
        "Bytes Sent";
    }
    leaf policy-errs {
      type uint64;
      description
        "Policy Errors";
    }
    leaf pkts-rx {
      type uint64;
      description
        "Packets Received";
    }
    leaf pkts-tx {
      type uint64;
      description
        "Packets Sent";
    }
    leaf data-retries {
      type uint64;
      description
        "Data Retries";
    }
    leaf rts-retries {
      type uint64;
      description
        "Rts retries";
    }
    leaf duplicate-rcv {
      type uint64;
      description
        "Duplicates received";
    }
    leaf decrypt-failed {
      type uint64;
      description
        "Decryption Failed";
    }
    leaf mic-mismatch {
      type uint64;
      description
        "Mic Errors";
    }
    leaf mic-missing {
      type uint64;
      description
        "Mic Missing Frames";
    }
    leaf most-recent-rssi {
      type int8;
      description
        "Last updated Radio Signal Strength indicator";
    }
    leaf most-recent-snr {
      type uint8;
      description
        "Last updated Signal strength to noise ratio";
    }
    leaf tx-excessive-retries {
      type uint64;
      description
        "Excessive Retries";
    }
    leaf tx-retries {
      type uint64;
      description
        "Retries count";
    }
    leaf rts-success-count {
      type uint64;
      description
        "Success Count";
    }
    leaf rts-fail-count {
      type uint64;
      description
        "Fail Count";
    }
    leaf tx-filtered {
      type uint64;
      description
        "Number of packets dropped due to Transmission filter";
    }
    leaf power-save-state {
      type uint8;
      description
        "Power save state";
    }
    leaf current-rate {
      type string;
      description
        "Current data rate at which the client is communicating";
    }
    leaf most-recent-link-status {
      type uint8;
      description
        "Most recent link status";
    }
    leaf airtime-used-inst {
      type uint32;
      description
        "AirTime used instantaneously by a client on its associated AP radio";
    }
    leaf airtime-used-cum {
      type uint64;
      description
        "Total AirTime used cumulatively by a client on its associated AP radio";
    }
    leaf frames-sent-inst {
      type uint32;
      description
        "Number of frames sent instantaneously by a client on its associated AP radio";
    }
    leaf frames-sent-cum {
      type uint64;
      description
        "Total number of frames sent cumulatively by a client on its associated AP radio";
    }
    leaf frames-dropped-inst {
      type uint32;
      description
        "Number of frames dropped instantaneously by a client on its associated AP radio";
    }
    leaf frames-dropped-cum {
      type uint64;
      description
        "Total number of frames dropped cumulatively by a client on its associated AP radio";
    }
    leaf client-state {
      type wireless-types:enm-atf-client-state;
      description
        "Client usage by a client on its associated AP radio";
    }
    leaf ext-stats-timestamp {
      type uint32;
      description
        "Extended 802.11 mac statistics";
    }
    leaf speed {
      type uint32;
      description
        "Data rate of the client in Mb/s";
    }
    leaf spatial-stream {
      type uint32;
      description
        "Number of spatial streams received by the client. Supported number of spatial streams is from 0 to 4";
    }
  }

  grouping ewlc-client-session-stats {
    description
      "Session statistics of the client";
    leaf most-ms-entries {
      type uint32;
      description
        "Maximum number of Client entries ever in the table";
    }
    leaf cur-ms-entries {
      type uint32;
      description
        "Current number of Client entries in the table, excluding FAPs";
    }
    leaf total-ms-entries {
      type uint32;
      description
        "Current number of Client entries in the table";
    }
    leaf total-ipv4-ms-entries {
      type uint32;
      description
        "total ipv4 search entries in table";
    }
    leaf cur-wgb-entries {
      type uint32;
      description
        "Current number of Work group bridge client entries";
    }
    leaf cur-foreign-entries {
      type uint32;
      description
        "Number of Foriegn Clients";
    }
    leaf cur-anchor-entries {
      type uint32;
      description
        "Number of Anchored Clients";
    }
    leaf cur-local-entries {
      type uint32;
      description
        "Number of Local Clients";
    }
  }

  grouping ewlc-client-delete-stats {
    description
      "DisassociationDeauthentication related stats of the client";
    leaf total-del-reason-none {
      type uint32;
      description
        "Total number of delete reason None recorded";
    }
    leaf total-del-reason-unspec {
      type uint32;
      description
        "Total number of delete reason Unspecified recorded";
    }
    leaf total-del-reason-prev-auth-not-valid {
      type uint32;
      description
        "Total number of delete reason-Previous Authentication not valid-recorded";
    }
    leaf total-del-reason-deauth-leaving {
      type uint32;
      description
        "Total number of delete reason-Deauthenticated-recorded";
    }
    leaf total-del-reason-disassoc-due-to-inactivity {
      type uint32;
      description
        "Total number of delete reason-Disassociated due to inactivity-recorded";
    }
    leaf total-del-reason-disassoc-ap-busy {
      type uint32;
      description
        "Total number of delete reason-Disassoc due to AP busy-recorded";
    }
    leaf total-del-reason-disassoc-ap-down {
      type uint32;
      description
        "Total number of delete reason-Diassoc due to AP down-recorded";
    }
    leaf total-del-reason-class2-frame-from-nonauth-sta {
      type uint32;
      description
        "Total number of delete reason-Class2 Frame from Non Authenticated Sta-recorded";
    }
    leaf total-del-reason-class2-frame-from-nonassoc-sta {
      type uint32;
      description
        "Total number of delete reason-Class2 Frame from Non Associated Sta-recorded";
    }
    leaf total-del-reason-disassoc-sta-has-left {
      type uint32;
      description
        "Total number of delete reason-Disassoc as STA has left-recorded";
    }
    leaf total-del-reason-sta-req-assoc-without-auth {
      type uint32;
      description
        "Total number of delete reason-STA requested association without authentication-recorded";
    }
    leaf total-del-reason-invalid-ie {
      type uint32;
      description
        "Total number of delete reason -Invalid- recorded";
    }
    leaf total-del-reason-micheal-fail {
      type uint32;
      description
        "Total number of delete reason -Micheal fail- recorded";
    }
    leaf total-del-reason-4way-handshake-timeout {
      type uint32;
      description
        "Total number of delete reason -4way handshake timeout- recorded";
    }
    leaf total-del-reason-group-key-update-timeout {
      type uint32;
      description
        "Total number of delete reason -group key update timeout- recorded";
    }
    leaf total-del-reason-invalid-rsn-ie {
      type uint32;
      description
        "Total number of delete reason -Invalid RSN Information Element- recorded";
    }
    leaf total-del-reason-group-cipher-invalid {
      type uint32;
      description
        "Total number of delete reason -Group Cipher Invalid- recorded";
    }
    leaf total-del-reason-unicast-cipher-invalid {
      type uint32;
      description
        "Total number of delete reason -Unicast Cipher Invalid- recorded";
    }
    leaf total-del-reason-akmp-invalid {
      type uint32;
      description
        "Total number of delete reason -AKMP invalid- recorded";
    }
    leaf total-del-reason-unsupport-rsn-ver {
      type uint32;
      description
        "Total number of delete reason -Unsupported RSN version- recorded";
    }
    leaf total-del-reason-invalid-rsn-ie-capab {
      type uint32;
      description
        "Total number of delete reason -Invalid RSN IE capabilities- recorded";
    }
    leaf total-del-reason-8021x-auth-fail {
      type uint32;
      description
        "Total number of delete reason -802.1x authentication failed- recorded";
    }
    leaf total-del-reason-cipher-suite-reject {
      type uint32;
      description
        "Total number of delete reason -Cipher Suite rejected- recorded";
    }
    leaf total-del-reason-unspec-qos-related-reason {
      type uint32;
      description
        "Total number of delete reason -Unspecified QOS related- recorded";
    }
    leaf total-del-reason-insuff-bw {
      type uint32;
      description
        "Total number of delete reason -Insufficient BandWidth- recorded";
    }
    leaf total-del-reason-poor-chnl-cond {
      type uint32;
      description
        "Total number of delete reason -Poor Channel condition- recorded";
    }
    leaf total-del-reason-sta-violating-txop {
      type uint32;
      description
        "Total number of delete reason -STA violating TXOP- recorded";
    }
    leaf total-del-reason-voice-sta-reanchor {
      type uint32;
      description
        "Total number of delete reason -Voice STA reanchor- recorded";
    }
    leaf total-del-reason-prob-sta-in-loc-calib {
      type uint32;
      description
        "Total number of delete reason -Problematic STA in loc calibration- recorded";
    }
    leaf total-del-reason-guest-anchor-down {
      type uint32;
      description
        "Total number of delete reason -Guest Anchor Down- recorded";
    }
    leaf total-del-reason-miss-reason-code {
      type uint32;
      description
        "Total number of delete reason -Missed reason code- recorded";
    }
    leaf total-del-reason-access-to-quaran {
      type uint32;
      description
        "Total number of delete reason -Access to quarantine- recorded";
    }
    leaf total-del-reason-max-assoc-client-reach {
      type uint32;
      description
        "Total number of delete reason -Max Associated client limit reached- recorded";
    }
    leaf total-del-reason-max-clients-reach-on-ap {
      type uint32;
      description
        "Total number of delete reason -Max client limit on AP reached- recorded";
    }
    leaf total-del-reason-webauth-reqd-timeout {
      type uint32;
      description
        "Total number of delete reason -Webauth required timeout- recorded";
    }
    leaf total-del-reason-ios-init-state-timeout {
      type uint32;
      description
        "Total number of delete reason -IOS init state timeout- recorded";
    }
    leaf total-del-reason-fail-aaa-server {
      type uint32;
      description
        "Total number of delete reason -Failure in AAA server- recorded";
    }
    leaf total-del-reason-webauth-fail {
      type uint32;
      description
        "Total number of delete reason -Webauth failure- recorded";
    }
    leaf total-del-reason-sta-roam-without-auth {
      type uint32;
      description
        "Total number of delete reason -STA roamed without authentication- recorded";
    }
    leaf total-del-reason-sta-cac-fail-policy {
      type uint32;
      description
        "Total number of delete reason -STA CAC fail in policy- recorded";
    }
    leaf total-del-reason-max-cli-reach-on-ap-radio {
      type uint32;
      description
        "Total number of delete reason -Maximum client reached on AP radio- recorded";
    }
    leaf total-del-reason-max-cli-reach-on-ap-wlan {
      type uint32;
      description
        "Total number of delete reason -Maximum client reached on AP WLAN- recorded";
    }
    leaf total-del-reason-sta-no-ip {
      type uint32;
      description
        "Total number of delete reason -STA has no IP address- recorded";
    }
    leaf total-del-reason-wcdb-add-fail {
      type uint32;
      description
        "Total number of delete reason -WCDB add failed- recorded";
    }
    leaf total-del-reason-wcdb-sc-fail {
      type uint32;
      description
        "Total number of delete reason -WCDB SC failed- recorded";
    }
    leaf total-del-reason-ip-theft {
      type uint32;
      description
        "Total number of delete reason -IP theft- recorded";
    }
    leaf total-del-reason-80211-auth-fail {
      type uint32;
      description
        "Total number of delete reason -802.11 authentication failure- recorded";
    }
    leaf total-del-reason-80211-assoc-fail {
      type uint32;
      description
        "Total number of delete reason -802.11 Association failure- recorded";
    }
    leaf total-del-reason-cids-shun-fail {
      type uint32;
      description
        "Total number of delete reason -CIDS shun failure- recorded";
    }
    leaf total-del-reason-vlan-misconfig {
      type uint32;
      description
        "Total number of delete reason -VLAN misconfigured- recorded";
    }
    leaf total-del-reason-epm-fail {
      type uint32;
      description
        "Total number of delete reason -EPM failure- recorded";
    }
    leaf total-del-reason-switch-wlan {
      type uint32;
      description
        "Total number of delete reason -Switching WLAN- recorded";
    }
    leaf total-del-reason-awips {
      type uint32;
      description
        "Total number of delete reason -AWIPS- recorded";
    }
    leaf total-del-reason-authz-fail {
      type uint32;
      description
        "Total number of delete reason -Authorization failure- recorded";
    }
    leaf total-del-reason-logout {
      type uint32;
      description
        "Total number of delete reason -Logged out- recorded";
    }
    leaf total-del-reason-admin-reset {
      type uint32;
      description
        "Total number of delete reason -Admin Reset- recorded";
    }
    leaf total-del-reason-anchor-close {
      type uint32;
      description
        "Total number of delete reason -Anchor closed connection- recorded";
    }
    leaf total-del-reason-reconcile {
      type uint32;
      description
        "Total number of delete reason -Reconciliation- recorded";
    }
    leaf total-del-reason-iapp-timeout {
      type uint32;
      description
        "Total number of delete reason -IAPP timeout- recorded";
    }
    leaf total-del-reason-unknown {
      type uint32;
      description
        "Total number of delete reason -Unknown- recorded";
    }
    leaf total-del-reason-wlan-shut {
      type uint32;
      description
        "Total number of delete reason -Wlan shut- recorded";
    }
    leaf total-del-reason-radio-shut {
      type uint32;
      description
        "Total number of delete reason -Radio Shut- recorded";
    }
    leaf total-del-reason-channel-change {
      type uint32;
      description
        "Total number of delete reason -Channel change- recorded";
    }
    leaf deauth-from-station {
      type uint32;
      description
        "Total number of Deauthentication from station count";
    }
    leaf deauth-to-station {
      type uint32;
      description
        "Total number of Deauthentication to station count";
    }
    leaf disassoc-from-station {
      type uint32;
      description
        "Total number of Disassociation from station count";
    }
    leaf disassoc-to-station {
      type uint32;
      description
        "Total number of Disassociation to station count";
    }
    leaf status-caps-unsupported {
      type uint32;
      description
        "Requested Capabilities Unsupported count";
    }
    leaf status-reassoc-no-assoc {
      type uint32;
      description
        "Reassoc denied due to No Assoc count";
    }
    leaf status-assoc-denied-unspec {
      type uint32;
      description
        "Assoc denied due to reason outside scope count";
    }
    leaf status-not-supported-auth-alg {
      type uint32;
      description
        "Not supported Auth algorithm count";
    }
    leaf status-unknown-auth-transaction {
      type uint32;
      description
        "Unknown Auth Transaction Sequence count";
    }
    leaf status-challenge-fail {
      type uint32;
      description
        "Auth rejected due to Challenge Fail count";
    }
    leaf status-auth-timeout {
      type uint32;
      description
        "Auth rejected due to Timeout count";
    }
    leaf status-max-sta {
      type uint32;
      description
        "Assoc denied due to Max Station on AP count";
    }
    leaf status-denied-rates {
      type uint32;
      description
        "Assoc denied due to STA Unsupport data rates count";
    }
    leaf status-assoc-denied-noshort {
      type uint32;
      description
        "Assoc denied due to STA Unsupport short preamble count";
    }
    leaf status-assoc-denied-nopbcc {
      type uint32;
      description
        "Assoc denied due to STA Unsupport PBCC modulation count";
    }
    leaf status-assoc-denied-noagility {
      type uint32;
      description
        "Assoc denied due to STA Unsupport Channel Agility count";
    }
    leaf status-assoc-req-rejected-temp {
      type uint32;
      description
        "Assoc Request rejected temporarily count";
    }
    leaf status-rmf-frame-policy-violation {
      type uint32;
      description
        "Robust Management Frame Policy Violation count";
    }
    leaf status-unspec-qos-related {
      type uint32;
      description
        "Unspecified QOS related failure count";
    }
    leaf status-insufficient-bandwidth {
      type uint32;
      description
        "Assoc denied due to Insufficient Bandwidth count";
    }
    leaf status-poor-channel-conditions {
      type uint32;
      description
        "Assoc denied due to Poor Channel Conditions count";
    }
    leaf status-qos-support-mandatory {
      type uint32;
      description
        "Assoc denied due to Unsupport QOS Facility count";
    }
    leaf status-request-declined {
      type uint32;
      description
        "Request has been declined count";
    }
    leaf status-invalid-qos-parameter {
      type uint32;
      description
        "Invalid QOS Parameters count";
    }
    leaf status-see-attached-tspec {
      type uint32;
      description
        "TS not created for attached TSPEC count";
    }
    leaf status-direct-link-disallowed {
      type uint32;
      description
        "Direct link is not allowed in the BSS by policy count";
    }
    leaf status-destination-sta-not-present {
      type uint32;
      description
        "Destination STA is not present within this BSS count";
    }
    leaf status-destination-sta-not-qos {
      type uint32;
      description
        "Destination STA is not a QoS STA count";
    }
    leaf status-invalid-ie {
      type uint32;
      description
        "Invalid Information Element count";
    }
    leaf status-group-cipher-invalid {
      type uint32;
      description
        "Invalid Group Cipher count";
    }
    leaf status-unicast-cipher-invalid {
      type uint32;
      description
        "Invalid Unicast Cipher count";
    }
    leaf status-akmp-invalid {
      type uint32;
      description
        "Invalid AKMP count";
    }
    leaf status-unsupported-rsn-version {
      type uint32;
      description
        "Unsupported RSN Information Element Version count";
    }
    leaf status-invalid-rsn-ie-capabilities {
      type uint32;
      description
        "Invalid RSN Information Element Capabilities count";
    }
    leaf status-cipher-suite-rejected {
      type uint32;
      description
        "Cipher Suite rejected due to security policy count";
    }
    leaf status-denied-ht-capabilities {
      type uint32;
      description
        "Assoc denied HT Capabilities Information Element count";
    }
    leaf status-invalid-ft-action-frame-count {
      type uint32;
      description
        "Invalid FT Action Frame Count";
    }
    leaf status-invalid-pmkid {
      type uint32;
      description
        "Invalid Auth Frame PMK Id count";
    }
    leaf status-invalid-mdie {
      type uint32;
      description
        "Invalid Mobility Domain Information Element count";
    }
    leaf status-invalid-ftie {
      type uint32;
      description
        "Invalid Fast Transition Information Element count";
    }
    leaf status-invalid-ftie-mic {
      type uint32;
      description
        "Invalid Fast Transition Information Element MIC count";
    }
    leaf status-ccx-qos-unspecified-failure {
      type uint32;
      description
        "CCX QOS Unspecified failure count";
    }
    leaf status-ccx-qos-policy {
      type uint32;
      description
        "CCX QOS TSPEC request refused due to AP Policy count";
    }
    leaf status-ccx-insufficient-bandwidth {
      type uint32;
      description
        "CCX Assoc denied due to Insufficient Bandwidth count";
    }
    leaf status-ccx-invalid-qos-parameter {
      type uint32;
      description
        "CCX Invalid QOS TSPEC Parameters count";
    }
  }

  grouping ewlc-client-others-stats {
    description
      "Statistics for add mobiledelete mobile and other Statistics";
    leaf total-mobile-adds {
      type uint32;
      description
        "Total number of add mobiles sent to the AP";
    }
    leaf total-mobile-dels {
      type uint32;
      description
        "Total number of delete mobiles sent to the AP";
    }
    leaf total-mobile-add-fails {
      type uint32;
      description
        "Total number of add mobile fails received";
    }
    leaf total-mobile-del-fails {
      type uint32;
      description
        "Total number of delete mobile fails received";
    }
    leaf monitoring-start-client {
      type int64;
      description
        "Start time of monitoring the client for Association failures";
    }
    leaf monitoring-end-client {
      type int64;
      description
        "End time of monitoring the client for Association failures";
    }
    leaf counters-init-time {
      type int64;
      description
        "mobile add counter init";
    }
    leaf counters-curr-time {
      type int64;
      description
        "mobile add counters current time";
    }
  }

  grouping ewlc-client-global-stats-op {
    description
      "Global client statistics table";
    container session-stats {
      description
        "Session statistics of the client";
      uses wireless-client-oper:ewlc-client-session-stats;
    }
    container delete-stats {
      description
        "DisassociationDeauthentication related Statistics of the client";
      uses wireless-client-oper:ewlc-client-delete-stats;
    }
    container others-stats {
      description
        "Statistics for adddelete mobile and other statistics";
      uses wireless-client-oper:ewlc-client-others-stats;
    }
  }

  grouping sm-device-classifier-data {
    description
      "Data of device classifier";
    leaf dc-profile-name {
      type string;
      description
        "Dc profile name";
    }
    leaf dc-device-name {
      type string;
      description
        "Dc device name";
    }
    leaf dc-device-class {
      type string;
      description
        "Dc device class";
    }
  }

  grouping sm-audit-id {
    description
      "Audit session id of the session";
    leaf aid {
      type string {
        length "0 .. 25";
      }
      description
        "audit session id of the session";
    }
  }

  grouping sm-posture-token {
    description
      "posture token associated with session";
    leaf token {
      type string {
        length "0 .. 61";
      }
      description
        "will be updated";
    }
  }

  grouping sm-pdata {
    description
      "Protocol DATA";
    leaf-list data {
      type uint8;
      ordered-by user;
      description
        "proto_data";
    }
  }

  grouping sm-protocol-tlv {
    description
      "Protocol TLV";
    leaf type {
      type uint16;
      description
        "prototype";
    }
    leaf length {
      type uint16;
      description
        "Length";
    }
    container value {
      description
        "protoValue";
      uses wireless-client-oper:sm-pdata;
    }
  }

  grouping sm-protocol-data {
    description
      "Protocol Data";
    leaf proto-type {
      type wireless-client-oper:sm-protocol-type;
      description
        "Protocol Type";
    }
    list tlv {
      description
        "List of TLV";
      uses wireless-client-oper:sm-protocol-tlv;
    }
  }

  grouping sm-protocol-info {
    description
      "Protocol Info";
    list protocol-data {
      description
        "List of Protocol Data";
      uses wireless-client-oper:sm-protocol-data;
    }
  }

  grouping sm-aaa-server-details {
    description
      "AAA server details";
    leaf server-address {
      type inet:ip-address;
      description
        "Address of AAA Server";
    }
    leaf server-status {
      type wireless-client-oper:aaa-req-status;
      description
        "Status of AAA Server";
    }
    leaf server-authport {
      type uint16;
      description
        "Authport of AAA Server";
    }
    leaf server-acctport {
      type uint16;
      description
        "Acctport of AAA Server";
    }
  }

  grouping sm-context {
    description
      "Session manager context";
    leaf mac {
      type yang:mac-address;
      description
        "Mac address";
    }
    leaf ipv4 {
      type inet:ipv4-address;
      description
        "Ipv4 address of session";
    }
    leaf-list ipv6 {
      type inet:ipv6-address;
      max-elements "16";
      ordered-by user;
      description
        "IPv6 list of addresses";
    }
    leaf intf-iifid {
      type uint32;
      description
        "If id assoc with the session";
    }
    leaf method-id {
      type wireless-client-oper:sm-auth-method-id;
      description
        "Method that is running on the session";
    }
    leaf domain {
      type wireless-client-oper:sm-domain;
      description
        "Domain of the session";
    }
    leaf scope {
      type wireless-client-oper:sm-target-scope;
      description
        "Scope of th esession";
    }
    container audit-id {
      description
        "Audit session id of the session";
      uses wireless-client-oper:sm-audit-id;
    }
    container posture-token {
      description
        "posture token associated with session";
      uses wireless-client-oper:sm-posture-token;
    }
    leaf acct-sess-id {
      type uint32;
      description
        "Accounting session id of the session";
    }
    leaf aaa-sess-id {
      type uint32;
      description
        "AAA Session ID";
    }
    leaf sess-iifid {
      type uint32;
      description
        "If id assoc with the session";
    }
    leaf username {
      type string;
      description
        "User name of the session authc";
    }
    leaf vlan-id {
      type uint32;
      description
        "vlan to which client is assoc";
    }
    leaf linksec-secured {
      type boolean;
      description
        "Link is secured";
    }
    leaf state {
      type wireless-client-oper:sm-ctx-state;
      description
        "link state";
    }
    leaf port-type {
      type wireless-client-oper:sm-port-type;
      description
        "port type whether wired or wireless";
    }
    leaf authorized {
      type boolean;
      description
        "Client is authorized or not";
    }
    leaf user-role {
      type string;
      description
        "User role match criteria";
    }
    leaf device-type {
      type string;
      description
        "Device type match criteria";
    }
    leaf protocol-map {
      type uint32;
      description
        "Device classifier data";
    }
    container dc-data {
      description
        "will be updated";
      uses wireless-client-oper:sm-device-classifier-data;
    }
    container http-tlv {
      description
        "http tlv maintained";
      uses common-types-ios-xe:mcp-bytestr;
    }
    leaf host-mode {
      type wireless-client-oper:sm-host-mode;
      description
        "Host mode for the client";
    }
    leaf control-direction {
      type wireless-client-oper:sm-control-direction;
      description
        "Control direction whether it is in or out";
    }
    leaf reauth-timeout {
      type uint32;
      description
        "re-authentication timeout";
    }
    leaf reauth-timestamp {
      type uint64;
      description
        "re authentication time stamp";
    }
    leaf paused-reauth {
      type boolean;
      description
        "reauth paused";
    }
    leaf reauth-ip-change {
      type boolean;
      description
        "Reauth to be performed on ip change";
    }
    leaf reauth-act-terminate {
      type boolean;
      description
        "Termination action for the session as part of session timeout";
    }
    leaf reauth-using-current-method {
      type uint8;
      description
        "Use current method to perform reauth";
    }
    leaf reauth-remain-time {
      type uint32;
      description
        "Remaining time for reauth for the session";
    }
    leaf term-cause {
      type uint32;
      description
        "Session termination cause";
    }
    leaf aaa-timeout-seen {
      type boolean;
      description
        "AAA Timeout seen";
    }
    leaf authz-fail-count {
      type uint32;
      description
        "Number of times the session is getting authz fail";
    }
    leaf ssn-flags {
      type uint32;
      description
        "Flags related to wireless";
    }
    leaf intf-name {
      type string;
      description
        "interface name on which session has come up";
    }
    leaf policy-name {
      type string;
      description
        "policy name that is tied to the session";
    }
    leaf acct-update-timeout {
      type uint32;
      description
        "Accounting periodic update timeout value";
    }
    leaf acct-update-timestamp {
      type uint64;
      description
        "Accounting periodic update timer expiry time-stamp";
    }
    container aaa-server {
      description
        "Details of aaa server";
      uses wireless-client-oper:sm-aaa-server-details;
    }
    container sensor {
      description
        "Protocol information";
      uses wireless-client-oper:sm-protocol-info;
    }
  }

  grouping sm-web-auth-data {
    description
      "Webauth local data structure";
    leaf mac {
      type yang:mac-address;
      description
        "Mac address of client";
    }
    leaf init-state-timeout {
      type uint32;
      description
        "Timeout after which session will be marked unauthc";
    }
    leaf retry-count {
      type uint16;
      description
        "Number of times the session will perform retry for authc";
    }
    leaf no-data-count {
      type uint16;
      description
        "Number of data client";
    }
    leaf deny-of-service {
      type uint8;
      description
        "will be updated";
    }
    leaf state {
      type wireless-client-oper:sm-webauth-state;
      description
        "will be updated";
    }
    leaf acl-flags {
      type uint8;
      description
        "Flags related to acl";
    }
    leaf appl-id {
      type wireless-client-oper:sm-webauth-method;
      description
        "App tag given to lfts";
    }
    leaf client-ipv4-addr {
      type inet:ipv4-address;
      description
        "Client ip v4 address";
    }
    leaf-list ipv6 {
      type inet:ipv6-address;
      max-elements "16";
      ordered-by user;
      description
        "IPv6 list of addresses";
    }
    leaf intf-iifid {
      type uint32;
      description
        "interface ifid of the session";
    }
    leaf webauth-type {
      type uint8;
      description
        "Type of webauth consent, auth-proxy, etc";
    }
    leaf is-cwa-session {
      type boolean;
      description
        "Is webauth via mab";
    }
    leaf is-sleeping {
      type boolean;
      description
        "Sleeping client enabled for the client";
    }
    leaf is-service-denied {
      type boolean;
      description
        "Service Denied for the client";
    }
  }

  grouping sm-dot1x-global-stats {
    description
      "Global stats of dot1x";
    leaf eapol-rx {
      type uint32;
      description
        "eapol rx packet";
    }
    leaf eapol-rx-start {
      type uint32;
      description
        "eapol rx start ptr";
    }
    leaf eapol-rx-logoff {
      type uint32;
      description
        "eapol rx logoff";
    }
    leaf eapol-rx-resp {
      type uint32;
      description
        "eapol rx response";
    }
    leaf eapol-rx-resp-id {
      type uint32;
      description
        "repol rx response id";
    }
    leaf eapol-rx-req {
      type uint32;
      description
        "eapol rx request";
    }
    leaf eapol-rx-invalid {
      type uint32;
      description
        "eapol rx invalid";
    }
    leaf eapol-rx-len-error {
      type uint32;
      description
        "eapol rx length error";
    }
    leaf eapol-tx {
      type uint32;
      description
        "eapol tx";
    }
    leaf eapol-tx-start {
      type uint32;
      description
        "eapol tx start ptr";
    }
    leaf eapol-tx-logoff {
      type uint32;
      description
        "eapol tx logogg";
    }
    leaf eapol-tx-resp {
      type uint32;
      description
        "eapol tx resp";
    }
    leaf eapol-tx-req {
      type uint32;
      description
        "eapol tx req";
    }
    leaf eapol-retx-req {
      type uint32;
      description
        "eapol retx req";
    }
    leaf eapol-retx-req-fail {
      type uint32;
      description
        "eapol retx req fail";
    }
    leaf eapol-tx-req-id {
      type uint32;
      description
        "eapol rx req id";
    }
    leaf eapol-retx-req-id {
      type uint32;
      description
        "eapol retx req id";
    }
    leaf eapol-retx-req-id-fail {
      type uint32;
      description
        "eapol retx req id fail";
    }
  }

  grouping sm-webauth-sclient {
    description
      "Sleeping client entry for the client";
    leaf client-mac {
      type yang:mac-address;
      description
        "client mac address";
    }
    leaf user {
      type string;
      description
        "username of sleeping client";
    }
    leaf password {
      type string;
      description
        "password of sleeping client in md5";
    }
    leaf timeout {
      type uint32;
      description
        "will be updated";
    }
    leaf create-entry {
      type boolean;
      description
        "Is the client present as part of sleeping client";
    }
  }

  grouping sm-webauth-http-stats {
    description
      "smd webauth http punt packet stats";
    leaf http-request-count {
      type uint32;
      description
        "http punt packets cound";
    }
    leaf read-event-count {
      type uint32;
      description
        "read event count of webauth";
    }
    leaf read-complete-count {
      type uint32;
      description
        "read complete count of webauth";
    }
    leaf write-event-count {
      type uint32;
      description
        "write event count of webauth";
    }
    leaf write-complete-count {
      type uint32;
      description
        "write complete count of webauth";
    }
    leaf aaa-message-count {
      type uint32;
      description
        "AAA Message count";
    }
    leaf ssl-event-read-wouldblk-count {
      type uint32;
      description
        "ssl event read wouldblk count";
    }
    leaf ssl-event-write-wouldblk-count {
      type uint32;
      description
        "ssl event write wouldblk count";
    }
    leaf ssl-event-ok-count {
      type uint32;
      description
        "ssl event ok count";
    }
    leaf http-new-req-no-session-error {
      type uint32;
      description
        "http new req no session error";
    }
    leaf http-new-req-ctx-exists-error {
      type uint32;
      description
        "http new req ctx exists error";
    }
    leaf num-of-socket-opened {
      type uint32;
      description
        "num of socket opened";
    }
    leaf num-of-socket-closed {
      type uint32;
      description
        "num of socket closed";
    }
    leaf-list http-counters {
      type uint32;
      max-elements "32";
      ordered-by user;
      description
        "http counters";
    }
  }

  grouping sm-webauth-duration-stats {
    description
      "sm webauth duration stats";
    leaf total {
      type uint32;
      description
        "will be updated";
    }
    leaf max {
      type uint32;
      description
        "will be updated";
    }
    leaf min {
      type uint32;
      description
        "will be updated";
    }
    leaf samples {
      type uint32;
      description
        "will be updated";
    }
  }

  grouping sm-webauth-stats {
    description
      "sm webauth stats";
    container http-stats {
      description
        "http stats";
      uses wireless-client-oper:sm-webauth-http-stats;
    }
    container iom-reading {
      description
        "iom reading";
      uses wireless-client-oper:sm-webauth-duration-stats;
    }
    container method-reading {
      description
        "will be updated";
      uses wireless-client-oper:sm-webauth-duration-stats;
    }
    container iom-writing {
      description
        "will be updated";
      uses wireless-client-oper:sm-webauth-duration-stats;
    }
    container method-writing {
      description
        "will be updated";
      uses wireless-client-oper:sm-webauth-duration-stats;
    }
    container iom-aaa {
      description
        "will be updated";
      uses wireless-client-oper:sm-webauth-duration-stats;
    }
    container method-aaa {
      description
        "will be updated";
      uses wireless-client-oper:sm-webauth-duration-stats;
    }
    leaf num-of-sleeping-clients {
      type uint32;
      description
        "number of sleeping clients";
    }
    leaf session-count {
      type uint32;
      description
        "session count on the machine";
    }
    leaf half-open-count {
      type uint32;
      description
        "half open count";
    }
  }

  grouping sm-aaa-attr-meta {
    description
      "meta data";
    leaf tag {
      type uint16;
      description
        "will be updated";
    }
    leaf prefix-required {
      type uint8;
      description
        "will be updated";
    }
    leaf mandatory {
      type uint8;
      description
        "will be updated";
    }
  }

  grouping sm-aaa-attr-node {
    description
      "aaa attribute node";
    container aaa-attr-value {
      description
        "aaa attribute value";
      uses common-types-ios-xe:mcp-bytestr;
    }
    leaf attr-val-print {
      type string;
      description
        "attribute value print";
    }
    container aaa-attr-meta {
      description
        "aaa meta-data that will be carried with the attribute";
      uses wireless-client-oper:sm-aaa-attr-meta;
    }
  }

  grouping sm-aaa-attr-list {
    description
      "aaa attribute list";
    list attr-list {
      description
        "aaa group server attribute list";
      uses wireless-client-oper:sm-aaa-attr-node;
    }
  }

  grouping epm-svc-key {
    description
      "svc key pointing to service template";
    leaf svc-name {
      type string {
        length "0 .. 255";
      }
      description
        "EPM authz policy: service name";
    }
  }

  grouping epm-local-attr {
    description
      "EPM authz policy: local attr";
    container applied-attrs {
      description
        "EPM authz policy: local db attrs";
      uses wireless-client-oper:sm-aaa-attr-list;
    }
    container failed-attrs {
      description
        "EPM authz policy: local db failed attrs";
      uses wireless-client-oper:sm-aaa-attr-list;
    }
  }

  grouping epm-svc-node {
    description
      "EPM authz policy: service node";
    container svc-key {
      description
        "EPM authz policy: service key";
      uses wireless-client-oper:epm-svc-key;
    }
    leaf svc-status {
      type wireless-client-oper:epm-svc-status;
      description
        "EPM authz policy: service status";
    }
    leaf svc-source {
      type wireless-client-oper:epm-svc-source;
      description
        "EPM authz policy: source of service application";
    }
    leaf svc-precedence {
      type uint8;
      description
        "EPM authz policy: service precedence";
    }
    leaf svc-applied-time {
      type uint64;
      description
        "EPM authz policy: service applied time";
    }
    leaf svc-flags {
      type uint8;
      description
        "EPM authz policy: service flags";
    }
    leaf is-param-map {
      type boolean;
      description
        "Field conveying if its parameter map";
    }
    leaf svc-mlist {
      type string;
      description
        "EPM authz policy: service method-list";
    }
    container applied-attrs {
      description
        "EPM authz policy: Applied authz attributes";
      uses wireless-client-oper:sm-aaa-attr-list;
    }
    container failed-attrs {
      description
        "EPM authz policy: failed authz attributes";
      uses wireless-client-oper:sm-aaa-attr-list;
    }
  }

  grouping epm-svc-block {
    description
      "Table containing EPM authorization policy info";
    leaf mac {
      type yang:mac-address;
      description
        "mac address of the client";
    }
    container local-db-attr {
      description
        "Table containing info on service list";
      uses wireless-client-oper:epm-local-attr;
    }
    leaf tgt-scope {
      type wireless-client-oper:sm-target-scope;
      description
        "target scope of policy on the session";
    }
    leaf up-source {
      type wireless-client-oper:epm-svc-source;
      description
        "EPM authz policy: user-profile source";
    }
    leaf up-mlist {
      type string;
      description
        "EPM authz policy: user-profile method-list";
    }
    leaf svcb-flags {
      type uint32;
      description
        "EPM authz policy: service block flags";
    }
    leaf is-up-failed {
      type boolean;
      description
        "EPM authz policy: user-profile application failure";
    }
    leaf up-precedence {
      type uint8;
      description
        "EPM authz policies: up precedence";
    }
    leaf up-applied-time {
      type uint64;
      description
        "EPM authz policy: up applied time";
    }
    leaf sync-seq-no {
      type uint8;
      description
        "EPM authz policy: sequence number for HA sync";
    }
    leaf is-vlan-group-present {
      type boolean;
      description
        "EPM authz policy: is vlan-group present";
    }
    leaf res-vlan-id {
      type uint32;
      description
        "EPM authz policy: resultant vlan-id";
    }
    leaf anchor-vlan-id {
      type uint32;
      description
        "EPM authz policy: Anchor vlan-id";
    }
    leaf anchor-vlan-override {
      type boolean;
      description
        "EPM authz policy: Anchor vlan override";
    }
    list epm-svc-list {
      description
        "Table containing info on service list";
      uses wireless-client-oper:epm-svc-node;
    }
    container up-applied-attrs {
      description
        "EPM authz policy: user-profile applied attrs";
      uses wireless-client-oper:sm-aaa-attr-list;
    }
    container up-failed-attrs {
      description
        "EPM authz policy: user-profile failed attrs";
      uses wireless-client-oper:sm-aaa-attr-list;
    }
    container up-attrs {
      description
        "EPM authz policy: user-profile attrs";
      uses wireless-client-oper:sm-aaa-attr-list;
    }
  }

  grouping sm-device-count {
    description
      "Session Management's device cache (device count)";
    leaf device-type {
      type string;
      description
        "Session Management's device cache (device type)";
    }
    leaf device-count {
      type uint32;
      description
        "Session Management's device cache (device count)";
    }
  }

  grouping st-client-exclusion-data {
    description
      "Structure for storing client information of Excluded clients";
    leaf generation-id {
      type uint32;
      description
        "Generation ID for the excluded client";
    }
    leaf client-mac {
      type yang:mac-address;
      description
        "Client MAC address for the excluded client";
    }
    leaf exclusion-time {
      type int32;
      description
        "Time in seconds for which the client was excluded";
    }
    leaf exclusion-timeout-timestamp {
      type int64;
      description
        "Timestamp for exclusion timeout";
    }
    leaf exclude-reason {
      type wireless-client-oper:exclude-reason;
      description
        "The reason why the client was excluded";
    }
    leaf description {
      type string;
      description
        "Description entered while manually adding a client to exclusionlist in configuration";
    }
    leaf authentication-method {
      type wireless-client-oper:exclusion-client-auth-method-id;
      description
        "Authentication method used for the excluded client";
    }
    leaf client-state {
      type uint8;
      description
        "State of the excluded client";
    }
    leaf ms-radio-type {
      type wireless-client-types:ms-phy-radio-type;
      description
        "Radio type to which the excluded client was trying to connect";
    }
    leaf ms-username {
      type string;
      description
        "Username of the excluded client";
    }
    leaf ap-mac-addr {
      type yang:mac-address;
      description
        "AP MAC address to which the client was associating";
    }
    leaf ap-name {
      type string;
      description
        "AP name to which the client was associating";
    }
    leaf ap-slot-id {
      type uint8;
      description
        "AP slot ID to which the client was associating";
    }
    leaf wlan-id {
      type uint32;
      description
        "WLAN ID to which the client was trying to connect";
    }
    leaf wlan-ssid {
      type string;
      description
        "SSID of the WLAN to which the client was trying to connect";
    }
    leaf vlan-id {
      type uint32;
      description
        "VLAN ID of the client";
    }
    leaf ip-addr {
      type inet:ip-address;
      description
        "IP address of the client";
    }
    leaf client-type {
      type wireless-client-types:ms-client-type;
      description
        "Client Type to distinguish different types of client join";
    }
  }

  grouping pre-auth-radius-override {
    description
      "Pre-auth radius fields";
    leaf vlan-if-name {
      type string;
      description
        "VLAN interface name";
    }
    leaf framed-ip-address {
      type inet:ip-address;
      description
        "IP override";
    }
  }

  grouping local-switching-radius-override {
    description
      "Local switching VLAN override";
    leaf vlanid {
      type uint32;
      description
        "VLAN override";
    }
  }

  grouping pmkcache-entry {
    description
      "PMK cache entry information";
    leaf client-mac {
      type yang:mac-address;
      description
        "Station MAC";
    }
    leaf pmk-type {
      type wireless-client-oper:pmkcache-type;
      description
        "pmk type i.e RSN, CCKM, 802.11r";
    }
    leaf audit-session-id {
      type string;
      description
        "Audit session ID";
    }
    container radius-override {
      description
        "NOT_EXPOSED";
      uses wireless-client-oper:pre-auth-radius-override;
    }
    container local-swithching-override {
      description
        "NOT_EXPOSED";
      uses wireless-client-oper:local-switching-radius-override;
    }
    leaf wake-up-ticks {
      type uint64;
      description
        "Remianing timestamp";
    }
    leaf client-type {
      type wireless-client-oper:dot11-client-type;
      description
        "NOT_EXPOSED";
    }
  }

  container client-oper-data {
    config false;
    description
      "root container of wireless client oper parameters+B278";
    list common-oper-data {
      key "client-mac";
      description
        "List containing common operational data of the client";
      uses wireless-client-oper:ewlc-client-common-oper-data;
    }
    container latency-stats {
      presence "latency-stats";
      description
        "Container of latency stats of the client";
      uses wireless-client-oper:st-tbl-client-latency-stats;
    }
    container global-stats {
      presence "global-stats";
      description
        "Container of global stats of the client";
      uses wireless-client-oper:ewlc-client-global-stats-op;
    }
    container dot11-stats {
      presence "dot11-stats";
      description
        "Container of dot11 stats of the client";
      uses wireless-client-oper:st-client-dot11-stats;
    }
    container cac-stats {
      presence "cac-stats";
      description
        "Wireless Call admission control throttle stats table";
      uses wireless-client-oper:st-cac-stats;
    }
    list dot11-oper-data {
      key "ms-mac-address";
      description
        "List containing dot11 operational data of the client";
      uses wireless-client-oper:ewlc-client-dot11-oper-data;
    }
    list client-pmk-cache {
      key "client-mac";
      description
        "Table for client PMK cache";
      uses wireless-client-oper:pmkcache-entry;
    }
    list mobility-oper-data {
      key "ms-mac-addr";
      description
        "List containing the mobility operational data of the client";
      uses wireless-client-oper:ewlc-mafsm-oper-data;
    }
    list mmif-client-stats {
      key "client-mac";
      description
        "Client Mobility Interface Stats";
      uses wireless-client-oper:mmif-client-stats;
    }
    list mmif-client-history {
      key "client-mac";
      description
        "Table for recent client mobility history";
      uses wireless-client-oper:mmif-client-history;
    }
    list ccx-stats {
      key "ms-mac-address";
      description
        "Container of the ccx stats data of the client";
      uses wireless-client-oper:ewlc-client-ccx-oper-data;
    }
    list traffic-stats {
      key "ms-mac-address";
      description
        "List containing the client traffic stats info";
      uses wireless-client-oper:ewlc-client-stats-oper-data;
    }
    list sm-main-data {
      key "mac";
      description
        "Session Management list containing smd's session info";
      uses wireless-client-oper:sm-context;
    }
    list policy-data {
      key "mac";
      description
        "EPM list containing info about authorization policies";
      uses wireless-client-oper:epm-svc-block;
    }
    list exclusion-data {
      key "client-mac";
      description
        "Exclusion data list containing information about excluded clients";
      uses wireless-client-oper:st-client-exclusion-data;
    }
    container dot1x-global-stats {
      presence "dot1xGlobalStats";
      description
        "Container of IEEE 802.1x global stats";
      uses wireless-client-oper:sm-dot1x-global-stats;
    }
    container sm-web-auth-stats {
      presence "smWebAuthStats";
      description
        "Webauth stats";
      uses wireless-client-oper:sm-webauth-stats;
    }
    list identity-web-auth-data {
      key "mac";
      description
        "contains the session manager webauth data";
      uses wireless-client-oper:sm-web-auth-data;
    }
    list sm-web-auth-s-client {
      key "client-mac";
      description
        "Webauth sleeping client";
      uses wireless-client-oper:sm-webauth-sclient;
    }
    list device-stats {
      key "device-type";
      description
        "device stats";
      uses wireless-client-oper:sm-device-count;
    }
    list wgb-wired-client-data {
      key "wgb-mac wired-client-mac";
      description
        "WGB wired client association table";
      uses wireless-client-oper:ewlc-wgb-wired-key;
    }
  }
}
