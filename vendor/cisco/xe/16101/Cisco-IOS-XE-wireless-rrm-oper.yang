module Cisco-IOS-XE-wireless-rrm-oper {
  yang-version 1;
  namespace "http://cisco.com/ns/yang/Cisco-IOS-XE-wireless-rrm-oper";
  prefix wireless-rrm-oper;

  import Cisco-IOS-XE-wireless-enum-types {
    prefix wireless-enum-types;
  }
  import Cisco-IOS-XE-wireless-rrm-types {
    prefix wireless-rrm-types;
  }
  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless rrm operational data.
     Copyright (c) 2016-2018 by Cisco Systems, Inc.
     All rights reserved.";

  revision 2018-05-01 {
    description
      "- Add sensor-covered to st-rad-neighbor-attr
       - Add st-rrm-load-attr
       - Add st-rrm-measurement-data
       - Add leafs rrf-is-contributing, rrf-sensor-metric, sensor-coverage-factor to st-rrm-radio-data
       - Add leaf member-secondary-ip to st-rrm-mgr-grp-member
       - Add leaf member-secondary-ip to st-mapping-rrm-grp-member
       - Add leafs my-group-secondary-ip, cntrlr-secondary-ip-addr, fra-sensor-coverage to st-rrm-group-ctrl
       - Add leaf mgmt-secondary-ip to st-rrm-mgr-main
       - Add list radio-measurement to rrm-oper-data";
    reference "3.1.0";
  }
  revision 2018-03-22 {
    description
      "List key changes";
    reference "3.0.0";
  }
  revision 2018-01-24 {
    description
      "The first generally available version";
    reference "2.0.0";
  }
  revision 2017-05-05 {
    description
      "Initial revision";
    reference "1.0.0";
  }

  typedef enm-rrm-chan-width80211 {
    type enumeration {
      enum "rrm-chanwidth-80211-5" {
        value 1;
        description
          "Represents channel width as 5Mhz";
      }
      enum "rrm-chanwidth-80211-10" {
        value 2;
        description
          "Represents channel width as 10Mhz";
      }
      enum "rrm-chanwidth-80211-20" {
        value 3;
        description
          "Represents channel width as 20Mhz";
      }
      enum "rrm-chanwidth-80211-40-above" {
        value 4;
        description
          "Represents channel width as 40Mhz";
      }
      enum "rrm-chanwidth-80211-40-below" {
        value 5;
        description
          "Represents channel width as 80Mhz 
           where secondary channel is 40Mhz lesser than 
           primary channel";
      }
      enum "rrm-chanwidth-80211-80-ext-above-s40-above" {
        value 6;
        description
          "Represents channel width as 80Mhz where secondary channel is 40Mhz more than primary channel";
      }
      enum "rrm-chanwidth-80211-80-ext-below-s40-above" {
        value 7;
        description
          "Represents channel width as 80Mhz where extension channel is 40Mhz lesser than primary channel";
      }
      enum "rrm-chanwidth-80211-80-ext-above-s40-below" {
        value 8;
        description
          "Represents channel width as 80Mhz where extension channel is 40Mhz more than primary channel";
      }
      enum "rrm-chanwidth-80211-80-ext-below-s40-below" {
        value 9;
        description
          "Represents channel width as 80Mhz where secondary channel is 20Mhz lesser and extension channel is 40Mhz lesser than primary channel";
      }
      enum "rrm-chanwidth-80211-max" {
        value 10;
        description
          "Represents channel width as 80Mhz with continuous channels";
      }
    }
    description
      "Represents all supported channel widths";
  }

  typedef enm-ant-pattern {
    type enumeration {
      enum "rrm-antenna-invalid" {
        value 0;
        description
          "Represents invalid antenna type";
      }
      enum "rrm-antenna-omni" {
        value 1;
        description
          "Represents omni antenna type";
      }
      enum "rrm-antenna-hemisperical" {
        value 2;
        description
          "Represents hemi sperical antenna type";
      }
      enum "rrm-antenna-max" {
        value 3;
        description
          "Represents invalid antenna";
      }
    }
    description
      "Represents various types of antenna";
  }

  typedef enm-cleanair-oper-state {
    type enumeration {
      enum "rrm-spectrum-down" {
        value 0;
        description
          "This value indicates clean air is not running";
      }
      enum "rrm-spectrum-up" {
        value 1;
        description
          "This value indicates clean air is running";
      }
    }
    description
      "Represents various values for cleanair operational state";
  }

  typedef enm-cleanair-sensord-error-code {
    type enumeration {
      enum "cleanair-sensord-no-error" {
        value 1;
        description
          "Indicates that cleanair sensor on AP is working fine";
      }
      enum "cleanair-sensord-bad-siconfig-error" {
        value 2;
        description
          "Indicates the cleanair sensor configuration error";
      }
      enum "cleanair-sensord-noncleairmode-error" {
        value 3;
        description
          "Represents that Access point is not in cleanair mode";
      }
      enum "cleanair-sensord-nochanconfig-error" {
        value 4;
        description
          "This will be added later by spectrum team";
      }
      enum "cleanair-sensord-resource-error" {
        value 5;
        description
          "Internal Error for cleanair Access Point sensor resource";
      }
      enum "cleanair-sensord-comm-error" {
        value 6;
        description
          "Indicates the AP and sensor communication error";
      }
      enum "cleanair-sensord-nosihw-error" {
        value 7;
        description
          "Represents Radio is not cleanair capable";
      }
      enum "cleanair-sensord-sistream-error" {
        value 8;
        description
          "Represents Internal cleanair data stream error";
      }
      enum "cleanair-sensord-radio-disabled-error" {
        value 9;
        description
          "Indicates that the radio has been disabled";
      }
      enum "cleanair-sensord-recoverable-error" {
        value 129;
        description
          "Indicates the sensor error and if it is recoverable";
      }
      enum "cleanair-sensord-unrecoverable-error" {
        value 130;
        description
          "Indicates a cleanair sensor crash";
      }
    }
    description
      "This will be added later by spectrum team";
  }

  typedef enm-is-static-member {
    type enumeration {
      enum "rrm-auto-member-config" {
        value 0;
        description
          "This value indicates that group member was selected through auto selection mechanism";
      }
      enum "rrm-static-member-config" {
        value 1;
        description
          "This value indicates that, group member was selected through static configuration";
      }
    }
    description
      "This value indicates if currently operating as static member";
  }

  typedef enm-rrm-grouping-role-db {
    type enumeration {
      enum "rrm-group-off" {
        value 0;
        description
          "RRM RF Grouping is off";
      }
      enum "rrm-group-static-leader" {
        value 1;
        description
          "static-leader - leader of static RRM RF Group";
      }
      enum "rrm-group-static-member" {
        value 2;
        description
          "static-member - member in static RRM RF Group.";
      }
      enum "rrm-group-auto-leader" {
        value 3;
        description
          "auto-leader  - leader of automatic RRM RF Group";
      }
      enum "rrm-group-auto-member" {
        value 4;
        description
          "auto-member - member in automatic RRM RF Group";
      }
    }
    description
      "This object indicates the group role with respect to RRM
       RF grouping. The controller can be either group member or
       group leader while being in automatic or static grouping,
       for a particular band.  If grouping is off , the value
       of the group role would be 'none'.";
  }

  typedef enm-rrm-group-state {
    type enumeration {
      enum "rrm-undefined" {
        value 0;
        description
          "Undefined - RRM manager currently is in undefined state";
      }
      enum "rrm-reset" {
        value 1;
        description
          "Reset - RRM manager currently is in reset state";
      }
      enum "rrm-ha-standby" {
        value 2;
        description
          "HA Stand by - RRM manager currently is in High Availability Stand by state";
      }
      enum "rrm-leader-idle" {
        value 3;
        description
          "Idle - RRM manager currently is in idle state";
      }
      enum "rrm-leader-prep" {
        value 4;
        description
          "Preparation - RRM manager currently is in preparation state";
      }
      enum "rrm-leader-comp" {
        value 5;
        description
          "Computation - RRM manager currently is in computation state";
      }
      enum "rrm-join-wait" {
        value 6;
        description
          "Join Wait - RRM manager currently is waiting for leader to join the group";
      }
      enum "rrm-groupie" {
        value 7;
        description
          "Groupie - RRM manager currently is in group member state";
      }
      enum "rrm-leader-assign" {
        value 8;
        description
          "Assign - RRM manager is currently in assigning state";
      }
      enum "rrm-max-group-state" {
        value 9;
        description
          "Maximum value - RRM manager currently is in invalid state";
      }
    }
    description
      "Represents the current rrm rf -grouping state";
  }

  typedef enm-rrm-group-state-actions {
    type enumeration {
      enum "rrm-no-action" {
        value 0;
        description
          "No action - Not a valid action";
      }
      enum "rrm-start" {
        value 1;
        description
          "Start - RRM RF-Grouping start";
      }
      enum "rrm-hello-timer" {
        value 2;
        description
          "Idle timer - Idle timer expiry action";
      }
      enum "rrm-calc-timer" {
        value 3;
        description
          "Calc timer - Calc timer expiry action";
      }
      enum "rrm-switch-polling-timer" {
        value 4;
        description
          "Switch polling timer - Switch polling timer expiry action";
      }
      enum "rrm-transmission-timer" {
        value 5;
        description
          "Transmission timer - Transmission timer expiry action";
      }
      enum "rrm-prep-timer" {
        value 6;
        description
          "Prep timer - Preparation timer expiry action";
      }
      enum "rrm-echo-timer" {
        value 7;
        description
          "Echo timer - Echo timer expiry action";
      }
      enum "rrm-remove-aged-member" {
        value 8;
        description
          "Represents Remove aged member (Members who did not respond to echo) timer expiry action";
      }
      enum "rrm-join-req" {
        value 9;
        description
          "Join req - Join request action";
      }
      enum "rrm-split-req" {
        value 10;
        description
          "Split request - Split request action";
      }
      enum "rrm-join-nack" {
        value 11;
        description
          "Join nack - Nack to join request action";
      }
      enum "rrm-client-data" {
        value 12;
        description
          "Client Data - Data from client or group member action";
      }
      enum "rrm-client-set" {
        value 13;
        description
          "Client set - Set packet from rrm client action";
      }
      enum "rrm-client-query" {
        value 14;
        description
          "Client Query - Query request from rrm rf-group leader";
      }
      enum "rrm-client-ack" {
        value 15;
        description
          "Client ack - Acknowledgement for client set action";
      }
      enum "rrm-hello-pkt" {
        value 16;
        description
          "Hello packet - Hello packet recieved from rrm rf-group leader";
      }
      enum "rrm-echo-pkt" {
        value 17;
        description
          "Echo packet - Echo packet received from rrm rf-group member";
      }
      enum "rrm-rrm-kill" {
        value 18;
        description
          "RRM Kill - RRM RF-Group kill action";
      }
      enum "rrm-calc-end" {
        value 19;
        description
          "Calc end - Calculation ended action";
      }
      enum "rrm-join-cmd" {
        value 20;
        description
          "Join cmd - Join cmd received from static leader";
      }
      enum "rrm-join-cmd-nack" {
        value 21;
        description
          "Join cmd nack - Nack received for the join command sent";
      }
      enum "rrm-join-cmd-timer" {
        value 22;
        description
          "Join cmd timer - Join command timer expiry action";
      }
      enum "rrm-mc-sync-timer" {
        value 23;
        description
          "MC Sync timer - MC sync timer expiry action. (Obsolete in ewlc devices)";
      }
      enum "rrm-mc-sync-throttle-timer" {
        value 24;
        description
          "MC Sync throttle timer - MC sync timer expiry action. (Obsolete in ewlc devices)";
      }
      enum "rrm-probe-pkt" {
        value 25;
        description
          "Probe pkt - Received probe packet from switch.(Obsolete in ewlc devices)";
      }
      enum "rrm-pre-alarm-pkt" {
        value 26;
        description
          "Pre alarm pkt - Received pre alarm packet indicating a wireless client is in coverage hole";
      }
      enum "rrm-pre-alarm-resp-pkt" {
        value 27;
        description
          "Pre alarm resp - Received pre alarm response from the controller";
      }
      enum "rrm-chdm-counter-reset-pkt" {
        value 28;
        description
          "Coverage Hole Detection counter reset packet received";
      }
      enum "rrm-config-pkt" {
        value 29;
        description
          "Config pkt - Received config packet from rrm rf-group leader";
      }
      enum "rrm-spectrum-fwd-pkt" {
        value 30;
        description
          "Spectrum forward packet received from the leader";
      }
      enum "rrm-ha-state-change" {
        value 31;
        description
          "High Availability State change - Notification that High Availability role has changed usually from standby to active";
      }
      enum "rrm-rrm-ha-group-update" {
        value 32;
        description
          "High Availability group update - Action to update group state after High Availability event change";
      }
      enum "rrm-rrm-max-action" {
        value 33;
        description
          "Maximum Action - Invalid rrm action.";
      }
    }
    description
      "This object type represents various action in rrm rf-grouping";
  }

  typedef enm-rrm-grouping-mode {
    type enumeration {
      enum "rrm-group-mode-auto" {
        value 0;
        description
          "Indicates rrm grouping mode is Auto";
      }
      enum "rrm-group-mode-static-member" {
        value 1;
        description
          "Indicates controller is currently a static member";
      }
      enum "rrm-group-mode-static-leader" {
        value 2;
        description
          "Indicates controller is currently a static leader";
      }
    }
    description
      "Represents rrm grouping mode";
  }

  grouping st-rad-neighbor-attr {
    description
      "This object represents the neighbor radio's related attributes";
    leaf prune-count {
      type int32;
      description
        "Represents prune count. When this values reaches zero neighbor radio will be removed from the neighbor list";
    }
    container id {
      description
        "Represents neighbor radio's identification. This is a combination of radio mac address and slot id";
      uses wireless-types:radio-slot-key;
    }
    container group-id {
      description
        "Represents neighbor radio's rf-goup id";
      uses wireless-rrm-types:st-group-id;
    }
    leaf ip {
      type inet:ip-address;
      description
        "Represents neighbor radio's ip address";
    }
    leaf rssi {
      type int8;
      description
        "Represents Received Signal Strength value of neighbor radio";
    }
    leaf snr {
      type int8;
      description
        "Represents Signal to Noise Ratio value of neighbor radio";
    }
    leaf channel {
      type uint8;
      description
        "Represents channel on which the neighbor radio is serving the client";
    }
    leaf power {
      type uint8;
      description
        "Represents neighbor radio's power";
    }
    leaf antenna {
      type wireless-rrm-oper:enm-ant-pattern;
      description
        "Represents antenna type of the neighbor radio";
    }
    leaf phy-type {
      type uint8;
      description
        "Represents phy type(802.11bg/802.11ac) of the neighbor radio";
    }
    leaf chan-width {
      type uint8;
      description
        "Represents current channel width of the neighbor radio";
    }
    leaf ap-tx-pwr {
      type uint8;
      description
        "Represents transmission power of the AP";
    }
    leaf client-tx-pwr {
      type uint8;
      description
        "Represents client transmission power of the radio";
    }
    leaf old {
      type boolean;
      description
        "Flag used to update neighbor list";
    }
    leaf packet-cnt {
      type uint32;
      description
        "Number of measurements from this RADIO";
    }
    leaf on-this-member {
      type boolean;
      description
        "Represents whether the neighbor is on this member";
    }
    leaf-list bssid {
      type uint8;
      max-elements "6";
      ordered-by user;
      description
        "Represents BSSID of the neighbor";
    }
    leaf auth-key {
      type string {
        length "0 .. 16";
      }
      description
        "The key to generate for authentication of this AP";
    }
    leaf roam-counts {
      type int32;
      description
        "Number of client roams to this neighbor";
    }
    leaf sensor-covered {
      type boolean;
      description
        "Represents neighbor covered by sensor";
    }
  }

  grouping st-rad-neighbor-list-data {
    description
      "Represents the list of neighbors for the given radio";
    container neighbor-attr {
      description
        "Attributes related to each neighbor radio";
      uses wireless-rrm-oper:st-rad-neighbor-attr;
    }
  }

  grouping st-rad-mon-neighbor-list-data {
    description
      "List used to represent list of neighbors currently in monitor mode";
    container mon-neighbor {
      description
        "Monitor neighbor radio's information";
      uses wireless-rrm-oper:st-rad-neighbor-attr;
    }
  }

  grouping st-rad-neighbor-list {
    description
      "Represents list of neighbor radios and their corresponding attributes";
    list neighbor-attr-ptr {
      description
        "Pointer to the list of neighbors";
      uses wireless-rrm-oper:st-rad-neighbor-list-data;
    }
  }

  grouping st-rad-mon-neighbor-list {
    description
      "This list represents list of monitor mode neighbor radios and there correponding attributes";
    list mon-neighbors-attr-ptr {
      description
        "Pointer to the list of neighbors";
      uses wireless-rrm-oper:st-rad-mon-neighbor-list-data;
    }
  }

  grouping st-rad-neighbor-data {
    description
      "Represents neighbor information for a paticular radio. This object includes both monitor and client serving radio information";
    container neighbor-attr {
      description
        "List of client serving neighbor radios";
      uses wireless-rrm-oper:st-rad-neighbor-list;
    }
    container mon-neighbor-attr {
      description
        "List of monitor mode neighbor radios";
      uses wireless-rrm-oper:st-rad-mon-neighbor-list;
    }
    leaf total-roams {
      type uint16;
      description
        "Total number client roames to this radio";
    }
    leaf max-roams {
      type uint16;
      description
        "Maximum number of client roams to this radio";
    }
  }

  grouping st-rrm-radio-radar-info {
    description
      "Represents radar information for a given radio and a given channel";
    leaf last-radar-detect-time {
      type uint32;
      description
        "Represents the time when radar was last detected on this radio";
    }
    leaf last-radar-detect-up-time {
      type uint32;
      description
        "Represents the time when radar was last detected with respect to AP up time";
    }
    leaf channel-number {
      type uint32;
      description
        "Represents Channel number on which radar was detected";
    }
    leaf first-radar-detect-time {
      type uint32;
      description
        "First time when radar was detected on this radio";
    }
    leaf radar-detected-here {
      type boolean;
      description
        "Boolean value to represent if radar was detected on this channel number";
    }
    leaf alarm-triggered {
      type boolean;
      description
        "Boolean value to indicate if alarm was triggered after radar detection";
    }
    leaf radar-blacklist-time {
      type uint32;
      description
        "Remaining time after which the radar detected channel will be considered for assignment by DCA ";
    }
    leaf radar-remaining-blacklist-time {
      type uint32;
      description
        "This field is used to calculate the remaining blacklist time";
    }
  }

  grouping st-rrm-radio-radar-attr {
    description
      "Represents radar information for a given radio";
    container chan-list {
      description
        "List of valid channels for the given radio";
      uses wireless-rrm-types:st-rrm-channel-list;
    }
    list radar-info {
      max-elements "64";
      description
        "Represents list of radar information for all the channels";
      uses wireless-rrm-oper:st-rrm-radio-radar-info;
    }
    leaf customized-chan {
      type uint8;
      description
        "Represents if the channel was dynamically assigned or the channel was customized manually";
    }
    leaf customized-chan-width-label {
      type wireless-rrm-oper:enm-rrm-chan-width80211;
      description
        "Represents if the channel width was dynamically assigned or the channel width was customized manually";
    }
    leaf sync-channel {
      type uint8;
      description
        "Represents if the channels need to synced";
    }
    leaf disable-time {
      type uint32;
      description
        "If the radio was disabled after radar detection this value represents for how long the radio was disabbled";
    }
    leaf disable-chan {
      type uint8;
      description
        "Represents the channel of radio before disabling";
    }
    leaf prev-chan-tx-power-dbm {
      type int8;
      description
        "Represents the power of radio before disabling";
    }
    leaf channel-changes {
      type uint32;
      description
        "Number of times channel was changed due to radar";
    }
  }

  grouping st-rrm-load-attr {
    description
      "Load information related to a radio";
    leaf traffic {
      type uint32;
      description
        "AP Radio Tx+Rx Traffic (utilization) percentage";
    }
    leaf interference {
      type uint32;
      description
        "AP Radio Interference (utilization) percentage";
    }
    leaf channel-utilization {
      type uint32;
      description
        "AP Radio Total Traffic + Interference (utilization) percentage";
    }
  }

  grouping st-rrm-measurement-data {
    description
      "Measurement information related to a radio";
    container load {
      description
        "Load information related to a radio";
      uses wireless-rrm-oper:st-rrm-load-attr;
    }
  }

  grouping st-rrm-radio-cb {
    description
      "Represents all information related to a radio that the rrm client is handling";
    leaf power-mode-counter {
      type int32;
      description
        "Power mode counter used during rrm run once mode. It indicates the number of AP's on which power assignment is remaining";
    }
    leaf mac-mode-counter {
      type int32;
      description
        "Mac mode counter used during rrm run once mode";
    }
    leaf channel-mode-counter {
      type int32;
      description
        "Channel mode counter used during run once mode. It indicates the number of AP's on which channel assignment is remaining";
    }
    leaf antenna-mode-counter {
      type int32;
      description
        "Antenna mode counter used during rrm run once mode";
    }
    leaf non-adjusted-pwr-dbm {
      type int8;
      description
        "Current power level in dbm";
    }
    leaf non-adjusted-pwr-lvl {
      type uint32;
      description
        "Current power level of the radio";
    }
    leaf coverage-power-adjustment {
      type int8;
      description
        "Some state for coveage hole detection";
    }
    leaf last-pwr-turn-up {
      type uint32;
      description
        "When did we last turn up power";
    }
    leaf last-rcvd-coverage-data {
      type uint32;
      description
        "When did we receive last coverage data";
    }
    leaf init-neighbor-msg-flag {
      type boolean;
      description
        "Flag to indicate if we are in initial off channel scanning";
    }
    leaf last-down {
      type uint32;
      description
        "When did we last do radio down";
    }
    container dca {
      description
        "Channel set packet retry mechanism";
      uses wireless-rrm-types:st-rrm-msg-seq;
    }
    container tpc {
      description
        "Power set packet retry mechanism";
      uses wireless-rrm-types:st-rrm-msg-seq;
    }
  }

  grouping st-rrm-active-noise {
    description
      "This abject represents active noise on the radio";
    leaf active-noise {
      type int8;
      description
        "To record the average noise on active channel";
    }
    leaf timestamp {
      type uint32;
      description
        "To represent when was the last one noise recorded";
    }
  }

  grouping st-rrm-active-noise-all {
    description
      "To record the average noise on all the channels";
    list a-noise {
      max-elements "64";
      description
        "Array of noise information on active channel";
      uses wireless-rrm-oper:st-rrm-active-noise;
    }
    leaf-list timestamp {
      type uint32;
      max-elements "64";
      ordered-by user;
      description
        "To represent when was the last noise recorded on the given channel";
    }
    leaf active-noise-chan-count {
      type int32;
      description
        "How many are valid measurments";
    }
  }

  grouping st-rrm-radio-dca-stats {
    description
      "Represents few DCA related statastics";
    leaf best-chan {
      type uint8;
      description
        "What would be best channel";
    }
    leaf current-chan-energy {
      type int8;
      description
        "Current dca energy level";
    }
    leaf last-chan-energy {
      type int8;
      description
        "Last dca channel energy level";
    }
    leaf chan-changes {
      type uint32;
      description
        "Number of channel changes for the given radio";
    }
    leaf last-changed {
      type uint64;
      description
        "Represents when was the last channel changed";
    }
  }

  grouping st-rrm-radio-data {
    description
      "This object represents parameters which would be modified when RRM is active";
    leaf best-tx-pwr-level {
      type uint16;
      description
        "Represents optimal transition power level";
    }
    leaf best-rts-thresh {
      type uint16;
      description
        "Represents optimal Request to Send threshold";
    }
    leaf best-frag-thresh {
      type uint16;
      description
        "Represents recommended MSDU(MAC Service Data Unit) fragmentation threshold by RRM for APIF (AP interface)";
    }
    leaf best-ed-thresh {
      type uint32;
      description
        "Represents optimal ED threshold";
    }
    leaf best-antenna-pattrn {
      type uint8;
      description
        "Optimal antenna pattern";
    }
    leaf chd-events {
      type uint32;
      description
        "Represents coverage hole detection events";
    }
    leaf load-prof-passed {
      type boolean;
      description
        "Boolean value to represent if load profile passed";
    }
    leaf coverage-profile-passed {
      type boolean;
      description
        "Boolean value to represent if coverage profile passed";
    }
    leaf interference-profile-passed {
      type boolean;
      description
        "Boolean value to represent if interference profile passed";
    }
    leaf noise-profile-passed {
      type boolean;
      description
        "Boolean value to represent if noise profile passed";
    }
    container a-noise-data {
      description
        "Noise data for all the channels for a given radio";
      uses wireless-rrm-oper:st-rrm-active-noise-all;
    }
    container dca-stats {
      description
        "Represents stats related to DCA algorithm";
      uses wireless-rrm-oper:st-rrm-radio-dca-stats;
    }
    leaf rrf-is-redundant {
      type uint8;
      description
        "Boolean value to represent if the given radio is redundant";
    }
    leaf rrf-is-contributing {
      type uint8;
      description
        "Boolean value to represent if the given radio is contributing";
    }
    leaf rrf-metric {
      type uint8;
      description
        "Represents the overlap factor for the given radio";
    }
    leaf rrf-sensor-metric {
      type uint8;
      description
        "Represents the sensor overlap factor for the given radio";
    }
    leaf rrf-silent {
      type uint8;
      description
        "Represents if the rrf is silent for the given radio";
    }
    leaf rrf-suggested-mode {
      type string;
      description
        "String representation of redundancy for the given radio";
    }
    leaf coverage-overlap-factor {
      type string;
      description
        "String representation for the coverage overlap factor";
    }
    leaf sensor-coverage-factor {
      type string;
      description
        "String representation for the sensor coverage factor";
    }
  }

  grouping st-rrm-rad-slot-data {
    description
      "Represents radio slot data";
    container radio-cb {
      description
        "Represents all information related to a radio that the rrm client is handling";
      uses wireless-rrm-oper:st-rrm-radio-cb;
    }
    container radio-data {
      description
        "Represents radio related data such as dca stats and radio redundency information";
      uses wireless-rrm-oper:st-rrm-radio-data;
    }
  }

  grouping st-rrm-client-data {
    description
      "Represents rrm client related data";
    leaf phy-type {
      type wireless-rrm-types:enm-rrm-phy-type;
      description
        "Represents the phy type which is also the key to this table";
    }
    leaf last-chd-run {
      type yang:timeticks;
      description
        "Timestamp indicating when the coverage hole detection algorithm was last run";
    }
    leaf disassociations {
      type uint32;
      description
        "Represents number of client disassociations due to smart roaming";
    }
    leaf rejections {
      type uint32;
      description
        "Represents number of client rejections due to smart roaming";
    }
    container group-id {
      description
        "Represents rrm group identification";
      uses wireless-rrm-types:st-group-id;
    }
    leaf ip {
      type inet:ip-address;
      description
        "IP address of the controller";
    }
  }

  grouping st-spectrum-config {
    description
      "Represents clean air configuration";
    leaf spectrum-intelligence-enable {
      type boolean;
      description
        "Represents if cleanair is enabled";
    }
    leaf spectrum-wtp-ca-si-capable {
      type wireless-rrm-types:enm-ca-si-capable;
      description
        "Represents the Access point if CA/SI";
    }
    leaf spectrum-operation-state {
      type wireless-rrm-oper:enm-cleanair-oper-state;
      description
        "Represents the current cleanair operation state";
    }
    leaf spectrum-admin-state {
      type boolean;
      description
        "Represents the current cleanair ap admin state";
    }
    leaf spectrum-capable {
      type boolean;
      description
        "Represents if the Access point is cleanair capable";
    }
    leaf rapid-update-enable {
      type boolean;
      description
        "Indicates if cleanair rapid mode has been enabled";
    }
    leaf rapid-update-period {
      type uint8;
      description
        "Indicates the cleanair rapid mode period or duration";
    }
    leaf sensord-operational-status {
      type int32;
      description
        "Represents the current state of the cleanair sensor on the access point";
    }
    leaf sensord-error-code {
      type wireless-rrm-oper:enm-cleanair-sensord-error-code;
      description
        "Represents the sensored error codes";
    }
    leaf sensord-crash-trap-raised {
      type uint8;
      description
        "Represents if we have raised a trap for the cleanair sensor failure";
    }
    leaf-list spectrum-nsi-key {
      type uint8;
      max-elements "16";
      ordered-by user;
      description
        "This is a random key assigned for spectrum message handshake";
    }
    leaf num-rad-slots {
      type uint8;
      description
        "Represents the number of radio slots supported by given AP";
    }
  }

  grouping st-rrm-aq-event {
    description
      "Represents event driven RRM Air quality";
    leaf timestamp {
      type uint32;
      description
        "Represents when did we receive the latest report";
    }
    leaf chan {
      type uint8;
      description
        "Represents the Active channel for the given report";
    }
    leaf metric {
      type uint8;
      description
        "Represents the derived metric for given air quality report";
    }
  }

  grouping st-spectrum-edrrm {
    description
      "This object represents spectrum event driven RRM";
    leaf aq-chan-count {
      type int32;
      description
        "Represents number of channels for which air quality report has been received";
    }
    list aq {
      max-elements "64";
      description
        "Represents air quality value when event driven RRM is active";
      uses wireless-rrm-oper:st-rrm-aq-event;
    }
  }

  grouping st-rrm-spectrum {
    description
      "Represents RRM spectrum";
    container config {
      description
        "Represents spectrum access point configuration";
      uses wireless-rrm-oper:st-spectrum-config;
    }
    container edrrm-info {
      description
        "Represents information related to event driven RRM";
      uses wireless-rrm-oper:st-spectrum-edrrm;
    }
  }

  grouping st-per-radio-spectrum-idr-data {
    description
      "Represents per radio spectrum interferer device id";
    leaf ap-timestamp {
      type yang:timeticks;
      description
        "Represents the timestamp of last received report";
    }
    leaf hw-slot-id {
      type uint8;
      description
        "Represents the slot identifier for the received repor";
    }
    leaf severity-index {
      type uint8;
      description
        "Represents the severity index as classified for an interferer";
    }
    leaf detecting-ap-mac {
      type yang:mac-address;
      description
        "Represents the Mac address of AP which has detected the interferer";
    }
    leaf detecting-ap-name {
      type string;
      description
        "Represents the name of AP which has detected the interferer";
    }
    leaf device-duty-cycle {
      type uint8;
      description
        "Represents the duty cycle of the interferer";
    }
    leaf rssi {
      type int8;
      description
        "Represents the received signal strength";
    }
    leaf radio-band-id {
      type uint8;
      description
        "Represents the Band ID for the given report";
    }
    leaf affected-channel-bitmap {
      type uint32;
      description
        "This represents BITMAP for the interferer detected on the channels";
    }
    leaf device-signature-len {
      type uint8;
      description
        "Represents that every device is associated with a dynamic signature, this represents the length of the signature";
    }
    leaf-list device-signature {
      type uint8;
      max-elements "48";
      ordered-by user;
      description
        "Represents that every device is associated with a dynamic signature";
    }
    leaf wtp-ca-si-capable {
      type wireless-rrm-types:enm-ca-si-capable;
      description
        "Displays if the Access point is Clean Air or SI Capable";
    }
  }

  grouping st-spectrum-device-record {
    description
      "Represents spectrum device data";
    leaf device-id {
      type yang:mac-address;
      description
        "Represents spectrum interferer device identifier";
    }
    leaf cluster-id {
      type yang:mac-address;
      description
        "Represents Cluster Identifier for the interferer";
    }
    leaf old-clst-id {
      type yang:mac-address;
      description
        "If cluster is updated, represents the old Cluster Identifier for the interferer";
    }
    leaf last-updated-time {
      type yang:timeticks;
      description
        "Latest timestamp for the report";
    }
    container idr-data {
      description
        "Represents interferer device data";
      uses wireless-rrm-oper:st-per-radio-spectrum-idr-data;
    }
    leaf alarm {
      type boolean;
      description
        "Indicates whether the traps are enabled";
    }
    leaf is-virtual {
      type boolean;
      description
        "Represents whether the current interferer is marked as virtual";
    }
  }

  grouping st-worst-intf-category-report {
    description
      "Represents air quality related interference category report";
    leaf intf-severity-index {
      type uint8;
      description
        "Represents the severity of the interferer";
    }
    leaf intf-power {
      type int8;
      description
        "Represents the interferer signal strength";
    }
    leaf duty-cycle {
      type uint8;
      description
        "Represents the duty cycles of the interferer";
    }
  }

  grouping st-per-channel-spectrum-aq-data {
    description
      "Represents per channel air quality related interference category report";
    leaf channel-num {
      type uint8;
      description
        "Represents the channel number for the report";
    }
    leaf hw-slot-id {
      type uint8;
      description
        "Represents the slot identifier for the received repor";
    }
    leaf min-aqi {
      type uint8;
      description
        "Represents the minimum air quality index as seen on the radio channel by given Access point";
    }
    leaf aqi {
      type uint8;
      description
        "Represents the latest air quality index as seen on the radio channel by given Access point";
    }
    leaf total-channel-power {
      type int8;
      description
        "Represents total channel power reported by Access point";
    }
    leaf total-channel-duty-cycle {
      type uint8;
      description
        "Represents total duty cycle reported by Access point";
    }
    leaf interference-power {
      type int8;
      description
        "Represents total interference power reported by Access point";
    }
    leaf interference-duty-cycle {
      type uint8;
      description
        "Represents total interference duty cycle reported by Access point";
    }
    leaf total-intf-device-count {
      type uint8;
      description
        "Represents number of interferers reported by Access point";
    }
    leaf interf-category-report-count {
      type uint8;
      description
        "Represents number of interferers category reported by Access point";
    }
    leaf spectrum-timestamp {
      type yang:timeticks;
      description
        "Represents latest timestamp for the report";
    }
    list intf-category-report {
      max-elements "5";
      description
        "Represents the interference category report";
      uses wireless-rrm-oper:st-worst-intf-category-report;
    }
  }

  grouping st-idr-ref {
    description
      "Represents interferer device data reference";
    leaf is-this-cluster-centre {
      type boolean;
      description
        "Flag represents if this is the cluster center for the interferer";
    }
  }

  grouping st-per-radio-spectrum-aq-data {
    description
      "Represents per radio spectrum air quality data";
    leaf slot-index {
      type uint8;
      description
        "Represents the radio slot for which interferer report has been received";
    }
    list per-channel-aq-list {
      max-elements "20";
      description
        "Represents per channel air quality list";
      uses wireless-rrm-oper:st-per-channel-spectrum-aq-data;
    }
    list idr-list {
      max-elements "12";
      description
        "Represents air quality interferer device data";
      uses wireless-rrm-oper:st-idr-ref;
    }
  }

  grouping st-spectrum-aq-data {
    description
      "Represents air quality data";
    leaf repoting-ap-mac-address {
      type yang:mac-address;
      description
        "Represents MAC address of Access point reporting the airquality report";
    }
    leaf repoting-ap-name {
      type string;
      description
        "Represents name of Access point reporting the airquality report";
    }
    list per-radio-aq-data {
      max-elements "2";
      description
        "Represents per radio air quality data";
      uses wireless-rrm-oper:st-per-radio-spectrum-aq-data;
    }
    leaf spectrum-aq-last-timestamp {
      type yang:timeticks;
      description
        "Represents the latest timestamp for the report";
    }
    leaf wtp-ca-si-capable {
      type wireless-rrm-types:enm-ca-si-capable;
      description
        "Displays if the Access point is Clean Air or SI Capable";
    }
  }

  grouping st-rrm-mgr-grp-member {
    description
      "Represents rrm rf-group member information";
    container id {
      description
        "Represents RRM RF-Group member id";
      uses wireless-rrm-types:st-member-id;
    }
    leaf member-ip {
      type inet:ip-address;
      description
        "Represents RRM RF-Group member ip";
    }
    leaf member-secondary-ip {
      type inet:ip-address;
      description
        "Represents RRM RF-Group member secondary IP";
    }
    leaf max-radio-cnt {
      type uint16;
      description
        "Represents maximum number of radios that the member can handle";
    }
    leaf curr-radio-cnt {
      type uint16;
      description
        "Represents number of radios currently associated to the member";
    }
    leaf rx-radio-cnt {
      type uint16;
      description
        "Represents number of receiver radios connected to the member";
    }
    leaf member-type {
      type uint16;
      description
        "Represents the type of the member. Usually this field represents the maximum number of radios supported by the member";
    }
    container mac {
      description
        "Represents RRM RF-Group member mac address";
      uses wireless-rrm-types:st-member-id;
    }
    leaf name {
      type string;
      description
        "Represents RRM RF-Group member name";
    }
    leaf isctrl {
      type boolean;
      description
        "Boolean value represents if the given member is a controller or agent";
    }
    leaf protocol-ver {
      type uint8;
      description
        "Represents RRM RF-Group member protocol version";
    }
    leaf kept {
      type uint32;
      description
        "Boolean value to represent if the member is still valid and it should be kept";
    }
    leaf update {
      type uint32;
      description
        "Represents reports that needs to be updated by the member";
    }
    leaf echo-count {
      type uint16;
      description
        "Represents total number of responses of an echo message the member responded";
    }
  }

  grouping st-mapping-rrm-grp-member {
    description
      "Table contains the information about the
       RRM grouping members corresponding to
       the dot11 band of the APs that have joined
       the controller.";
    leaf member-ip {
      type inet:ip-address;
      description
        "Represents the address of the dot11
         group member for the dot11 grouping containing
         this controller.";
    }
    leaf member-secondary-ip {
      type inet:ip-address;
      description
        "Represents RRM RF-Group member secondary IP";
    }
    leaf member-type {
      type uint16;
      description
        "Represents the type of the member. Usually this field represents the maximum number of radios supported by the member";
    }
    leaf name {
      type string;
      description
        "This object specifies the name of the dot11
         group member for the dot11 grouping containing
         this controller.";
    }
    leaf has-joined {
      type boolean;
      description
        "This object indicates whether the member has joined this
         RRM RF Group yet. If not the value would be 'false'.
         Else it would be true. This field is significant only
         if the current group is a static RRM RF Group.
         In all other cases a value of 'true' would be shown";
    }
    leaf nack-reason {
      type uint16;
      description
        "This object indicates the reason the member could not
         join the RRM RF Group. This field is relevant only 
         if the corresponding instance for
         'has_joined' is 'false'";
    }
  }

  grouping st-rrm-grp-history {
    description
      "Represents list of all the rrm rf-groups that the controller tried to join";
    list group-id {
      max-elements "4";
      description
        "Represents the Group-id of the group that the controller tried to join";
      uses wireless-rrm-types:st-group-id;
    }
    leaf-list count {
      type int32;
      max-elements "4";
      ordered-by user;
      description
        "Represents the counter which will be decremented after every rrm grouping algorithm and once this counter value reaches zero. The controller can try again to join this gruop";
    }
  }

  grouping st-rrm-dca-ctrl {
    description
      "Represents information related to rrm DCA algorithm";
    leaf dca-last-run {
      type uint32;
      description
        "Indicates the time when the DCA algorithm was last run";
    }
    leaf run-time {
      type uint32;
      description
        "Indicates the time elapsed during the last run of the DCA algorithm";
    }
    leaf dca-last-update {
      type uint32;
      description
        "Indicates the time when the DCA algorithm was last run";
    }
    leaf phy-type {
      type wireless-rrm-types:enm-rrm-phy-type;
      description
        "Represents phy type (802.11bg/802.11ac)";
    }
    leaf force-assign {
      type boolean;
      description
        "Indicates if the channel needs to be assigned forcefully. It will be true always";
    }
    leaf unassign-cnt {
      type uint32;
      description
        "Represents the number of radios that are not assigned to any channel manually and needs to considered for the channel assignement";
    }
    leaf radio-cnt {
      type uint32;
      description
        "Represents total number of radios currently handled by the rrm rf-group leader";
    }
    leaf count {
      type uint32;
      description
        "Represents number of times DCA has run on this controller";
    }
  }

  grouping st-rrm-dpc-ctrl {
    description
      "Represents information related to rrm TPC algorithm";
    leaf dpc-last-run {
      type uint32;
      description
        "Represents time when TPC algorithm was last run";
    }
    leaf last-chd-run {
      type uint32;
      description
        "Represents time when coverage hole detection algorithm was last run";
    }
    leaf run-time {
      type uint32;
      description
        "Represents time elapsed during the last run of TPC algorithm";
    }
    leaf unassign-cnt {
      type uint32;
      description
        "Represents number of radios that needs to be considered for the next run of TPC";
    }
    leaf radio-cnt {
      type uint32;
      description
        "Represents number of radios currently handled by the rrm rf-group leader";
    }
    leaf contribution {
      type uint8;
      description
        "Bit mask that represents the various contributors for the TPC algorithm";
    }
  }

  grouping st-rrm-rrf-ctrl {
    description
      "Represents various values related to the FRA algorithm";
    leaf last-run {
      type uint32;
      description
        "Represents the time when the FRA algorithm was last run";
    }
    leaf run-time {
      type uint32;
      description
        "Represents the time elapsed during the last run of the FRA";
    }
    leaf last-run-uptime {
      type uint32;
      description
        "Represents the time when FRA was last run compared to the controller up time";
    }
    leaf run-count {
      type uint32;
      description
        "Represents number of times FRA was run";
    }
  }

  grouping st-rrm-group-ctrl {
    description
      "Represents various values related to the rrm rf-grouping algorithm";
    leaf phy-type {
      type wireless-rrm-types:enm-rrm-phy-type;
      description
        "Represents the phy type (802.11bg/802.11ac)";
    }
    leaf current-state {
      type wireless-rrm-oper:enm-rrm-group-state;
      description
        "Represents the current state of the state machine";
    }
    container my-group-id {
      description
        "Represents group id of the current controller";
      uses wireless-rrm-types:st-group-id;
    }
    container last-my-group-id {
      description
        "Represents the last group id of the controller";
      uses wireless-rrm-types:st-group-id;
    }
    leaf my-group-ip {
      type inet:ip-address;
      description
        "Represents group ip of the current controller";
    }
    leaf my-group-secondary-ip {
      type inet:ip-address;
      description
        "Represents group IP address of the current controller";
    }
    leaf max-group-size {
      type int32;
      description
        "Represents maximum size of the group";
    }
    container history {
      description
        "Represents the failed group join history";
      uses wireless-rrm-oper:st-rrm-grp-history;
    }
    container join {
      description
        "Represents a temporary variable that will be set with the new group id that the controller decides to join after the rf-grouping algorithm is complete";
      uses wireless-rrm-types:st-group-id;
    }
    leaf join-ip {
      type inet:ip-address;
      description
        "Represents a temporary variable that will be set with the new group ip that the controller decides to join after the rf-grouping algorithm is complete";
    }
    leaf cookie {
      type uint16;
      description
        "Represents a random variable that is used to make sure that the message is delivered with acknowledgement";
    }
    leaf last-run {
      type uint32;
      description
        "Represents time when the rrm rf-grouping algorithm was last run";
    }
    leaf last-run-uptime {
      type uint32;
      description
        "Represents time when the rrm rf-grouping algorithm was last run with respect to the controller up time";
    }
    leaf update {
      type uint32;
      description
        "Represents reports that needs to be updated by the member";
    }
    leaf to-run {
      type uint8;
      description
        "Bit mask that represents the list of algorithms that needs to be run";
    }
    container dca {
      description
        "Represents all the DCA algorithm related configurations and operational data";
      uses wireless-rrm-oper:st-rrm-dca-ctrl;
    }
    container txpower {
      description
        "Represents all the TPC algorithm related configurations and operational data";
      uses wireless-rrm-oper:st-rrm-dpc-ctrl;
    }
    container rrf {
      description
        "Represents all the FRA algorithm related configurations and operational data";
      uses wireless-rrm-oper:st-rrm-rrf-ctrl;
    }
    leaf current-grouping-mode {
      type wireless-rrm-types:enm-rrm-ctrl-mode;
      description
        "Represents the current grouping mode";
    }
    leaf grouping-mode {
      type wireless-rrm-oper:enm-rrm-grouping-mode;
      description
        "Represents rrm grouping mode";
    }
    leaf join-req-try {
      type uint16;
      description
        "Represents the number of times the controller has tried to join the other controller";
    }
    leaf join-protocol-ver {
      type uint16;
      description
        "Represents the prtocol version of the controller";
    }
    leaf current-grouping-role {
      type wireless-rrm-oper:enm-rrm-grouping-role-db;
      description
        "Represents the current grouping role";
    }
    leaf leader-reason {
      type wireless-rrm-oper:enm-rrm-group-state-actions;
      description
        "Represents the reason for being the rf-group leader. It is valid only if the current grouping role is leader";
    }
    leaf cntrlr-name {
      type string;
      description
        "Represents the controller name";
    }
    leaf cntrlr-ip-addr {
      type inet:ip-address;
      description
        "Represents the controller IP address";
    }
    leaf cntrlr-secondary-ip-addr {
      type inet:ip-address;
      description
        "Represents the controller IPv6 address";
    }
    leaf grouping-update-interval-sec {
      type uint32;
      description
        "Represents when the rf-grouping algorithm was last run";
    }
    leaf is-static-member {
      type wireless-rrm-oper:enm-is-static-member;
      description
        "Represents Boolean value to indicate if the controller is currently static member";
    }
    container dpc-config {
      description
        "Represents user configurations related to TPC algorithm";
      uses wireless-rrm-types:st-rrm-dpc-config;
    }
    leaf run-count {
      type uint32;
      description
        "Field to indicate number of rrm runs";
    }
    leaf group-mode {
      type wireless-rrm-types:enm-rrm-ctrl-mode;
      description
        "Represents current rrm group mode";
    }
    leaf fra-sensor-coverage {
      type uint8;
      description
        "Represents FRA global sensor coverage";
    }
  }

  grouping st-rrm-static-grp-member {
    description
      "Represents all the statically configured rrm rf-group members";
    leaf cntrlr-name {
      type string;
      description
        "This object specifies the configured group member name";
    }
    leaf cntrlr-ip-addr {
      type inet:ip-address;
      description
        "This object specifies the configured group member ip address";
    }
    leaf has-joined {
      type boolean;
      description
        "This object indicates whether the member has joined this
         RRM RF Group yet. If not the value would be 'false'.
         Else it would be true. This field is significant only
         if the current group is a static RRM RF Group.
         In all other cases a value of 'true' would be shown";
    }
    leaf nack-reason {
      type uint16;
      description
        "This object indicates the reason the member could not
         join the RRM RF Group. This field is relevant only
         if the corresponding instance for
         'has_joined' is 'false'";
    }
    leaf max-radio-num {
      type uint16;
      description
        "Represents the maximum number of radios supported for a given rf-group";
    }
    leaf last-join-cmd-ts {
      type yang:timeticks;
      description
        "Represents time stamp when the static member joined the controller";
    }
  }

  grouping st-rrm-mgr-oper-data {
    description
      "Represents rrm manager opertaional data";
    leaf min-rssi {
      type int8;
      description
        "Represents minimum of the Received Signal Strength of the radio among all the radios applied to AP";
    }
    leaf max-rssi {
      type int8;
      description
        "Represents maximum of the Received Signal Strength of the radio among all the radios applied to AP";
    }
    leaf avg-rssi {
      type int8;
      description
        "Represents average of the Received Signal Strength of the radio among all the radios applied to AP";
    }
    leaf min-dwell {
      type int64;
      description
        "Represents the configured minimum dwell time. This values will be used during the DCA algorithm computation";
    }
    leaf avg-dwell {
      type int64;
      description
        "Represents the configured average dwell time. This values will be used during the DCA algorithm computation";
    }
    leaf max-dwell {
      type int64;
      description
        "Represents the configured maximum dwell time. This values will be used during the DCA algorithm computation";
    }
    leaf dca-thresh-val {
      type uint8;
      description
        "Represents the configured dca threshold value. This values will be used during the DCA algorithm computation";
    }
    leaf power-mode-counter {
      type uint32;
      description
        "Represents power mode counter used during RRM Run once mode";
    }
    leaf channel-list-string {
      type string;
      description
        "String representation of all the channels for the given phy type";
    }
    leaf unused-channel-list-string {
      type string;
      description
        "String representation of all the unused channels for the given phy type";
    }
    leaf default-dca-channel-list-string {
      type string;
      description
        "String representation of all the dca channels for the given phy type";
    }
    leaf disassociations {
      type uint32;
      description
        "Represents the disassociations count for the given phy types";
    }
    leaf rejections {
      type uint32;
      description
        "Represents the rejections count for the given phy types";
    }
    leaf is-dca-in-stabilization-period {
      type uint8;
      description
        "Boolean value which indicates if the DCA is still running in the stabilization period. Initial 10 cycles of DCA are considered to be stablization period and DCA algorithm runs every 10 mins irrespective of the configured value";
    }
    container default-dca-channels {
      description
        "Default DCA Channels";
      uses wireless-rrm-types:st-rrm-channels-list;
    }
    container default-non-dca-channels {
      description
        "Default non DCA Channels";
      uses wireless-rrm-types:st-rrm-channels-list;
    }
  }

  grouping st-rrm-mgr-main {
    description
      "This object specifies the main data of the rrm manager process. Phy type is the key to this table";
    leaf phy-type {
      type wireless-enum-types:radio-type;
      description
        "Represents phy type (802.11bg/802.11ac) key to this table";
    }
    container grp {
      description
        "Represents rrm rf-grouping related configurations and operational data";
      uses wireless-rrm-oper:st-rrm-group-ctrl;
    }
    leaf tpc-version {
      type uint8;
      description
        "Represents the TPC version that is currently running in the controller";
    }
    leaf max-num-neighbors {
      type uint32;
      description
        "Adjust for RRM Scalability purpose";
    }
    container oper-data {
      description
        "Represents rrm manager oper data";
      uses wireless-rrm-oper:st-rrm-mgr-oper-data;
    }
    leaf mgmt-ip {
      type inet:ip-address;
      description
        "Represents management ip address of the controller";
    }
    leaf mgmt-secondary-ip {
      type inet:ip-address;
      description
        "Represents management IP address of the controller";
    }
    leaf host-name {
      type string;
      description
        "Represents host name of the controller";
    }
    leaf rf-name {
      type string;
      description
        "Represents the rf network name";
    }
    list rrm-mgr-static-grp-member {
      key "cntrlr-ip-addr";
      description
        "Represents list of configured static members";
      uses wireless-rrm-oper:st-rrm-static-grp-member;
    }
    list rrm-mgr-grp-member {
      key "member-ip";
      description
        "Represents list of rrm rf-group members";
      uses wireless-rrm-oper:st-rrm-mgr-grp-member;
    }
    list rrm-mapping-grp-member {
      key "member-ip";
      description
        "Represents list of rrm rf-group members";
      uses wireless-rrm-oper:st-mapping-rrm-grp-member;
    }
  }

  container rrm-oper-data {
    config false;
    description
      "Represents Radio Resoursce Management Operational Data";
    list ap-auto-rf-dot11-data {
      key "wtp-mac radio-slot-id";
      description
        "Contains all tables information related to radio RF parameters";
      uses wireless-rrm-oper:st-rad-neighbor-data;
      uses wireless-types:radio-slot-key;
    }
    list ap-dot11-radar-data {
      key "wtp-mac radio-slot-id";
      description
        "Contains all tables information related to radio radar parameters";
      uses wireless-rrm-oper:st-rrm-radio-radar-attr;
      uses wireless-types:radio-slot-key;
    }
    list ap-dot11-spectrum-data {
      key "wtp-mac radio-slot-id";
      description
        "Contains all tables information related to radio spectrum parameters";
      uses wireless-rrm-oper:st-rrm-spectrum;
      uses wireless-types:radio-slot-key;
    }
    list radio-measurement {
      key "wtp-mac radio-slot-id";
      description
        "Represents the information related to radio measurements parameters";
      uses wireless-rrm-oper:st-rrm-measurement-data;
      uses wireless-types:radio-slot-key;
    }
    list client-by-phy-stats {
      key "phy-type";
      description
        "Represents the information related to 802.11 optimised romaing clients";
      uses wireless-rrm-oper:st-rrm-client-data;
    }
    list radio-slot {
      key "wtp-mac radio-slot-id";
      description
        "Represents Radio slot information";
      uses wireless-rrm-oper:st-rrm-rad-slot-data;
      uses wireless-types:radio-slot-key;
    }
    list main-data {
      key "phy-type";
      description
        "Represents main information related to RRM Manager";
      uses wireless-rrm-oper:st-rrm-mgr-main;
    }
    list spectrum-device-stats {
      key "device-id";
      description
        "This object represents device table data";
      uses wireless-rrm-oper:st-spectrum-device-record;
    }
    list spectrum-air-quality {
      key "repoting-ap-mac-address";
      description
        "This object represents air quality table data";
      uses wireless-rrm-oper:st-spectrum-aq-data;
    }
  }
}
