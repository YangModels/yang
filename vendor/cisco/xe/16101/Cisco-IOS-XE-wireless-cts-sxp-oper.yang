module Cisco-IOS-XE-wireless-cts-sxp-oper {
  yang-version 1;
  namespace "http://cisco.com/ns/yang/Cisco-IOS-XE-wireless-cts-sxp-oper";
  prefix wireless-oper-cts-sxp;

  import Cisco-IOS-XE-wireless-types {
    prefix wireless-types;
  }
  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for AP SXP operational data.
     Copyright (c) 2018 by Cisco Systems, Inc.
     All rights reserved.";

  revision 2018-08-07 {
    description
      "Initial revision";
    reference "1.0.0";
  }

  grouping cts-ap-sxp-conn-status-key {
    description
      "Key element structure for AP SXP connection";
    leaf wtp-mac {
      type yang:mac-address;
      description
        "SXP connection status for a specific AP MAC";
    }
    leaf peer-ip {
      type inet:ip-address;
      description
        "SXP Connection peer IP";
    }
    leaf conn-mode {
      type uint8;
      description
        "SXP Connection mode like SPEAKER, LISTENER 
         or BOTH.
         A value of '1' indicates connection in 'Speaker'.
         A value of '2' indicates connection in 'Listener'.
         A value of '3' indicates connection in 'Bi-directional'.";
    }
  }

  grouping cts-ap-sxp-conn-status {
    description
      "Non-key elements in the SXP operational data";
    leaf src-ip {
      type inet:ip-address;
      description
        "SXP Connection source IP";
    }
    leaf nego-version {
      type uint8;
      description
        "SXP Version running on the device
         A value of '1' indicates connection in 'SXP 1.0'.
         A value of '2' indicates connection in 'SXP 2.0'.
         A value of '3' indicates connection in 'SXP 3.0'.
         A value of '4' indicates connection in 'SXP 4.0'.";
    }
    leaf conn-status {
      type uint8;
      description
        "SXP connection status like ON, OFF or PENDING_ON
         A value of '0' indicates connection in 'off' state.
         A value of '1' indicates connection in 'pending_on' state.
         A value of '2' indicates connection in 'on' state.
         A value of '3' indicates connection in 'delete hold down' state.
         Otherwise it indicates connection in off state.";
    }
    leaf password-type {
      type wireless-types:enm-cts-sxp-password-type;
      description
        "SXP Connection password type like default password
         or None";
    }
  }

  container cts-sxp-oper-data {
    config false;
    description
      "AP SXP operatinal data";
    list flex-mode-ap-sxp-connection-status {
      key "wtp-mac peer-ip conn-mode";
      description
        "AP SXP connections operational state";
      uses wireless-oper-cts-sxp:cts-ap-sxp-conn-status-key;
      uses wireless-oper-cts-sxp:cts-ap-sxp-conn-status;
    }
  }
}
