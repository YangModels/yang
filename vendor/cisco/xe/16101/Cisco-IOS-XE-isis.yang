module Cisco-IOS-XE-isis {
  namespace "http://cisco.com/ns/yang/Cisco-IOS-XE-isis";
  prefix ios-isis;

  import ietf-inet-types {
    prefix inet;
  }


  import Cisco-IOS-XE-types {
    prefix ios-types;
  }

  import Cisco-IOS-XE-interface-common {
    prefix ios-ifc;
  }

  import Cisco-IOS-XE-snmp {
    prefix ios-snmp;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Intermediate System-to-Intermediate System (IS-IS) Yang model.
     Copyright (c) 2016-2017 by Cisco Systems, Inc.
     All rights reserved.";

  // =========================================================================
  // REVISION
  // =========================================================================
  revision 2018-06-28{
    description
        "Added must constraints for deleting vrf";
  }

  revision 2017-11-27 {
     description
       "Added Change 25GE name";
  }

  revision 2017-11-14 {
    description
      "This revision has changes for the new 40 and 100GE interface addition";
  }

  revision 2017-09-15 {
    description
      "This revision has changes for the new 2gig interface addition";
  }
  revision 2017-08-16 {
    description
      "This revision has changes for new 5gig and 25gig interfaces addition";
  }

  revision 2017-07-20 {
    description
      "Add isis bfd";
  }
  revision 2017-04-28 {
    description
      "inet:ipv6-prefix changed to ios-types:ipv6-prefix";
  }
  revision 2017-03-28 {
    description
      "Added NED Yang Data Model support for MPLS-TE";
  }

  revision 2017-02-07 {
    description
      "Initial revision";
  }


  typedef isis-net {
    type string;
    //pattern "(([0-9a-fA-F]{2}\.[0-9a-fA-F]{4})|[0-9a-fA-F]{4})"
    //+"\.([0-9a-fA-F]{4}\.){2,10}00";
  }

  typedef isis-level-type {
    type enumeration {
      enum "level-1";
      enum "level-1-2";
      enum "level-2";
    }
  }

  typedef isis-routes-level-type {
    type enumeration {
      enum "level-1";
      enum "level-1-2";
      enum "level-2";
    }
  }

  typedef authentication-level-type {
    type enumeration {
      enum "level-1";
      enum "level-2";
    }
  }

  grouping isis-bfd-grouping {
    container bfd {
      description
        "Bidirectional Forwarding Protocol";
      presence "true";
      leaf disable {
	description 
          "disable bfd";
        type empty;
      }
    } 
  }

  // interface * / isis
  grouping config-interface-isis-grouping {
      container adjacency-filter {
        description
          "Filter IS-IS adjacencies";
        leaf name {
          type string;
        }
        leaf match-all {
          description
            "Match all area addresses";
          type empty;
        }
      }
      container advertise {
        description
          "Control addresses advertisements in LSPs";
        leaf prefix {
          description
            "Interface IP address";
          type empty;
        }
      }

      container authentication {
        description
          "ISIS authentication for interface related PDUs";
        uses isis-authentication-grouping;
      }

      container circuit-type {
        description
          "Configure circuit type for interface";
        presence "true";
        leaf levels {
          type enumeration {
            enum "level-1";
            enum "level-1-2";
            enum "level-2-only";
          }
        }
      }
      container csnp-interval {
        description
          "Set CSNP interval in seconds";
        choice csnp-interval-choice {
          case csnp-interval-level-case {
            list csnp-interval-list {
              key "levels";
              leaf levels {
                type enumeration {
                  enum "level-1";
                  enum "level-2";
                }
              }
              leaf value {
                type uint16;
              }
            }
          }
          case csnp-interval-only-case {
            leaf value {
              type uint16;
            }
          }
        }
      }
      container hello {
        description
          "Add padding to IS-IS hello packets";
        container padding {
          description
            "Pad hello packets";
          presence "true";
          leaf always {
            description
              "Never pad hello packets if no prefix present";
            type empty;
          }
        }
      }
      container hello-interval {
        description
          "Set Hello interval in seconds";
        choice hello-interval-choice {
          case hello-interval-level-case {
            list hello-interval-list {
              key "levels";
              leaf levels {
                type enumeration {
                  enum "level-1";
                  enum "level-2";
                }
              }
              leaf value {
                type union {
                  type uint16 {
                    range "1..65535";
                  }
                  type enumeration {
                    enum "minimal";
                  }
                }
              }
            }
          }
          case hello-interval-only-case {
            leaf value {
              type union {
                type uint16 {
                  range "1..65535";
                }
                type enumeration {
                  enum "minimal";
                }
              }
            }
          }
        }
      }
      container hello-multiplier {
        description
          "Set multiplier for Hello holding time";
        choice hello-multiplier-choice {
          case hello-multiplier-level-case {
            list hello-multiplier-list {
              key "levels";
              leaf levels {
                type enumeration {
                  enum "level-1";
                  enum "level-2";
                }
              }
              leaf value {
                type uint16 {
                  range "3..1000";
                }
              }
            }
          }
          case hello-multiplier-only-case {
            leaf value {
              type uint16 {
                range "3..1000";
              }
            }
          }
        }
      }
      container ipv6 {
        description
          "IPv6 interface configuration";

        uses isis-metric-grouping;

        leaf tag {
          description
            "Assign an admin tag to an ISIS interface IPv6 route";
          type uint32 {
            range "1..4294967295";
          }
        }
        uses isis-bfd-grouping;
      }
      leaf lsp-interval {
        description
          "Set LSP transmission interval";
        type uint32 {
          range "1..4294967295";
        }
      }
      leaf mesh-group {
        description
          "Set ISIS mesh group";
        type union {
          type uint32 {
            range "1..4294967295";
          }
          type enumeration {
            enum "blocked";
          }
        }
      }

      uses isis-metric-grouping;

      leaf network {
        description
          "Network type";
        type enumeration {
          enum "point-to-point";
        }
      }
      container password {
        description
          "Configure the authentication password for interface";
        choice password-choice {
          case password-level-case {
            list password-list {
              key "levels";
              leaf levels {
                type enumeration {
                  enum "level-1";
                  enum "level-2";
                }
              }
              leaf password {
                type string;
              }
            }
          }
          case password-only-case {
            leaf password {
              type string;
            }
          }
        }
      }
      container priority {
        description
          "Set priority for Designated Router election";
        choice priority-choice {
          case priority-level-case {
            list priority-list {
              key "levels";
              leaf levels {
                type enumeration {
                  enum "level-1";
                  enum "level-2";
                }
              }
              leaf value {
                type uint8 {
                  range "0..127";
                }
              }
            }
          }
          case priority-only-case {
            leaf value {
              type uint8 {
                range "0..127";
              }
            }
          }
        }
      }
      leaf protocol {
        description
          "Set ISIS protocol's state under current interface";
        type enumeration {
          enum "shutdown";
        }
      }
      leaf retransmit-interval {
        description
          "Set per-LSP retransmission interval";
        type uint16;
      }
      leaf retransmit-throttle-interval {
        description
          "Set interface LSP retransmission interval";
        type uint16;
      }
      leaf tag {
        description
          "Assign an admin tag to an ISIS interface IP route";
        type uint32 {
          range "1..4294967295";
        }
      }
      uses isis-bfd-grouping;
      container three-way-handshake {
        description
          "Select Cisco or IETF three-way handshake";
        presence "true";
        leaf implementor {
          type enumeration {
            enum "cisco";
            enum "ietf";
          }
        }
      }
  }

  // router / isis grouping
  grouping narrow-wide-transition-grouping {
    leaf narrow-wide {
      type isis-level-type;
    }
    leaf transition {
      description
        "Accept both styles of TLVs during transition";
      type isis-level-type;
    }
  }

  // router / isis grouping
  grouping spf-intervals-grouping {
    leaf interval {
      type uint32 {
        range "1 .. 120";
      }
    }
    leaf initial-wait {
      type uint32 {
        range "1 .. 120000";
      }
    }
    leaf minimum-wait {
      type uint32 {
        range "1 .. 120000";
      }
    }
  }

  // router / isis grouping
  grouping authenticate-snp-grouping {
    leaf authenticate {
      description
        "Authentication";
      type empty;
    }
    leaf snp {
      description
        "SNP PDUs";
      type enumeration {
        enum "send-only";
        enum "validate";
      }
    }
  }

  // router / isis grouping
  grouping lsp-gen-interval-grouping {
    leaf interval {
      type uint32 {
        range "1 .. 120";
      }
    }
    leaf initial-wait {
      type uint32 {
        range "1 .. 120000";
      }
    }
    leaf wait {
      type uint32 {
        range "1 .. 120000";
      }
    }
  }

  // router / isis grouping
  grouping set-overload-bit-suppress-grouping {
    leaf external {
      description
        "If overload-bit set, don't advertise IP prefixes learned from other protocols";
      type empty;
    }
    leaf interlevel {
      description
        "If overload-bit set, don't advertise IP prefixes learned from another ISIS level";
      type empty;
    }
  }

  // router / isis grouping
  grouping summary-address-metric-tag-grouping {
    leaf metric {
      description
        "Set metric for summay route";
      type uint32 {
        range "1 .. 4294967295";
      }
    }
    leaf tag {
      description
        "Set tag";
      type uint32 {
        range "1 .. 4294967295";
      }
    }
  }

  // router / isis grouping
  grouping authentication-level-grouping {
    leaf levels {
      type authentication-level-type;
    }
  }

  // router / isis grouping
  grouping isis-authentication-grouping {
    container mode {
      description
        "Authentication mode";
      container md5 {
        description
          "Keyed message digest";
        presence "Keyed message digest";
        uses authentication-level-grouping;
      }
      container text {
        description
          "Clear text password";
        presence "Clear text password";
        uses authentication-level-grouping;
      }
    }
    container key-chain {
      description
        "Authentication key-chain";
      choice key-chain-choice {
        case key-chain-level-case {
          list key-chain-list {
            key "levels";
            uses authentication-level-grouping;
            leaf name {
              type string;
            }
          }
        }
        case key-chain-only-case {
          leaf name {
            type string;
          }
        }
      }
    }
    container send-only {
      description
        "Authentication send only, receive ignore";
      presence "Authentication send only, receive ignore";
      uses authentication-level-grouping;
    }
  }

  grouping isis-metric-grouping {
    container metric {
      description
        "Configure the metric for interface";
      choice metric-choice {
        case metric-level-case {
          list metric-list {
            key "levels";
            leaf levels {
              type enumeration {
                enum "level-1";
                enum "level-2";
              }
            }
            leaf value {
              type union {
                type uint32 {
                  range "1..16777214";
                }
                type enumeration {
                  enum "maximum";
                }
              }
            }
          }
        }
        case metric-only-case {
          leaf value {
            type union {
              type uint32 {
                range "1..16777214";
              }
              type enumeration {
                enum "maximum";
              }
            }
          }
        }
      }
    }
  }

  // router / isis grouping
  grouping redist-level-grouping {
    leaf levels {
      type isis-routes-level-type;
    }
  }

  // router / isis grouping
  grouping isis-redist-grouping {
    leaf levels {
      type isis-routes-level-type;
    }
    leaf metric {
      description
        "ISIS default metric";
      type uint32 {
        range "0 .. 4294967295";
      }
    }
    leaf metric-type {
      description
        "OSPF/IS-IS exterior metric type for redistributed routes";
      type enumeration {
        enum "external";
        enum "internal";
        enum "rib-metric-as-external";
        enum "rib-metric-as-internal";
      }
    }
    leaf route-map {
      description
        "Route map reference";
      type string;
    }
  }

  grouping isis-redist-af-grouping {
    leaf include-connected {
      description
        "Include connected";
      type empty;
    }
    uses isis-redist-grouping;
  }

  grouping isis-redist-ospf-match-grouping {
    uses redist-level-grouping;
    leaf metric {
      description
        "ISIS default metric";
      type uint32 {
        range "0 .. 4294967295";
      }
    }
    leaf route-map {
      description
        "Route map reference";
      type string;
    }
  }

  grouping isis-redist-clns-ip-grouping {
    container clns {
      description
        "Redistribution of BGP NSAP routes";
      presence "Redistribution of BGP NSAP routes";
      uses isis-redist-grouping;
    }
    container ip {
      description
        "Redistribution of BGP IP routes";
      presence true;
      uses isis-redist-grouping;
    }
  }

  grouping isis-ipv4-ipv6-common-grouping {
    leaf adjacency-check {
      description
        "Check ISIS neighbor protocol support";
      type empty;
    }
    container bfd {
      description
        "BFD configuration commands";
      leaf all-interfaces {
        description
          "Enable BFD on all interfaces";
        type empty;
      }
      leaf check-ctrl-plane-failure {
        description
          "BFD check control plane failure";
        type empty;
      }
    }
    leaf router-id {
      description
        "Interface of stable IP address for system";
      type string;
    }
  }

  grouping isis-common-grouping {
    container advertise {
      description
        "Control which IP routes flow in L1 and L2 LSPs";
      leaf passive-only {
        description
          "only interface address of passive interfaces";
        type empty;
      }
    }
    container default-information {
      description
        "Control distribution of default information";
      container originate {
        presence "Distribute a default route";
        description
          "Distribute a default route";
        leaf route-map {
          description
            "Route-map reference";
          type string;
        }
      }
    }
    leaf help {
      description
        "Description of the interactive help system";
      type empty;
    }
    leaf maximum-paths {
      description
        "Forward packets over multiple paths";
      type uint32 {
        range "1 .. 32";
      }
    }
    container metric {
      description
        "Set ISIS metric for all interfaces";
      choice metric-choice {
        case metric-level-case {
          list metrics {
            key "level";
            leaf level {
              type enumeration {
                enum "level-1";
                enum "level-2";
              }
            }
            leaf metric {
              type uint32 {
                range "1..16777214";
              }
            }
          }
        }
        case metric-only-case {
          leaf metric {
            type uint32 {
              range "1..16777214";
            }
          }
        }
      }
    }
    container prc-interval {
      description
        "Minimum interval between partial route calculations";
      leaf interval {
        type uint32 {
          range "1 .. 120";
        }
      }
      leaf initial-wait {
        type uint32 {
          range "1 .. 120000";
        }
      }
      leaf minimum-wait {
        type uint32 {
          range "1 .. 120000";
        }
      }
    }
    container set-overload-bit {
      description
        "Signal other routers not to use us in SPF";
      presence "Signal other routers not to use us in SPF";
      choice set-overload-bit-choice {
        container on-startup {
          description
            "Set overload-bit only temporarily after reboot";
          choice on-startup-choice {
            container time {
              leaf time {
                type uint32 {
                  range "5 .. 86400";
                }
              }
              leaf suppress {
                description
                  "If overload-bit set, suppress the following types of IP prefixes";
                type empty;
              }
              leaf external {
                description
                  "If overload-bit set, don't advertise IP prefixes learned from other protocols";
                type empty;
              }
              leaf interlevel {
                description
                  "If overload-bit set, don't advertise IP prefixes learned from another ISIS level";
                type empty;
              }
            }
            container wait-for-bgp {
              description
                "Let BGP decide when to unset the overload bit";
              presence "Let BGP decide when to unset the overload bitW";
              container suppress {
                description
                  "If overload-bit set, suppress the following types of IP prefixes";
                uses set-overload-bit-suppress-grouping;
              }
            }
          }
        }
        container suppress {
          description
            "If overload-bit set, suppress the following types of IP prefixes";
          uses set-overload-bit-suppress-grouping;
        }
      }
    }
    container spf-interval {
      description
        "Minimum interval between SPF calculations";
      choice spf-interval-choice {
        list level-1-2 {
          key "level";
          leaf level {
            type enumeration {
              enum "level-1";
              enum "level-2";
            }
          }
          uses spf-intervals-grouping;
        }
        container intervals {
          uses spf-intervals-grouping;
        }
      }
    }
  }

  grouping isis-address-family-grouping {
    uses isis-common-grouping;
    uses isis-ipv4-ipv6-common-grouping;
    leaf distance {
      description
        "Administrative distance";
      type uint32 {
        range "1 .. 254";
      }
    }
    container distribute-list {
      description
        "Filter networks in routing updates";
      list prefix-list {
        description
          "Filter connections based on an IPv6 prefix-list";
        key "name";
        leaf name {
          type string;
        }
        container in {
          description
            "Filter incoming routing updates";
          presence "true";
          container interface {
            description
              "Specify interface";
            uses ios-ifc:interface-grouping;
          }
        }
      }
    }
    container ipv6 {
      description
        "IPv6 specific commands";
      container route {
        description
          "ISIS IPV6 routes";
        container priority {
          description
            "Assign priority to IPV6 prefixes";
          container high {
            description
              "Assign high priority to important IPV6 prefixes in ISIS IPV6 local RIB";
            leaf tag {
              description
                "Assign high priority to IPV6 prefixes with a specific route tag";
              type uint32;
            }
          }
        }
      }
    }
    container multi-topology {
      description
        "Enable multi-topology mode";
      presence "Enable multi-topology mode";
      leaf transition {
        description
          "Accept and generate both IS-IS IPv6 and Multi-topology IPv6 TLVs";
        type empty;
      }
    }
    container redistribute {
      description
        "Redistribute IPv6 prefixes from another routing protocol";
      container application {
        description
          "Application Protocol";
        presence "Application Protocol";
        uses isis-redist-af-grouping;
      }
      container bgp {
        description
          "Border Gateway Protocol (BGP)";
        leaf as-number {
          type ios-types:bgp-as-number-type;
        }
        uses isis-redist-af-grouping;
      }
      container connected {
        description
          "Connected";
        presence "Connected";
        uses isis-redist-grouping;
      }
      list eigrp {
        description
          "Enhanced Interior Gateway Routing Protocol (EIGRP)";
        key "as-number";
        leaf as-number {
          type uint32 {
            range "1 .. 65535";
          }
        }
        uses isis-redist-af-grouping;
      }
      container isis {
        description
          "ISO IS-IS";
        presence "true";
        list isis-redistribute {
          key "area-tag";
          leaf area-tag {
            type string;
          }
          uses isis-redist-af-grouping;
        }
        list isis-leak {
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            
            type empty;
          }
          choice isis-redist-isis-ip-choice {
            leaf distribute-list {
              description
                "select routes";
              type string;
            }
            leaf route-map {
              description
                "Route map for route matching";
              type string;
            }
          }
        }
      }
      container lisp {
        description
          "Locator ID Separation Protocol (LISP)";
        presence "Locator ID Separation Protocol (LISP)";
        uses isis-redist-af-grouping;
      }
      container nd {
        description
          "Neighbor Discovery";
        presence "Neighbor Discovery";
        uses isis-redist-af-grouping;
      }
      container nemo {
        description
          "Network Mobility (NEMO)";
        uses isis-redist-af-grouping;
      }
      list ospf {
        description
          "Open Shortest Path First (OSPF)";
        key "process-id";
        leaf process-id {
          type uint32 {
            range "1 .. 65535";
          }
        }
        uses isis-redist-af-grouping;
        container match {
          description
            "Redistribution of OSPF routes";
          container internal {
            presence "Redistribute OSPF internal routes";
            description
              "Redistribute OSPF internal routes";
            uses isis-redist-grouping;
          }
          container external {
            description
              "Redistribute OSPF external routes";
            presence "Redistribute OSPF external routes";
            leaf external-routes {
              type ios-types:redist-ospf-external-type;
            }
            uses isis-redist-grouping;
          }
          container nssa-external {
            description
              "Redistribute OSPF NSSA external routes";
            presence "Redistribute OSPF NSSA external routes";
            leaf nssa-external-routes {
              type ios-types:redist-ospf-external-type;
            }
            uses isis-redist-grouping;
          }
        }
      }
      list rip {
        description
          "IPv6 Routing Information Protocol (RIPv6)";
        key "process";
        leaf process {
          type string;
        }
        uses isis-redist-af-grouping;
      }
      container static {
        description
          "Static routes";
        presence "Static routes";
        uses isis-redist-grouping;
      }
    }
    list summary-prefix {
      description
        "Configure IPv6 summary prefix";
      key "prefix";
      leaf prefix {
        type ios-types:ipv6-prefix;
      }
      leaf levels {
        type enumeration {
          enum "level-1";
          enum "level-1-2";
          enum "level-2";
        }
      }
    }
    container table-map {
      description
        "Map external entry attributes into routing table";
      leaf name {
        type string;
      }
      leaf filter {
        description
          "Selective route download";
        type empty;
      }
    }
  }

  grouping isis-redist-vrf-grouping {
    container application {
      description
        "Application";
      list appname {
        key "appname";
        leaf appname {
          description
            "Application name";
          type string;
        }
        uses isis-redist-grouping;
      }
    }
    container bgp {
      description
        "Border Gateway Protocol (BGP)";
      list bp-as-num {
        key "bp-as-num";
        leaf bp-as-num {
          description
            "Autonomous system number";
          type ios-types:bgp-as-number-type;
        }
        uses isis-redist-clns-ip-grouping;
        uses isis-redist-grouping;
      }
      leaf a_LESSER_1_PERIOD_0-XX_PERIOD_YY_GREATER_ {
        description
          "Autonomous system number";
        type empty;
      }
    }
    container connected {
      description
        "Connected";
      presence "true";
      uses isis-redist-grouping;
    }
    container eigrp {
      description
        "Enhanced Interior Gateway Routing Protocol (EIGRP)";
      list eigrp-as {
        key "eigrp-as";
        leaf eigrp-as {
          description
            "AS number";
          type uint16 {
            range "1..65535";
          }
        }
        uses isis-redist-grouping;
      }
    }
    container isis {
      description
        "ISO IS-IS";
      list isis-atag {
        key "isis-atag";
        leaf isis-atag {
          description
            "ISO routing area tag";
          type string;
        }
        container ip {
          description
            "Redistribution of IP routes between levels or processes";
          uses isis-redist-grouping;
        }
      }
      container ip {
        description
          "Redistribution of IP routes between levels or processes";
        presence "true";
        uses isis-redist-grouping;
      }
    }
    container iso-igrp {
      description
        "IGRP for OSI networks";
      presence "true";
      list iso-atag {
        key "iso-atag";
        leaf iso-atag {
          description
            "ISO routing area tag";
          type string;
        }
        leaf route-map {
          description
            "Route map reference";
          type empty;
        }
      }
      container route-map {
        description
          "Route map reference";
        presence "true";
        leaf rm-point {
          description
            "Pointer to route-map entries";
          type string;
        }
      }
    }
    container lisp {
      description
        "Locator ID Separation Protocol (LISP)";
      presence "true";
      uses isis-redist-grouping;
    }
    container mobile {
      description
        "Mobile routes";
      presence "true";
      uses isis-redist-grouping;
    }
    leaf ospf {
      description
        "Process ID";
      type uint16 {
        range "1..65535";
      }
    }
    container ospfv3 {
      description
        "OSPFv3";
      list os3-id {
        key "os3-id";
        leaf os3-id {
          description
            "Process ID";
          type uint16 {
            range "1..65535";
          }
        }
        uses isis-redist-grouping;
      }
    }
    container rip {
      description
        "Routing Information Protocol (RIP)";
      presence "true";
      uses isis-redist-grouping;
    }
    container static {
      description
        "Static routes";
      presence "true";
      uses isis-redist-clns-ip-grouping;
      uses isis-redist-grouping;
    }
  }

  // router/isis grouping
  grouping tie-break-prefer-repair-grouping {
    leaf downstream {
      description
        "priority number";
      type uint8 {
        range "1..255";
      }
    }
    leaf linecard-disjoint {
      description
        "priority number";
      type uint8 {
        range "1..255";
      }
    }
    leaf lowest-backup-path-metric {
      description
        "priority number";
      type uint8 {
        range "1..255";
      }
    }
    leaf node-protecting {
      description
        "priority number";
      type uint8 {
        range "1..255";
      }
    }
    leaf primary-path {
      description
        "priority number";
      type uint8 {
        range "1..255";
      }
    }
    leaf secondary-path {
      description
        "priority number";
      type uint8 {
        range "1..255";
      }
    }
    leaf srlg-disjoint {
      description
        "priority number";
      type uint8 {
        range "1..255";
      }
    }
  }

  grouping isis-topology-grouping {
    list distance {
      description
        "Define an administrative distance";
      key "number";
      leaf number {
        type uint8 {
          range "1 .. 255";
        }
      }
      list ip-list {
        key "ip";
        leaf ip {
          description
            "IP Source address";
          type inet:ipv4-address;
        }
        list wildcard-bits {
          key "w-bits";
          leaf w-bits {
            type inet:ipv4-address;
          }
          leaf access-list {
            type ios-types:default-access-list-standard-id-type;
          }
        }
      }
      leaf clns {
        description
          "Distance applied for CLNS derived routes";
        type empty;
      }
      leaf ip {
        description
          "Distance applied for IP derived routes";
        type empty;
      }
    }
    container ip {
      description
        "IP specific commands";
      container route {
        description
          "ISIS IP routes";
        container priority {
          description
            "Assign priority to IP prefixes";
          container high {
            description
              "Assign high priority to important IP prefixes in ISIS IP local RIB";
            leaf tag {
              description
                "Assign high priority to IP prefixes with a specific route tag";
              type uint32 {
                range "1 .. 4294967295";
              }
            }
          }
        }
      }
    }
    leaf priority {
      description
        "priority value";
      type uint8 {
        range "0..127";
      }
    }
    container redistribute {
      description
        "Redistribute information from another routing protocol";
      list application {
        description
          "Application";
        key "name";
        leaf name {
          description
            "Application name";
          type string;
        }
        uses isis-redist-grouping;
      }
      container bgp {
        description
          "Border Gateway Protocol (BGP)";
        leaf as-number {
          type ios-types:bgp-as-number-type;
        }
        uses isis-redist-grouping;
        uses isis-redist-clns-ip-grouping;
      }
      container connected {
        description
          "Connected";
        presence "Connected";
        uses isis-redist-grouping;
      }
      list eigrp {
        description
          "Enhanced Interior Gateway Routing Protocol (EIGRP)";
        key "as-number";
        leaf as-number {
          type uint32 {
            range "1 .. 65535";
          }
        }
        uses isis-redist-grouping;
      }
      container isis {
        description
          "ISO IS-IS";
        list isis-redistribute {
          key "area-tag";
          leaf area-tag {
            type string;
          }
          container ip {
            description
              "Redistribution of IP routes between levels or processes";
            presence "true";
            uses isis-redist-grouping;
          }
        }
        list ip {
          description
            "Redistribution of IP routes between levels";
          key "isis-redist-levels1 isis-redist-levels2";
          leaf isis-redist-levels1 {
            type enumeration {
              enum "level-1";
              enum "level-2";
            }
          }
          leaf isis-redist-levels2 {
            type enumeration {
              enum "level-1";
              enum "level-2";
            }
          }
          leaf into {
            description
              "from level-n into level-m";
            
            type empty;
          }
          choice isis-redist-isis-ip-choice {
            leaf distribute-list {
              description
                "select routes";
              type uint32 {
                range "100 .. 199";
              }
            }
            leaf route-map {
              description
                "Route map for route matching";
              type string;
            }
          }
        }
      }
      container iso-igrp {
        description
          "IGRP for OSI networks";
        presence "IGRP for OSI networks";
        choice iso-igrp-choice {
          container area-tag-route-map-container {
            leaf area-tag {
              type string;
            }
            leaf route-map {
              description
                "Route map reference";
              type string;
            }
          }
          leaf route-map {
            description
              "Route map reference";
            type string;
          }
        }
        uses redist-level-grouping;
        leaf metric {
          description
            "ISIS default metric";
          type uint32 {
            range "0 .. 4294967295";
          }
        }
        leaf metric-type {
          description
            "OSPF/IS-IS exterior metric type for redistributed routes";
          type enumeration {
            enum "external";
            enum "internal";
            enum "rib-metric-as-external";
            enum "rib-metric-as-internal";
          }
        }
      }
      container lisp {
        description
          "Locator ID Separation Protocol (LISP)";
        presence "true";
        uses isis-redist-af-grouping;
      }
      container maximum-prefix {
        description
          "Maximum number of prefixes redistributed to protocol";
        leaf number {
          type uint32 {
            range "1 .. 4294967295";
          }
        }
        leaf threshold-value {
          type uint32 {
            range "1 .. 100";
          }
        }
        leaf warning-only {
          description
            "Only give warning message when limit is exceeded";
          type empty;
        }
        leaf withdraw {
          description
            "Withdraw redistibuted prefixes";
          type empty;
        }
      }
      container mobile {
        description
          "Mobile routes";
        presence "Mobile routes";
        uses isis-redist-grouping;
      }
      container odr {
        description
          "On Demand stub Routes";
        presence "On Demand stub Routes";
        uses isis-redist-grouping;
      }
      list ospf {
        description
          "Open Shortest Path First (OSPF)";
        key "process-id";
        leaf process-id {
          type uint32 {
            range "1 .. 65535";
          }
        }
        uses isis-redist-grouping;
        container match {
          description
            "Redistribution of OSPF routes";
          container internal {
            presence "Redistribute OSPF internal routes";
            description
              "Redistribute OSPF internal routes";
            uses isis-redist-grouping;
          }
          container external {
            description
              "Redistribute OSPF external routes";
            presence "Redistribute OSPF external routes";
            leaf external-routes {
              type ios-types:redist-ospf-external-type;
            }
            uses isis-redist-grouping;
          }
          container nssa-external {
            description
              "Redistribute OSPF NSSA external routes";
            presence "Redistribute OSPF NSSA external routes";
            leaf nssa-external-routes {
              type ios-types:redist-ospf-external-type;
            }
            uses isis-redist-grouping;
          }
        }
        leaf vrf {
          description
            "VPN Routing/Forwarding Instance";
	  must "/ios:native/ios:vrf/ios:definition[ios:name=current()] or /ios:native/ios:ip/ios:vrf[ios:name=current()]" {
	    error-message "VRF must be created 1st, deleted last";
          }
          type string;
        }
      }
      list ospfv3 {
        description
          "Open Shortest Path First (OSPF)";
        key "process-id";
        leaf process-id {
          type uint32 {
            range "1 .. 65535";
          }
        }
        uses isis-redist-grouping;
        container match {
          description
            "Redistribution of OSPF routes";
          container internal {
            presence "Redistribute OSPF internal routes";
            description
              "Redistribute OSPF internal routes";
            uses isis-redist-grouping;
          }
          container external {
            description
              "Redistribute OSPF external routes";
            presence "Redistribute OSPF external routes";
            leaf external-routes {
              type ios-types:redist-ospf-external-type;
            }
            uses isis-redist-grouping;
          }
          container nssa-external {
            description
              "Redistribute OSPF NSSA external routes";
            presence "Redistribute OSPF NSSA external routes";
            leaf nssa-external-routes {
              type ios-types:redist-ospf-external-type;
            }
            uses isis-redist-grouping;
          }
        }
        leaf vrf {
          description
            "VPN Routing/Forwarding Instance";
	  must "/ios:native/ios:vrf/ios:definition[ios:name=current()] or /ios:native/ios:ip/ios:vrf[ios:name=current()]" {
	    error-message "VRF must be created 1st, deleted last";
          }
          type string;
        }
      }
      container rip {
        description
          "Routing Information Protocol (RIP)";
        presence "Routing Information Protocol (RIP)";
        uses isis-redist-grouping;
      }
      container static {
        description
          "Static routes";
        presence "Static routes";
        uses isis-redist-clns-ip-grouping;
      }
      container vrf {
        description
          "Specify a source VRF";
        list vrf-nm {
          key "vrf-nm";
          leaf vrf-nm {
            description
              "Source VRF name";
            type string;
          }
          uses isis-redist-vrf-grouping;
        }
        container global {
          description
            "global VRF";
          uses isis-redist-vrf-grouping;
        }
      }
    }
    container set-attached-bit {
      description
        "Conditionally advertise us as attached to L2";
      leaf route-map {
        description
          "Route-map reference";
        type string;
      }
    }
    uses ios-snmp:router-snmp-grouping;
    list summary-address {
      description
        "Configure IP address summaries";
      key "ip mask";
      leaf ip {
        type inet:ipv4-address;
      }
      leaf mask {
        type inet:ipv4-address;
      }
      container level-1 {
        description
          "Summarize into level-1 area";
        presence "Summarize into level-1 area";
        uses summary-address-metric-tag-grouping;
      }
      container level-1-2 {
        description
          "Summarize into both area and sub-domain";
        presence "Summarize into both area and sub-domain";
        uses summary-address-metric-tag-grouping;
      }
      container level-2 {
        description
          "Summarize into level-2 sub-domain";
        presence "Summarize into level-2 sub-domain";
        uses summary-address-metric-tag-grouping;
      }
      container metric-tag-container {
        uses summary-address-metric-tag-grouping;
      }
    }
    container traffic-share {
      description
        "How to compute traffic share over alternate paths";
      container min {
        description
          "All traffic shared among min metric paths";
        leaf across-interfaces {
          description
            "Use different interfaces for equal-cost paths";
          type empty;
        }
      }
    }
    uses isis-common-grouping;
  }

  grouping isis-af-ipv4-grouping {
    leaf help {
      description
        "Description of the interactive help system";
      type empty;
    }
    uses ios-snmp:router-snmp-grouping;
    list topology {
      description
        "Associate the routing protocol to a topology instance";
      key "name";
      leaf name {
        type string;
      }
      leaf tid {
        description
          "Configuring the routing protocol topology tid";
        type uint32 {
          range "5..4095";
        }
      }
      leaf ignore-attached-bit {
        description
          "Never install default route to closest L2 router";
        type empty;
      }
      uses isis-topology-grouping;
    }
  }

  grouping config-isis-main-grouping {
    container metric-style {
      description
        "Use old-style (ISO 10589) or new-style packet formats";
      choice metric-style-choice {
        container narrow {
          description
            "Use old style of TLVs with narrow metric";
          presence "true";
          uses narrow-wide-transition-grouping;
        }
        container transition {
          description
            "Send and accept both styles of TLVs during transition";
          presence "true";
          leaf transition {
            type isis-level-type;
          }
        }
        container wide {
          description
            "Use new style of TLVs to carry wider metric";
          presence "true";
          uses narrow-wide-transition-grouping;
        }
      }
    }
    container address-family {
      description
        "Enter Address Family command mode";
      container ipv4 {
        description
          "Address family";
        leaf unicast-multicast {
          type enumeration {
            enum "unicast";
            enum "multicast";
          }
        }
        uses isis-af-ipv4-grouping;
      }
      container ipv6 {
        description
          "Address family";
        leaf unicast {
          type empty;
        }
        uses isis-address-family-grouping;
      }
    }
    uses isis-topology-grouping;
    container area-password {
      description
        "Configure the authentication password for an area";
      leaf name {
        type string;
      }
      uses authenticate-snp-grouping;
    }
    container authentication {
      description
        "ISIS authentication for LSPs";
      uses isis-authentication-grouping;
    }
    container distribute-list {
      description
        "Filter networks in routing updates";
      choice distribute-list-choice {
        case acl-case {
          leaf acl-name {
            type ios-types:access-list-standard-id-type;
          }
          leaf in {
            description
              "Filter incoming routing updates";
            type string;
          }
        }
        case gateway-prefix-case {
          leaf gateway {
            description
              "Filtering incoming updates based on gateway";
            type string;
          }
          leaf prefix {
            description
              "Filter prefixes in routing updates";
            type string;
          }
          leaf gateway-prefix-in {
            description
              "Filter incoming routing updates";
            type string;
          }
        }
        case route-map-case {
          leaf route-map {
            description
              "Filter prefixes based on the route-map";
            type string;
          }
          leaf route-map-in {
            description
              "Filter incoming routing updates";
            type empty;
          }
        }
      }
    }
    container domain-password {
      description
        "Set the authentication password for a routing domain";
      leaf name {
        type string;
      }
      uses authenticate-snp-grouping;
    }
    container fast-flood {
      description
        "Flood LSPs (that triggered SPF) before running SPF";
      presence "Flood LSPs (that triggered SPF) before running SPF";
      leaf number {
        type uint32 {
          range "1 .. 15";
        }
      }
    }
    container fast-reroute {
      description
        "Configure Fast-Reroute";
      container load-sharing {
        description
          "Distributes repair paths equally among links and prefixes";
        container level-1 {
          description
            "Apply to level-1";
          presence "true";
          leaf disable {
            description
              "Disable load-sharing";
            type empty;
          }
        }
        container level-2 {
          description
            "Apply to level-2";
          presence "true";
          leaf disable {
            description
              "Disable load-sharing";
            type empty;
          }
        }
      }
      container per-prefix {
        description
          "Enable Fast-Reroute Per-Prefix";
        container level-1 {
          description
            "Apply to level-1";
          leaf all {
            description
              "Enable Fast-Reroute for primary paths";
            type empty;
          }
          leaf route-map {
            description
              "route-map name";
            type string;
          }
        }
        container level-2 {
          description
            "Apply to level-2";
          leaf all {
            description
              "Enable Fast-Reroute for primary paths";
            type empty;
          }
          leaf route-map {
            description
              "route-map name";
            type string;
          }
        }
      }
      container remote-lfa {
        description
          "Configuring fast-reroute remote-lfa";
        container level-1 {
          description
            "Apply to level-1";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
        container level-2 {
          description
            "Apply to level-2";
          container mpls-ldp {
            description
              "Use mpls-ldp tunnel type";
            presence "true";
            container maximum-metric {
              description
                "maximum metric to reach release node";
              presence "true";
              leaf max-met {
                description
                  "metric value";
                type uint32 {
                  range "1..4294967295";
                }
              }
            }
          }
        }
      }
      container tie-break {
        description
          "Set repair path preference";
        container level-1 {
          description
            "Apply to level-1";
          uses tie-break-prefer-repair-grouping;
        }
        container level-2 {
          description
            "Apply to level-2";
          uses tie-break-prefer-repair-grouping;
        }
      }
    }
    container ti-lfa {
      container level-1 {
        description
          "Apply to level-1";
        container maximum-metric {
          description
            "maximum metric to reach release node";
          leaf max-met {
            description
              "metric value";
            type uint32 {
              range "1..4294967295";
            }
          }
        }
      }
      container level-2 {
        description
          "Apply to level-2";
        presence true;
        container maximum-metric {
          description
            "maximum metric to reach release node";
          leaf max-met {
            description
              "metric value";
            type uint32 {
              range "1..4294967295";
            }
          }
        }
      }
    }
    container hello {
      description
        "Pad ISIS hello PDUs to full MTU";
      container padding {
        description
          "Pad hello PDU";
        presence "Pad hello PDU";
        leaf pad-type {
          type enumeration {
            enum "multi-point";
            enum "point-to-point";
          }
        }
      }
    }
    container hostname {
      description
        "Dynamic hostname for IS-IS";
      leaf dynamic {
        description
          "Dynamic hostname";
        type empty;
      }
    }
    leaf ignore-lsp-errors {
      description
        "Ignore LSPs with bad checksums";
      type empty;
    }
    leaf is-type {
      description
        "IS Level for this routing process (OSI only)";
      type enumeration {
        enum "level-1";
        enum "level-1-2";
        enum "level-2-only";
      }
    }
    container ispf {
      description
        "Configure execution of incremental SPF";
      leaf level {
        type enumeration {
          enum "level-1";
          enum "level-1-2";
          enum "level-2";
        }
      }
      leaf number {
        type uint32 {
          range "1 .. 600";
        }
      }
    }
    container log-adjacency-changes {
      description
        "Log changes in adjacency state";
      presence "Log changes in adjacency state";
      leaf all {
        description
          "Include changes generated by non-IIH event";
        type empty;
      }
    }
    container lsp-full {
      description
        "If we run out of LSP fragments";
      container suppress {
        description
          "suppress the following types of IP prefixes";
        choice lsp-full-choince {
          container external-interlevel-container {
            leaf external {
              description
                "don't advertise IP prefixes learned from other protocols";
              type empty;
            }
            leaf interlevel {
              description
                "don't advertise IP prefixes learned from another ISIS level";
              type empty;
            }
          }
          leaf none {
            description
              "don't suppress any prefixes";
            type empty;
          }
        }
      }
    }
    container lsp-gen-interval {
      description
        "Minimum interval between regenerating same LSP";
      choice lsp-gen-interval-choice {
        container intervals {
          uses lsp-gen-interval-grouping;
        }
        container intervals-levels {
          container intervals-level-1 {
            leaf level-1 {
              description
                "Set interval for level 1 only";
              type empty;
            }
            uses lsp-gen-interval-grouping;
          }
          container intervals-level-2 {
            leaf level-2 {
              description
                "Set interval for level 2 only";
              type empty;
            }
            uses lsp-gen-interval-grouping;
          }
        }
      }
    }
    leaf lsp-mtu {
      description
        "Set maximum LSP size";
      type uint32 {
        range "128 .. 4352";
      }
    }
    leaf lsp-refresh-interval {
      description
        "Set LSP refresh interval";
      type uint32 {
        range "1 .. 65535";
      }
    }
    leaf max-area-addresses {
      description
        "Allow configuration of more manual area addresses";
      type uint32 {
        range "3 .. 254";
      }
    }
    leaf max-lsp-lifetime {
      description
        "Set maximum LSP lifetime";
      type uint32 {
        range "1 .. 65535";
      }
    }
    container microloop {
      description
        "Enable microloop protection configuration commands";
      container avoidance {
        description
          "Enable local microloop avoidance";
        presence "true";
        leaf disable {
          description
            "Disable Microloop avoidance";
          type empty;
        }
        leaf protected {
          description
            "Microloop avoidance for protected link or prefix only";
          type empty;
        }
        leaf rib-update-delay {
          description
            "Value of the delay in milliseconds";
          type uint32 {
            range "1..600000";
          }
        }
      }
    }
    container mpls {
      description
        "Configure MPLS routing protocol parameters";
      container ldp {
        description
          "routing protocol commands for MPLS LDP";
        container autoconfig {
          description
            "Configure LDP automatic configuration";
          presence "true";
          leaf level-1 {
            description
              "Configure ISIS level-1 to run MPLS LDP";
            type empty;
          }
          leaf level-2 {
            description
              "Configure ISIS level-2 to run MPLS LDP";
            type empty;
          }
        }
        leaf sync {
          description
            "Configure LDP-IGP Synchronization";
          type empty;
        }
        leaf sync-igp-shortcuts {
          description
            "Configure LDP-IGP Synchronization on MPLS shortcuts";
          type empty;
        }
      }
      container traffic-eng {
        description
          "routing protocol commands for MPLS Traffic Engineering";
        leaf level-1 {
          description
            "Run MPLS TE on IS-IS level 1 only";
          type empty;
        }
        leaf level-2 {
          description
            "Run MPLS TE on IS-IS level 2 only";
          type empty;
        }
        leaf multicast-intact {
          description
            "MPLS TE and PIM interaction";
          type empty;
        }
        container router-id {
          description
            "Traffic Engineering stable IP address for system";
          uses ios-ifc:interface-grouping;
        }
        container scanner {
          description
            "Timer parameters for TE database";
          leaf interval {
            description
              "Time (secs) between LSPDB walks for TE";
            type uint32 {
              range "1 .. 60";
            }
          }
          leaf max-flash {
            description
              "Max. number of LSPs ISIS may send to TE db without delay: <0..200>";
            type uint32 {
              range "0 .. 200";
            }
          }
        }
      }
    }
    list net {
      description
        "A Network Entity Title for this process (OSI only)";
      key "tag";
      leaf tag {
        type isis-net;
      }
    }
    container nsf {
      description
        "Non-stop forwarding";
      leaf cisco {
        description
          "Checkpoint method";
        type empty;
      }
      leaf ietf {
        description
          "IETF method";
        type empty;
      }
      container interface {
        description
          "Interface properties";
        leaf wait {
          description
            "Seconds";
          type uint8 {
            range "1..60";
          }
        }
      }
      leaf interval {
        description
          "Minutes";
        type uint16 {
          range "0..1440";
        }
      }
    }
    container partition {
      description
        "CLNS area partition";
      leaf avoidance {
        description
          "Withdraw area prefix if partition detected";
        type empty;
      }
    }
    uses ios-ifc:passive-interface-grouping;
    container protocol {
      description
        "Set protocol's administrative state";
      leaf shutdown {
        description
          "Set protocol's administrative state to disable";
        type empty;
      }
    }
    container segment-routing {
      description
        "Enable Segment Routing Feature";
      leaf mpls {
        description
          "Enable Segment Routing Feature using MPLS encapsulation";
        type empty;
      }
      container prefix-sid-map {
        description
          "Enable prefix-sid-map";
        leaf advertise-local {
          description
            "Advertise active local prefix-SID mappings";
          type empty;
        }
        container receive {
          description
            "Enable prefix-SID mapping client";
          presence "true";
          leaf disable {
            description
              "Disable prefix-SID mapping";
            type empty;
          }
        }
      }
    }
    container skeptical {
      description
        "Be a cautious NSF helper when refresh adjacency";
      leaf interval {
        description
          "Minutes";
        type uint16 {
          range "0..1440";
        }
      }
    }
    leaf update-queue-depth {
      description
        "Set Update process queue depth";
      type uint32 {
        range "1 .. 2147483647";
      }
    }
    container use {
      description
        "Use different algorithms during SPF";
      leaf external-metrics {
        description
          "Honour external metrics during SPF";
        type empty;
      }
    }
    leaf vrf {
      description
        "VRF name for this process";
      type string;
    }
    uses isis-ipv4-ipv6-common-grouping;
  }

  grouping config-isis-container-grouping {
    container isis-container { 
      list isis {
        description
          "ISO IS-IS";
        key "area-tag";
        leaf area-tag {
          type string;
        }
        uses config-isis-main-grouping;
      }
    }
  }

  grouping config-isis-grouping {
    container isis { 
      description
        "ISO IS-IS";
      presence "true";
      uses config-isis-main-grouping;
    }
  }


  /////////////////////////////////////////////////////////
  // native / router / isis
  /////////////////////////////////////////////////////////
  augment "/ios:native/ios:router" {
    uses config-isis-grouping;
    uses config-isis-container-grouping;
  }

  /////////////////////////////////////////////////////////
  // native / interface * / isis
  /////////////////////////////////////////////////////////
  augment "/ios:native/ios:interface/ios:FastEthernet/ios:isis" {
    uses config-interface-isis-grouping;
  }

  augment "/ios:native/ios:interface/ios:GigabitEthernet/ios:isis" {
    uses config-interface-isis-grouping;
  }

  augment "/ios:native/ios:interface/ios:TenGigabitEthernet/ios:isis" {
    uses config-interface-isis-grouping;
  }

  augment "/ios:native/ios:interface/ios:FiveGigabitEthernet/ios:isis" {
    uses config-interface-isis-grouping;
  }

  augment "/ios:native/ios:interface/ios:TwentyFiveGigE/ios:isis" {
    uses config-interface-isis-grouping;
  }

  augment "/ios:native/ios:interface/ios:TwoGigabitEthernet/ios:isis" {
    uses config-interface-isis-grouping;
  }

  augment "/ios:native/ios:interface/ios:FortyGigabitEthernet/ios:isis" {
    uses config-interface-isis-grouping;
  }

  augment "/ios:native/ios:interface/ios:HundredGigE/ios:isis" {
    uses config-interface-isis-grouping;
  }

  augment "/ios:native/ios:interface/ios:Loopback/ios:isis" {
    uses config-interface-isis-grouping;
  }

  augment "/ios:native/ios:interface/ios:Tunnel/ios:isis" {
    uses config-interface-isis-grouping;
  }

  augment "/ios:native/ios:interface/ios:Vlan/ios:isis" {
    uses config-interface-isis-grouping;
  }

  augment "/ios:native/ios:interface/ios:LISP/ios:isis" {
    uses config-interface-isis-grouping;
  }

  augment "/ios:native/ios:interface/ios:Virtual-Template/ios:isis" {
    uses config-interface-isis-grouping;
  }
  augment "/ios:native/ios:interface/ios:BDI/ios:isis" {
    uses config-interface-isis-grouping;
  }
}
