module Cisco-IOS-XE-wireless-flex-cfg {
  yang-version 1;
  namespace "http://cisco.com/ns/yang/Cisco-IOS-XE-wireless-flex-cfg";
  prefix wireless-flex-cfg;

  import Cisco-IOS-XE-wireless-enum-types {
    prefix wireless-enum-types;
  }
  import Cisco-IOS-XE-wireless-types {
    prefix wireless-types;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing flex configurations
     Copyright (c) 2016-2018 by Cisco Systems, Inc.
     All rights reserved.";

  revision 2018-06-05 {
    description
      "- Add constraints
       - Password encryption type configuration";
    reference "3.0.0";
  }
  revision 2018-03-08 {
    description
      "Add remote lan configuration";
    reference "2.1.0";
  }
  revision 2018-01-24 {
    description
      "The first generally available version";
    reference "2.0.0";
  }
  revision 2017-05-05 {
    description
      "Initial revision";
    reference "1.0.0";
  }

  grouping vlan-acl-list {
    description
      "This table represents the configuration of vlan-acl mappings for REAPs";
    leaf vlan-id {
      type uint32;
      description
        "This object represents the VLAN ID to be mapped to the ACL for the reap group";
    }
    leaf ingress-acl-name {
      type string;
      default "";
      description
        "This object specifies the name of the ingress Access Control List for the vlan-acl mapping";
    }
    leaf egress-acl-name {
      type string;
      default "";
      description
        "This object specifies the name of the egress Access Control List for the vlan-acl mapping";
    }
  }

  grouping local-auth-user-list {
    description
      "This object represents the local authenticated user list";
    leaf user-name {
      type string;
      description
        "This object represents the user name for this group. user name is used for authenticating a client associated to an AP within the group";
    }
    leaf password {
      type string;
      default "";
      description
        "This object represents the password for this conceptual row.";
    }
    leaf password-type {
      type wireless-enum-types:crypt-type;
      default "clear";
      description
        "Password encryption type for authentication by AP";
    }
  }

  grouping policy-acl-list {
    description
      "This table represents the configuration of webpolicy acl mappings for REAP groups";
    leaf acl-name {
      type string;
      description
        "This object specifies the name of the webpolicy Access Control List to be mapped to the REAP group";
    }
    leaf is-punt {
      type boolean;
      default "false";
      description
        "This object represents whether to Configure central-webauth for this ACL.";
    }
    leaf urlfilterlist-name {
      type string;
      description
        "This object represents mapping of IPv4/Ipv6 ACL nameto url filter list this ACL.";
    }
  }

  grouping if-name-vlan-id-list {
    description
      "This table defines the VLAN Name- ACL mappings to be configured for the REAP";
    leaf interface-name {
      type string;
      description
        "This object specifies the name of the Vlan name for the vlan-acl mapping.";
    }
    leaf vlan-id {
      type uint32 {
        range "1 .. 4096";
      }
      description
        "This object specifies the VLAN ID to be mapped to the Acl for the Access Point identified by vlan name.";
    }
    leaf acl-name {
      type string;
      default "";
      description
        "This object specifies the name of the Access Control List for the vlan-acl mapping";
    }
  }

  grouping flex-policy-config {
    description
      "This object encompasses the flex profile attributes";
    leaf policy-name {
      type string;
      description
        "This object specifies the name of the flex profile";
    }
    leaf description {
      type string;
      default "";
      description
        "This object specifies the description for the flex profile";
    }
    leaf is-peap {
      type boolean;
      default "false";
      description
        "This parameter represents whether PEAP is enabled";
    }
    leaf is-leap {
      type boolean;
      default "false";
      description
        "This parameter represents whether LEAP is enabled";
    }
    leaf is-eap {
      type boolean;
      default "false";
      description
        "This parameter represents whether EAP is enabled";
    }
    leaf is-tls {
      type boolean;
      default "false";
      description
        "This parameter represents whether TLS is enabled";
    }
    leaf eap-fast-profile-name {
      type string;
      default "";
      description
        "This object uniquely identifies the eap fast profile used for local auth";
    }
    leaf radius-server-group-name {
      type string;
      default "";
      description
        "This object uniquely identifies the radius server group name entry in cLReapGroupConfigTable.";
    }
    leaf multicast-overriden-intf {
      type boolean;
      default "false";
      description
        "This object specifies whether multicast across the Layer 2 broadcast domain on the overridden interface is configured";
    }
    leaf fallback-radio-shut {
      type boolean;
      default "false";
      description
        "This object specifies whether Fallback Radio Shut feature is enabled for the flexconnect Access Points connected to the Wireless LAN Controller";
    }
    leaf arp-caching {
      type boolean;
      default "false";
      description
        "This object specifies whether ARP cache feature is enabled for the flexconnect Access Points connected to the Wireless LAN Controller";
    }
    leaf cts-inline-tagging {
      type boolean;
      default "false";
      description
        "This object specifies whether cts inline tagging feature is enabled for the flexconnect Access Points connected to the Wireless LAN Controller";
    }
    leaf cts-rolebased-enforce {
      type boolean;
      default "false";
      description
        "This object specifies whether cts rolebased enforcement feature is enabled for flexconnect Access Points connected to the Wireless LAN Controller";
    }
    leaf cts-profile-name {
      type string;
      default "default-sxp-profile";
      description
        "This object specifies the cts sxp profile name";
    }
    leaf join-min-latency {
      type boolean;
      default "false";
      description
        "This object represents if this REAP AP should join controller which has least latency";
    }
    leaf radius-enable {
      type boolean;
      default "true";
      description
        "This parameter represents whether RADIUS is enabled";
    }
    leaf native-vlan-id {
      type uint32 {
        range "0 .. 4094";
      }
      default "0";
      description
        "This object defines the Native VLAN ID for the particular AP";
    }
    leaf vlan-enable {
      type boolean;
      default "true";
      description
        "This object indicates the availability of Native VLAN configured on this REAP";
    }
    leaf http-proxy-ip {
      type inet:ip-address;
      default "0.0.0.0";
      description
        "This object indicates HTTP proxy Ip address";
    }
    leaf http-proxy-port {
      type uint16 {
        range "0 .. 65535";
      }
      default "0";
      description
        "This object indicates HTTP proxy port";
    }
    leaf is-home-ap-enable {
      type boolean;
      default "false";
      description
        "This object represents if the APs connected to this profile/group are used as Home APs";
    }
    leaf is-radio-backhaul {
      type boolean;
      default "false";
      description
        "This object can be used to enable or disable WLAN on backhaul radio";
    }
    leaf is-resilient-mode {
      type boolean;
      default "false";
      description
        "This object can be used to enable or disable Standalone mode support on a REAP AP.";
    }
    leaf efficient-ap-upgrade-enable {
      type boolean;
      default "true";
      description
        "This parameter represents whether Efficient AP image upgrade is enabled";
    }
    leaf slave-max-retry-count {
      type uint32;
      default "0";
      description
        "This object specifies the maximum retries the the slave has to undertake to start the download from the master in the hreap group";
    }
    container vlan-acls {
      description
        "VLAN ACLs";
      list vlan-acl {
        key "vlan-id";
        description
          "List of VLAN ACLs";
        uses wireless-flex-cfg:vlan-acl-list;
      }
    }
    container policy-acls {
      description
        "Policy ACLs";
      list policy-acl {
        key "acl-name";
        description
          "List of Policy ACLs";
        uses wireless-flex-cfg:policy-acl-list;
      }
    }
    container local-auth-users {
      description
        "Local auth users";
      list local-auth-user {
        key "user-name";
        description
          "List of Local auth users";
        uses wireless-flex-cfg:local-auth-user-list;
      }
    }
    container if-name-vlan-ids {
      description
        "Interface name vlan IDs";
      list if-name-vlan-id {
        key "interface-name";
        description
          "This object specifies the interface name vlan id list";
        uses wireless-flex-cfg:if-name-vlan-id-list;
      }
    }
  }

  grouping st-split-tunnel {
    description
      "Configuration of Split tunnel";
    leaf split-tunnel-enabled {
      type boolean;
      description
        "Enable or Disable split tunnel";
    }
    leaf acl-name {
      type string {
        length "0..31" {
          error-message "Invalid string length for acl name:Valid string has be 0 to 32 characters";
          error-app-tag "must-violation";
        }
      }
      description
        "ACL in split tunnel";
    }
    leaf split-tunnel-override {
      type boolean;
      description
        "Split tunnel override";
    }
    leaf split-tunnel-gateway {
      type inet:ip-address;
      description
        "Gateway for split tunnel";
    }
    leaf split-tunnel-netmask {
      type inet:ip-address;
      description
        "Netmask for split tunnel";
    }
  }

  grouping st-multi-domain-vlans {
    description
      "Configure voice and data vlan's";
    leaf voice-vlan-id {
      type uint16;
      description
        "Configure voice vlan id";
    }
    leaf data-vlan-id {
      type uint16;
      description
        "Configure data vlan id";
    }
  }

  grouping st-rlan-profiling {
    description
      "Configures Client profiling on RLAN";
    leaf radius-profiling {
      type boolean;
      description
        "Configures Client profiling on RLAN in Radius mode";
    }
    leaf radius-dhcp-profiling {
      type boolean;
      description
        "Configures Client profiling on RLAN in Radius mode based on dhcp attribute";
    }
    leaf http-tlv-caching {
      type boolean;
      description
        "Configures HTTP TLV caching on RLAN";
    }
    leaf dhcp-tlv-caching {
      type boolean;
      description
        "Configures DHCP TLV caching on RLAN";
    }
  }

  grouping st-flow-monitor {
    description
      "Flexible Netflow configuration";
    leaf flow-monitor-ingress-name {
      type string {
        length "1..32" {
          error-message "Invalid string length for Wireless flow monitor ingress names:Valid string has be 1 to 32 characters";
          error-app-tag "must-violation";
        }
      }
      must "../../central-switching = 'true' and ../ingress-enable = 'true' " {
        error-message "RLAN switching policy central-switching and ingress-enable should be enabled when using flow monitors";
        error-app-tag "must-violation";
      }
      description
        "Enable flow monitor on ingress traffic";
    }
    leaf flow-monitor-egress-name {
      type string {
        length "1..32" {
          error-message "Invalid string length for Wireless flow monitor egress names:Valid string has be 1 to 32 characters";
          error-app-tag "must-violation";
        }
      }
      must "../../central-switching = 'true' and ../egress-enable = 'true' " {
        error-message "RLAN switching policy central-switching and egress-enable should be enabled when using flow monitors";
        error-app-tag "must-violation";
      }
      description
        "Enable flow monitor on egress traffic";
    }
    leaf ingress-enable {
      type boolean;
      must "../../central-switching = 'true' and (string-length(../flow-monitor-ingress-name) > 0)" {
        error-message "RLAN switching policy central-switching should be enabled and ingress-name must be entered when using flow monitors";
        error-app-tag "must-violation";
      }
      description
        "Enable/Disable flow monitor on ingress traffic";
    }
    leaf egress-enable {
      type boolean;
      must "../../central-switching = 'true' and (string-length(../flow-monitor-egress-name) > 0)" {
        error-message "RLAN switching policy central-switching should be enabled and egress-name must be entered when using flow monitors";
        error-app-tag "must-violation";
      }
      description
        "Enable/Disable flow monitor on egress traffic";
    }
  }

  grouping blacklist-params {
    description
      "Set client blacklisting listing on RLAN";
    leaf is-blacklist-enabled {
      type boolean;
      default "true";
      description
        "Enable/Disable blacklisting";
    }
    leaf blacklist-timeout {
      type uint32 {
        range "0 .. 2147483647";
      }
      default "60";
      description
        "Set time the client will be excluded";
    }
  }

  grouping st-rlan-policy-profile-config {
    description
      "Remote lan policy profile";
    leaf profile-name {
      type string {
        length "1..32" {
          error-message "Invalid string length for Remote lan Policy Profile name:Valid string has be 1 to 32 characters";
          error-app-tag "must-violation";
        }
      }
      description
        "Remote Lan Policy Profile Name";
    }
    leaf status {
      type boolean;
      default "false";
      description
        "Remote Lan Policy Profile status";
    }
    leaf description {
      type string;
      default "";
      description
        "Remote Lan Policy Profile Description";
    }
    leaf ipv4-acl {
      type string {
        length "0..31" {
          error-message "Invalid string length for ipv4 acl name:Valid string has be 0 to 32 characters";
          error-app-tag "must-violation";
        }
      }
      description
        "Name of IPV4 ACL";
    }
    leaf ipv6-acl {
      type string {
        length "0..31" {
          error-message "Invalid string length for ipv6 acl name:Valid string has be 0 to 32 characters";
          error-app-tag "must-violation";
        }
      }
      description
        "Configure the name of IPV6 ACL";
    }
    leaf aaa-override {
      type boolean;
      default "false";
      description
        "Enable or Disable AAA override for the global RLAN parameters.";
    }
    leaf aaa-policy-name {
      type string;
      default "default-aaa-policy";
      description
        "This object specifies the aaa policy name.";
    }
    leaf central-switching {
      type boolean;
      default "true";
      description
        "Enable or Disable central switching";
    }
    leaf central-dhcp {
      type boolean;
      description
        "Enable or Disable central dhcp";
    }
    leaf interface-name {
      type string;
      default "1";
      description
        "This object specifies the name of the Vlan name for the vlan-acl mapping.";
    }
    leaf poe {
      type boolean;
      description
        "Enable or Disable poe";
    }
    leaf host-mode {
      type wireless-types:enm-host-mode;
      default "single-host-mode";
      description
        "Configure the host mode for the remote lan";
    }
    container host-mode-vlans {
      description
        "Change the host mode vlan for the remote lan";
      uses wireless-flex-cfg:st-multi-domain-vlans;
    }
    leaf violation-mode {
      type wireless-types:enm-violation-mode;
      description
        "the violation mode for the remote lan.";
    }
    container blacklist {
      description
        "Configure the blacklist for the remote lan";
      uses wireless-flex-cfg:blacklist-params;
    }
    leaf pre-auth {
      type boolean;
      description
        "Enable or Disable pre_auth";
    }
    container profiling {
      description
        "Configure the profiling for the remote lan";
      uses wireless-flex-cfg:st-rlan-profiling;
    }
    leaf session-timeout {
      type uint32 {
        range "20 .. 86400";
      }
      default "1800";
      description
        "Configure the session timeout for the remote lan";
    }
    container flow-monitor-ipv4 {
      description
        "Configure the flow monitor ipv4 for the remote lan";
      uses wireless-flex-cfg:st-flow-monitor;
    }
    container flow-monitor-ipv6 {
      description
        "Configure the flow monitor ipv6 for the remote lan";
      uses wireless-flex-cfg:st-flow-monitor;
    }
    container split-tunnel-param {
      description
        "Configure the split tunnel for the remote lan";
      uses wireless-flex-cfg:st-split-tunnel;
    }
    leaf dhcp-server {
      type inet:ip-address;
      description
        "Configure DHCP parameters for Remote-LAN";
    }
    leaf is-dhcp-enabled {
      type boolean;
      default "false";
      description
        "Configure DHCP enabled for Remote-LAN";
    }
    leaf accounting-list {
      type string;
      description
        "Configure the accounting list for IEEE 802.1x";
    }
  }

  grouping st-rlan-web-pre-auth-acl {
    description
      "Configuration of RLAN Web ACL";
    leaf ipv4-acl {
      type string {
        length "0..31" {
          error-message "Invalid string length for ipv4 acl name:Valid string has be 0 to 32 characters";
          error-app-tag "must-violation";
        }
      }
      description
        "Configure IPv4 RLAN Web ACL";
    }
    leaf ipv6-acl {
      type string {
        length "0..31" {
          error-message "Invalid string length for ipv6 acl name:Valid string has be 0 to 32 characters";
          error-app-tag "must-violation";
        }
      }
      description
        "Configure IPv6 RLAN Web ACL";
    }
  }

  grouping st-rlan-config {
    description
      "Configure remote lan profile";
    leaf rlan-id {
      type uint32 {
        range "1 .. 128";
      }
      description
        "Remote Lan Profile Id";
    }
    leaf profile-name {
      type string;
      description
        "Remote Lan Profile Name";
    }
    leaf mac-filtering {
      type string;
      description
        "Mac filtering on remote lan";
    }
    leaf auth-list {
      type string;
      description
        "Configure auth list on remote lan";
    }
    leaf security-8021x-dot1x {
      type boolean;
      description
        "Configures 802.1X";
    }
    leaf auth-list-dot1x {
      type string;
      description
        "Configures security web auth";
    }
    leaf security-web-auth {
      type boolean;
      description
        "Configures security web auth";
    }
    leaf local-auth-eap-profile-name {
      type string;
      description
        "Configure the EAP profile on a Remote-LAN";
    }
    leaf local-eap-auth-enabled {
      type boolean;
      description
        "Enable/Disable the EAP profile on a Remote-LAN";
    }
    leaf web-auth-parameter-map {
      type string;
      description
        "Configure parameter map on a Remote-LAN";
    }
    leaf max-associated-clients {
      type uint32;
      default "0";
      description
        "Configure maximum client connections per Remote-LAN";
    }
    leaf status {
      type boolean;
      default "false";
      description
        "Remote Lan Profile status";
    }
    container web-pre-auth-acl {
      description
        "Configure Web ACL for Remote-LAN";
      uses wireless-flex-cfg:st-rlan-web-pre-auth-acl;
    }
  }

  container flex-cfg-data {
    description
      "Yang model for configuring site";
    container flex-policy-entries {
      description
        "Flex policy profile configuration";
      list flex-policy-entry {
        key "policy-name";
        description
          "This object specifies the flex profile name mapped to the site tag";
        uses wireless-flex-cfg:flex-policy-config;
      }
    }
    container rlan-configs {
      description
        "RLAN profile configuration";
      list rlan-config {
        key "rlan-id";
        unique "profile-name";
        description
          "This object specifies the RLAN profile";
        uses wireless-flex-cfg:st-rlan-config {
          refine "profile-name" {
            mandatory true;
          }
        }
      }
    }
    container rlan-policy-profile-configs {
      description
        "RLAN policy profile configuration";
      list rlan-policy-profile-config {
        key "profile-name";
        description
          "This object specifies the RLAN policy profile";
        uses wireless-flex-cfg:st-rlan-policy-profile-config;
      }
    }
  }
}
