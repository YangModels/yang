module Cisco-IOS-XE-sla {
  namespace "http://cisco.com/ns/yang/Cisco-IOS-XE-sla";
  prefix ios-sla;


  import ietf-inet-types {
    prefix inet;
  }

  import Cisco-IOS-XE-native {
    prefix ios;
  }

  import Cisco-IOS-XE-types {
    prefix ios-types;
  }

  organization
    "Cisco Systems, Inc.";

  contact
    "Cisco Systems, Inc.
     Customer Service
     Postal: 170 W Tasman Drive
     San Jose, CA 95134
     Tel: +1 1800 553-NETS
     E-mail: cs-yang@cisco.com";

  description
    "Cisco XE Native Service Level Agreements (SLA) Yang model.
     Copyright (c) 2016, 2018 by Cisco Systems, Inc.
     All rights reserved.";

  // =========================================================================
  // REVISION
  // =========================================================================
  revision 2018-08-03 {
    description
      "Added loss support for ethernet-y1731.";
  }

  revision 2018-07-04 {
    description
      "Add icmp-jitter, tcp-connect, dns cases and its options. Add
       other options for the existing cases.";
  }

  revision 2018-06-28{
    description
        "Added leafref for ip sla schedule entry-number";
  }

  revision 2018-05-23 {
    description
      "Add http-raw request support and the other options for http probe";
  }
  revision 2018-04-11 {
    description
      "Add source-port, control and codec options for ip sla udp-jitter probe";
  }
  revision 2018-01-15 {
    description
      "Add ethernet case and its options under ip sla";
  }
  revision 2017-08-31 {
    description
      "Add dependency between ip sla schedule and ip sla reaction configuration";
  }
  revision 2017-08-03 {
    description
      "Add depedency between ip sla schedule and ip sla entry";
  }
  revision 2017-02-07 {
    description
      "Initial revision";
  }

  grouping ip-sla-sub-mode-commands-grouping {
    leaf owner {
      description
        "Owner of Entry";
      type string;
    }
    leaf tag {
      description
        "User defined tag";
      type string;
    }
    leaf threshold {
      description
        "Operation threshold in milliseconds";
      units miliseconds;
      type uint32 {
        range "0..60000";
      }
    }
    leaf timeout {
      description
        "Timeout of an operation";
      units miliseconds;
      type uint32 {
        range "0..604800000";
      }
    }
    leaf frequency {
      description
        "Frequency of an operation";
      units seconds;
      type uint32 {
        range "1..604800";
      }
    }
  }

  grouping ip-sla-full-history-grouping {
    container history {
    description
      "History and Distribution Data";
      container enhanced {
        description
          "Enable enhanced history collection";
        leaf interval {
          description
            "Aggregation interval";
          type uint16 {
            range "1..3600";
          }
        }
        leaf buckets {
          description
            "Number of buckets to collect data";
          type uint8 {
            range "1..100";
          }
        }
      }
      leaf buckets-kept {
          description
            "Maximum number of history buckets to collect";
          type uint8;
      }
      leaf distributions-of-statistics-kept {
        description
          "Maximum number of statistics distribution buckets to capture";
        type uint8;
      }
      leaf filter {
        description
          "Add operation to History when...";
        type enumeration {
          enum "all";
          enum "failures";
          enum "none";
          enum "overThreshold";
        }
      }
      leaf hours-of-statistics-kept {
        description
          "Maximum number of statistics hour groups to capture";
        type uint8 {
          range "0..25";
        }
      }
      leaf lives-kept {
        description
          "Maximum number of history lives to collect";
        type uint8 {
          range "0..2";
        }
      }
      leaf statistics-distribution-interval {
        description
          "Statistics distribution interval size";
        type uint8 {
          range "1..100";
        }
      }
    }
  }

  grouping ip-sla-history-without-enhanced-grouping {
    container history {
    description
      "History and Distribution Data";
      leaf buckets-kept {
        description
          "Maximum number of history buckets to collect";
        type uint8;
      }
      leaf distributions-of-statistics-kept {
        description
          "Maximum number of statistics distribution buckets to capture";
        type uint8;
      }
      leaf filter {
        description
          "Add operation to History when...";
        type enumeration {
          enum "all";
          enum "failures";
          enum "none";
          enum "overThreshold";
        }
      }
      leaf hours-of-statistics-kept {
        description
          "Maximum number of statistics hour groups to capture";
        type uint8 {
          range "0..25";
        }
      }
      leaf lives-kept {
        description
          "Maximum number of history lives to collect";
        type uint8 {
          range "0..2";
        }
      }
      leaf statistics-distribution-interval {
        description
          "Statistics distribution interval size";
        type uint8 {
          range "1..100";
        }
      }
    }
  }

  grouping ip-sla-path-echo-grouping {
    leaf paths-of-statistics-kept {
      description
              "Maximum number of statistics paths to capture";
      type uint8 {
    	  range "1..128";
      }
    }
    leaf samples-of-history-kept {
      description
        "Maximum number of history samples to collect";
      type uint8 {
        range "1..30";
      }
    }
    leaf hops-of-statistics-kept {
      description
        "Maximum number of statistics hops to capture";
      type uint8 {
        range "1..30";
      }
    }
    leaf-list lsr-path {
      description
        "Loose Source Routing Path";
      type union {
        type string;
        type inet:ipv4-address;
      }
    }
    leaf request-data-size {
      description
        "Request data size";
      type uint32 {
        range "0..16384";
      }
    }
    choice tos-param {
      case tos {
        leaf tos {
          description
            "Type Of Service";
          type uint8 {
            range "0..255";
          }
        }
      }
      case traffic-class {
        leaf traffic-class {
          description
            "Traffic class";
         type uint8 {
            range "0..255";
          }
        }
      }
    }
    leaf verify-data {
      description
        "Verify data";
      type empty;
    }
    leaf vrf {
      description
        "Configure IP SLAs for a VPN Routing/Forwarding instance";
      type string;
    }
    uses ip-sla-history-without-enhanced-grouping;
  }

  grouping ip-sla-path-jitter-grouping {
    leaf-list lsr-path {
      description
        "Loose Source Routing Path";
      type union {
        type string;
        type inet:ipv4-address;
      }
    }
    leaf request-data-size {
      description
        "Request data size";
      type uint32 {
        range "0..16384";
      }
    }
    choice tos-param {
      case tos {
        leaf tos {
          description
            "Type Of Service";
          type uint8 {
            range "0..255";
          }
        }
      }
      case traffic-class {
        leaf traffic-class {
          description
            "Traffic class";
         type uint8 {
            range "0..255";
          }
        }
      }
    }
    leaf flow-label {
      description "Flow Label Value for IPv6 destination";
      type uint64 {
        range "0..1048575";
      }
    }
    leaf verify-data {
      description
        "Verify data";
      type empty;
    }
    leaf vrf {
      description
        "Configure IP SLAs for a VPN Routing/Forwarding instance";
      type string;
    }
  }

  grouping ip-sla-default-path-jitter-grouping {
    leaf frequency {
      description
        "Frequency of an operation";
      type empty;
    }
    leaf lsr-path {
      description
        "Loose Source Routing Path";
      type empty;
    }
    leaf owner {
      description
        "Owner of Entry";
      type empty;
    }
    leaf request-data-size {
      description
        "Request data size";
      type empty;
    }
    leaf tag {
      description
        "User defined tag";
      type empty;
    }
    leaf threshold {
      description
        "Operation threshold in milliseconds";
      type empty;
    }
    leaf timeout {
      description
        "Timeout of an operation";
      type empty;
    }
    leaf tos {
      description
        "Type Of Service";
      type empty;
    }
    leaf verify-data {
      description
        "Verify data";
      type empty;
    }
    leaf vrf {
      description
        "Configure IP SLAs for a VPN Routing/Forwarding instance";
      type empty;
    }
  }

  grouping ip-sla-udp-jitter-grouping {
    container history {
      description
        "History and Distribution Data";
      leaf distributions-of-statistics-kept {
        description
          "Maximum number of statistics distribution buckets to capture";
        type uint8 {
          range "1..20";
        }
      }
      container enhanced {
        description
          "Enable enhanced history collection";
        leaf interval {
          description
            "Aggregation interval";
          type uint16 {
            range "1..3600";
          }
        }
        leaf buckets {
          description
            "Number of buckets to collect data";
          type uint8 {
            range "1..100";
          }
        }
      }
      leaf hours-of-statistics-kept {
        description "Maximum number of statistics hour groups to capture";
        type uint8 {
          range "0..25";
        }
      }
      leaf statistics-distribution-interval {
        description "Statistics distribution interval size";
        type uint8 {
          range "1..100";
        }
      }
    }
    leaf data-pattern {
      description
        "Data Pattern in Hex 0-FFFFFFFF";
      type string;
    }
    leaf request-data-size {
      description
      "Number of bytes in payload";
      type uint16 {
        range "16..17512";
      }
    }
    leaf response-data-size {
      description
      "Number of bytes in response payload";
      type uint16 {
        range "20..17512";
      }
    }
    choice tos-param {
      case tos {
        leaf tos {
          description
            "Type Of Service";
          type uint8 {
            range "0..255";
          }
        }
      }
      case traffic-class {
        leaf traffic-class {
          description
            "Traffic class";
         type uint8 {
            range "0..255";
          }
        }
      }
    }
    leaf vrf {
      description
        "Configure IP SLAs for a VPN Routing/Forwarding instance";
      type string;
    }
    leaf verify-data {
      description
        "Verify data";
      type empty;
    }
    leaf precision {
      description "Set precision of measurement";
      type enumeration {
        enum "microseconds" {
        }
        enum "milliseconds" {
        }
      }
    }
    leaf optimize{
      description
        "Optimize timestamp of measurement";
      type enumeration {
        enum "timestamp" {
        }
      }
    }
    leaf enhanced {
      description
        "Improve the accuracy of measurement";
      type enumeration {
        enum "timestamp" {
        }
      }
    }
    leaf operation-packet-priority {
      description
        "Set operation packet properties";
      type enumeration {
        enum "high" {
        }
        enum "low" {
        }
      }
    }
    container clock-tolerance {
      description "Set acceptable clock synchronization error";
      presence true;
      container ntp {
        description
          "Acceptable clock synchronization error due to NTP";
        presence true;
        container oneway {
          description
            "Acceptable clock synchronization error in oneway measurement";
          choice clock-tolerance-param {
            case absolute-type {
              leaf absolute {
                description "Acceptable error in microseconds";
                type uint32 {
                  range "0..100000";
                }
              }
            }
            case percent-type {
              leaf percent {
                description
                  "Acceptable error as percent of value measured";
                type uint8 {
                  range "0..100";
                }
              }
            }
          } // end choice
        } // end container oneway
      } // end ntp
    } // end clock-tolerance
  }

  grouping ip-sla-udp-echo-grouping {
    uses ip-sla-full-history-grouping;
    leaf request-data-size {
      description
      "Number of bytes in payload";
      type uint16 {
        range "16..17512";
      }
    }
    choice tos-param {
      case tos {
        leaf tos {
          description
            "Type Of Service";
          type uint8 {
            range "0..255";
          }
        }
      }
      case traffic-class {
        leaf traffic-class {
          description
            "Traffic class";
         type uint8 {
            range "0..255";
          }
        }
      }
    }
    leaf vrf {
      description
        "Configure IP SLAs for a VPN Routing/Forwarding instance";
      type string;
    }
    leaf data-pattern {
      description
        "Data Pattern in Hex 0-FFFFFFFF";
      type string;
    }
  }

  grouping ip-sla-ethernet-delay-grouping {
    container aggregate {
      description
        "Aggregate parameters";
      leaf interval {
        description
          "Specify interval period";
        type uint32 {
          range "1..65535";
        }
      }
    }
    container history {
      description
        "History parameters";
      leaf interval {
        description
          "Specify number of intervals";
        type uint8 {
          range "1..10";
        }
      }
    }
  }//end grouping

  grouping config-ip-sla-grouping {
    container sla {
      description
        "IP Service Level Agreement";
      list entry {
        key "number";
        leaf number {
          type uint32;
        }
        choice sla-param {
          case icmp-echo-case {
            container icmp-echo {
              description
                "ICMP Echo Operation";
              leaf destination {
                type union {
                  type string;
                  type inet:ipv4-address;
                }
              }
              choice source-param {
                case source-interface {
                  leaf source-interface {
                    description
                      "Source Interface (ingress icmp packet interface)";
                    type string;
                  }
                }
                case source-ip {
                  leaf source-ip {
                    description
                      "Source Address";
                    type union {
                      type string;
                      type inet:ipv4-address;
                    }
                  }
                }
              }
              leaf data-pattern {
                description
                  "Data Pattern";
                type string;
              }
              uses ip-sla-sub-mode-commands-grouping;
              uses ip-sla-full-history-grouping;
              leaf request-data-size {
                description
                  "Request data size";
                type uint32 {
                  range "0..16384";
                }
              }
              choice tos-param {
                case tos {
                  leaf tos {
                    description
                      "Type Of Service";
                    type uint8 {
                      range "0..255";
                    }
                  }
                }
                case traffic-class {
                  leaf traffic-class {
                    description
                      "Traffic class";
                   type uint8 {
                      range "0..255";
                    }
                  }
                }
              }
              leaf verify-data {
                description
                  "Verify data";
                type empty;
              }
              leaf vrf {
                description
                  "Configure IP SLAs for a VPN Routing/Forwarding instance";
                type string;
              }
            }
          } // end icmp-echo-case
          case icmp-jitter-case {
            container icmp-jitter {
              description "ICMP-jitter Operations";
              leaf dst-ip {
                description
                "Destination IP address or hostname, broadcast disallowed";
                type union {
                  type string;
                  type inet:ipv4-address;
                }
              }
              leaf interval {
                description
                  "Inter Packet Interval";
                units milliseconds;
                type uint16 {
                  range "4..60000";
                }
              }
              leaf num-packets {
                description
                  "Number of Packets to be transmitted";
                units packets;
                type uint16 {
                  range "1..60000";
                }
              }
              leaf source-ip {
                description
                  "IP address or hostname, broadcast disallowed";
                type union {
                  type string;
                  type inet:ipv4-address;
                }
              }
              uses ip-sla-sub-mode-commands-grouping;
              container history {
                description
                  "History and Distribution Data";
                leaf distributions-of-statistics-kept {
                  description
                    "Maximum number of statistics distribution buckets to capture";
                  type uint8 {
                    range "1..20";
                  }
                }
                container enhanced {
                  description
                    "Enable enhanced history collection";
                  leaf interval {
                    description
                      "Aggregation interval";
                    type uint16 {
                      range "1..3600";
                    }
                  }
                  leaf buckets {
                    description
                      "Number of buckets to collect data";
                    type uint8 {
                      range "1..100";
                    }
                  }
                }
                leaf hours-of-statistics-kept {
                  description
                    "Maximum number of statistics hour groups to capture";
                  type uint8 {
                    range "0..25";
                  }
                }
                leaf statistics-distribution-interval {
                  description
                    "Statistics distribution interval value in msec";
                  units milliseconds;
                  type uint8 {
                    range "1..100";
                  }
                }
              } // end History
              leaf tos {
                description
                  "Type Of Service";
                type uint8;
              }
              leaf vrf {
                description
                  "Configure IP SLAs for a VPN Routing/Forwarding instance";
                type string;
              }
            }// end imcp-jitter
          } // end icmp-jitter case
          case path-echo-case {
            container path-echo {
              description
                "Path Discovered ICMP Echo Operation";
              leaf dst-ip {
                description
                  "Destination IP address or hostname, broadcast disallowed";
                type union {
                  type string;
                  type inet:ipv4-address;
                }
              }
              leaf source-ip {
                description
                  "IP address or hostname, broadcast disallowed";
                type union {
                  type string;
                  type inet:ipv4-address;
                }
              }
              uses ip-sla-sub-mode-commands-grouping;
              uses ip-sla-path-echo-grouping;
            }
          } // end path-echo-case
          case path-jitter-case {
            container path-jitter {
              description
                "Path Discovered ICMP Jitter Operation";
              leaf dst-ip {
                type union {
                  type string;
                  type inet:ipv4-address;
                  type inet:ipv6-address;
                }
              }
              leaf source-ip {
                description
                  "Source IP Address";
                type union {
                  type string;
                  type inet:ipv4-address;
                }
              }
              container default {
                description
                  "Set a command to its defaults";
                uses ip-sla-default-path-jitter-grouping;
              }
              uses ip-sla-sub-mode-commands-grouping;
              uses ip-sla-path-jitter-grouping;
            }
          } // end path-jitter-case
          case udp-echo-case {
            // ip sla * /udp-echo
            container udp-echo {
              description
               "UDP echo operation";
              leaf dest-addr {
                description
                 "Hostname or A.B.C.D  Destination IP address or hostname, broadcast disallowed";
                type union {
                  type inet:ip-address;
                  type string;
                }
              }
              leaf dest-port {
                description
                 "Port Number (Recommended ports greater than 1023)";
                type uint16 {
                  range "1..65535";
                }
              }
              leaf source-ip {
                description
                 "Source address: Hostname or A.B.C.D IP address or hostname, broadcast disallowed";
                type union {
                  type inet:ip-address;
                  type string;
                }
              }
              leaf source-port {
                description
                 "Source Port: Port Number (Recommended ports greater than 1023)";
                type uint16 {
                  range "1..65535";
                }
              }
              uses ip-sla-sub-mode-commands-grouping;
              uses ip-sla-udp-echo-grouping;
            }
          } // end udp-echo-case
          case udp-jitter-case {
            // ip sla * /udp-jitter
            container udp-jitter {
              description
                "UDP jitter operation";
              leaf dest-addr {
                description
                  "Hostname or A.B.C.D/X:X:X:X::X  Destination IP/IPv6 address";
                type union {
                  type inet:ip-address;
                  type inet:ipv6-address;
                  type string;
                }
              }
              leaf portno {
                description
                  "Port Number";
                type uint16 {
                  range "1..65535";
                }
              }
              choice type-param {
                case codec {
                   leaf codec {
                     description "codec type to be configured";
                     type enumeration {
                       enum "g711alaw" {
                       }
                       enum "g711ulaw" {
                       }
                       enum "g729a" {
                       }
                     }
                   }
                   leaf advantage-factor {
                     description "Advantage Factor";
                     type uint16 {
                       range "0..20";
                     }
                   }
                   leaf codec-interval {
                     description "Inter Packet Interval";
                     type uint32 {
                       range "4..60000";
                     }
                   }
                   leaf codec-numpackets {
                     description "Number of Packets";
                     type uint32 {
                       range "1..60000";
                     }
                   }
                   leaf codec-size {
                     description "Number of Packets";
                     type uint16 {
                       range "16..16384";
                     }
                   }
                }
                case non-codec {
                   leaf num-packets {
                     description "Number of Packets (default 10)";
                     type uint16 {
                       range "1..60000";
                     }
                   }
                   leaf interval {
                     description "Delay (default 20)";
                     type uint16 {
                       range "4..60000";
                     }
                   }
                }
              }
              leaf source-ip {
                description
                  "Hostname or A.B.C.D/X:X:X:X::X Source IP/IPv6 address";
                type union {
                  type inet:ip-address;
                  type inet:ipv6-address;
                  type string;
                }
              }
              leaf source-port {
                description
                  "Source port";
                type uint16 {
                  range "1..65535";
                }
              }
              leaf control {
                description "Enable or disable control packets";
                type enumeration {
                  enum "enable" {
                  }
                  enum "disable" {
                  }
                }
              }
              uses ip-sla-sub-mode-commands-grouping;
              uses ip-sla-udp-jitter-grouping;
            }
          } //end udp-jitter-case
          case http-case {
            //ip sla * / http
            container http {
              description
               "HTTP Operation";
              choice http-choice {
               case http-get {
                  container get {
                    description
                      "HTTP get operation";
                    leaf url {
                      description
                        "URL";
                      type string;
                    }
                    leaf cache {
                      description "Enable or Disable download of cached HTTP page";
                      type enumeration {
                        enum "enable" {
                        }
                        enum "disable" {
                        }
                      }
                    }
                    leaf source-ip {
                      description
                        "Source Hostname or A.B.C.D/X:X:X:X::X  IPv4/IPv6 address";
                      type union {
                        type inet:ipv6-address;
                        type inet:ip-address;
                        type string;
                      }
                    }
                    leaf source-port {
                      description
                        "Source port";
                      type uint16 {
                        range "1..65535";
                      }
                    }
                    leaf name-server {
                      description
                        "Hostname or A.B.C.D/X:X:X:X::X  IPv4/IPv6 address";
                      type union {
                        type string;
                        type inet:ip-address;
                        type inet:ipv6-address;
                      }
                    }
                    leaf proxy {
                      description "Proxy information string";
                      type string;
                    }
                    leaf version {
                      description "Http Version";
                      type enumeration {
                        enum "1.0" {
                        }
                        enum "1.1" {
                        }
                      }
                    }
                  }
                }
                case http-raw {
                  container raw {
                    description
                      "HTTP raw operation";
                    leaf url {
                      type string;
                    }
                    leaf cache {
                      description "Enable or Disable download of cached HTTP page";
                      type enumeration {
                        enum "enable" {
                        }
                        enum "disable" {
                        }
                      }
                    }
                    leaf source-ip {
                      description
                        "Source Hostname or A.B.C.D/X:X:X:X::X  IPv4/IPv6 address";
                      type union {
                        type inet:ip-address;
                        type inet:ipv6-address;
                        type string;
                      }
                    }
                    leaf source-port {
                      description
                        "Source port";
                      type uint16 {
                        range "1..65535";
                      }
                    }
                    leaf name-server {
                      description
                        "Hostname or A.B.C.D/X:X:X:X::X  IPv4/IPv6 address";
                      type union {
                        type string;
                        type inet:ip-address;
                        type inet:ipv6-address;
                      }
                    }
                    leaf proxy {
                      description "Proxy information string";
                      type string;
                    }
                    leaf version {
                      description "Http Version";
                      type enumeration {
                        enum "1.0" {
                        }
                        enum "1.1" {
                        }
                      }
                    }
                  }
                }
              }
              //http submode CMDs:
              leaf owner {
                description
                  "Owner of Entry";
                type string;
              }
              leaf tag {
                description
                  "User defined tag";
                type string;
              }
              leaf threshold {
                description
                  "Operation threshold in milliseconds";
                units miliseconds;
                type uint32 {
                  range "0..60000";
                }
              }
              leaf timeout {
                description
                  "Timeout of an operation";
                units miliseconds;
                type uint32 {
                  range "0..604800000";
                }
              }
              leaf frequency {
                description
                  "Frequency of an operation";
                units seconds;
                type uint32 {
                  range "60..604800";
                }
              }
              container history {
                description
                  "History and Distribution Data";
                leaf distributions-of-statistics-kept {
                  description
                    "Maximum number of statistics distribution buckets to capture";
                  type uint8;
                }
                leaf hours-of-statistics-kept {
                  description
                    "Maximum number of statistics hour groups to capture";
                  type uint8 {
                    range "0..25";
                  }
                }
                leaf statistics-distribution-interval {
                  description
                    "Statistics distribution interval size";
                  type uint8 {
                    range "1..100";
                  }
                }
              }
              leaf http-status-code-ignore {
                description "HTTP Status Code Check Disable";
                type empty;
              }
              leaf vrf {
                description
                  "Configure IP SLAs for a new VPN Routing/Forwarding instance";
                type string;
              }
              choice tos-param {
                case tos {
                  leaf tos {
                    description
                      "Type Of Service";
                    type uint8 {
                      range "0..255";
                    }
                  }
                }
                case traffic-class {
                  leaf traffic-class {
                    description
                      "Traffic class";
                   type uint8 {
                      range "0..255";
                    }
                  }
                }
              }
              container http-raw-request {
                description "HTTP Raw Request configuration";
                leaf raw-request-string {
                   description "HTTP Raw string";
                   type string;
                }
              }
            } // end ip sla http
          } // end http-case
          case dhcp-case {
            container dhcp {
              description
                "DHCP Operation";
              leaf dst-ip {
                description
                  "Destination IP address or hostname, broadcast disallowed";
                type union {
                  type string;
                  type inet:ipv4-address;
                }
              }
              leaf source-ip {
                description
                  "IP address or hostname, broadcast disallowed";
                type union {
                  type string;
                  type inet:ipv4-address;
                }
              }
              uses ip-sla-sub-mode-commands-grouping;
              uses ip-sla-history-without-enhanced-grouping;
            } //end ip sla dhcp
          }//end dhcp-case
          case tcp-connect-case {
            container tcp-connect {
              description
               "TCP connect operation";
              leaf dest-addr {
                description
                 "Destination IPv6/IP address or hostname";
                type union {
                  type inet:ip-address;
                  type inet:ipv6-address;
                  type string;
                }
              }
              leaf dest-port {
                description
                 "Port Number (Recommended ports greater than 1023)";
                type uint16 {
                  range "1..65535";
                }
              }
              leaf source-ip {
                description
                 "Source IPv6/IP address or hostname";
                type union {
                  type inet:ip-address;
                  type inet:ipv6-address;
                  type string;
                }
              }
              leaf source-port {
                description
                 "Source Port: Port Number (Recommended ports greater than 1023)";
                type uint16 {
                  range "1..65535";
                }
              }
              leaf control {
                description "Enable or disable control packets";
                type enumeration {
                  enum "enable" {
                  }
                  enum "disable" {
                  }
                }
              }
              uses ip-sla-sub-mode-commands-grouping;
              uses ip-sla-full-history-grouping;
              choice tos-param {
                case tos {
                  leaf tos {
                    description
                      "Type Of Service";
                    type uint8 {
                      range "0..255";
                    }
                  }
                }
                case traffic-class {
                  leaf traffic-class {
                    description
                      "Traffic class";
                   type uint8 {
                      range "0..255";
                    }
                  }
                }
              }
              leaf vrf {
                description
                  "Configure IP SLAs for a VPN Routing/Forwarding instance";
                type string;
              }
            } // tcp-connect
          } // end choice tcp
          case dns-case {
            container dns {
              description
               "DNS operation";
              leaf dest-addr {
                description
                 "Destination IPv6/IP address or hostname";
                type union {
                  type inet:ip-address;
                  type inet:ipv6-address;
                  type string;
                }
              }
              leaf name-server {
                description
                 "Name Server: IPv6/IP address or hostname";
                type union {
                  type inet:ip-address;
                  type inet:ipv6-address;
                  type string;
                }
              }
              leaf source-ip {
                description
                 "Source IPv6/IP address or hostname";
                type union {
                  type inet:ip-address;
                  type inet:ipv6-address;
                  type string;
                }
              }
              leaf source-port {
                description
                 "Source Port: Port Number (Recommended ports greater than 1023)";
                type uint16 {
                  range "1..65535";
                }
              }
              uses ip-sla-sub-mode-commands-grouping;
              uses ip-sla-history-without-enhanced-grouping;
              leaf vrf {
                description
                  "Configure IP SLAs for a VPN Routing/Forwarding instance";
                type string;
              }
            } // end dns
          } // end dns case
          case ftp-case {
            container ftp {
              description
               "DNS operation";
              container get {
                presence true;
                description
                  "FTP get operation";
                leaf url {
                  description
                   "URL";
                  type union {
                    type string;
                  }
                }
                leaf mode {
                  description
                   "Specify mode to be used";
                  type enumeration {
                    enum "active" {
                    }
                    enum "passive" {
                    }
                  }
                }
                leaf source-ip {
                  description
                   "Source IPv6/IP address or hostname";
                  type union {
                    type inet:ip-address;
                    type inet:ipv6-address;
                    type string;
                  }
                }
                uses ip-sla-sub-mode-commands-grouping;
                uses ip-sla-full-history-grouping;
              } // end ftp get
            } // end ftp
          } // end ftp case
          case ethernet-case {
            container ethernet {
              description
                "Ethernet Operations";

              container y1731 {
                description
                  "Y1731 Ethernet OAM Performance Measurement Operations";
                container delay {
                  description
                    "Y1731 Delay and Delay Variation Operation";
                  leaf name {
                    description
                      "Y1731 Delay option";
                    type enumeration {
                      enum "1DM";
                      enum "DMM";
                      enum "DMMv1";
                    }
                  }

                  leaf burst {
                    description
                      "Enable bursting of delay frames";
                    type empty;
                  }

                  leaf domain {
                    description
                      "Specify the Ethernet OAM domain";
                    type string;
                  }

                  choice evc-or-vlan {
                     leaf evc {
                        description
                          "Specify the Ethernet Virtual Circuit Identifier";
                        type string;
                     }
                     leaf vlan {
                       description
                         "Specify the VLAN";
                       type uint16 {
                         range "1..4096";
                       }
                     }
                  }//evc-or-vlan-choice

                  choice mac-or-mpid {
                    leaf mac-address {
                      description
                        "Specify the remote mac-address";
                      type ios-types:cisco-mac-address-type;
                    }
                    leaf mpid {
                      description
                        "Specify the remote MPID";
                      type uint16 {
                        range "1..8191";
                      }
                    }
                  }//mac-or-mpid

                  leaf cos {
                    description
                      "Specify the Class of Service";
                    type uint8 {
                      range "0..7";
                    }
                  }

                  container source {
                    description
                      "Specify the local MPID or MAC-Address";
                    choice mac-or-mpid {
                        leaf mac-address {
                            description
                              "Specify the local mac-address";
                            type ios-types:cisco-mac-address-type;
                        }
                        leaf mpid {
                          description
                            "Specify the local MPID";
                          type uint16 {
                            range "1..8191";
                          }
                        }
                    }
                  }//source
                }//delay
                container loss {
                  description
                    "Y1731 Loss Operation";

                  leaf name {
                    description
                      "Y1731 Delay option";
                      type enumeration {
                        enum "LMM";
                        enum "SLM";
                      }
                    }

                    leaf burst {
                      description
                        "Enable bursting of delay frames. Applicable only to SLM option";
                      type empty;
                    }

                    leaf domain {
                      description
                        "Specify the Ethernet OAM domain";
                      type string;
                    }

                    choice evc-or-vlan {
                      leaf evc {
                        description
                          "Specify the Ethernet Virtual Circuit Identifier";
                        type string;
                      }
                      leaf vlan {
                        description
                          "Specify the VLAN";
                        type uint16 {
                          range "1..4096";
                        }
                      }
                    }//evc-or-vlan-choice

                    choice mac-or-mpid {
                      leaf mac-address {
                        description
                          "Specify the remote mac-address";
                        type ios-types:cisco-mac-address-type;
                      }
                      leaf mpid {
                        description
                          "Specify the remote MPID";
                        type uint16 {
                          range "1..8191";
                        }
                      }
                    }//mac-or-mpid

                    leaf cos {
                      description
                        "Specify the Class of Service";
                      type uint8 {
                        range "0..7";
                      }
                    }//cos

                    container source {
                      description
                        "Specify the local MPID or MAC-Address";
                      choice mac-or-mpid {
                        leaf mac-address {
                          description
                            "Specify the local mac-address";
                              type ios-types:cisco-mac-address-type;
                        }
                        leaf mpid {
                          description
                            "Specify the local MPID";
                          type uint16 {
                            range "1..8191";
                        }
                      }
                    }//mac-or-mpid
                  }//source
                }//loss
              }//y1731

              uses ip-sla-ethernet-delay-grouping;

            }//ethernet
          }//case

        } // end choice sla-param
      } // end ip sla entry

      // ip sla enable
      container enable {
        leaf reaction-alerts {
          type empty;
        }
      }
      // ip sla responder
      container responder {
        description "Enable IP SLAs Responder";
        presence true;
        container udp-echo {
          description "Setup udp-echo responder";
          leaf port {
            description "Permanent port";
            type uint16 {
              range "1..65535";
            }
          }
          list ipaddress {
            description "Permanent address";
            key "host";
            leaf host {
              type union {
                type inet:ipv4-address;
                type inet:ipv6-address;
              }
            }
            leaf port {
              description "Permanent port";
              type uint16 {
                range "1..65535";
              }
            }
          }
        }
        container tcp-connect {
          description "Setup tcp-connect responder";
          leaf port {
            description "Permanent port";
            type uint16 {
              range "1..65535";
            }
          }
          list ipaddress {
            description "Permanent address";
            key "host";
            leaf host {
              type union {
                type inet:ipv4-address;
                type inet:ipv6-address;
              }
            }
            leaf port {
              description "Permanent port";
              type uint16 {
                range "1..65535";
              }
            }
          }
        }
      }
      // ip sla logging
      container logging {
        description "low-memory";
        leaf traps {
          description "Enable syslog traps";
          type empty;
        }
      }
      // ip sla group
      container group {
        description "Group Configuration or Group Scheduling";
        list schedule {
          description "Group scheduling";
          key "entry-number";
          leaf entry-number {
            description "Group schedule entry number";
            type uint32 {
              range "1..2147483647";
            }
          }
          list probe-ids {
            key "word";
            leaf word {
              type string;
            }
            container schedule-period {
              description "Group schedule period range";
              leaf seconds {
                description "seconds";
                type uint32;
              }
              container frequency {
                description
                  "Group operation frequency";
                choice frequency-choice {
                  case frequency-value {
                    leaf frequency-val {
                      description
                        "Specify frequency in seconds";
                      type uint32;
                    }
                  }
                  case frequency-range {
                      leaf range {
                        description
                          "Group operation frequency-range for random scheduling";
                      type string;
                    }
                  }
                }
              }

              container start-time {
                description
                  "When to start this entry";
                leaf now {
                  description
                    "Start now";
                  type empty;
                }
              }

              leaf life {
                description
                  "Length of time to execute in seconds";
                type union {
                  type uint32;
                  type enumeration {
                    enum "forever";
                  }
                }
              }

            }// end container schedule-period

          }
        }
      }
      // ip sla schedule
      list schedule {
        description
          "Entry Scheduling";
        key "entry-number";
        leaf entry-number {
	  type leafref {
	    path "/ios:native/ios:ip/ios-sla:sla/ios-sla:entry/ios-sla:number";
          }
        }
        leaf ageout {
          description
            "How long to keep this Entry when inactive";
          type uint32 {
            range "0..2073600";
          }
        }
        leaf life {
          description
            "Length of time to execute in seconds";
          type union {
            type uint32;
            type enumeration {
              enum "forever";
            }
          }
        }
        leaf recurring {
          description
            "Probe to be scheduled automatically every day";
          type empty;
        }
        container start-time {
          description
            "When to start this entry";
          leaf after {
            description
              "Start after a certain amount of time from now";
            type string;
          }
          leaf hour-min {
            type string;
          }
          leaf hour-min-sec {
            type string;
          }
          leaf now {
            description
              "Start now";
            type empty;
          }
          leaf pending {
            description
              "Start pending";
            type empty;
          }
          leaf random {
            description
              "Start after random time (range)";
            type uint32 {
              range "500..10000";
            }
          }
        }
      }

      // ip sla reaction-configuration
      list reaction-configuration {
        description
          "IP SLA's reaction configuration";
        key "entry-number";
        leaf entry-number {
          description
            "Entry number";
          type uint64 {
            range "1..2147483647";
          }
        }

        // ip sla reaction-configuration * react
        container react {
          container connectionLoss {
            presence true;
            container threshold-type {
              container xOfy {
                leaf x-val {
                  description
                    "X value";
                  type uint8 {
                    range "1..16";
                  }
                }
                leaf y-val {
                  description
                    "Y value";
                  type uint8 {
                    range "1..16";
                  }
                }
                leaf action-type {
                  type enumeration {
                    enum "none";
                    enum "trapAndTrigger";
                    enum "trapOnly";
                    enum "triggerOnly";
                  }
                }
              }
            }
          }

          container rtt {
            presence true;
            container threshold-value {
              leaf upper-limit-val {
                description
                  "Upper limit";
                type uint32 {
                  range "1..60000";
                }
              }
              leaf lower-limit-val {
                description
                  "Lower limit";
                type uint32 {
                  range "1..60000";
                }
              }
              leaf threshold-type {
                description
                  "Threshold type";
                type enumeration {
                  enum "immediate";
                }
              }
              leaf action-type {
                type enumeration {
                  enum "none";
                  enum "trapAndTrigger";
                  enum "trapOnly";
                  enum "triggerOnly";
                }
              }
            }
          } //end rtt
        } //end react
      } //end reaction-configuration

      // ip sla server
      container server {
        description "IPPM server configuration";
        container twamp {
          description "IPPM TWAMP server configuration";
          presence "true";
        }
      }
    }
  }

  /////////////////////////////////////////////////////////
  // native / ip / sla
  /////////////////////////////////////////////////////////
  augment "/ios:native/ios:ip" {
    uses config-ip-sla-grouping;
  } //augment

}
