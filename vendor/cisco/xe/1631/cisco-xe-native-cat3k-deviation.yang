module cisco-xe-native-cat3k-deviation {
  namespace "http://cisco.com/ns/cisco-xe-native-cat3k-deviation";

  prefix nd;

  import ned {
    prefix ios;
  }

  organization
    "Cisco Systems, Inc.";

  contact
    "Cisco Systems, Inc.

     Customer Service

     Postal: 170 W Tasman Drive
     San Jose, CA 95134

     Tel: +1 1800 553-NETS

     E-mail: cs-yang@cisco.com";

  description
    "This module defines deviation statements for Cisco IOS ned
     module.";

  revision 2016-07-20 {
    description
      "Initial Revision";

    reference
      "RFC 6020: YANG - A Data Modeling Language for the
       Network Configuration Protocol (NETCONF)";
  }

  deviation /ios:native/ios:bridge-domain {
    deviate not-supported;
    description "Not supported in this release";
  }

  deviation /ios:native/ios:ethernet/ios:evc {
    deviate not-supported;
    description "Not supported in this release";
  }

  deviation /ios:native/ios:interface/ios:FastEthernet/ios:service {
    deviate not-supported;
    description "Not supported in this release";
  }

  deviation /ios:native/ios:interface/ios:GigabitEthernet/ios:service {
    deviate not-supported;
    description "Not supported in this release";
  }

  deviation /ios:native/ios:interface/ios:TenGigabitEthernet/ios:service {
    deviate not-supported;
    description "Not supported in this release";
  }

  deviation /ios:native/ios:interface/ios:Port-channel/ios:service {
    deviate not-supported;
    description "Not supported in this release";
  }

  deviation /ios:native/ios:interface/ios:Port-channel-subinterface/ios:Port-channel/ios:service {
    deviate not-supported;
    description "Not supported in this release";
  }

  deviation /ios:native/ios:interface/ios:Virtual-Template/ios:service {
    deviate not-supported;
    description "Not supported in this release";
  }

  deviation /ios:native/ios:interface/ios:VirtualPortGroup/ios:service {
    deviate not-supported;
    description "Not supported in this release";
  }

  deviation /ios:native/ios:interface/ios:overlay/ios:service {
    deviate not-supported;
    description "Not supported in this release";
  }

  deviation /ios:native/ios:interface/ios:vasileft/ios:service {
    deviate not-supported;
    description "Not supported in this release";
  }

  deviation /ios:native/ios:interface/ios:vasiright/ios:service {
    deviate not-supported;
    description "Not supported in this release";
  }

  // G.8032
  deviation /ios:native/ios:ethernet/ios:ring {
    deviate not-supported;
    description "Not supported in this release";
  }

  deviation /ios:native/ios:mpls/ios:traffic-eng {
    deviate not-supported;
    description "Not supported in this release";
  }

  // OTV
  deviation /ios:native/ios:otv {
    deviate not-supported;
    description "Not supported in this release";
  }

  deviation /ios:native/ios:interface/ios:overlay/ios:otv {
    deviate not-supported;
    description "Not supported in this release";
  }

  // PfR
  deviation /ios:native/ios:pfr {
    deviate not-supported;
    description "Not supported in this release";
  }

  deviation /ios:native/ios:pfr-map {
    deviate not-supported;
    description "Not supported in this release";
  }

  // EVPN / L2VPN / VFI
  deviation /ios:native/ios:l2/ios:vfi {
    deviate not-supported;
    description "Not supported in this release";
  }

  deviation /ios:native/ios:l2vpn {
    deviate not-supported;
    description "Not supported in this release";
  }

  deviation /ios:native/ios:platform/ios:l2vpn {
    deviate not-supported;
    description "Not supported in this release";
  }

  deviation /ios:native/ios:router/ios:bgp/ios:address-family/ios:no-vrf/ios:l2vpn {
    deviate not-supported;
    description "Not supported in this release";
  }
  
  deviation /ios:native/ios:xconnect {
    deviate not-supported;
    description "Not supported in this release";
  }
  
  // Service Insertion / WAAS
  deviation /ios:native/ios:service-insertion {
    deviate not-supported;
    description "Not supported in this release";
  }

  // Zone
  deviation /ios:native/ios:zone {
    deviate not-supported;
    description "Not supported in this release";
  }

  // Zone-Pair
  deviation /ios:native/ios:zone-pair {
    deviate not-supported;
    description "Not supported in this release";
  }

  deviation /ios:native/ios:module {
    deviate not-supported;
    description "Not supported in this release";
  }

  deviation /ios:native/ios:controller {
    deviate not-supported;
    description "Not supported in this release";
  }

  deviation /ios:native/ios:vmps {
    deviate not-supported;
    description "Not supported in this release";
  }

  deviation /ios:native/ios:mls {
    deviate not-supported;
    description "Not supported in this release";
  }

  deviation /ios:native/ios:policer {
    deviate not-supported;
    description "Not supported in this release";
  }

  deviation /ios:native/ios:pseudowire-class {
    deviate not-supported;
    description "Not supported in this release";
  }

  deviation /ios:native/ios:gatekeeper {
    deviate not-supported;
    description "Not supported in this release";
  }

  deviation /ios:native/ios:mgcp {
    deviate not-supported;
    description "Not supported in this release";
  }

  deviation /ios:native/ios:mac-address-table/ios:evc-xconnect {
    deviate not-supported;
    description "Not supported in this release";
  }

  deviation /ios:native/ios:vpdn {
    deviate not-supported;
    description "Not supported in this release";
  }

  deviation /ios:native/ios:bba-group {
    deviate not-supported;
    description "Not supported in this release";
  }

  deviation /ios:native/ios:ptp {
    deviate not-supported;
    description "Not supported in this release";
  }

  deviation /ios:native/ios:esmc {
    deviate not-supported;
    description "Not supported in this release";
  }

  deviation /ios:native/ios:setup {
    deviate not-supported;
    description "Not supported in this release";
  }

  deviation /ios:native/ios:tod-clock {
    deviate not-supported;
    description "Not supported in this release";
  }

  deviation /ios:native/ios:l3vpn {
    deviate not-supported;
    description "Not supported in this release";
  }

  deviation /ios:native/ios:virtual-service {
    deviate not-supported;
    description "Not supported in this release";
  }

  deviation /ios:native/ios:segment-routing {
    deviate not-supported;
    description "Not supported in this release";
  }

  deviation /ios:native/ios:dot11 {
    deviate not-supported;
    description "Not supported in this release";
  }

  deviation /ios:native/ios:voice {
    deviate not-supported;
    description "Not supported in this release";
  }

  deviation /ios:native/ios:voice-card {
    deviate not-supported;
    description "Not supported in this release";
  }

  deviation /ios:native/ios:card {
    deviate not-supported;
    description "Not supported in this release";
  }

  deviation /ios:native/ios:memory-size {
    deviate not-supported;
    description "Not supported in this release";
  }

  deviation /ios:native/ios:onep {
    deviate not-supported;
    description "Not supported in this release";
  }

  deviation /ios:native/ios:transceiver {
    deviate not-supported;
    description "Not supported in this release";
  }
}
