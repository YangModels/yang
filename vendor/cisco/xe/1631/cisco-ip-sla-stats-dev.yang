module cisco-ip-sla-stats-dev {

    yang-version 1;

    namespace "urn:cisco:params:xml:ns:yang:cisco-ip-sla-stats-dev";
    prefix slastatsd;

    import cisco-ip-sla-stats {
        prefix slastats;
    }

    organization
        "Cisco Systems, Inc.";

    contact
        " Cisco Systems, Inc.
          Customer Service

          Postal: 170 W Tasman Drive
          San Jose, CA 95134

          Tel: +1 1800 553-NETS

          E-mail: cs-yang@cisco.com";
    
    description
        " This module contains a collection of YANG deviations for
          cisco-ip-sla-stats model. Modifies the usage of yang:date-and-time
          temporarily to string so that Router's time notation is
          passed as it is without conversion to yang:date-and-time format.";
    
    reference "TODO";

    revision 2015-06-30 {
        description "Proposed";
    }

   deviation "/slastats:ip-sla-stats/slastats:sla-oper-entry/slastats:latest-oper-start-time" {

        deviate replace {
            type string;
        }
    }

   deviation "/slastats:ip-sla-stats/slastats:sla-oper-entry/slastats:measure-stats/slastats:intv-start-time" {

        deviate replace {
            type string;
        }
    }

}
