/*-------------------------------------------------------------------
 *  cisco-qos-action-oper.yang - qos action operation data model 
 * 
 *  April 2015, Xia Wu   
 *                                           
 *  Copyright (c) 2013 by Cisco Systems, Inc.
 *  All rights reserved.                     
 *-------------------------------------------------------------------
 */
module cisco-qos-action-oper {
    namespace "urn:cisco:params:xml:ns:yang:cisco-qos-action-oper";
    prefix qos-stats;

    import cisco-qos-common {
        prefix qos;
    }

    import ietf-diffserv-target {
        prefix target;
    }

    import ietf-yang-types {
        prefix yang;
    }

    import ietf-interfaces {
        prefix if;
    } 

    import ietf-diffserv-action {
        prefix ietf-action;
    }
    
    import cisco-qos-action-marking-cfg {
        prefix marking;
    }
    
    import cisco-qos-action-qlimit-cfg {
        prefix qlimit;
    }
    
    import ietf-diffserv-action {
        prefix action;
    }
    organization "Cisco Systems";
    contact
        "Editor:   Xia Wu
        <mailto:xiaw2@cisco.com>";
    description
        "This module contains YANG definitions for
        qos operational data 

        Copyright (c) 2015 by Cisco Systems, Inc.
        All rights reserved.";

    revision 2015-05-09 {
        description "first revision";
        reference "ietf-diffserv-action.yang";
    }

    feature aggregate-priority-stats-support {
        description "The support for stats for aggregate priority";
    }

    feature drop-pkts-flow-stats-support {
        description "The support for stats for drop pacekts flow";
    }

    feature drop-pkts-no-buffer-stats-support {
        description "The support for stats for no buffer packets";
    }

    feature queue-peak-size-stats-support {
        description "The support for stats for max queue depth";
    }

    feature marking-stats-support {
        description "The support for marking stats";
    }
    
    feature priority-bandwidth-exceed-drops-support {
        description "The support for priority bandwidth exceed drops counter";
    }
    grouping WRED-CLASS-COUNTS {
        container wred-class-counts {
            description 
               "statistics for random-detect";
            leaf transmitted-pkts { 
                type yang:zero-based-counter64;
                description "Transmitted packtes";
            }
            leaf transmitted-bytes { 
                type yang:zero-based-counter64;
                description "Transmitted bytes";
            }
            leaf tail-drop-pkts { 
                type yang:zero-based-counter64;
                description "Tail drop packets";
            }
            leaf tail-drop-bytes { 
                type yang:zero-based-counter64;
                description "Tail drop bytes";
            }
            leaf early-drop-pkts { 
                type yang:zero-based-counter64;
                description "Early drop packets";
            }
            leaf early-drop-bytes { 
                type yang:zero-based-counter64;
                description "Early drop bytes";
            }
        }
        description "grouping for statistics for random-detect";
    }

    grouping AGG-PRIORITY-STATS {
        container agg-priority-stats {
            leaf output-pkts {
                type yang:zero-based-counter64;
                description
                    "Number of packets transmitted from queue ";
            }
            leaf output-bytes {
                type yang:zero-based-counter64;
                description
                    "Number of bytes transmitted from queue ";
            }
            leaf queue-size-pkts {
                type yang:zero-based-counter64;
                description "Number of packets currently buffered";
            }
            leaf queue-size-bytes {
                type yang:zero-based-counter64;
                description "Number of bytes currently buffered";
            }
            leaf drop-pkts {
                type yang:zero-based-counter64;
                description "Total number of packets dropped";
            }
            leaf drop-bytes {
                type yang:zero-based-counter64;
                description "Total number of bytes dropped";
            }
            leaf drop-pkts-flow {
                type yang:zero-based-counter64;
                description "Number of packets that were dropped by flow-based \
                    fair-queuing (fair-queue). This is a sub-set of drop-pkts";
            }
            leaf drop-pkts-no-buffer {
                type yang:zero-based-counter64;
                description "Number of packets dropped due to buffers being \
                    unavailable system-wide or at the associated interface. This \
                    is a sub-set of drop-pkts";
            }  
            description "Container for counters in aggregate priority";
        }
        description "Grouping for counters in aggregate priority";
    }
    augment "/if:interfaces-state/if:interface/target:diffserv-target-entry/"
        + "target:diffserv-target-classifier-statistics" {
            description 
                "extend the classifier statistics to \
                 add the cac statistics";
            container cac-stats {
                description "statistics for cac";
                leaf num-admitted-flows {
                    type uint32;
                    description "Number of admitted flow";
                } 
                leaf num-non-admitted-flows {
                    type uint32;
                    description "Number of non-admitted flows";
                }
            }
    }
            
    augment "/if:interfaces-state/if:interface/target:diffserv-target-entry" {      
            description 
                "Extend the classifier-statistics to \
                 add aggregate priority stats";
            container priority-oper-lists {
                list priority-oper-list {
                    key "priority-level";
                    if-feature aggregate-priority-stats-support;
                    leaf priority-level {
                        type uint8;
                        description "Priority Level, 0 means no priority level set";
                    }
                    uses AGG-PRIORITY-STATS;
                    uses qlimit:QUEUELIMIT;
                    uses action:queuelimit;
                    description "Statistics for priority levels";  
                }
                description "Statistics for aggregrate priority per policy instance";
            }
        }
    
    augment "/if:interfaces-state/if:interface/target:diffserv-target-entry/"
        + "target:diffserv-target-classifier-statistics" {
            description 
                "marking statistics";
            container marking-stats   { 
                if-feature marking-stats-support;
                container marking-dscp-stats {
                    uses ietf-action:marking;
                    leaf marked-pkts {
                        type yang:zero-based-counter64;
                        description "Number of packets been marked";
                    }
                    description "Statistics for set dscp";
                }
            
                container marking-dscp-tunnel-stats {
                    uses marking:MARKING-DSCP-TUNNEL;
                    leaf marked-pkts {
                        type yang:zero-based-counter64;
                        description "Number of packets been marked";
                    }
                    description "Statistics for set dscp tunnel";
                }
            
                container marking-cos-stats {
                    uses marking:MARKING-COS;
                    leaf marked-pkts {
                        type yang:zero-based-counter64;
                        description "Number of packets been marked";
                    }
                    description "Statistics for set cos";
                }
            
                container marking-cos-inner-stats {
                    uses marking:MARKING-COS-INNER;
                    leaf marked-pkts {
                        type yang:zero-based-counter64;
                        description "Number of packets been marked";
                    }
                    description "Statistics for set cos-inner";
                }
            
                container marking-discard-class-stats {
                    uses marking:MARKING-DISCARD-CLASS;
                    leaf marked-pkts {
                        type yang:zero-based-counter64;
                        description "Number of packets been marked";
                    }
                    description "Statistics for set discard-class";
                }
            
                container marking-qos-grp-stats {
                    uses marking:MARKING-QOS-GRP;
                    leaf marked-pkts {
                        type yang:zero-based-counter64;
                        description "Number of packets been marked";
                    }
                    description "Statistics for set qos-group";
                }
            
                container marking-prec-stats {
                    uses marking:MARKING-PREC;
                    leaf marked-pkts {
                        type yang:zero-based-counter64;
                        description "Number of packets been marked";
                    }
                    description "Statistics for set precedence";
                }
            
                container marking-prec-tunnel-stats {
                    uses marking:MARKING-PREC-TUNNEL;
                    leaf marked-pkts {
                        type yang:zero-based-counter64;
                        description "Number of packets been marked";
                    }
                    description "Statistics for set precedence tunnel";
                }
            
                container marking-mpls-exp-imp-stats {
                    uses marking:MARKING-MPLS-EXP-IMP;
                    leaf marked-pkts {
                        type yang:zero-based-counter64;
                        description "Number of packets been marked";
                    }
                    description "Statistics for set mpls exp imposition";
                }
            
                container marking-mpls-exp-top-stats {
                    uses marking:MARKING-MPLS-EXP-TOP;
                    leaf marked-pkts {
                        type yang:zero-based-counter64;
                        description "Number of packets been marked";
                    }
                    description "Statistics for set mpls exp topmost";
                }
           
                container marking-fr-de-stats {
                    uses marking:MARKING-FR-DE;
                    leaf marked-pkts {
                        type yang:zero-based-counter64;
                        description "Number of packets been marked";
                    }
                    description "Statistics for set fr-de";
                }
            
                container marking-fr-fecn-becn-stats {
                    uses marking:MARKING-FR-FECN-BECN;
                    leaf marked-pkts {
                        type yang:zero-based-counter64;
                        description "Number of packets been marked";
                    }
                    description "Statistics for set fr-fecn-becn";
                }
            
                container marking-atm-clp-stats {
                    uses marking:MARKING-ATM-CLP;
                    leaf marked-pkts {
                        type yang:zero-based-counter64;
                        description "Number of packets been marked";
                    }
                    description "Statistics for set atm-clp";
                }
            
                container marking-vlan-inner-stats {
                    uses marking:MARKING-VLAN-INNER;
                    leaf marked-pkts {
                        type yang:zero-based-counter64;
                        description "Number of packets been marked";
                    }
                    description "Statistics for set vlan-inner";
                }
            
                container marking-dei-stats {
                    uses marking:MARKING-DEI;
                    leaf marked-pkts {
                        type yang:zero-based-counter64;
                        description "Number of packets been marked";
                    }
                    description "Statistics for set dei";
                }
            
                container marking-dei-imp-stats {
                    uses marking:MARKING-DEI-IMP;
                    leaf marked-pkts {
                        type yang:zero-based-counter64;
                        description "Number of packets been marked";
                    }
                    description "Statistics for set dei-imposition";
                }
            
                container marking-srp-priority-stats {
                    uses marking:MARKING-SRP-PRIORITY;
                    leaf marked-pkts {
                        type yang:zero-based-counter64;
                        description "Number of packets been marked";
                    }
                    description "Statistics for set srp-priority";
                }
            
                container marking-wlan-user-priority-stats {
                    uses marking:MARKING-WLAN-USER-PRIORITY;
                    leaf marked-pkts {
                        type yang:zero-based-counter64;
                        description "Number of packets been marked";
                    }
                    description "Statistics for set wlan-user-priority";
                }
                description "statistics for marking actions";
            }
        }
        
    augment "/if:interfaces-state/if:interface/target:diffserv-target-entry/"
        + "target:diffserv-target-classifier-statistics/target:meter-statistics" {
            description "Extend the ietf model to add the meter rate statistics";
            leaf meter-succeed-rate {
                type uint64;
                description
                    "rates which succeed the meter";
            }
            leaf meter-failed-rate {
                type uint64;
                description
                    "rates which failed the meter";
            }
        }
    augment "/if:interfaces-state/if:interface/target:diffserv-target-entry/"
        + "target:diffserv-target-classifier-statistics/target:queuing-statistics" {
            description 
                "output-pkts: Number of packets transmitted from queue             
                output-bytes: Number of bytes transmitted from queue              
                queue-size-pkts: Number of packets currently buffered
                queue-size-bytes: Number of bytes currently buffered         
                drop-pkts: Total number of packets dropped
                drop-bytes: Total number of bytes dropped
                drop-pkts-flow: Number of packets that were dropped by flow-based \
                fair-queuing (fair-queue). This is a sub-set of drop-pkts
                drop-pkts-no-buffer: Number of packets dropped due to buffers being \
                unavailable system-wide or at the associated interface. This \
                is a sub-set of drop-pkts \
                queue-peak-size-pkts: Queue max que depth Packets \
                queue-peak-size-bytes: Queue max que depth Bytes";

            leaf drop-pkts-flow       { 
                if-feature drop-pkts-flow-stats-support;
                type yang:zero-based-counter64;
                description "Total number of packets dropped";
            }

            leaf drop-pkts-no-buffer  { 
                if-feature drop-pkts-no-buffer-stats-support;
                type yang:zero-based-counter64;
                description "Number of packets dropped due to buffers being \
                unavailable system-wide or at the associated interface. This \
                is a sub-set of drop-pkts";
            }

            leaf queue-peak-size-pkts { 
                if-feature queue-peak-size-stats-support;
                type yang:zero-based-counter64;
                description "Queue max que depth Packets";
            }

            leaf queue-peak-size-bytes { 
                if-feature queue-peak-size-stats-support;
                type yang:zero-based-counter64;
                description "Queue max que depth Bytes";
            }
            
            container priority-stats {
                description "statistcis for priority under class level";
                leaf bandwidth-exceed-drops {
                    if-feature priority-bandwidth-exceed-drops-support;
                    type yang:zero-based-counter64;
                    description "Bandwidth exceed drops";
                }
            }
        }

    augment "/if:interfaces-state/if:interface/target:diffserv-target-entry/"
        + "target:diffserv-target-classifier-statistics/target:queuing-statistics/"
        + "target:wred-stats" {
            description "Extend wred-stats for add more wred stats options";
            leaf mean-queue-depth { 
                type uint16;
                description "Current mean queue depth";
            }

            leaf transmitted-pkts { 
                type yang:zero-based-counter64;
                description "Transmitted packtes";
            }
            leaf transmitted-bytes { 
                type yang:zero-based-counter64;
                description "Transmitted bytes";
            }
            leaf tail-drop-pkts { 
                type yang:zero-based-counter64;
                description "Total number of packets dropped";
            }
            leaf tail-drop-bytes { 
                type yang:zero-based-counter64;
                description "Total number of bytes dropped";
            }

            container subclass-lists {
                description "Lists of statistics for random-detect \
                    based on subclass type and value pair";
                list subclass-list {
                    key "match-type"; 

                    leaf match-type {
                        type qos:match-type;
                        description "Subclass type";
                    }

                    choice counts-list {
                        when "match-type = ''" {
                            description "Counts based on subclass type";
                        }
                        case cos {
                            container cos-counts-lists {
                                list cos-counts-list {
                                    key "cos-min cos-max";
                                    uses qos:COS-RANGE;
                                    description 
                                        "Counters for sub-class matching a range of \
                                        Class-of-Service (COS) value (and, optionally, \
                                                additional COS range";
                                    uses WRED-CLASS-COUNTS;
                                }
                                container cos-default {
                                    uses WRED-CLASS-COUNTS;
                                    description "statistics for cos default";
                                }
                                description "List for statistics based on cos value range";
                            }
                        }

                        case dscp {
                            container dscp-counts-lists {
                                list dscp-counts-list {
                                    key "dscp-min dscp-max";
                                    description 
                                        "Composed by one single dscp range and multiple dscp ranges";
                                    uses qos:DSCP-RANGE;
                                    uses WRED-CLASS-COUNTS;
                                }
                                container dscp-default {
                                    uses WRED-CLASS-COUNTS;
                                    description "statistics for dscp default";
                                }
                                description "List for statistics based on dscp value range";
                            }
                        }
                        case discard-class {
                            container disc-class-counts-lists {
                                list disc-class-counts-list {
                                    key "disc-class-min disc-class-max";
                                    description 
                                        "Composed multiple discard class ranges";
                                    uses qos:DISC-CLASS-RANGE;
                                    uses WRED-CLASS-COUNTS;
                                }

                                container discard-class-default {
                                    uses WRED-CLASS-COUNTS;
                                    description "statistics for discard class default";
                                }
                                description "List for statistics based on discard class value range";
                            }
                        }
                        case prec {
                            container prec-counts-lists {
                                list prec-counts-list {
                                    key "prec-min prec-max";
                                    description 
                                        "Composed by multiple precedence ranges";
                                    uses qos:PREC-RANGE;
                                    uses WRED-CLASS-COUNTS;
                                }
                                container prec-default {
                                    uses WRED-CLASS-COUNTS;
                                    description "statistics for precedence default";
                                }
                                description "List for statistics based on precedence value range";
                            }

                        }

                        case mpls-exp {
                            container mpls-exp-counts-lists {
                                list mpls-exp-counts-list {
                                    key "exp-min exp-max";
                                    description 
                                        "Composed by mpls exp ranges";
                                    uses qos:MPLS-EXP-RANGE;
                                    uses WRED-CLASS-COUNTS;
                                }
                                container mpls-exp-default {
                                    uses WRED-CLASS-COUNTS;
                                    description "statistics for mpls-exp default";
                                }
                                description "List for statistics based on mpls exp value range";
                            }
                        }

                        case dei {
                            container dei-counts-lists {
                                list dei-counts-list {
                                    key "dei-min dei-max";
                                    description 
                                        "Composed by multiple dei ranges";
                                    uses qos:DEI-RANGE;
                                    uses WRED-CLASS-COUNTS;
                                }
                                container dei-default {
                                    uses WRED-CLASS-COUNTS;
                                    description "statistics for dei default";
                                }
                                description "List for statistics based on dei value range";
                            }
                        }

                        case atm-clp {
                            container clp-counts-lists {
                                list clp-counts-list {
                                    key "clp-val";
                                    description "Composed by multiple atm clp values";
                                    uses qos:CLP-VAL;
                                    uses WRED-CLASS-COUNTS;
                                }

                                container atm-clp-default {
                                    uses WRED-CLASS-COUNTS;
                                    description "statistic for atm clp default";
                                }
                                description "List for statistics based on atm clp value range";
                            }
                        }
                        description "Statistics for each value range for \
                            a specifc subclass type";
                    } 
                    description "List of statistics for random-detect \
                    based on subclass type and value pair";
                }
            }
        }
}
