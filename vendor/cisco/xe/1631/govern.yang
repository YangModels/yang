module govern {
  namespace "urn:cisco:params:xml:ns:yang:govern";
  prefix govern;

  organization
       "Cisco Systems, Inc.";

  contact
       "Cisco Systems, Inc.
        Customer Service
        
        Postal: 170 W Tasman Drive
                San Jose, CA 95134
        
        Tel: +1 1800 553-NETS
        
        E-mail: cs-yang@cisco.com";

  description
       "This module contains a collection of YANG extensions used
        to support the governance of YANG modules.
        
        Multiple extension items described in this module may be 
        included in the top-level of a YANG module.  These extensions
        are used by tooling to identify the status and required 
        treatment of YANG modules by tooling, documentation and 
        versioning systems.";

  revision 2014-07-16 {
    description "Initial set of YANG extensions to 
                 support model governance";
    reference "Cisco extensions to support model governance";
  }
  extension proposed {
    description
              "Indicates model content is preliminary, 
               subject to change and is not currently 
               used in shipping code";
  }
  extension provisional {
    description
              "Indicates model content has been reviewed 
               and approved by YANG and subject matter experts.  
               The model is ready to be used.  
               The model is not currently used in shipping code";
  }
  extension production {
    description
              "Indicates model content review, approved 
               and in use in hipping code.  The model 
               content is subject to model ersioning control";
  }
  extension ietf-rfc {
    description
              "Indicates model content is approved and 
               published as an IETF-RFC.  Cisco internal 
               versions of these modules may add Cisco 
               specific annotations for internal use";
  }
  extension ietf-draft {
    description
              "Indicates model content is proposed as 
               an IETF draft.  The model content is 
               subject to change during the IETF ratification
               process";
  }
  extension yang-open-source {
    description
              "Indicates model content has been published 
               to the YANG Git Open Source Repository.  
               Changes in these models should be
               updated into the YANG OS Repository";
  }
}
