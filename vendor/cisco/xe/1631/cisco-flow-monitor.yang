module cisco-flow-monitor {

    yang-version 1;

    namespace "urn:cisco:params:xml:ns:yang:cisco-flow-monitor";
    prefix flow-monitor;

    import tailf-common { prefix tailf; }

    organization
        "Cisco Systems, Inc.";

    contact
        " Cisco Systems, Inc. Customer Service Postal: 170 W Tasman Drive
        San Jose, CA 95134 Tel: +1 1800 553-NETS E-mail: cs-yang@cisco.com";

    description
        "This module contains a collection of YANG definitions for ...";

    reference "TODO";

    revision 2015-10-26{
        description "Proposed";
    }

    container flow-monitors {
        config false;
        description
            "All of the flow monitors";

        list flow-monitor {
            key "name";
            description
                "A flow monitor";
            
            leaf name {
                type string;
                description
                    "Name of the flow monitor";
            }

            container flows {
                description
                    "All the flows for this flow monitor";

                list flow {
                    key "source-address";
                    description
                        "A flow";

                    leaf source-address {
                        type string;
                        description
                            "Source address of the flow";
                    }

                    leaf destination-address {
                        type string;
                        description
                            "Destination address of the flow";
                    }

                    leaf interface-input {
                        type string;
                        description
                            "Input interface of the flow";
                    }

                    leaf interface-output {
                        type string;
                        description
                            "Output interface of the flow";
                    }

                    leaf bytes {
                        type uint64;
                        description
                            "Number of bytes passed through";
                    }

                    leaf packets {
                        type uint64;
                        description
                            "Number of packets passed through";
                    }
                }
            }
        }
    }
}
