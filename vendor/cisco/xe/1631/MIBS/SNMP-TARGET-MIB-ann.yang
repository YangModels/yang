module SNMP-TARGET-MIB-ann {
  namespace "urn:dummy";
  prefix dummy;

  import tailf-common {
    prefix tailf;
  }
  import SNMP-TARGET-MIB {
    prefix x;
  }

  tailf:annotate "/x:SNMP-TARGET-MIB/x:snmpTargetObjects" {
    tailf:callpoint "snmpagent" {
      tailf:internal;
    }
  }

/*
  tailf:annotate "/x:SNMP-TARGET-MIB/x:snmpTargetAddrTable/x:snmpTargetAddrEntry/x:snmpTargetAddrTAddress" {
    tailf:validate "snmpagent" {
      tailf:internal;
      tailf:dependency "../snmpTargetAddrTDomain";
    }
  }
  tailf:annotate "/x:SNMP-TARGET-MIB/x:snmpTargetAddrTable/x:snmpTargetAddrEntry/x:snmpTargetAddrTMask" {
    tailf:validate "snmpagent" {
      tailf:internal;
      tailf:dependency "../snmpTargetAddrTDomain";
    }
  }
*/

}
