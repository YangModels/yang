module SNMP-USER-BASED-SM-MIB-ann {
  namespace "urn:dummy";
  prefix dummy;

  import tailf-common {
    prefix tailf;
  }
  import SNMP-USER-BASED-SM-MIB {
    prefix x;
  }

  tailf:annotate "/x:SNMP-USER-BASED-SM-MIB/x:usmStats" {
    tailf:callpoint "snmpagent" {
      tailf:internal;
    }
  }
}
