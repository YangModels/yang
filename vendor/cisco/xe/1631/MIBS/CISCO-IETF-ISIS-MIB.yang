/*
 * Generated by confdc --mib2yang-std
 * Source: mgmt/dmi/model/common/mib-source/CISCO-IETF-ISIS-MIB.mib
 */
/*
 * This YANG module has been generated by smidump 0.5.0:
 *
 *      smidump -f yang CISCO-IETF-ISIS-MIB
 *
 * Do not edit. Edit the source file instead!
 */

module CISCO-IETF-ISIS-MIB {

  namespace "urn:ietf:params:xml:ns:yang:smiv2:CISCO-IETF-ISIS-MIB";
  prefix CISCO-IETF-ISIS-MIB;

  import DIFFSERV-MIB {
    prefix "diffserv-mib";
  }

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "  Cisco Systems
    Customer Service
    
    Postal: 170 W. Tasman Drive
            San Jose, CA  95134
            USA
    
    Tel: +1 800 553-NETS
    
    E-mail: cs-clns@cisco.com";

  description
   "This document describes a management information base for
    the IS-IS Routing protocol, as described in ISO 10589,
    when it is used to construct routing tables for IP networks,
    as described in RFC 1195. This MIB is entirely based upon
    the IETF draft draft-ietf-isis-wg-mib-16.";

  revision 2005-08-16 {
    description
     "Corrected DESCRIPTION clause for ciiAreaAddrTable,
      ciiAreaAddrEntry, ciiAreaAddr and for 
      ciiSysLevelOverloadState based on similar
      definitions in draft-ietf-isis-wg-mib-18.txt.";
  }

  revision 2005-02-08 {
    description
     "Initial version.";
  }

  typedef CiiOSINSAddress {
    type binary {
      length "0..20";
    }
    description
     "OSI Network Service Address, e.g. NSAP, SNPA, or Network
      Entity Title";
  }

  typedef CiiSystemID {
    type binary {
      length "6";
    }
    description
     "A system ID.";
  }

  typedef CiiLinkStatePDUID {
    type binary {
      length "0|8";
    }
    description
     "A Link State PDU Identifier.";
  }

  typedef CiiAdminState {
    type enumeration {
      enum "on" {
        value "1";
      }
      enum "off" {
        value "2";
      }
    }
    description
     "Type used in enabling and disabling a row.
      Values match those in RFC 2863.";
  }

  typedef CiiLSPBuffSize {
    type int32 {
      range "512..16000";
    }
    description
     "Integer sub range for LSP size.";
  }

  typedef CiiLevelState {
    type enumeration {
      enum "off" {
        value "1";
      }
      enum "on" {
        value "2";
      }
      enum "waiting" {
        value "3";
      }
      enum "overloaded" {
        value "4";
      }
    }
    description
     "States of the IS-IS protocol.";
  }

  typedef CiiSupportedProtocol {
    type enumeration {
      enum "iso8473" {
        value "129";
      }
      enum "ipV6" {
        value "142";
      }
      enum "ip" {
        value "204";
      }
    }
    description
     "Types of network protocol supported by Integrated IS-IS.
      The values for ISO8473 and IP are those registered for
      these protocols in ISO TR9577.";
  }

  typedef CiiDefaultMetric {
    type int32 {
      range "0..63";
    }
    description
     "Integer sub-range for default metric for single hop.
      ISO 10589 provides for 4 types of metric.  Only the
      'default' metric is used in practice.";
  }

  typedef CiiWideMetric {
    type uint32 {
      range "0..16777215";
    }
    description
     "Wide Metric for IS Neighbors.  ISO 10589 provides a
      6 bit metric.  Traffic Engineering extensions provide
      24 bit metrics.";
  }

  typedef CiiFullMetric {
    type uint32;
    description
     "Full Metric for IP Routes.  Traffic Engineering extensions
      provide 32 bit metrics.";
  }

  typedef CiiMetricType {
    type enumeration {
      enum "internal" {
        value "1";
      }
      enum "external" {
        value "2";
      }
    }
    description
     "Is this an Internal or External Metric?";
  }

  typedef CiiMetricStyle {
    type enumeration {
      enum "narrow" {
        value "1";
      }
      enum "wide" {
        value "2";
      }
      enum "both" {
        value "3";
      }
    }
    description
     "Do we use 1195 style Metrics or wide metrics.";
  }

  typedef CiiISLevel {
    type enumeration {
      enum "none" {
        value "0";
      }
      enum "area" {
        value "1";
      }
      enum "domain" {
        value "2";
      }
    }
    description
     "Identifies a level.";
  }

  typedef CiiPDUHeader {
    type binary {
      length "0..64";
    }
    description
     "A block to contain the header from a PDU.";
  }

  typedef CiiCircuitID {
    type binary {
      length "0|7";
    }
    description
     "ID for a circuit.";
  }

  typedef CiiISPriority {
    type int32 {
      range "0..127";
    }
    description
     "Integer sub-range for IS-IS priority.";
  }

  typedef CiiUnsigned16TC {
    type uint32 {
      range "0..65535";
    }
    description
     "An Unsigned32 further restricted to 16 Bits. Note that
      the ASN.1 BER encoding may still require 24 Bits for
      some values.";
  }

  typedef CiiUnsigned8TC {
    type uint32 {
      range "0..255";
    }
    description
     "An Unsigned32 further restricted to 8 Bits. Note that
      the ASN.1 BER encoding may still require 16 Bits for
      some values.";
  }


  container CISCO-IETF-ISIS-MIB {
    config false;

    container ciiSysObject {
      smiv2:oid "1.3.6.1.4.1.9.10.118.1.1.1";

      leaf ciiSysVersion {
        type enumeration {
          enum "unknown" {
            value "0";
          }
          enum "one" {
            value "1";
          }
        }
        description
         "The version number of the IS-IS protocol that
          is implemented.";
        reference
         "{ISIS.aoi version (1)}";
        smiv2:defval "one";
        smiv2:max-access "read-only";
        smiv2:oid "1.3.6.1.4.1.9.10.118.1.1.1.1";
      }

      leaf ciiSysType {
        type enumeration {
          enum "level1IS" {
            value "1";
          }
          enum "level2IS" {
            value "2";
          }
          enum "level1L2IS" {
            value "3";
          }
        }
        description
         "At which levels is the Intermediate System
          running? This object follows the
          replaceOnlyWhileDisabled behavior.";
        reference
         "{ISIS.aoi iSType (2)}";
        smiv2:defval "level1L2IS";
        smiv2:max-access "read-write";
        smiv2:oid "1.3.6.1.4.1.9.10.118.1.1.1.2";
      }

      leaf ciiSysID {
        type CISCO-IETF-ISIS-MIB:CiiSystemID;
        description
         "The ID for this Intermediate System.
          This value is appended to each of the
          area addresses to form the Network Entity Titles.
          The derivation of a value for this object is
          implementation-specific.  Some implementations may
          automatically assign values and not permit an
          SNMP write, while others may require the value
          to be set manually.";
        reference
         "{ISIS.aoi systemId (119)}";
        smiv2:max-access "read-write";
        smiv2:oid "1.3.6.1.4.1.9.10.118.1.1.1.3";
      }

      leaf ciiSysMaxPathSplits {
        type int32 {
          range "1..32";
        }
        description
         "Maximum number of paths with equal routing metric value
          which it is permitted to split between. This object
          follows the replaceOnlyWhileDisabled behavior.";
        reference
         "{ISIS.aoi maximumPathSplits (3)}";
        smiv2:defval "2";
        smiv2:max-access "read-write";
        smiv2:oid "1.3.6.1.4.1.9.10.118.1.1.1.4";
      }

      leaf ciiSysMaxLSPGenInt {
        type int32 {
          range "1..65235";
        }
        units "seconds";
        description
         "Maximum interval, in seconds, between generated LSPs
          by this Intermediate System. This object follows
          the resettingTimer behavior.  The value must be
          greater than any value configured for
          ciiSysLevelMinLSPGenInt, and should be at least 300
          seconds less than ciiSysMaxAge.";
        reference
         "{ISIS.aoi maximumLSPGenerationInterval (6)}";
        smiv2:defval "900";
        smiv2:max-access "read-write";
        smiv2:oid "1.3.6.1.4.1.9.10.118.1.1.1.5";
      }

      leaf ciiSysPollESHelloRate {
        type CISCO-IETF-ISIS-MIB:CiiUnsigned16TC {
          range "1..65535";
        }
        units "seconds";
        description
         "The value, in seconds, to be used for the suggested ES
          configuration timer in ISH PDUs when soliciting the ES
          configuration.";
        reference
         "{ISIS.aoi pollESHelloRate (13)}";
        smiv2:defval "50";
        smiv2:max-access "read-write";
        smiv2:oid "1.3.6.1.4.1.9.10.118.1.1.1.6";
      }

      leaf ciiSysWaitTime {
        type CISCO-IETF-ISIS-MIB:CiiUnsigned16TC {
          range "1..65535";
        }
        units "seconds";
        description
         "Number of seconds to delay in 'waiting' state before
          entering 'on' state. This object follows the resettingTimer
          behavior.";
        reference
         "{ISIS.aoi waitingTime (15)}";
        smiv2:defval "60";
        smiv2:max-access "read-write";
        smiv2:oid "1.3.6.1.4.1.9.10.118.1.1.1.7";
      }

      leaf ciiSysAdminState {
        type CISCO-IETF-ISIS-MIB:CiiAdminState;
        description
         "The administrative state of this Intermediate
          System.  Setting this object to the value 'on'
          when its current value is 'off' enables
          the Intermediate System.";
        smiv2:defval "off";
        smiv2:max-access "read-write";
        smiv2:oid "1.3.6.1.4.1.9.10.118.1.1.1.8";
      }

      leaf ciiSysL2toL1Leaking {
        type boolean;
        description
         "If true, allow the router to leak L2 routes into L1.";
        smiv2:defval "false";
        smiv2:max-access "read-write";
        smiv2:oid "1.3.6.1.4.1.9.10.118.1.1.1.9";
      }

      leaf ciiSysMaxAge {
        type CISCO-IETF-ISIS-MIB:CiiUnsigned16TC {
          range "350..65535";
        }
        units "seconds";
        description
         "Value to place in RemainingLifeTime field of
          the LSPs we generate.
          This should be at least 300 seconds greater than
          ciiSysMaxLSPGenInt.";
        smiv2:defval "1200";
        smiv2:max-access "read-write";
        smiv2:oid "1.3.6.1.4.1.9.10.118.1.1.1.10";
      }

      leaf ciiSysReceiveLSPBufferSize {
        type CISCO-IETF-ISIS-MIB:CiiUnsigned16TC {
          range "1492..16000";
        }
        units "bytes";
        description
         "Size of the largest Buffer we are designed or
          configured to store.  This should be at least
          as big as the maximum ciiSysLevelOrigLSPBuffSize
          supported by the system.
          
          If resources allow, we will store and flood LSPs
          larger than ciiSysReceiveLSPBufferSize, as this
          can help avoid problems in networks with different
          values for ciiSysLevelOrigLSPBuffSize.";
        smiv2:defval "1492";
        smiv2:max-access "read-write";
        smiv2:oid "1.3.6.1.4.1.9.10.118.1.1.1.11";
      }
    }

    container ciiCirc {
      smiv2:oid "1.3.6.1.4.1.9.10.118.1.3";

      leaf ciiNextCircIndex {
        type diffserv-mib:IndexIntegerNextFree;
        description
         "This object is used to assign values to
          ciiCircIndex as described in 'Textual
          Conventions for SNMPv2'.  The network manager
          reads this object, and then writes the value
          back as the ciiCircIndex in a SET that creates
          a new instance of ciiCircEntry.  If the SET
          fails with the code 'inconsistentValue', then
          the process must be repeated; If the SET succeeds,
          then the object is incremented, and the new
          ciiCircEntry is created according to the manager's
          directions.";
        smiv2:max-access "read-only";
        smiv2:oid "1.3.6.1.4.1.9.10.118.1.3.1";
      }
    }

    container ciiManAreaAddrTable {
      description
       "The set of manual area addresses configured on this
        Intermediate System.";
      reference
       "{ISIS.aoi manualAreaAddresses (10)}";
      smiv2:oid "1.3.6.1.4.1.9.10.118.1.1.2";

      list ciiManAreaAddrEntry {
        key "ciiManAreaAddr";
        description
         "Each entry contains one area address manually configured
          on this system";
        smiv2:oid "1.3.6.1.4.1.9.10.118.1.1.2.1";

        leaf ciiManAreaAddr {
          type CISCO-IETF-ISIS-MIB:CiiOSINSAddress;
          description
           "A manually configured area address for this system. This
            object follows the index behavior.
            
            Note: an index for the entry {1, {49.0001} active} in
            this table would be the ordered pair
            (1, (0x03 0x49 0x00 0x01)), as the length of an Octet
            string is part of the OID.";
          smiv2:max-access "not-accessible";
          smiv2:oid "1.3.6.1.4.1.9.10.118.1.1.2.1.1";
        }

        leaf ciiManAreaAddrExistState {
          type snmpv2-tc:RowStatus;
          description
           "The state of the ciiManAreaAddrEntry. This object
            follows the Row Status behavior. If the ciiSysAdminState
            for this Intermediate System is 'on', and an
            attempt is made to set this object to the value 'destroy'
            or 'notInService' when this is the only
            ciiManAreaAddrEntry in state 'active' for this
            Intermediate System should return inconsistentValue.";
          smiv2:max-access "read-write";
          smiv2:oid "1.3.6.1.4.1.9.10.118.1.1.2.1.2";
        }
      }
    }

    container ciiAreaAddrTable {
      description
       "The union of the sets of area addresses reported in all
        Level 1 LSPs with fragment number zero generated by this
        Intermediate System, or received from other Intermediate
        Systems which are reachable via Level 1 routing.";
      reference
       "{ISIS.aoi areaAddresses (18)}";
      smiv2:oid "1.3.6.1.4.1.9.10.118.1.1.3";

      list ciiAreaAddrEntry {
        key "ciiAreaAddr";
        description
         "Each entry contains one area address reported in a
          Level 1 LSP generated or received by this Intermediate
          System.";
        smiv2:oid "1.3.6.1.4.1.9.10.118.1.1.3.1";

        leaf ciiAreaAddr {
          type CISCO-IETF-ISIS-MIB:CiiOSINSAddress;
          description
           "An area address reported in a Level 1 LSP.";
          smiv2:max-access "read-only";
          smiv2:oid "1.3.6.1.4.1.9.10.118.1.1.3.1.1";
        }
      }
    }

    container ciiSysProtSuppTable {
      description
       "This table contains the manually configured set of
        protocols supported by this Intermediate System.";
      smiv2:oid "1.3.6.1.4.1.9.10.118.1.1.4";

      list ciiSysProtSuppEntry {
        key "ciiSysProtSuppProtocol";
        description
         "Each entry contains one protocol supported by
          this Intermediate System.";
        smiv2:oid "1.3.6.1.4.1.9.10.118.1.1.4.1";

        leaf ciiSysProtSuppProtocol {
          type CISCO-IETF-ISIS-MIB:CiiSupportedProtocol;
          description
           "One supported protocol. This object follows the index
            behavior.";
          smiv2:max-access "not-accessible";
          smiv2:oid "1.3.6.1.4.1.9.10.118.1.1.4.1.1";
        }

        leaf ciiSysProtSuppExistState {
          type snmpv2-tc:RowStatus;
          description
           "The state of the ciiSysProtSuppEntry. This object
            follows the RowStatus behavior.";
          smiv2:max-access "read-write";
          smiv2:oid "1.3.6.1.4.1.9.10.118.1.1.4.1.2";
        }
      }
    }

    container ciiSummAddrTable {
      description
       "The set of IP summary addresses to use in forming
        summary TLVs originated by this Intermediate System.
        
        An administrator may use a summary address to combine
        and modify IP Reachability announcements.  If the
        Intermediate system can reach any subset of the summary
        address, the summary address will be announced instead,
        at the configured metric.";
      smiv2:oid "1.3.6.1.4.1.9.10.118.1.1.5";

      list ciiSummAddrEntry {
        key "ciiSummAddressType ciiSummAddress ciiSummAddrPrefixLen";
        description
         "Each entry contains one IP summary address.";
        smiv2:oid "1.3.6.1.4.1.9.10.118.1.1.5.1";

        leaf ciiSummAddressType {
          type inet-address:InetAddressType;
          description
           "The Type of IP address for this summary address.
            This object follows the index behavior.";
          smiv2:max-access "not-accessible";
          smiv2:oid "1.3.6.1.4.1.9.10.118.1.1.5.1.1";
        }

        leaf ciiSummAddress {
          type inet-address:InetAddress {
            length "4|16";
          }
          description
           "The IP Address value for this summary address.
            This object follows the index behavior.";
          smiv2:max-access "not-accessible";
          smiv2:oid "1.3.6.1.4.1.9.10.118.1.1.5.1.2";
        }

        leaf ciiSummAddrPrefixLen {
          type inet-address:InetAddressPrefixLength {
            range "0..128";
          }
          description
           "The Length of the IP NetMask for this summary address.";
          smiv2:max-access "not-accessible";
          smiv2:oid "1.3.6.1.4.1.9.10.118.1.1.5.1.3";
        }

        leaf ciiSummAddrExistState {
          type snmpv2-tc:RowStatus;
          description
           "The existence state of this summary address. This object
            follows the row status behavior.";
          smiv2:max-access "read-write";
          smiv2:oid "1.3.6.1.4.1.9.10.118.1.1.5.1.4";
        }

        leaf ciiSummAddrMetric {
          type CISCO-IETF-ISIS-MIB:CiiDefaultMetric;
          description
           "The metric value to announce this summary
            address with in LSPs generated by this system.";
          smiv2:defval "20";
          smiv2:max-access "read-write";
          smiv2:oid "1.3.6.1.4.1.9.10.118.1.1.5.1.5";
        }

        leaf ciiSummAddrFullMetric {
          type CISCO-IETF-ISIS-MIB:CiiFullMetric;
          description
           "The wide metric value to announce this summary
            address with in LSPs generated by this system.";
          smiv2:defval "20";
          smiv2:max-access "read-write";
          smiv2:oid "1.3.6.1.4.1.9.10.118.1.1.5.1.6";
        }
      }
    }

    container ciiRedistributeAddrTable {
      description
       "This table provides criteria to decide if a route should
        be leaked from L2 to L1 when Domain Wide Prefix leaking is
        enabled.
        
        Addresses that match the summary mask in the table will
        be announced at L1 by routers when ciiSysL2toL1Leaking
        is enabled.  Routes that fall into the ranges specified
        are announced as is, without being summarized.  Routes
        that do not match a summary mask are not announced.";
      smiv2:oid "1.3.6.1.4.1.9.10.118.1.1.6";

      list ciiRedistributeAddrEntry {
        key "ciiRedistributeAddrType ciiRedistributeAddrAddress ciiRedistributeAddrPrefixLen";
        description
         "Each entry contains one IP summary address to
          manage leaking L2 addresses into L1.";
        smiv2:oid "1.3.6.1.4.1.9.10.118.1.1.6.1";

        leaf ciiRedistributeAddrType {
          type inet-address:InetAddressType;
          description
           "The Type of IP address for this summary address.
            This object follows the index behavior.";
          smiv2:max-access "not-accessible";
          smiv2:oid "1.3.6.1.4.1.9.10.118.1.1.6.1.1";
        }

        leaf ciiRedistributeAddrAddress {
          type inet-address:InetAddress {
            length "4|16";
          }
          description
           "The IP Address value for this summary address.
            This object follows the index behavior.";
          smiv2:max-access "not-accessible";
          smiv2:oid "1.3.6.1.4.1.9.10.118.1.1.6.1.2";
        }

        leaf ciiRedistributeAddrPrefixLen {
          type inet-address:InetAddressPrefixLength {
            range "0..128";
          }
          description
           "The Length of the IP NetMask for this summary address.";
          smiv2:max-access "not-accessible";
          smiv2:oid "1.3.6.1.4.1.9.10.118.1.1.6.1.3";
        }

        leaf ciiRedistributeAddrExistState {
          type snmpv2-tc:RowStatus;
          description
           "The existence state of this summary address. This object
            follows the row status behavior.";
          smiv2:max-access "read-write";
          smiv2:oid "1.3.6.1.4.1.9.10.118.1.1.6.1.4";
        }
      }
    }

    container ciiRouterTable {
      description
       "The set of hostnames and router ID.";
      smiv2:oid "1.3.6.1.4.1.9.10.118.1.1.7";

      list ciiRouterEntry {
        key "ciiRouterSysID ciiRouterLevel";
        description
         "Each entry tracks information about one peer at
          one level.";
        smiv2:oid "1.3.6.1.4.1.9.10.118.1.1.7.1";

        leaf ciiRouterSysID {
          type CISCO-IETF-ISIS-MIB:CiiSystemID;
          description
           "The System ID of the Router Peer.";
          smiv2:max-access "not-accessible";
          smiv2:oid "1.3.6.1.4.1.9.10.118.1.1.7.1.1";
        }

        leaf ciiRouterLevel {
          type CISCO-IETF-ISIS-MIB:CiiISLevel;
          description
           "The level of this Intermediate System.";
          smiv2:max-access "not-accessible";
          smiv2:oid "1.3.6.1.4.1.9.10.118.1.1.7.1.2";
        }

        leaf ciiRouterHostName {
          type snmp-framework:SnmpAdminString;
          description
           "The hostname listed in LSP, or zero-length string if none.";
          smiv2:max-access "read-only";
          smiv2:oid "1.3.6.1.4.1.9.10.118.1.1.7.1.3";
        }

        leaf ciiRouterID {
          type uint32;
          description
           "The Router ID of the Peer found in LSP, or zero if none.";
          smiv2:max-access "read-only";
          smiv2:oid "1.3.6.1.4.1.9.10.118.1.1.7.1.4";
        }
      }
    }

    container ciiSysLevelTable {
      description
       "Level specific information about the System.";
      smiv2:oid "1.3.6.1.4.1.9.10.118.1.2.1";

      list ciiSysLevelEntry {
        key "ciiSysLevelIndex";
        description
         "Describe variables defined for Area or Domain.";
        smiv2:oid "1.3.6.1.4.1.9.10.118.1.2.1.1";

        leaf ciiSysLevelIndex {
          type enumeration {
            enum "level1IS" {
              value "1";
            }
            enum "level2IS" {
              value "2";
            }
          }
          description
           "The level that this entry describes.";
          smiv2:max-access "not-accessible";
          smiv2:oid "1.3.6.1.4.1.9.10.118.1.2.1.1.1";
        }

        leaf ciiSysLevelOrigLSPBuffSize {
          type CISCO-IETF-ISIS-MIB:CiiLSPBuffSize;
          description
           "The maximum size of LSPs and SNPs originated by
            this Intermediate System at this level.
            This object follows the replaceOnlyWhileDisabled
            behavior.";
          reference
           "{ISIS.aoi originatingL1LSPBufferSize (9)}";
          smiv2:defval "1492";
          smiv2:max-access "read-write";
          smiv2:oid "1.3.6.1.4.1.9.10.118.1.2.1.1.2";
        }

        leaf ciiSysLevelMinLSPGenInt {
          type CISCO-IETF-ISIS-MIB:CiiUnsigned16TC {
            range "1..65535";
          }
          units "seconds";
          description
           "Minimum interval, in seconds, between successive
            generation of LSPs with the same LSPID at this level
            by this Intermediate System.  This object
            follows the resettingTimer behavior.";
          reference
           "{ISIS.aoi minimumLSPGenerationInterval (11)}";
          smiv2:defval "30";
          smiv2:max-access "read-write";
          smiv2:oid "1.3.6.1.4.1.9.10.118.1.2.1.1.3";
        }

        leaf ciiSysLevelOverloadState {
          type CISCO-IETF-ISIS-MIB:CiiLevelState;
          description
           "The state of the database at this level.
            The value 'off' indicates that IS-IS is not active at
            this level.
            The value 'on' indicates that IS-IS is active at this
            level, and not overloaded.
            The value 'waiting' indicates a database that is low on
            an essential resource, such as memory.
            The administrator may force the state to 'overloaded'
            by setting the object ciiSysLevelSetOverload.
            If the state is 'waiting' or 'overloaded', we originate
            LSPs with the Overload bit set.";
          reference
           "{ISIS.aoi l1State (17)}";
          smiv2:max-access "read-only";
          smiv2:oid "1.3.6.1.4.1.9.10.118.1.2.1.1.4";
        }

        leaf ciiSysLevelSetOverload {
          type boolean;
          description
           "Administratively set the overload bit for the level.
            The overload bit will continue to be set if the
            implementation runs out of memory, independent of
            this variable";
          smiv2:defval "false";
          smiv2:max-access "read-write";
          smiv2:oid "1.3.6.1.4.1.9.10.118.1.2.1.1.5";
        }

        leaf ciiSysLevelSetOverloadUntil {
          type yang:timeticks;
          description
           "If set, the overload bit should be set, and cleared
            after sysUpTime exceeds this value.";
          smiv2:defval "0";
          smiv2:max-access "read-write";
          smiv2:oid "1.3.6.1.4.1.9.10.118.1.2.1.1.6";
        }

        leaf ciiSysLevelMetricStyle {
          type CISCO-IETF-ISIS-MIB:CiiMetricStyle;
          description
           "Which style of Metric do we generate in our LSPs
            at this level? This object follows the
            replaceOnlyWhileDisabled behavior.";
          smiv2:defval "narrow";
          smiv2:max-access "read-write";
          smiv2:oid "1.3.6.1.4.1.9.10.118.1.2.1.1.7";
        }

        leaf ciiSysLevelSPFConsiders {
          type CISCO-IETF-ISIS-MIB:CiiMetricStyle;
          description
           "Which style of Metric do we consider in our
            SPF computation at this level?";
          smiv2:defval "narrow";
          smiv2:max-access "read-write";
          smiv2:oid "1.3.6.1.4.1.9.10.118.1.2.1.1.8";
        }

        leaf ciiSysLevelTEEnabled {
          type boolean;
          description
           "Do we do Traffic Engineering at this level?";
          smiv2:defval "false";
          smiv2:max-access "read-write";
          smiv2:oid "1.3.6.1.4.1.9.10.118.1.2.1.1.9";
        }
      }
    }

    container ciiCircTable {
      description
       "The table of circuits used by this
        Intermediate System.";
      smiv2:oid "1.3.6.1.4.1.9.10.118.1.3.2";

      list ciiCircEntry {
        key "ciiCircIndex";
        description
         "An ciiCircEntry exists for each circuit used by
          Integrated IS-IS on this system.";
        smiv2:oid "1.3.6.1.4.1.9.10.118.1.3.2.1";

        leaf ciiCircIndex {
          type int32 {
            range "1..2147483647";
          }
          description
           "The identifier of this circuit, unique within the
            Intermediate System.  This object follows
            the index behavior.  This is for SNMP Indexing
            purposes only and need not have any relation to
            any protocol value.";
          smiv2:max-access "not-accessible";
          smiv2:oid "1.3.6.1.4.1.9.10.118.1.3.2.1.1";
        }

        leaf ciiCircIfIndex {
          type if-mib:InterfaceIndex;
          description
           "The value of ifIndex for the interface to which this
            circuit corresponds.   This object cannot be modified
            after creation";
          smiv2:max-access "read-write";
          smiv2:oid "1.3.6.1.4.1.9.10.118.1.3.2.1.2";
        }

        leaf ciiCircIfSubIndex {
          type int32;
          description
           "A specifier for the part of the interface ifIndex to which
            this circuit corresponds, such as a DLCI or VPI/VCI.
            This object cannot be modified after creation";
          smiv2:max-access "read-write";
          smiv2:oid "1.3.6.1.4.1.9.10.118.1.3.2.1.3";
        }

        leaf ciiCircAdminState {
          type CISCO-IETF-ISIS-MIB:CiiAdminState;
          description
           "The administrative state of the circuit. This
            object follows the CiiAdminState behavior.";
          smiv2:defval "off";
          smiv2:max-access "read-write";
          smiv2:oid "1.3.6.1.4.1.9.10.118.1.3.2.1.4";
        }

        leaf ciiCircExistState {
          type snmpv2-tc:RowStatus;
          description
           "The existence state of this circuit. This object follows
            the RowStatus behavior.  Setting the state to
            'notInService' halts the generation and processing of
            IS-IS protocol PDUs on this circuit.  Setting the state
            to 'destroy' will also erase any configuration associated
            with the circuit.";
          smiv2:max-access "read-write";
          smiv2:oid "1.3.6.1.4.1.9.10.118.1.3.2.1.5";
        }

        leaf ciiCircType {
          type enumeration {
            enum "broadcast" {
              value "1";
            }
            enum "ptToPt" {
              value "2";
            }
            enum "staticIn" {
              value "3";
            }
            enum "staticOut" {
              value "4";
            }
            enum "dA" {
              value "5";
            }
          }
          description
           "The type of the circuit. This object follows the
            replaceOnlyWhileDisabled behavior. The type specified
            must be compatible with the type of the interface defined
            by the value of ciiCircIfIndex.";
          reference
           "{ISIS.aoi type (33)}";
          smiv2:max-access "read-write";
          smiv2:oid "1.3.6.1.4.1.9.10.118.1.3.2.1.6";
        }

        leaf ciiCircExtDomain {
          type boolean;
          description
           "If true, suppress normal transmission of and
            interpretation of Intra-domain IS-IS PDUs on this
            circuit.";
          reference
           "{ISIS.aoi externalDomain (46)}";
          smiv2:defval "false";
          smiv2:max-access "read-write";
          smiv2:oid "1.3.6.1.4.1.9.10.118.1.3.2.1.7";
        }

        leaf ciiCircLevel {
          type enumeration {
            enum "level1" {
              value "1";
            }
            enum "level2" {
              value "2";
            }
            enum "level1L2" {
              value "3";
            }
          }
          description
           "Indicates which type of packets will be sent and
            accepted on this circuit. The values used will be
            modified by the settings of ciiSysType. This
            object follows the replaceOnlyWhileDisabled behavior.";
          smiv2:defval "level1L2";
          smiv2:max-access "read-write";
          smiv2:oid "1.3.6.1.4.1.9.10.118.1.3.2.1.8";
        }

        leaf ciiCircPassiveCircuit {
          type boolean;
          description
           "Should we include this interface in LSPs, even if
            it is not running the IS-IS Protocol?";
          smiv2:defval "false";
          smiv2:max-access "read-write";
          smiv2:oid "1.3.6.1.4.1.9.10.118.1.3.2.1.9";
        }

        leaf ciiCircMeshGroupEnabled {
          type enumeration {
            enum "inactive" {
              value "1";
            }
            enum "blocked" {
              value "2";
            }
            enum "set" {
              value "3";
            }
          }
          description
           "Is this port a member of a mesh group, or blocked?
            Circuits in the same mesh group act as a virtual
            multiaccess network.  LSPs seen on one circuit in
            a mesh group will not be flooded to another circuit
            in the same mesh group.";
          reference
           "{ RFC 2973 }";
          smiv2:defval "inactive";
          smiv2:max-access "read-write";
          smiv2:oid "1.3.6.1.4.1.9.10.118.1.3.2.1.10";
        }

        leaf ciiCircMeshGroup {
          type uint32;
          description
           "Circuits in the same mesh group act as a virtual
            multiaccess network.  LSPs seen on one circuit in
            a mesh group will not be flooded to another circuit
            in the same mesh group.  If ciiCircMeshGroupEnabled
            is inactive or blocked, this value is ignored.";
          reference
           "{ RFC 2973 }";
          smiv2:max-access "read-write";
          smiv2:oid "1.3.6.1.4.1.9.10.118.1.3.2.1.11";
        }

        leaf ciiCircSmallHellos {
          type boolean;
          description
           "Can we send unpadded hellos on LAN circuits?  'false'
            means LAN Hellos must be padded.
            Implementations should allow the administrator to read
            this value.  An implementation need not be able to
            support unpadded hellos to be conformant.";
          smiv2:defval "false";
          smiv2:max-access "read-write";
          smiv2:oid "1.3.6.1.4.1.9.10.118.1.3.2.1.12";
        }

        leaf ciiCircLastUpTime {
          type yang:timeticks;
          description
           "If the circuit is enabled, the value of sysUpTime
            when ciiCircAdminState most recently entered
            the state 'on'.  If the circuit is not 'on',
            the value of sysUpTime when the circuit last
            entered state 'on', 0 if the circuit has never
            been 'on'.";
          smiv2:max-access "read-only";
          smiv2:oid "1.3.6.1.4.1.9.10.118.1.3.2.1.13";
        }

        leaf ciiCirc3WayEnabled {
          type boolean;
          description
           "Is this circuit enabled to run 3Way handshake?";
          smiv2:defval "true";
          smiv2:max-access "read-write";
          smiv2:oid "1.3.6.1.4.1.9.10.118.1.3.2.1.14";
        }

        leaf ciiCircExtendedCircID {
          type uint32;
          description
           "The value to be used as the extended circuit ID in
            3Way handshake.  This value is only used if
            ciiCirc3WayEnabled is true, and must be unique across
            all circuits on this IS.";
          smiv2:max-access "read-write";
          smiv2:oid "1.3.6.1.4.1.9.10.118.1.3.2.1.15";
        }
      }
    }

    container ciiCircLevelTable {
      description
       "Level specific information about circuits used by IS-IS";
      smiv2:oid "1.3.6.1.4.1.9.10.118.1.4.1";

      list ciiCircLevelEntry {
        key "ciiCircIndex ciiCircLevelIndex";
        description
         "An ciiCircLevelEntry exists for each level on
          each circuit used by Integrated IS-IS on this system.";
        smiv2:oid "1.3.6.1.4.1.9.10.118.1.4.1.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiCircLevelIndex {
          type enumeration {
            enum "level1IS" {
              value "1";
            }
            enum "level2IS" {
              value "2";
            }
          }
          description
           "The level that this entry describes.";
          smiv2:max-access "not-accessible";
          smiv2:oid "1.3.6.1.4.1.9.10.118.1.4.1.1.1";
        }

        leaf ciiCircLevelMetric {
          type CISCO-IETF-ISIS-MIB:CiiDefaultMetric;
          description
           "The metric value of this circuit for this level.";
          reference
           "{ISIS.aoi l1DefaultMetric (35)}";
          smiv2:defval "10";
          smiv2:max-access "read-write";
          smiv2:oid "1.3.6.1.4.1.9.10.118.1.4.1.1.2";
        }

        leaf ciiCircLevelWideMetric {
          type CISCO-IETF-ISIS-MIB:CiiWideMetric;
          description
           "The wide metric value of this circuit for this level.";
          smiv2:defval "10";
          smiv2:max-access "read-write";
          smiv2:oid "1.3.6.1.4.1.9.10.118.1.4.1.1.3";
        }

        leaf ciiCircLevelISPriority {
          type CISCO-IETF-ISIS-MIB:CiiISPriority;
          description
           "The priority for becoming LAN Designated
            Intermediate System at this level.";
          reference
           "{ISIS.aoi l2IntermediateSystemPriority (73)}";
          smiv2:defval "64";
          smiv2:max-access "read-write";
          smiv2:oid "1.3.6.1.4.1.9.10.118.1.4.1.1.4";
        }

        leaf ciiCircLevelIDOctet {
          type int32 {
            range "0..255";
          }
          description
           "A one byte identifier that can be used in protocol packets
            to identify a circuit.  Values of ciiCircLevelIDOctet
            do not need to be unique.  They are only required to
            differ on LANs where the Intermediate System is the
            Designated Intermediate System.";
          smiv2:max-access "read-write";
          smiv2:oid "1.3.6.1.4.1.9.10.118.1.4.1.1.5";
        }

        leaf ciiCircLevelID {
          type CISCO-IETF-ISIS-MIB:CiiCircuitID;
          description
           "On a point to point circuit with a fully initialized
            adjacency to a peer IS, the value of this object is
            the circuit ID negotiated during adjacency initialization.
            On a point to point circuit without such an adjacency,
            the value is the concatenation of the local system ID
            and the one byte ciiCircLevelIDOctet for this circuit
            i.e. the value that would be proposed for the circuit ID.
            
            On other circuit types, the value returned is the zero
            length OCTET STRING.";
          reference
           "{ISIS.aoi ptPtCircuitID (51)}";
          smiv2:max-access "read-only";
          smiv2:oid "1.3.6.1.4.1.9.10.118.1.4.1.1.6";
        }

        leaf ciiCircLevelDesIS {
          type CISCO-IETF-ISIS-MIB:CiiCircuitID;
          description
           "The ID of the LAN Designated Intermediate System
            on this circuit at this level. If, for any reason,
            this system is not partaking in the relevant
            Designated Intermediate System election process,
            then the value returned is the zero length OCTET STRING.";
          reference
           "{ISIS.aoi l2DesignatedIntermediateSystem (75)}";
          smiv2:max-access "read-only";
          smiv2:oid "1.3.6.1.4.1.9.10.118.1.4.1.1.7";
        }

        leaf ciiCircLevelHelloMultiplier {
          type int32 {
            range "2..100";
          }
          description
           "This value is multiplied by the corresponding HelloTimer
            and the result in seconds (rounded up) is used as the
            holding time in transmitted hellos, to be used by
            receivers of hello packets from this IS";
          reference
           "{ISIS.aoi iSISHelloTimer (45)}";
          smiv2:defval "10";
          smiv2:max-access "read-write";
          smiv2:oid "1.3.6.1.4.1.9.10.118.1.4.1.1.8";
        }

        leaf ciiCircLevelHelloTimer {
          type int32 {
            range "10..600000";
          }
          units "milliseconds";
          description
           "Maximum period, in milliseconds, between IIH PDUs
            on multiaccess networks at this level for LANs.
            The value at L1 is used as the period between
            Hellos on L1L2 point to point circuits.  Setting
            this value at level 2 on an L1L2 point to point
            circuit will result in an error of InconsistentValue.
            
            This object follows the resettingTimer behavior.";
          reference
           "{ISIS.aoi iSISHelloTimer (45)}";
          smiv2:defval "3000";
          smiv2:max-access "read-write";
          smiv2:oid "1.3.6.1.4.1.9.10.118.1.4.1.1.9";
        }

        leaf ciiCircLevelDRHelloTimer {
          type int32 {
            range "10..120000";
          }
          units "milliseconds";
          description
           "Period, in milliseconds, between Hello PDUs on
            multiaccess networks when this IS is the Designated
            Intermediate System.  This object follows the
            resettingTimer behavior.";
          reference
           "{ISIS.aoi iSISHelloTimer (45)}";
          smiv2:defval "1000";
          smiv2:max-access "read-write";
          smiv2:oid "1.3.6.1.4.1.9.10.118.1.4.1.1.10";
        }

        leaf ciiCircLevelLSPThrottle {
          type CISCO-IETF-ISIS-MIB:CiiUnsigned16TC {
            range "1..65535";
          }
          units "milliseconds";
          description
           "Minimal interval of time, in milliseconds, between
            transmissions of LSPs on an interface at this level.";
          reference
           "{ISIS.aoi minimumBroadcastLSPTransmissionInterval (5)}";
          smiv2:defval "30";
          smiv2:max-access "read-write";
          smiv2:oid "1.3.6.1.4.1.9.10.118.1.4.1.1.11";
        }

        leaf ciiCircLevelMinLSPRetransInt {
          type int32 {
            range "1..300";
          }
          units "seconds";
          description
           "Minimum interval, in seconds, between re-transmission of
            an LSP at this level. This object follows the
            resettingTimer behavior.
            
            Note that ciiCircLevelLSPThrottle controls
            how fast we send back to back LSPs.  This variable
            controls how fast we re-send the same LSP.";
          reference
           "{ISIS.aoi minimumLSPTransmissionInterval (5)}";
          smiv2:defval "5";
          smiv2:max-access "read-write";
          smiv2:oid "1.3.6.1.4.1.9.10.118.1.4.1.1.12";
        }

        leaf ciiCircLevelCSNPInterval {
          type int32 {
            range "1..600";
          }
          units "seconds";
          description
           "Interval of time, in seconds, between periodic
            transmission of a complete set of CSNPs on
            multiaccess networks if this router is the
            designated router at this level.
            
            This object follows the resettingTimer behavior.";
          reference
           "{ISIS.aoi completeSNPInterval (8)}";
          smiv2:defval "10";
          smiv2:max-access "read-write";
          smiv2:oid "1.3.6.1.4.1.9.10.118.1.4.1.1.13";
        }

        leaf ciiCircLevelPartSNPInterval {
          type int32 {
            range "1..120";
          }
          units "seconds";
          description
           "Minimum interval in seconds between sending Partial
            Sequence Number PDUs at this level. This object
            follows the resettingTimer behavior.";
          reference
           "{ISIS.aoi partialSNPInterval (14)}";
          smiv2:defval "2";
          smiv2:max-access "read-write";
          smiv2:oid "1.3.6.1.4.1.9.10.118.1.4.1.1.14";
        }
      }
    }

    container ciiSystemCounterTable {
      description
       "System wide counters for this Intermediate System.";
      smiv2:oid "1.3.6.1.4.1.9.10.118.1.5.1";

      list ciiSystemCounterEntry {
        key "ciiSysStatLevel";
        description
         "System-wide IS-IS counters.";
        smiv2:oid "1.3.6.1.4.1.9.10.118.1.5.1.1";

        leaf ciiSysStatLevel {
          type enumeration {
            enum "level1IS" {
              value "1";
            }
            enum "level2IS" {
              value "2";
            }
          }
          description
           "The level that this entry describes.";
          smiv2:max-access "not-accessible";
          smiv2:oid "1.3.6.1.4.1.9.10.118.1.5.1.1.1";
        }

        leaf ciiSysStatCorrLSPs {
          type yang:counter32;
          units "frames";
          description
           "Number of corrupted in-memory LSP frames detected.
            
            LSPs received from the wire with a bad checksum
            are silently dropped and not counted.
            
            LSPs received from the wire with parse errors
            are counted by ciiSysStatLSPErrors.";
          reference
           "{ISIS.aoi corruptedLSPsDetected (19)}";
          smiv2:max-access "read-only";
          smiv2:oid "1.3.6.1.4.1.9.10.118.1.5.1.1.2";
        }

        leaf ciiSysStatAuthTypeFails {
          type yang:counter32;
          units "frames";
          description
           "The number of frames with authentication type mismatches
            recognized by this Intermediate System.";
          smiv2:max-access "read-only";
          smiv2:oid "1.3.6.1.4.1.9.10.118.1.5.1.1.3";
        }

        leaf ciiSysStatAuthFails {
          type yang:counter32;
          units "frames";
          description
           "The number of frames with authentication failures
            recognized by this Intermediate System.";
          smiv2:max-access "read-only";
          smiv2:oid "1.3.6.1.4.1.9.10.118.1.5.1.1.4";
        }

        leaf ciiSysStatLSPDbaseOloads {
          type yang:counter32;
          description
           "Number of times the LSP database has become
            overloaded.";
          reference
           "{ISIS.aoi lSPL1DatabaseOverloads (20)}";
          smiv2:max-access "read-only";
          smiv2:oid "1.3.6.1.4.1.9.10.118.1.5.1.1.5";
        }

        leaf ciiSysStatManAddrDropFromAreas {
          type yang:counter32;
          description
           "Number of times a manual address has been dropped from
            the area.";
          reference
           "{ISIS.aoi manualAddressesDroppedFromArea (21)}";
          smiv2:max-access "read-only";
          smiv2:oid "1.3.6.1.4.1.9.10.118.1.5.1.1.6";
        }

        leaf ciiSysStatAttmptToExMaxSeqNums {
          type yang:counter32;
          description
           "Number of times the IS has attempted to exceed the
            maximum sequence number.";
          reference
           "{ISIS.aoi attemptsToExceedmaximumSequenceNumber (22)}";
          smiv2:max-access "read-only";
          smiv2:oid "1.3.6.1.4.1.9.10.118.1.5.1.1.7";
        }

        leaf ciiSysStatSeqNumSkips {
          type yang:counter32;
          description
           "Number of times a sequence number skip has occurred.";
          reference
           "{ISIS.aoi sequenceNumberSkips (23)}";
          smiv2:max-access "read-only";
          smiv2:oid "1.3.6.1.4.1.9.10.118.1.5.1.1.8";
        }

        leaf ciiSysStatOwnLSPPurges {
          type yang:counter32;
          description
           "Number of times a zero-aged copy of the system's own LSP
            is received from some other node.";
          reference
           "{ISIS.aoi ownLSPPurges (24)}";
          smiv2:max-access "read-only";
          smiv2:oid "1.3.6.1.4.1.9.10.118.1.5.1.1.9";
        }

        leaf ciiSysStatIDFieldLenMismatches {
          type yang:counter32;
          units "frames";
          description
           "Number of times a PDU is received with a different value
            for ID field length to that of the receiving system.";
          reference
           "{ISIS.aoi iDFieldLengthMismatches (25)}";
          smiv2:max-access "read-only";
          smiv2:oid "1.3.6.1.4.1.9.10.118.1.5.1.1.10";
        }

        leaf ciiSysStatPartChanges {
          type yang:counter32;
          description
           "Partition changes";
          smiv2:max-access "read-only";
          smiv2:oid "1.3.6.1.4.1.9.10.118.1.5.1.1.11";
        }

        leaf ciiSysStatSPFRuns {
          type yang:counter32;
          description
           "Number of times we ran SPF at this level.";
          smiv2:max-access "read-only";
          smiv2:oid "1.3.6.1.4.1.9.10.118.1.5.1.1.12";
        }

        leaf ciiSysStatLSPErrors {
          type yang:counter32;
          units "frames";
          description
           "Number of LSP frames with errors we have received.";
          smiv2:max-access "read-only";
          smiv2:oid "1.3.6.1.4.1.9.10.118.1.5.1.1.13";
        }
      }
    }

    container ciiCircuitCounterTable {
      description
       "Circuit specific counters for this
        Intermediate System.";
      smiv2:oid "1.3.6.1.4.1.9.10.118.1.5.2";

      list ciiCircuitCounterEntry {
        key "ciiCircIndex ciiCircuitType";
        description
         "An ciiCircuitCounterEntry exists for each circuit
          used by Integrated IS-IS on this system.";
        smiv2:oid "1.3.6.1.4.1.9.10.118.1.5.2.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiCircuitType {
          type enumeration {
            enum "lanlevel1" {
              value "1";
            }
            enum "lanlevel2" {
              value "2";
            }
            enum "p2pcircuit" {
              value "3";
            }
          }
          description
           "What type of circuit saw these counts?
            
            The point to point Hello PDU includes
            both L1 and L2, and ISs form a single
            adjacency on point to point links.
            Thus we combine counts on
            point to point links into one group.";
          smiv2:max-access "not-accessible";
          smiv2:oid "1.3.6.1.4.1.9.10.118.1.5.2.1.1";
        }

        leaf ciiCircAdjChanges {
          type yang:counter32;
          description
           "The number of times an adjacency state change has
            occurred on this circuit.";
          reference
           "{ISIS.aoi changesInAdjacencyState (40)}";
          smiv2:max-access "read-only";
          smiv2:oid "1.3.6.1.4.1.9.10.118.1.5.2.1.2";
        }

        leaf ciiCircNumAdj {
          type uint32;
          description
           "The number of adjacencies on this circuit.";
          reference
           "{ISIS.aoi changesInAdjacencyState (40)}";
          smiv2:max-access "read-only";
          smiv2:oid "1.3.6.1.4.1.9.10.118.1.5.2.1.3";
        }

        leaf ciiCircInitFails {
          type yang:counter32;
          description
           "The number of times initialization of this circuit has
            failed.  This counts events such as PPP NCP failures.
            Failures to form an adjacency are counted by
            ciiCircRejAdjs.";
          smiv2:max-access "read-only";
          smiv2:oid "1.3.6.1.4.1.9.10.118.1.5.2.1.4";
        }

        leaf ciiCircRejAdjs {
          type yang:counter32;
          description
           "The number of times an adjacency has been rejected on
            this circuit.";
          reference
           "{ISIS.aoi rejectedAdjacencies (42)}";
          smiv2:max-access "read-only";
          smiv2:oid "1.3.6.1.4.1.9.10.118.1.5.2.1.5";
        }

        leaf ciiCircIDFieldLenMismatches {
          type yang:counter32;
          units "frames";
          description
           "The number of times an IS-IS control PDU with an ID
            field length different to that for this system has been
            received.";
          reference
           "{ISIS.aoi iDFieldLengthMismatches (25)}";
          smiv2:max-access "read-only";
          smiv2:oid "1.3.6.1.4.1.9.10.118.1.5.2.1.6";
        }

        leaf ciiCircMaxAreaAddrMismatches {
          type yang:counter32;
          description
           "The number of times an IS-IS control PDU with a
            max area address field different to that for this
            system has been received.";
          reference
           "{ISIS.aoi iDFieldLengthMismatches (25)}";
          smiv2:max-access "read-only";
          smiv2:oid "1.3.6.1.4.1.9.10.118.1.5.2.1.7";
        }

        leaf ciiCircAuthTypeFails {
          type yang:counter32;
          description
           "The number of times an IS-IS control PDU with
            an auth type field different to that for this
            system has been received.";
          smiv2:max-access "read-only";
          smiv2:oid "1.3.6.1.4.1.9.10.118.1.5.2.1.8";
        }

        leaf ciiCircAuthFails {
          type yang:counter32;
          description
           "The number of times an IS-IS control PDU with
            the correct auth type has failed to pass authentication
            validation.";
          smiv2:max-access "read-only";
          smiv2:oid "1.3.6.1.4.1.9.10.118.1.5.2.1.9";
        }

        leaf ciiCircLANDesISChanges {
          type yang:counter32;
          description
           "The number of times the Designated IS has changed
            on this circuit at this level.  If the circuit is
            point to point, this count is zero.";
          smiv2:max-access "read-only";
          smiv2:oid "1.3.6.1.4.1.9.10.118.1.5.2.1.10";
        }
      }
    }

    container ciiPacketCounterTable {
      description
       "Information about IS-IS protocol traffic at one level
        on one circuit in one direction";
      smiv2:oid "1.3.6.1.4.1.9.10.118.1.5.3";

      list ciiPacketCounterEntry {
        key "ciiCircIndex ciiPacketCountLevel ciiPacketCountDirection";
        description
         "Information about IS-IS protocol traffic at one level
          on one circuit in one direction";
        smiv2:oid "1.3.6.1.4.1.9.10.118.1.5.3.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiPacketCountLevel {
          type enumeration {
            enum "level1" {
              value "1";
            }
            enum "level2" {
              value "2";
            }
          }
          description
           "The level at which these PDU counts have been collected.";
          smiv2:max-access "not-accessible";
          smiv2:oid "1.3.6.1.4.1.9.10.118.1.5.3.1.1";
        }

        leaf ciiPacketCountDirection {
          type enumeration {
            enum "sending" {
              value "1";
            }
            enum "receiving" {
              value "2";
            }
          }
          description
           "Were we sending or receiving these PDUs?";
          smiv2:max-access "not-accessible";
          smiv2:oid "1.3.6.1.4.1.9.10.118.1.5.3.1.2";
        }

        leaf ciiPacketCountIIHellos {
          type yang:counter32;
          units "frames";
          description
           "The number of IS-IS Hello PDU frames seen in this
            direction at this level.
            
            Point-to-Point IIH PDUs are counted at
            the lowest enabled level: at L1 on L1 or L1L2 circuits,
            and at L2 otherwise.";
          reference
           "{ISIS.aoi iSISControlPDUsSent (43)}";
          smiv2:max-access "read-only";
          smiv2:oid "1.3.6.1.4.1.9.10.118.1.5.3.1.3";
        }

        leaf ciiPacketCountISHellos {
          type yang:counter32;
          units "frames";
          description
           "The number of ES-IS Hello PDU frames seen in this
            direction.  ISH PDUs are counted at the
            lowest enabled level: at L1 on L1 or L1L2
            circuits, and at L2 otherwise.";
          smiv2:max-access "read-only";
          smiv2:oid "1.3.6.1.4.1.9.10.118.1.5.3.1.4";
        }

        leaf ciiPacketCountESHellos {
          type yang:counter32;
          units "frames";
          description
           "The number of ES Hello PDU frames seen in this
            direction.  ESH PDUs are counted at the
            lowest enabled level: at L1 on L1 or L1L2
            circuits, and at L2 otherwise.";
          smiv2:max-access "read-only";
          smiv2:oid "1.3.6.1.4.1.9.10.118.1.5.3.1.5";
        }

        leaf ciiPacketCountLSPs {
          type yang:counter32;
          units "frames";
          description
           "The number of IS-IS LSP frames seen in this
            direction at this level.";
          reference
           "{ISIS.aoi iSISControlPDUsSent (43)}";
          smiv2:max-access "read-only";
          smiv2:oid "1.3.6.1.4.1.9.10.118.1.5.3.1.6";
        }

        leaf ciiPacketCountCSNPs {
          type yang:counter32;
          units "frames";
          description
           "The number of IS-IS CSNP frames seen in this
            direction at this level.";
          reference
           "{ISIS.aoi iSISControlPDUsSent (43)}";
          smiv2:max-access "read-only";
          smiv2:oid "1.3.6.1.4.1.9.10.118.1.5.3.1.7";
        }

        leaf ciiPacketCountPSNPs {
          type yang:counter32;
          units "frames";
          description
           "The number of IS-IS PSNP frames seen in this
            direction at this level.";
          reference
           "{ISIS.aoi iSISControlPDUsSent (43)}";
          smiv2:max-access "read-only";
          smiv2:oid "1.3.6.1.4.1.9.10.118.1.5.3.1.8";
        }

        leaf ciiPacketCountUnknowns {
          type yang:counter32;
          units "frames";
          description
           "The number of unknown IS-IS PDU frames seen
            at this level.";
          reference
           "{ISIS.aoi iSISControlPDUsSent (43)}";
          smiv2:max-access "read-only";
          smiv2:oid "1.3.6.1.4.1.9.10.118.1.5.3.1.9";
        }
      }
    }

    container ciiISAdjTable {
      description
       "The table of adjacencies to Intermediate Systems.";
      smiv2:oid "1.3.6.1.4.1.9.10.118.1.6.1";

      list ciiISAdjEntry {
        key "ciiCircIndex ciiISAdjIndex";
        description
         "Each entry corresponds to one adjacency to an
          Intermediate System on this system.";
        smiv2:oid "1.3.6.1.4.1.9.10.118.1.6.1.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiISAdjIndex {
          type int32 {
            range "1..2000000000";
          }
          description
           "A unique value identifying the IS adjacency from all
            other such adjacencies on this circuit. This value is
            automatically assigned by the system when the adjacency
            is created.";
          smiv2:max-access "not-accessible";
          smiv2:oid "1.3.6.1.4.1.9.10.118.1.6.1.1.1";
        }

        leaf ciiISAdjState {
          type enumeration {
            enum "down" {
              value "1";
            }
            enum "initializing" {
              value "2";
            }
            enum "up" {
              value "3";
            }
            enum "failed" {
              value "4";
            }
          }
          description
           "The state of the adjacency";
          reference
           "{ISIS.aoi adjacencyState (78)}";
          smiv2:max-access "read-only";
          smiv2:oid "1.3.6.1.4.1.9.10.118.1.6.1.1.2";
        }

        leaf ciiISAdj3WayState {
          type enumeration {
            enum "up" {
              value "0";
            }
            enum "initializing" {
              value "1";
            }
            enum "down" {
              value "2";
            }
            enum "failed" {
              value "3";
            }
          }
          description
           "The 3Way state of the adjacency.  These are picked
            to match the historical on-the-wire representation
            of the 3Way state, and are not intended to match
            ciiISAdjState.";
          reference
           "{ RFC 3373 }";
          smiv2:max-access "read-only";
          smiv2:oid "1.3.6.1.4.1.9.10.118.1.6.1.1.3";
        }

        leaf ciiISAdjNeighSNPAAddress {
          type CISCO-IETF-ISIS-MIB:CiiOSINSAddress;
          description
           "The SNPA address of the neighboring system.";
          reference
           "{ISIS.aoi neighbourSNPAAddress (79)}";
          smiv2:max-access "read-only";
          smiv2:oid "1.3.6.1.4.1.9.10.118.1.6.1.1.4";
        }

        leaf ciiISAdjNeighSysType {
          type enumeration {
            enum "l1IntermediateSystem" {
              value "1";
            }
            enum "l2IntermediateSystem" {
              value "2";
            }
            enum "l1L2IntermediateSystem" {
              value "3";
            }
            enum "unknown" {
              value "4";
            }
          }
          description
           "The type of the neighboring system.";
          reference
           "{ISIS.aoi neighbourSystemType (80)}";
          smiv2:max-access "read-only";
          smiv2:oid "1.3.6.1.4.1.9.10.118.1.6.1.1.5";
        }

        leaf ciiISAdjNeighSysID {
          type CISCO-IETF-ISIS-MIB:CiiSystemID;
          description
           "The system ID of the neighboring Intermediate
            System.";
          reference
           "{ISIS.aoi neighbourSystemIds (83)}";
          smiv2:max-access "read-only";
          smiv2:oid "1.3.6.1.4.1.9.10.118.1.6.1.1.6";
        }

        leaf ciiISAdjNbrExtendedCircID {
          type uint32;
          description
           "The 4 byte Extended Circuit ID learned from the
            Neighbor during 3-way handshake, or 0.";
          smiv2:max-access "read-only";
          smiv2:oid "1.3.6.1.4.1.9.10.118.1.6.1.1.7";
        }

        leaf ciiISAdjUsage {
          type enumeration {
            enum "level1" {
              value "1";
            }
            enum "level2" {
              value "2";
            }
            enum "level1and2" {
              value "3";
            }
          }
          description
           "How is the adjacency used?  On a point-to-point link,
            this might be level1and2, but on a LAN, the usage will
            be level1 on the adjacency between peers at L1,
            and level2 for the adjacency between peers at L2.";
          reference
           "{ISIS.aoi adjacencyUsage (82)}";
          smiv2:max-access "read-only";
          smiv2:oid "1.3.6.1.4.1.9.10.118.1.6.1.1.8";
        }

        leaf ciiISAdjHoldTimer {
          type CISCO-IETF-ISIS-MIB:CiiUnsigned16TC {
            range "1..65535";
          }
          units "seconds";
          description
           "The holding time in seconds for this adjacency.
            This value is based on received IIH PDUs and
            the elapsed time since receipt.";
          reference
           "{ISIS.aoi holdingTimer (85)}";
          smiv2:max-access "read-only";
          smiv2:oid "1.3.6.1.4.1.9.10.118.1.6.1.1.9";
        }

        leaf ciiISAdjNeighPriority {
          type CISCO-IETF-ISIS-MIB:CiiISPriority;
          description
           "Priority of the neighboring Intermediate System for
            becoming the Designated Intermediate System.";
          reference
           "{ISIS.aoi lANPriority (86)}";
          smiv2:max-access "read-only";
          smiv2:oid "1.3.6.1.4.1.9.10.118.1.6.1.1.10";
        }

        leaf ciiISAdjLastUpTime {
          type yang:timeticks;
          units "hundredths of a second";
          description
           "If the ciiISAdjState is in state 'up', the value
            of sysUpTime when the adjacency most recently
            entered the state 'up',  or 0 if it has never
            been in state 'up'.";
          smiv2:max-access "read-only";
          smiv2:oid "1.3.6.1.4.1.9.10.118.1.6.1.1.11";
        }
      }
    }

    container ciiISAdjAreaAddrTable {
      description
       "This table contains the set of Area Addresses of
        neighboring Intermediate Systems as reported in received
        IIH PDUs.";
      reference
       "{ISIS.aoi areaAddressesOfNeighbour (84)}";
      smiv2:oid "1.3.6.1.4.1.9.10.118.1.6.2";

      list ciiISAdjAreaAddrEntry {
        key "ciiCircIndex ciiISAdjIndex ciiISAdjAreaAddrIndex";
        description
         "Each entry contains one Area Address reported by a
          neighboring Intermediate System in its IIH PDUs.";
        smiv2:oid "1.3.6.1.4.1.9.10.118.1.6.2.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiISAdjIndex {
          type leafref {
            path "/CISCO-IETF-ISIS-MIB:CISCO-IETF-ISIS-MIB/CISCO-IETF-ISIS-MIB:ciiISAdjTable/CISCO-IETF-ISIS-MIB:ciiISAdjEntry/CISCO-IETF-ISIS-MIB:ciiISAdjIndex";
          }
        }

        leaf ciiISAdjAreaAddrIndex {
          type int32 {
            range "1..2000000000";
          }
          description
           "An index for the areas associated with one neighbor.
            This provides a simple way to walk the table.";
          smiv2:max-access "not-accessible";
          smiv2:oid "1.3.6.1.4.1.9.10.118.1.6.2.1.1";
        }

        leaf ciiISAdjAreaAddress {
          type CISCO-IETF-ISIS-MIB:CiiOSINSAddress;
          description
           "One Area Address as reported in IIH PDUs received from
            the neighbor.";
          smiv2:max-access "read-only";
          smiv2:oid "1.3.6.1.4.1.9.10.118.1.6.2.1.2";
        }
      }
    }

    container ciiISAdjIPAddrTable {
      description
       "This table contains the set of IP Addresses of
        neighboring Intermediate Systems as reported in received
        IIH PDUs.";
      smiv2:oid "1.3.6.1.4.1.9.10.118.1.6.3";

      list ciiISAdjIPAddrEntry {
        key "ciiCircIndex ciiISAdjIndex ciiISAdjIPAddrIndex";
        description
         "Each entry contains one IP Address reported by a
          neighboring Intermediate System in its IIH PDUs.";
        smiv2:oid "1.3.6.1.4.1.9.10.118.1.6.3.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiISAdjIndex {
          type leafref {
            path "/CISCO-IETF-ISIS-MIB:CISCO-IETF-ISIS-MIB/CISCO-IETF-ISIS-MIB:ciiISAdjTable/CISCO-IETF-ISIS-MIB:ciiISAdjEntry/CISCO-IETF-ISIS-MIB:ciiISAdjIndex";
          }
        }

        leaf ciiISAdjIPAddrIndex {
          type int32 {
            range "1..2000000000";
          }
          description
           "An index to this table which identifies the IP addresses
            to which this entry belongs.";
          smiv2:max-access "not-accessible";
          smiv2:oid "1.3.6.1.4.1.9.10.118.1.6.3.1.1";
        }

        leaf ciiISAdjIPAddrType {
          type inet-address:InetAddressType;
          description
           "The type of one IP Address as reported in IIH PDUs
            received from the neighbor.";
          smiv2:max-access "read-only";
          smiv2:oid "1.3.6.1.4.1.9.10.118.1.6.3.1.2";
        }

        leaf ciiISAdjIPAddrAddress {
          type inet-address:InetAddress {
            length "4|16";
          }
          description
           "One IP Address as reported in IIH PDUs received from the
            neighbor.";
          smiv2:max-access "read-only";
          smiv2:oid "1.3.6.1.4.1.9.10.118.1.6.3.1.3";
        }
      }
    }

    container ciiISAdjProtSuppTable {
      description
       "This table contains the set of protocols supported by
        neighboring Intermediate Systems as reported in received
        IIH PDUs.";
      smiv2:oid "1.3.6.1.4.1.9.10.118.1.6.4";

      list ciiISAdjProtSuppEntry {
        key "ciiCircIndex ciiISAdjIndex ciiISAdjProtSuppProtocol";
        description
         "Each entry contains one protocol supported by a
          neighboring Intermediate System as reported in its IIH
          PDUs.";
        smiv2:oid "1.3.6.1.4.1.9.10.118.1.6.4.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiISAdjIndex {
          type leafref {
            path "/CISCO-IETF-ISIS-MIB:CISCO-IETF-ISIS-MIB/CISCO-IETF-ISIS-MIB:ciiISAdjTable/CISCO-IETF-ISIS-MIB:ciiISAdjEntry/CISCO-IETF-ISIS-MIB:ciiISAdjIndex";
          }
        }

        leaf ciiISAdjProtSuppProtocol {
          type CISCO-IETF-ISIS-MIB:CiiSupportedProtocol;
          description
           "One supported protocol as reported in IIH PDUs received
            from the neighbor.";
          smiv2:max-access "read-only";
          smiv2:oid "1.3.6.1.4.1.9.10.118.1.6.4.1.1";
        }
      }
    }

    container ciiRATable {
      description
       "The table of Reachable Addresses to NSAPs or Address
        Prefixes.";
      smiv2:oid "1.3.6.1.4.1.9.10.118.1.7.1";

      list ciiRAEntry {
        key "ciiCircIndex ciiRAIndex";
        description
         "Each entry defines a Reachable Address to a NSAP or
          Address Prefix.";
        smiv2:oid "1.3.6.1.4.1.9.10.118.1.7.1.1";

        leaf ciiCircIndex {
          type leafref {
            path "/CISCO-IETF-ISIS-MIB:CISCO-IETF-ISIS-MIB/CISCO-IETF-ISIS-MIB:ciiCircTable/CISCO-IETF-ISIS-MIB:ciiCircEntry/CISCO-IETF-ISIS-MIB:ciiCircIndex";
          }
        }

        leaf ciiRAIndex {
          type int32 {
            range "1..2000000000";
          }
          description
           "The identifier for this ciiRAEntry. This value must be
            unique amongst all Reachable Addresses on the same parent
            Circuit. This object follows the index and ManualOrAutomatic
            behaviors.";
          smiv2:max-access "not-accessible";
          smiv2:oid "1.3.6.1.4.1.9.10.118.1.7.1.1.1";
        }

        leaf ciiRAExistState {
          type snmpv2-tc:RowStatus;
          description
           "The existence state of this Reachable Address. This
            object follows the ManualOrAutomatic behaviors.";
          smiv2:max-access "read-write";
          smiv2:oid "1.3.6.1.4.1.9.10.118.1.7.1.1.2";
        }

        leaf ciiRAAdminState {
          type CISCO-IETF-ISIS-MIB:CiiAdminState;
          description
           "The administrative state of the Reachable Address. This
            object follows the CiiAdminState and ManualOrAutomatic
            behaviors.";
          smiv2:defval "off";
          smiv2:max-access "read-write";
          smiv2:oid "1.3.6.1.4.1.9.10.118.1.7.1.1.3";
        }

        leaf ciiRAAddrPrefix {
          type CISCO-IETF-ISIS-MIB:CiiOSINSAddress;
          description
           "The destination of this Reachable Address. This is an
            Address Prefix. This object follows the
            replaceOnlyWhileDisabled and ManualOrAutomatic
            behaviors.";
          reference
           "{ISIS.aoi addressPrefix (98)}";
          smiv2:max-access "read-write";
          smiv2:oid "1.3.6.1.4.1.9.10.118.1.7.1.1.4";
        }

        leaf ciiRAMapType {
          type enumeration {
            enum "none" {
              value "1";
            }
            enum "explicit" {
              value "2";
            }
            enum "extractIDI" {
              value "3";
            }
            enum "extractDSP" {
              value "4";
            }
          }
          description
           "The type of mapping to be employed to ascertain the SNPA
            Address which should be used in forwarding PDUs for this
            Reachable Address prefix. This object follows the
            ManualOrAutomatic behavior. The following values of
            mapping type are defined:
            
                none: The mapping is null because the neighbor SNPA is
                      implicit by nature of the subnetwork (e.g. a
                      point-to-point linkage).
            
                explicit: The subnetwork addresses in the object
                      ciiRASNPAAddress is to be used.
            
                extractIDI: The SNPA is embedded in the IDI of
                      the destination NSAP Address. The mapping
                      algorithm extracts the SNPA to be used
                      according to the format and encoding rules of
                      ISO8473/Add2. This SNPA extraction algorithm can
                      be used in conjunction with Reachable Address
                      prefixes from the X.121, F.69, E.163 and E.164
                      addressing subdomains.
            
                extractDSP: All, or a suffix, of the SNPA is embedded
                      in the DSP of the destination address. This SNPA
                      extraction algorithm extracts the embedded
                      subnetwork addressing information by performing a
                      logical AND of the ciiRASNPAMask object value
                      with the destination address. The part of the
                      SNPA extracted from the destination NSAP is
                      appended to the ciiRASNPAPrefix object value to
                      form the next hop subnetwork addressing
                      information.";
          reference
           "{ISO10589-ISIS.aoi mappingType (107)}";
          smiv2:max-access "read-write";
          smiv2:oid "1.3.6.1.4.1.9.10.118.1.7.1.1.5";
        }

        leaf ciiRAMetric {
          type CISCO-IETF-ISIS-MIB:CiiDefaultMetric;
          description
           "The metric value for reaching the specified
            prefix over this circuit. This object follows the
            ManualOrAutomatic behavior.";
          reference
           "{ISIS.aoi DefaultMetric (99)}";
          smiv2:defval "20";
          smiv2:max-access "read-write";
          smiv2:oid "1.3.6.1.4.1.9.10.118.1.7.1.1.6";
        }

        leaf ciiRAMetricType {
          type CISCO-IETF-ISIS-MIB:CiiMetricType;
          description
           "Indicates whether the metric is internal or
            external. This object follows the ManualOrAutomatic
            behavior.";
          reference
           "{ISIS.aoi DefaultMetricType (103)}";
          smiv2:defval "internal";
          smiv2:max-access "read-write";
          smiv2:oid "1.3.6.1.4.1.9.10.118.1.7.1.1.7";
        }

        leaf ciiRASNPAAddress {
          type CISCO-IETF-ISIS-MIB:CiiOSINSAddress;
          description
           "The SNPA Address to which a PDU may be forwarded in
            order to reach a destination which matches the address
            prefix of the Reachable Address. This object follows the
            ManualOrAutomatic behavior.";
          reference
           "{ISIS.aoi sNPAAddresses (109)}";
          smiv2:defval "";
          smiv2:max-access "read-write";
          smiv2:oid "1.3.6.1.4.1.9.10.118.1.7.1.1.8";
        }

        leaf ciiRASNPAMask {
          type CISCO-IETF-ISIS-MIB:CiiOSINSAddress;
          description
           "A bit mask with 1 bits indicating the positions in the
            effective destination address from which embedded SNPA
            information is to be extracted. For the extraction the
            first octet of the ciiRASNPAMask object value is aligned
            with the first octet (AFI) of the NSAP Address. If the
            ciiRASNPAMask object value and NSAP Address are of
            different lengths, the shorter of the two is logically
            padded with zeros before performing the extraction. This
            object follows the ManualOrAutomatic behavior.";
          reference
           "{ISIS.aoi sNPAMask (122)}";
          smiv2:defval "'00'H";
          smiv2:max-access "read-write";
          smiv2:oid "1.3.6.1.4.1.9.10.118.1.7.1.1.9";
        }

        leaf ciiRASNPAPrefix {
          type CISCO-IETF-ISIS-MIB:CiiOSINSAddress;
          description
           "A fixed SNPA prefix for use when the ciiRAMapType is
            extractDSP. The SNPA Address to use is formed by
            concatenating the fixed SNPA prefix with a variable SNPA
            part that is extracted from the effective destination
            address. For Reachable Address prefixes in which the
            entire SNPA is embedded in the DSP the SNPA Prefix shall
            be null. This object follows the ManualOrAutomatic
            behavior.";
          reference
           "{ISIS.aoi sNPAPrefix (123)}";
          smiv2:defval "'00'H";
          smiv2:max-access "read-write";
          smiv2:oid "1.3.6.1.4.1.9.10.118.1.7.1.1.10";
        }

        leaf ciiRAType {
          type enumeration {
            enum "manual" {
              value "1";
            }
            enum "automatic" {
              value "2";
            }
          }
          description
           "The type of Reachable address. Those of type
            manual are created by the network manager. Those
            of type automatic are created through propagation
            of routing information from another routing
            protocol (eg. IDRP). ";
          smiv2:defval "manual";
          smiv2:max-access "read-write";
          smiv2:oid "1.3.6.1.4.1.9.10.118.1.7.1.1.11";
        }
      }
    }

    container ciiIPRATable {
      description
       "The table of IP Reachable Addresses to networks,
        subnetworks or hosts either manually configured or
        learned from another protocol.";
      smiv2:oid "1.3.6.1.4.1.9.10.118.1.8.1";

      list ciiIPRAEntry {
        key "ciiIPRADestType ciiIPRADest ciiIPRADestPrefixLen ciiIPRANextHopIndex";
        description
         "Each entry defines an IP Reachable Address to a network,
          subnetwork or host.
          
          Each IP Reachable Address may have multiple entries in the
          table, one for each equal cost path to the reachable address.";
        smiv2:oid "1.3.6.1.4.1.9.10.118.1.8.1.1";

        leaf ciiIPRADestType {
          type inet-address:InetAddressType;
          description
           "The type of this IP Reachable Address.  This object
            follows the ManualOrAutomatic behavior.";
          smiv2:max-access "not-accessible";
          smiv2:oid "1.3.6.1.4.1.9.10.118.1.8.1.1.1";
        }

        leaf ciiIPRADest {
          type inet-address:InetAddress {
            length "4|16";
          }
          description
           "The destination of this IP Reachable Address. This is
            either a network address, subnetwork address or host
            address. This object follows the ManualOrAutomatic
            behavior.";
          smiv2:max-access "not-accessible";
          smiv2:oid "1.3.6.1.4.1.9.10.118.1.8.1.1.2";
        }

        leaf ciiIPRADestPrefixLen {
          type inet-address:InetAddressPrefixLength {
            range "0..128";
          }
          description
           "The length of the IP Netmask for Reachability Address.
            This object follows the ManualOrAutomatic behavior.";
          smiv2:max-access "not-accessible";
          smiv2:oid "1.3.6.1.4.1.9.10.118.1.8.1.1.3";
        }

        leaf ciiIPRANextHopIndex {
          type int32 {
            range "1..65535";
          }
          description
           "Index of next hop.  Used when there are multiple Equal
            Cost Multipath alternatives for the same destination.";
          smiv2:max-access "not-accessible";
          smiv2:oid "1.3.6.1.4.1.9.10.118.1.8.1.1.4";
        }

        leaf ciiIPRANextHopType {
          type inet-address:InetAddressType;
          description
           "The type of the IP next hop address.";
          smiv2:max-access "read-write";
          smiv2:oid "1.3.6.1.4.1.9.10.118.1.8.1.1.5";
        }

        leaf ciiIPRANextHop {
          type inet-address:InetAddress {
            length "4|16";
          }
          description
           "The IP next hop to this destination.";
          smiv2:max-access "read-write";
          smiv2:oid "1.3.6.1.4.1.9.10.118.1.8.1.1.6";
        }

        leaf ciiIPRAType {
          type enumeration {
            enum "manual" {
              value "1";
            }
            enum "automatic" {
              value "2";
            }
          }
          description
           "The type of this IP Reachable Address. Those of type
            manual are created by the network manager. Those of type
            automatic are created through propagation of routing
            information from another routing protocol.  This object
            follows the ManualOrAutomatic behavior.";
          smiv2:max-access "read-write";
          smiv2:oid "1.3.6.1.4.1.9.10.118.1.8.1.1.7";
        }

        leaf ciiIPRAExistState {
          type snmpv2-tc:RowStatus;
          description
           "The state of this IP Reachable Address. This object
            follows the ExistenceState and ManualOrAutomatic
            behaviors.";
          smiv2:max-access "read-write";
          smiv2:oid "1.3.6.1.4.1.9.10.118.1.8.1.1.8";
        }

        leaf ciiIPRAAdminState {
          type CISCO-IETF-ISIS-MIB:CiiAdminState;
          description
           "The administrative state of the IP Reachable Address. This
            object follows the CiiAdminState and ManualOrAutomatic
            behaviors.";
          smiv2:defval "off";
          smiv2:max-access "read-write";
          smiv2:oid "1.3.6.1.4.1.9.10.118.1.8.1.1.9";
        }

        leaf ciiIPRAMetric {
          type CISCO-IETF-ISIS-MIB:CiiDefaultMetric;
          description
           "The metric value for reaching the specified
            destination over this circuit. This object follows the
            ManualOrAutomatic behavior.";
          smiv2:defval "10";
          smiv2:max-access "read-write";
          smiv2:oid "1.3.6.1.4.1.9.10.118.1.8.1.1.10";
        }

        leaf ciiIPRAMetricType {
          type CISCO-IETF-ISIS-MIB:CiiMetricType;
          description
           "Indicates whether the metric is internal or
            external. This object follows the ManualOrAutomatic
            behavior.";
          smiv2:defval "internal";
          smiv2:max-access "read-write";
          smiv2:oid "1.3.6.1.4.1.9.10.118.1.8.1.1.11";
        }

        leaf ciiIPRAFullMetric {
          type CISCO-IETF-ISIS-MIB:CiiFullMetric;
          description
           "The wide metric value for reaching the specified
            destination over this circuit. This object follows the
            ManualOrAutomatic behavior.";
          smiv2:defval "10";
          smiv2:max-access "read-write";
          smiv2:oid "1.3.6.1.4.1.9.10.118.1.8.1.1.12";
        }

        leaf ciiIPRASNPAAddress {
          type CISCO-IETF-ISIS-MIB:CiiOSINSAddress;
          description
           "The SNPA Address to which a PDU may be forwarded in
            order to reach a destination which matches this IP
            Reachable Address. This object follows the
            ManualOrAutomatic behavior.";
          smiv2:defval "";
          smiv2:max-access "read-write";
          smiv2:oid "1.3.6.1.4.1.9.10.118.1.8.1.1.13";
        }

        leaf ciiIPRASourceType {
          type enumeration {
            enum "static" {
              value "1";
            }
            enum "direct" {
              value "2";
            }
            enum "ospfv2" {
              value "3";
            }
            enum "ospfv3" {
              value "4";
            }
            enum "isis" {
              value "5";
            }
            enum "rip" {
              value "6";
            }
            enum "igrp" {
              value "7";
            }
            enum "eigrp" {
              value "8";
            }
            enum "bgp" {
              value "9";
            }
            enum "other" {
              value "10";
            }
          }
          description
           "The origin of this route.";
          smiv2:max-access "read-only";
          smiv2:oid "1.3.6.1.4.1.9.10.118.1.8.1.1.14";
        }
      }
    }

    container ciiLSPSummaryTable {
      description
       "The table of LSP Headers.";
      smiv2:oid "1.3.6.1.4.1.9.10.118.1.9.1";

      list ciiLSPSummaryEntry {
        key "ciiLSPLevel ciiLSPID";
        description
         "Each entry provides a summary describing an
          LSP currently stored in the system.";
        smiv2:oid "1.3.6.1.4.1.9.10.118.1.9.1.1";

        leaf ciiLSPLevel {
          type CISCO-IETF-ISIS-MIB:CiiISLevel;
          description
           "At which level does this LSP appear?";
          smiv2:max-access "not-accessible";
          smiv2:oid "1.3.6.1.4.1.9.10.118.1.9.1.1.1";
        }

        leaf ciiLSPID {
          type CISCO-IETF-ISIS-MIB:CiiLinkStatePDUID;
          description
           "The 8 byte LSP ID, consisting of the SystemID,
            Circuit ID, and Fragment Number.";
          smiv2:max-access "not-accessible";
          smiv2:oid "1.3.6.1.4.1.9.10.118.1.9.1.1.2";
        }

        leaf ciiLSPSeq {
          type uint32;
          description
           "The sequence number for this LSP.";
          smiv2:max-access "read-only";
          smiv2:oid "1.3.6.1.4.1.9.10.118.1.9.1.1.3";
        }

        leaf ciiLSPZeroLife {
          type boolean;
          description
           "Is this LSP being purged by this System?";
          smiv2:max-access "read-only";
          smiv2:oid "1.3.6.1.4.1.9.10.118.1.9.1.1.4";
        }

        leaf ciiLSPChecksum {
          type CISCO-IETF-ISIS-MIB:CiiUnsigned16TC;
          description
           "The 16 bit Fletcher Checksum.";
          smiv2:max-access "read-only";
          smiv2:oid "1.3.6.1.4.1.9.10.118.1.9.1.1.5";
        }

        leaf ciiLSPLifetimeRemain {
          type CISCO-IETF-ISIS-MIB:CiiUnsigned16TC;
          units "seconds";
          description
           "The remaining lifetime in seconds for this LSP.";
          smiv2:max-access "read-only";
          smiv2:oid "1.3.6.1.4.1.9.10.118.1.9.1.1.6";
        }

        leaf ciiLSPPDULength {
          type CISCO-IETF-ISIS-MIB:CiiUnsigned16TC;
          description
           "The length of this LSP.";
          smiv2:max-access "read-only";
          smiv2:oid "1.3.6.1.4.1.9.10.118.1.9.1.1.7";
        }

        leaf ciiLSPAttributes {
          type CISCO-IETF-ISIS-MIB:CiiUnsigned8TC;
          description
           "Flags carried by the LSP.";
          smiv2:max-access "read-only";
          smiv2:oid "1.3.6.1.4.1.9.10.118.1.9.1.1.8";
        }
      }
    }

    container ciiLSPTLVTable {
      description
       "The contents of each LSP.";
      smiv2:oid "1.3.6.1.4.1.9.10.118.1.9.2";

      list ciiLSPTLVEntry {
        key "ciiLSPLevel ciiLSPID ciiLSPTLVIndex";
        description
         "Each entry describes an LSP current stored in the
          system.";
        smiv2:oid "1.3.6.1.4.1.9.10.118.1.9.2.1";

        leaf ciiLSPLevel {
          type leafref {
            path "/CISCO-IETF-ISIS-MIB:CISCO-IETF-ISIS-MIB/CISCO-IETF-ISIS-MIB:ciiLSPSummaryTable/CISCO-IETF-ISIS-MIB:ciiLSPSummaryEntry/CISCO-IETF-ISIS-MIB:ciiLSPLevel";
          }
        }

        leaf ciiLSPID {
          type leafref {
            path "/CISCO-IETF-ISIS-MIB:CISCO-IETF-ISIS-MIB/CISCO-IETF-ISIS-MIB:ciiLSPSummaryTable/CISCO-IETF-ISIS-MIB:ciiLSPSummaryEntry/CISCO-IETF-ISIS-MIB:ciiLSPID";
          }
        }

        leaf ciiLSPTLVIndex {
          type uint32;
          description
           "The index of this TLV in the LSP.  The first TLV has index 1
            and the Nth TLV has an index of N.";
          smiv2:max-access "not-accessible";
          smiv2:oid "1.3.6.1.4.1.9.10.118.1.9.2.1.1";
        }

        leaf ciiLSPTLVSeq {
          type uint32;
          description
           "The sequence number for this LSP.";
          smiv2:max-access "read-only";
          smiv2:oid "1.3.6.1.4.1.9.10.118.1.9.2.1.2";
        }

        leaf ciiLSPTLVChecksum {
          type CISCO-IETF-ISIS-MIB:CiiUnsigned16TC;
          description
           "The 16 bit Fletcher Checksum.";
          smiv2:max-access "read-only";
          smiv2:oid "1.3.6.1.4.1.9.10.118.1.9.2.1.3";
        }

        leaf ciiLSPTLVType {
          type CISCO-IETF-ISIS-MIB:CiiUnsigned8TC;
          description
           "The type of this TLV.";
          smiv2:max-access "read-only";
          smiv2:oid "1.3.6.1.4.1.9.10.118.1.9.2.1.4";
        }

        leaf ciiLSPTLVLen {
          type CISCO-IETF-ISIS-MIB:CiiUnsigned8TC;
          description
           "The length of this TLV.";
          smiv2:max-access "read-only";
          smiv2:oid "1.3.6.1.4.1.9.10.118.1.9.2.1.5";
        }

        leaf ciiLSPTLVValue {
          type binary {
            length "0..255";
          }
          description
           "The value of this TLV.";
          smiv2:max-access "read-only";
          smiv2:oid "1.3.6.1.4.1.9.10.118.1.9.2.1.6";
        }
      }
    }
  }

  notification ciiDatabaseOverload {
    description
     "This notification is generated when the system
      enters or leaves the Overload state.  The number
      of times this has be generated and cleared is kept
      track of by ciiSysStatLSPDbaseOloads.";
    smiv2:oid "1.3.6.1.4.1.9.10.118.0.1";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiSysLevelIndex {
        type leafref {
          path "/CISCO-IETF-ISIS-MIB:CISCO-IETF-ISIS-MIB/CISCO-IETF-ISIS-MIB:ciiSysLevelTable/CISCO-IETF-ISIS-MIB:ciiSysLevelEntry/CISCO-IETF-ISIS-MIB:ciiSysLevelIndex";
        }
      }

      leaf ciiSysLevelOverloadState {
        type leafref {
          path "/CISCO-IETF-ISIS-MIB:CISCO-IETF-ISIS-MIB/CISCO-IETF-ISIS-MIB:ciiSysLevelTable/CISCO-IETF-ISIS-MIB:ciiSysLevelEntry/CISCO-IETF-ISIS-MIB:ciiSysLevelOverloadState";
        }
      }
    }
  }

  notification ciiManualAddressDrops {
    description
     "This notification is generated when one of the
      manual areaAddresses assigned to this system is
      ignored when computing routes.  The object
      ciiNotifManualAddress describes the area that
      has been dropped.
      
      The number of times this event has been generated
      is counted by ciiSysStatManAddrDropFromAreas.
      
      This notification is edge triggered, and should not
      be regenerated until an address that was used in
      the previous computation has been dropped.";
    smiv2:oid "1.3.6.1.4.1.9.10.118.0.2";

    container object-1 {

      leaf ciiNotifManualAddress {
        type CISCO-IETF-ISIS-MIB:CiiOSINSAddress;
        description
         "Manually configured area address used in
          this notification.";
        smiv2:max-access "accessible-for-notify";
        smiv2:oid "1.3.6.1.4.1.9.10.118.1.10.1.12";
      }
    }
  }

  notification ciiCorruptedLSPDetected {
    description
     "This notification is generated when we find that
      an LSP that was stored in memory has become
      corrupted.  The number of times this has been
      generated is counted by ciiSysStatCorrLSPs.
      
      We forward an LSP ID.  We may have independent
      knowledge of the ID, but in some implementations
      there is a chance that the ID itself will be
      corrupted.";
    smiv2:oid "1.3.6.1.4.1.9.10.118.0.3";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }
  }

  notification ciiAttemptToExceedMaxSequence {
    description
     "When the sequence number on an LSP we generate
      wraps the 32 bit sequence counter, we purge and
      wait to re-announce this information.  This
      notification describes that event.  Since these
      should not be generated rapidly, we generate
      an event each time this happens.
      
      While the first 6 bytes of the LSPID are ours,
      the other two contain useful information.";
    smiv2:oid "1.3.6.1.4.1.9.10.118.0.4";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }
  }

  notification ciiIDLenMismatch {
    description
     "A notification sent when we receive a PDU
      with a different value of the System ID Length.
      This notification includes an index to identify
      the circuit where we saw the PDU and the header of
      the PDU which may help a network manager identify
      the source of the confusion.
      
      This should be an edge-triggered notification.
      We should not send a second notification about
      PDUs received on the same circuit.";
    smiv2:oid "1.3.6.1.4.1.9.10.118.0.5";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiPduFieldLen {
        type CISCO-IETF-ISIS-MIB:CiiUnsigned8TC;
        description
         "Holds the System ID length reported in PDU we received.";
        smiv2:max-access "accessible-for-notify";
        smiv2:oid "1.3.6.1.4.1.9.10.118.1.10.1.3";
      }
    }

    container object-3 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-4 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiMaxAreaAddressesMismatch {
    description
     "A notification sent when we receive a PDU
      with a different value of the Maximum Area
      Addresses.  This notification includes the
      header of the packet, which may help a
      network manager identify the source of the
      confusion.
      
      This should be an edge-triggered notification.
      We should not send a second notification about
      PDUs received from the same circuit.";
    smiv2:oid "1.3.6.1.4.1.9.10.118.0.6";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiPduMaxAreaAddress {
        type CISCO-IETF-ISIS-MIB:CiiUnsigned8TC;
        description
         "Holds the Max Area Addresses reported in a PDU
          we received.";
        smiv2:max-access "accessible-for-notify";
        smiv2:oid "1.3.6.1.4.1.9.10.118.1.10.1.4";
      }
    }

    container object-3 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-4 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiOwnLSPPurge {
    description
     "A notification sent when we receive a PDU
      with our systemID and zero age.  This
      notification includes the circuit Index
      and router ID from the LSP, if available,
      which may help a network manager
      identify the source of the confusion.";
    smiv2:oid "1.3.6.1.4.1.9.10.118.0.7";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }
  }

  notification ciiSequenceNumberSkip {
    description
     "When we receive an LSP with our System ID
      and different contents, we may need to reissue
      the LSP with a higher sequence number.
      
      We send this notification if we need to increase
      the sequence number by more than one.  If two
      Intermediate Systems are configured with the same
      System ID, this notification will fire.";
    smiv2:oid "1.3.6.1.4.1.9.10.118.0.8";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }
  }

  notification ciiAuthenticationTypeFailure {
    description
     "A notification sent when we receive a PDU
      with the wrong authentication type field.
      This notification includes the header of the
      packet, which may help a network manager
      identify the source of the confusion.
      
      This should be an edge-triggered notification.
      We should not send a second notification about
      PDUs received from the same circuit.";
    smiv2:oid "1.3.6.1.4.1.9.10.118.0.9";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiAuthenticationFailure {
    description
     "A notification sent when we receive a PDU
      with incorrect authentication information
      field.  This notification includes the header
      of the packet, which may help a network manager
      identify the source of the confusion.
      This should be an edge-triggered notification.
      We should not send a second notification about
      PDUs received from the same circuit.";
    smiv2:oid "1.3.6.1.4.1.9.10.118.0.10";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiVersionSkew {
    description
     "A notification sent when we receive a Hello
      PDU from an IS running a different version
      of the protocol. This notification includes
      the header of the packet, which may help a
      network manager identify the source of the
      confusion.
      
      This should be an edge-triggered notification.
      We should not send a second notification about
      PDUs received from the same circuit.";
    smiv2:oid "1.3.6.1.4.1.9.10.118.0.11";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduProtocolVersion {
        type CISCO-IETF-ISIS-MIB:CiiUnsigned8TC;
        description
         "Holds the Protocol version reported in PDU we received.";
        smiv2:max-access "accessible-for-notify";
        smiv2:oid "1.3.6.1.4.1.9.10.118.1.10.1.5";
      }
    }

    container object-4 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiAreaMismatch {
    description
     "A notification sent when we receive a Hello
      PDU from an IS which does not share any
      area address. This notification includes
      the header of the packet, which may help a
      network manager identify the source of the
      confusion.
      
      This should be an edge-triggered notification.
      We should not send a second notification about
      PDUs received from the same circuit.";
    smiv2:oid "1.3.6.1.4.1.9.10.118.0.12";

    container object-1 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-2 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiRejectedAdjacency {
    description
     "A notification sent when we receive a Hello
      PDU from an IS, but do not establish an
      adjacency for some reason.
      
      This should be an edge-triggered notification.
      We should not send a second notification about
      PDUs received from the circuit.";
    smiv2:oid "1.3.6.1.4.1.9.10.118.0.13";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiLSPTooLargeToPropagate {
    description
     "A notification sent when we attempt to propagate
      an LSP which is larger than the dataLinkBlockSize
      for the circuit.
      This should be an edge-triggered notification.
      We should not send a second notification about
      PDUs received from the same circuit.";
    smiv2:oid "1.3.6.1.4.1.9.10.118.0.14";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduLspSize {
        type int32 {
          range "0..2147483647";
        }
        description
         "Holds the size of LSP we received that is too
          big to forward.";
        smiv2:max-access "accessible-for-notify";
        smiv2:oid "1.3.6.1.4.1.9.10.118.1.10.1.6";
      }
    }

    container object-4 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }
  }

  notification ciiOrigLSPBuffSizeMismatch {
    description
     "A notification sent when a Level 1 LSP or Level
      2 LSP is received which is larger than the local
      value for ciiSysLevelOrigLSPBuffSize, or when an
      LSP is received containing the originatingLSPBufferSize
      option and the value in the PDU option field does
      not match the local value for ciiSysLevelOrigLSPBuffSize.
      We pass up the size from the option field or the
      size of the LSP that exceeds our configuration.
      
      This should be an edge-triggered notification.
      We should not send a second notification about
      PDUs received from the same circuit.";
    smiv2:oid "1.3.6.1.4.1.9.10.118.0.15";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }

    container object-4 {

      leaf ciiPduOriginatingBufferSize {
        type CISCO-IETF-ISIS-MIB:CiiUnsigned16TC {
          range "0..16000";
        }
        description
         "Holds the size of ciiSysLevelOrigLSPBuffSize advertised by
          the peer in the originatingLSPBufferSize TLV.";
        smiv2:max-access "accessible-for-notify";
        smiv2:oid "1.3.6.1.4.1.9.10.118.1.10.1.7";
      }
    }
  }

  notification ciiProtocolsSupportedMismatch {
    description
     "A notification sent when a non-pseudonode
      segment 0 LSP is received that has no matching
      protocols supported.
      This may be because the system does not generate
      the field, or because there are no common elements.
      The list of protocols supported should be included
      in the notification: it may be empty if the TLV
      is not supported, or if the TLV is empty.
      
      This should be an edge-triggered notification.
      We should not send a second notification about
      PDUs received from the same circuit.";
    smiv2:oid "1.3.6.1.4.1.9.10.118.0.16";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduProtocolsSupported {
        type binary {
          length "0..255";
        }
        description
         "The list of protocols supported by an
          adjacent system.  This may be empty.";
        smiv2:max-access "accessible-for-notify";
        smiv2:oid "1.3.6.1.4.1.9.10.118.1.10.1.8";
      }
    }

    container object-4 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }

    container object-5 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }
  }

  notification ciiAdjacencyChange {
    description
     "A notification sent when an adjacency changes
      state, entering or leaving state up.
      The first 6 bytes of the ciiPduLspId are the
      SystemID of the adjacent IS.
      The ciiAdjState is the new state of the adjacency.";
    smiv2:oid "1.3.6.1.4.1.9.10.118.0.17";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-3 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }

    container object-4 {

      leaf ciiAdjState {
        type enumeration {
          enum "down" {
            value "1";
          }
          enum "initializing" {
            value "2";
          }
          enum "up" {
            value "3";
          }
          enum "failed" {
            value "4";
          }
        }
        description
         "The current state of an adjacency.";
        smiv2:max-access "accessible-for-notify";
        smiv2:oid "1.3.6.1.4.1.9.10.118.1.10.1.9";
      }
    }
  }

  notification ciiLSPErrorDetected {
    description
     "This notification is generated when we receive
      an LSP with a parse error.  The ciiCircIfIndex
      holds in index of the circuit on which the PDU
      arrived.  The ciiPduFragment holds start of the LSP,
      and the ciiErrorOffset points to the problem.
      
      If the problem is a mal-formed TLV, ciiErrorOffset
      points to start of the TLV and ciiErrorTLVType
      holds the value of the type.
      
      If the problem is with the LSP header, ciiErrorOffset
      points to the suspicious byte.
      
      The number of such LSPs is accumulated in
      ciiSysStatLSPErrors.";
    smiv2:oid "1.3.6.1.4.1.9.10.118.0.18";

    container object-1 {

      leaf ciiNotifIsLevelIndex {
        type enumeration {
          enum "level1IS" {
            value "1";
          }
          enum "level2IS" {
            value "2";
          }
        }
        description
         "The index value used in this notification
          to indicate the system level.";
        smiv2:max-access "accessible-for-notify";
        smiv2:oid "1.3.6.1.4.1.9.10.118.1.10.1.13";
      }
    }

    container object-2 {

      leaf ciiPduLspId {
        type CISCO-IETF-ISIS-MIB:CiiLinkStatePDUID;
        description
         "An Octet String that uniquely identifies
          a Link State PDU.";
        smiv2:max-access "accessible-for-notify";
        smiv2:oid "1.3.6.1.4.1.9.10.118.1.10.1.1";
      }
    }

    container object-3 {

      leaf ciiCircIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIndex";
        }
      }

      leaf ciiCircIfIndex {
        type leafref {
          path "/CISCO-IETF-ISIS-MIB:CISCO-IETF-ISIS-MIB/CISCO-IETF-ISIS-MIB:ciiCircTable/CISCO-IETF-ISIS-MIB:ciiCircEntry/CISCO-IETF-ISIS-MIB:ciiCircIfIndex";
        }
      }
    }

    container object-4 {

      leaf ciiPduFragment {
        type CISCO-IETF-ISIS-MIB:CiiPDUHeader;
        description
         "Holds up to 64 initial bytes of a PDU that
          triggered the notification.";
        smiv2:max-access "accessible-for-notify";
        smiv2:oid "1.3.6.1.4.1.9.10.118.1.10.1.2";
      }
    }

    container object-5 {

      leaf ciiErrorOffset {
        type uint32;
        description
         "An offset to a problem in a PDU.  If the problem
          is a malformed TLV, this points to the beginning
          of the TLV.  If the problem is in the header, this
          points to the byte that is suspicious.";
        smiv2:max-access "accessible-for-notify";
        smiv2:oid "1.3.6.1.4.1.9.10.118.1.10.1.10";
      }
    }

    container object-6 {

      leaf ciiErrorTLVType {
        type uint32 {
          range "0..255";
        }
        description
         "The type for a malformed TLV.";
        smiv2:max-access "accessible-for-notify";
        smiv2:oid "1.3.6.1.4.1.9.10.118.1.10.1.11";
      }
    }
  }

  smiv2:alias "ciscoIetfIsisMIB" {
    smiv2:oid "1.3.6.1.4.1.9.10.118";
  }

  smiv2:alias "ciscoIetfIsisMIBNotifs" {
    smiv2:oid "1.3.6.1.4.1.9.10.118.0";
  }

  smiv2:alias "ciscoIetfIsisMIBObjects" {
    smiv2:oid "1.3.6.1.4.1.9.10.118.1";
  }

  smiv2:alias "ciiSystem" {
    smiv2:oid "1.3.6.1.4.1.9.10.118.1.1";
  }

  smiv2:alias "ciiSysObject" {
    smiv2:oid "1.3.6.1.4.1.9.10.118.1.1.1";
  }

  smiv2:alias "ciiSysLevel" {
    smiv2:oid "1.3.6.1.4.1.9.10.118.1.2";
  }

  smiv2:alias "ciiCirc" {
    smiv2:oid "1.3.6.1.4.1.9.10.118.1.3";
  }

  smiv2:alias "ciiCircLevelValues" {
    smiv2:oid "1.3.6.1.4.1.9.10.118.1.4";
  }

  smiv2:alias "ciiCounters" {
    smiv2:oid "1.3.6.1.4.1.9.10.118.1.5";
  }

  smiv2:alias "ciiISAdj" {
    smiv2:oid "1.3.6.1.4.1.9.10.118.1.6";
  }

  smiv2:alias "ciiReachAddr" {
    smiv2:oid "1.3.6.1.4.1.9.10.118.1.7";
  }

  smiv2:alias "ciiIPReachAddr" {
    smiv2:oid "1.3.6.1.4.1.9.10.118.1.8";
  }

  smiv2:alias "ciiLSPDataBase" {
    smiv2:oid "1.3.6.1.4.1.9.10.118.1.9";
  }

  smiv2:alias "ciiNotification" {
    smiv2:oid "1.3.6.1.4.1.9.10.118.1.10";
  }

  smiv2:alias "ciiNotificationEntry" {
    smiv2:oid "1.3.6.1.4.1.9.10.118.1.10.1";
  }

  smiv2:alias "ciscoIetfIsisMIBConform" {
    smiv2:oid "1.3.6.1.4.1.9.10.118.2";
  }

  smiv2:alias "ciscoIetfIsisMIBGroups" {
    smiv2:oid "1.3.6.1.4.1.9.10.118.2.1";
  }

  smiv2:alias "ciscoIetfIsisMIBCompliances" {
    smiv2:oid "1.3.6.1.4.1.9.10.118.2.2";
  }

}
