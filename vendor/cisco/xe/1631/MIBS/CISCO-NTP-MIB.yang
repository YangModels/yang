/*
 * Generated by confdc --mib2yang-std
 * Source: mgmt/dmi/model/common/mib-source/CISCO-NTP-MIB.mib
 */
/*
 * This YANG module has been generated by smidump 0.5.0:
 *
 *      smidump -f yang CISCO-NTP-MIB
 *
 * Do not edit. Edit the source file instead!
 */

module CISCO-NTP-MIB {

  namespace "urn:ietf:params:xml:ns:yang:smiv2:CISCO-NTP-MIB";
  prefix CISCO-NTP-MIB;

  import INET-ADDRESS-MIB {
    prefix "inet-address";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "Cisco Systems
    Customer Service
    
    Postal: 170 W. Tasman Drive
    San Jose, CA 95134
    USA
    
    Tel: +1 800 553-NETS
    
    E-mail: cs-snmp@cisco.com";

  description
   "This MIB module defines a MIB which provides
    mechanisms to monitor an NTP server.
    
    The MIB is derived from the Technical Report
    #Management of the NTP with SNMP# TR No. 98-09
    authored by A.S. Sethi and Dave Mills in the
    University of Delaware.
    
    Below is a brief overview of NTP system architecture
    and implementation model. This will help understand
    the objects defined below and their relationships.
    
    NTP Intro:
    The Network Time Protocol (NTP) Version 3, is used to
    synchronize timekeeping among a set of distributed
    time servers and clients.  The service model is based
    on a returnable-time design which depends only on
    measured clock offsets, but does not require reliable
    message delivery.  The synchronization subnet uses a
    self-organizing, hierarchical master-slave
    configuration, with synchronization paths determined
    by a minimum-weight spanning tree.  While multiple
    masters (primary servers) may exist, there is no
    requirement for an election protocol.
    
    System Archiecture:
    In the NTP model a number of primary reference
    sources, synchronized by wire or radio to national
    standards, are connected to widely accessible
    resources, such as backbone gateways, and operated as
    primary time servers.  The purpose of NTP is to convey
    timekeeping information from these servers to other
    time servers via the Internet and also to cross-check
    clocks and mitigate errors due to equipment or
    propagation failures.  Some number of local-net hosts
    or gateways, acting as secondary time servers, run NTP
    with one or more of the primary servers.  In order to
    reduce the protocol overhead, the secondary servers
    distribute time via NTP to the remaining local-net
    hosts.  In the interest of reliability, selected hosts
    can be equipped with less accurate but less expensive
    radio clocks and used for backup in case of failure of
    the primary and/or secondary servers or communication
    paths between them.
    
    NTP is designed to produce three products: clock
    offset, round-trip delay and dispersion, all of which
    are relative to a selected reference clock.  Clock
    offset represents the amount to adjust the local clock
    to bring it into correspondence with the reference
    clock.  Roundtrip delay provides the capability to
    launch a message to arrive at the reference clock at a
    specified time.  Dispersion represents the maximum
    error of the local clock relative to the reference
    clock.  Since most host time servers will synchronize
    via another peer time server, there are two components
    in each of these three products, those determined by
    the peer relative to the primary reference source of
    standard time and those measured by the host relative
    to the peer.  Each of these components are maintained
    separately in the protocol in order to facilitate
    error control and management of the subnet itself.  
    They provide not only precision measurements of offset
    and delay, but also definitive maximum error bounds,
    so that the user interface can determine not only the
    time, but the quality of the time as well.
    
    Implementation Model:
    In what may be the most common client/server model a
    client sends an NTP message to one or more servers and
    processes the replies as received.  The server
    interchanges addresses and ports, overwrites certain
    fields in the message, recalculates the checksum and
    returns the message immediately.  Information included
    in the NTP message allows the client to determine the
    server time with respect to local time and adjust the
    local clock accordingly.  In addition, the message
    includes information to calculate the expected
    timekeeping accuracy and reliability, as well as
    select the best from possibly several servers.
    
    While the client/server model may suffice for use on
    local nets involving a public server and perhaps many
    workstation clients, the full generality of NTP
    requires distributed participation of a number of
    client/servers or peers arranged in a dynamically
    reconfigurable, hierarchically distributed
    configuration.  It also requires sophisticated
    algorithms for association management, data
    manipulation and local-clock control.
    
    Glossary:
    1. Host: Refers to an instantiation of the NTP
            protocol on a local processor.
    2. Peer: Refers to an instantiation of the NTP
            protocol on a remote processor connected by
            a network path from the local host.";

  revision 2006-07-31 {
    description
     "Added ciscoNtpSysExtGroup and ciscoNtpSrvNotifGroup groups
      to support monitoring of NTP server status.
      ciscoNtpMIBComplianceRev3 is deprecated and replaced
      by ciscoNtpMIBComplianceRev4.";
  }

  revision 2004-07-23 {
    description
     "Added cntpPeersPeerName and cntpPeersPeerType
      objects to cntpPeerVarTable.";
  }

  revision 2003-07-29 {
    description
     "Added cntpPeersPrefPeer object to
      cntpPeersVarTable.";
  }

  revision 2003-07-07 {
    description
     "ciscoNtpPeersGroup is deprecated by
      ciscoNtpPeersGroupRev1.
      ciscoNtpMIBCompliance is deprecated by
      ciscoNtpMIBComplianceRev1.";
  }

  revision 2002-02-20 {
    description
     "cntpPeersUpdateTime is deprecated by
      cntpPeersUpdateTimeRev1.";
  }

  revision 2000-06-16 {
    description
     "Initial version of this MIB module.";
  }

  typedef NTPTimeStamp {
    type binary {
      length "8";
    }
    description
     "NTP timestamps are represented as a 64-bit
      unsigned fixed-point number, in seconds relative to
      00:00 on 1 January 1900.  The integer part is in the
      first 32 bits and the fraction part is in the last
      32 bits.";
    reference
     "D.L. Mills, 'Network Time Protocol (Version 3)',
      RFC-1305, March 1992, Section 3.1";
  }

  typedef NTPLeapIndicator {
    type enumeration {
      enum "noWarning" {
        value "0";
      }
      enum "addSecond" {
        value "1";
      }
      enum "subtractSecond" {
        value "2";
      }
      enum "alarm" {
        value "3";
      }
    }
    description
     "This is a two-bit code warning of an impending leap
      second to be inserted in the NTP timescale.  The bits
      are set before 23:59 on the day of insertion and reset
      after 00:00 on the following day.  This causes the
      number of seconds (rollover interval) in the day of
      insertion to be increased or decreased by one.  The two
      bits are coded as below,
      00, no warning
      01, last minute has 61 seconds
      10, last minute has 59 seconds
      11, alarm condition (clock not synchronized)";
    reference
     "D.L. Mills, 'Network Time Protocol(Version 3)',
      RFC-1305, March 1992, Section 3.2.1";
  }

  typedef NTPSignedTimeValue {
    type binary {
      length "4";
    }
    description
     "The time in seconds that could represent signed
      quantities like time delay with respect to some
      source.  This textual-convention is specific to Cisco
      implementation of NTP where 32-bit integers are used
      for such quantities.  The signed integer part is in
      the first 16 bits and the fraction part is in the
      last 16 bits.";
    reference
     "D.L. Mills, 'Network Time Protocol (Version 3)',
      RFC-1305, March 1992, Sections 2,  3.2.1";
  }

  typedef NTPUnsignedTimeValue {
    type binary {
      length "4";
    }
    description
     "The time in seconds that could represent unsigned
      quantities like maximum error of the local clock
      with respect to some source.  This textual-convention
      is specific to Cisco implementation of NTP where
      32-bit integers are used for such quantities.  The
      unsigned integer part is in the first 16 bits and the
      fraction part is in the last 16 bits.";
    reference
     "D.L. Mills, 'Network Time Protocol (Version 3)',
      RFC-1305, March 1992, Sections 2, 3.2.1";
  }

  typedef NTPStratum {
    type int32 {
      range "0..255";
    }
    description
     "Indicates the stratum of the clock.  The stratum
      defines the accuracy of a time server.  Higher the
      stratum, lower the accuracy.
      0, unspecified
      1, primary reference (e.g., calibrated atomic clock,
         radio clock)
      2-255, secondary reference (via NTP)";
    reference
     "D.L. Mills, 'Network Time Protocol (Version 3)',
      RFC-1305, March 1992, Section 2.2";
  }

  typedef NTPRefId {
    type binary {
      length "4";
    }
    description
     "The reference clock identifier.  In the case of
      stratum 0 (unspecified) or stratum 1 (primary
      reference source), this is a four-octet,
      left-justified, zero-padded ASCII string as defined
      in RFC-1305.  In the case of stratum 2 and greater
      (secondary reference) this is the four-octet Internet
      address of the peer selected for synchronization.
      
      Some examples of stratum 0 identifiers are,
      DCN, DCN routing protocol
      NIST, NIST public modem
      TSP, TSP time protocol
      DTS, Digital Time Service
      
      Some examples of stratum 1 identifiers are,
      ATOM, Atomic clock (calibrated)
      VLF, VLF radio (OMEGA,, etc.)
      LORC, LORAN-C radionavigation
      GOES, GOES UHF environment satellite
      GPS, GPS UHF satellite positioning";
    reference
     "D.L. Mills, Network Time Protocol (Version 3)',
      RFC-1305, March 1992, Section 3.2.1";
  }

  typedef NTPPollInterval {
    type int32 {
      range "-20..20";
    }
    description
     "The minimum interval between transmitted NTP
      messages, in seconds as a power of two.  For
      instance, a value of six indicates a minimum
      interval of 64 seconds.";
  }

  typedef NTPAssocIdentifier {
    type int32 {
      range "0..2147483647";
    }
    description
     "The association identifier of the peer.  Every peer
      with which an NTP server is associated with is
      identified by an association identifier.";
  }


  container CISCO-NTP-MIB {
    config false;

    container cntpSystem {
      smiv2:oid "1.3.6.1.4.1.9.9.168.1.1";

      leaf cntpSysLeap {
        type CISCO-NTP-MIB:NTPLeapIndicator;
        description
         "Two-bit code warning of an impending leap second to
          be inserted in the NTP timescale. This object can be
          set only when the cntpSysStratum has a value of 1.";
        smiv2:max-access "read-write";
        smiv2:oid "1.3.6.1.4.1.9.9.168.1.1.1";
      }

      leaf cntpSysStratum {
        type CISCO-NTP-MIB:NTPStratum;
        description
         "The stratum of the local clock. If the value is set
          to 1, i.e., this is a primary reference, then the
          Primary-Clock procedure described in Section 3.4.6,
          in RFC-1305 is invoked.";
        smiv2:max-access "read-write";
        smiv2:oid "1.3.6.1.4.1.9.9.168.1.1.2";
      }

      leaf cntpSysPrecision {
        type int32 {
          range "-20..20";
        }
        description
         "Signed integer indicating the precision
          of the system clock, in seconds to the nearest
          power of two.  The value must be rounded to the
          next larger power of two; for instance, a 50-Hz
          (20 ms) or 60-Hz (16.67 ms) power-frequency clock
          would be assigned the value -5 (31.25 ms), while a
          1000-Hz (1 ms) crystal-controlled clock would be
          assigned the value -9 (1.95 ms).";
        smiv2:max-access "read-only";
        smiv2:oid "1.3.6.1.4.1.9.9.168.1.1.3";
      }

      leaf cntpSysRootDelay {
        type CISCO-NTP-MIB:NTPSignedTimeValue;
        units "seconds";
        description
         "A signed fixed-point number indicating the total
          round-trip delay in seconds, to the primary reference
          source at the root of the synchronization subnet.";
        reference
         "D.L. Mills, 'Network Time Protocol (Version 3)',
          RFC-1305, March 1992, Sections 2.2, 3.2.1";
        smiv2:max-access "read-only";
        smiv2:oid "1.3.6.1.4.1.9.9.168.1.1.4";
      }

      leaf cntpSysRootDispersion {
        type CISCO-NTP-MIB:NTPUnsignedTimeValue;
        units "seconds";
        description
         "The maximum error in seconds, relative to the
          primary reference source at the root of the
          synchronization subnet.  Only positive values greater
          than zero are possible.";
        reference
         "D.L. Mills, 'Network Time Protocol (Version 3)',
          RFC-1305, March 1992, Sections 2, 2.2, 3.2.1";
        smiv2:max-access "read-only";
        smiv2:oid "1.3.6.1.4.1.9.9.168.1.1.5";
      }

      leaf cntpSysRefId {
        type CISCO-NTP-MIB:NTPRefId;
        description
         "The reference identifier of the local clock.";
        smiv2:max-access "read-only";
        smiv2:oid "1.3.6.1.4.1.9.9.168.1.1.6";
      }

      leaf cntpSysRefTime {
        type CISCO-NTP-MIB:NTPTimeStamp;
        description
         "The local time when the local clock was last
          updated.  If the local clock has never been
          synchronized, the value is zero.";
        smiv2:max-access "read-only";
        smiv2:oid "1.3.6.1.4.1.9.9.168.1.1.7";
      }

      leaf cntpSysPoll {
        type CISCO-NTP-MIB:NTPPollInterval;
        description
         "The interval at which the NTP server polls other NTP
          servers to synchronize its clock.";
        smiv2:max-access "read-only";
        smiv2:oid "1.3.6.1.4.1.9.9.168.1.1.8";
      }

      leaf cntpSysPeer {
        type CISCO-NTP-MIB:NTPAssocIdentifier;
        description
         "The current synchronization source.  This will
          contain the unique association identifier
          cntpPeersAssocId of the corresponding peer entry in
          the cntpPeersVarTable of the peer acting as the
          synchronization source.  If there is no peer, the
          value will be 0.";
        smiv2:max-access "read-only";
        smiv2:oid "1.3.6.1.4.1.9.9.168.1.1.9";
      }

      leaf cntpSysClock {
        type CISCO-NTP-MIB:NTPTimeStamp;
        description
         "The current local time.  Local time is derived from
          the hardware clock of the particular machine and
          increments at intervals depending on the design used.";
        smiv2:max-access "read-only";
        smiv2:oid "1.3.6.1.4.1.9.9.168.1.1.10";
      }

      leaf cntpSysSrvStatus {
        type enumeration {
          enum "unknown" {
            value "1";
          }
          enum "notRunning" {
            value "2";
          }
          enum "notSynchronized" {
            value "3";
          }
          enum "syncToLocal" {
            value "4";
          }
          enum "syncToRefclock" {
            value "5";
          }
          enum "syncToRemoteServer" {
            value "6";
          }
        }
        description
         "Current state of the NTP server with values coded as follows:
          1: server status is unknown
          2: server is not running
          3: server is not synchronized to any time source
          4: server is synchronized to its own local clock
          5: server is synchronized to a local hardware refclock (e.g. GPS)
          6: server is synchronized to a remote NTP server";
        smiv2:defval "unknown";
        smiv2:max-access "read-only";
        smiv2:oid "1.3.6.1.4.1.9.9.168.1.1.11";
      }
    }

    container cntpPeersVarTable {
      description
       "This table provides information on the peers with
        which the local NTP server has associations.  The
        peers are also NTP servers but running on different
        hosts.";
      smiv2:oid "1.3.6.1.4.1.9.9.168.1.2.1";

      list cntpPeersVarEntry {
        key "cntpPeersAssocId";
        description
         "Each peers' entry provides NTP information retrieved
          from a particular peer NTP server.  Each peer is
          identified by a unique association identifier.
          
          Entries are automatically created when the user
          configures the NTP server to be associated with remote
          peers.  Similarly entries are deleted when the user
          removes the peer association from the NTP server.
          
          Entries can also be created by the management station
          by setting values for the following objects:
          cntpPeersPeerAddress or cntpPeersPeerName, 
          cntpPeersHostAddress and
          cntpPeersMode and making the cntpPeersEntryStatus as
          active(1).  At the least, the management station has
          to set a value for cntpPeersPeerAddress or
          cntpPeersPeerName to make the row active.";
        smiv2:oid "1.3.6.1.4.1.9.9.168.1.2.1.1";

        leaf cntpPeersAssocId {
          type CISCO-NTP-MIB:NTPAssocIdentifier;
          description
           "An integer value greater than 0 that uniquely
            identifies a peer with which the local NTP server
            is associated.";
          smiv2:max-access "not-accessible";
          smiv2:oid "1.3.6.1.4.1.9.9.168.1.2.1.1.1";
        }

        leaf cntpPeersConfigured {
          type boolean;
          description
           "This is a bit indicating that the association
            was created from configuration information and
            should not be de-associated even if the peer
            becomes unreachable.";
          smiv2:max-access "read-only";
          smiv2:oid "1.3.6.1.4.1.9.9.168.1.2.1.1.2";
        }

        leaf cntpPeersPeerAddress {
          type inet:ipv4-address;
          description
           "The IP address of the peer.  When creating a new
            association, a value should be set either for this
            object or the corresponding instance of 
            cntpPeersPeerName, before the row is made active.";
          smiv2:max-access "read-write";
          smiv2:oid "1.3.6.1.4.1.9.9.168.1.2.1.1.3";
        }

        leaf cntpPeersPeerPort {
          type int32 {
            range "1..65535";
          }
          description
           "The UDP port number on which the peer receives NTP
            messages.";
          smiv2:max-access "read-only";
          smiv2:oid "1.3.6.1.4.1.9.9.168.1.2.1.1.4";
        }

        leaf cntpPeersHostAddress {
          type inet:ipv4-address;
          description
           "The IP address of the local host.  Multi-homing can
            be supported using this object.";
          smiv2:max-access "read-write";
          smiv2:oid "1.3.6.1.4.1.9.9.168.1.2.1.1.5";
        }

        leaf cntpPeersHostPort {
          type int32 {
            range "1..65535";
          }
          description
           "The UDP port number on which the local host receives
            NTP messages.";
          smiv2:max-access "read-only";
          smiv2:oid "1.3.6.1.4.1.9.9.168.1.2.1.1.6";
        }

        leaf cntpPeersLeap {
          type CISCO-NTP-MIB:NTPLeapIndicator;
          description
           "Two-bit code warning of an impending leap
            second to be inserted in the NTP timescale of
            the peer.";
          smiv2:max-access "read-only";
          smiv2:oid "1.3.6.1.4.1.9.9.168.1.2.1.1.7";
        }

        leaf cntpPeersMode {
          type enumeration {
            enum "unspecified" {
              value "0";
            }
            enum "symmetricActive" {
              value "1";
            }
            enum "symmetricPassive" {
              value "2";
            }
            enum "client" {
              value "3";
            }
            enum "server" {
              value "4";
            }
            enum "broadcast" {
              value "5";
            }
            enum "reservedControl" {
              value "6";
            }
            enum "reservedPrivate" {
              value "7";
            }
          }
          description
           "The association mode of the NTP server, with values
            coded as follows,
            0, unspecified
            1, symmetric active - A host operating in this mode
                    sends periodic messages regardless of the
                    reachability state or stratum of its peer.  By
                    operating in this mode the host announces its
                    willingness to synchronize and be synchronized
                    by the peer
            2, symmetric passive - This type of association is
                    ordinarily created upon arrival of a message
                    from a peer operating in the symmetric active
                    mode and persists only as long as the peer is
                    reachable and operating at a stratum level
                    less than or equal to the host; otherwise, the
                    association is dissolved.  However, the
                    association will always persist until at least
                    one message has been sent in reply.  By
                    operating in this mode the host announces its
                    willingness to synchronize and be synchronized
                    by the peer
            3, client -  A host operating in this mode sends
                    periodic messages regardless of the
                    reachability state or stratum of its peer.  By
                    operating in this mode the host, usually a LAN
                    workstation, announces its willingness to be
                    synchronized by, but not to synchronize the peer
            4, server - This type of association is ordinarily
                    created upon arrival of a client request message
                    and exists only in order to reply to that
                    request, after which the association is
                    dissolved.  By operating in this mode the host,
                    usually a LAN time server, announces its
                    willingness to synchronize, but not to be
                    synchronized by the peer
            5, broadcast - A host operating in this mode sends
                    periodic messages regardless of the
                    reachability state or stratum of the peers.
                    By operating in this mode the host, usually a
                    LAN time server operating on a high-speed
                    broadcast medium, announces its willingness to
                    synchronize all of the peers, but not to be
                    synchronized by any of them
            6, reserved for NTP control messages
            7, reserved for private use.
            
            When creating a new peer association, if no value
            is specified for this object, it defaults to
            symmetricActive(1).";
          reference
           "D.L. Mills, 'Network Time Protocol (Version 3)',
            RFC-1305, March 1992, Section 3.3";
          smiv2:max-access "read-write";
          smiv2:oid "1.3.6.1.4.1.9.9.168.1.2.1.1.8";
        }

        leaf cntpPeersStratum {
          type CISCO-NTP-MIB:NTPStratum;
          description
           "The stratum of the peer clock.";
          smiv2:max-access "read-only";
          smiv2:oid "1.3.6.1.4.1.9.9.168.1.2.1.1.9";
        }

        leaf cntpPeersPeerPoll {
          type CISCO-NTP-MIB:NTPPollInterval;
          description
           "The interval at which the peer polls the local host.";
          smiv2:max-access "read-only";
          smiv2:oid "1.3.6.1.4.1.9.9.168.1.2.1.1.10";
        }

        leaf cntpPeersHostPoll {
          type CISCO-NTP-MIB:NTPPollInterval;
          description
           "The interval at which the local host polls the peer.";
          smiv2:max-access "read-only";
          smiv2:oid "1.3.6.1.4.1.9.9.168.1.2.1.1.11";
        }

        leaf cntpPeersPrecision {
          type int32 {
            range "-20..20";
          }
          description
           "Signed integer indicating the precision of the peer
            clock, in seconds to the nearest power of two.  The
            value must be rounded to the next larger power of
            two; for instance, a 50-Hz (20 ms) or 60-Hz
            (16.67 ms) power-frequency clock would be assigned
            the value -5 (31.25 ms), while a 1000-Hz (1 ms)
            crystal-controlled clock would be assigned the value
            -9 (1.95 ms).";
          smiv2:max-access "read-only";
          smiv2:oid "1.3.6.1.4.1.9.9.168.1.2.1.1.12";
        }

        leaf cntpPeersRootDelay {
          type CISCO-NTP-MIB:NTPSignedTimeValue;
          units "seconds";
          description
           "A signed fixed-point number indicating the total
            round-trip delay in seconds, from the peer to the
            primary reference source at the root of the
            synchronization subnet.";
          smiv2:max-access "read-only";
          smiv2:oid "1.3.6.1.4.1.9.9.168.1.2.1.1.13";
        }

        leaf cntpPeersRootDispersion {
          type CISCO-NTP-MIB:NTPUnsignedTimeValue;
          units "seconds";
          description
           "The maximum error in seconds, of the peer clock
            relative to the primary reference source at the root
            of the synchronization subnet.  Only positive values
            greater than zero are possible.";
          smiv2:max-access "read-only";
          smiv2:oid "1.3.6.1.4.1.9.9.168.1.2.1.1.14";
        }

        leaf cntpPeersRefId {
          type CISCO-NTP-MIB:NTPRefId;
          description
           "The reference identifier of the peer.";
          smiv2:max-access "read-only";
          smiv2:oid "1.3.6.1.4.1.9.9.168.1.2.1.1.15";
        }

        leaf cntpPeersRefTime {
          type CISCO-NTP-MIB:NTPTimeStamp;
          description
           "The local time at the peer when its clock was last
            updated.  If the peer clock has never been
            synchronized, the value is zero.";
          smiv2:max-access "read-only";
          smiv2:oid "1.3.6.1.4.1.9.9.168.1.2.1.1.16";
        }

        leaf cntpPeersOrgTime {
          type CISCO-NTP-MIB:NTPTimeStamp;
          description
           "The local time at the peer, when its latest
            NTP message was sent.  If the peer becomes unreachable
            the value is set to zero.";
          smiv2:max-access "read-only";
          smiv2:oid "1.3.6.1.4.1.9.9.168.1.2.1.1.17";
        }

        leaf cntpPeersReceiveTime {
          type CISCO-NTP-MIB:NTPTimeStamp;
          description
           "The local time, when the latest NTP message from
            the peer arrived.  If the peer becomes unreachable
            the value is set to zero.";
          smiv2:max-access "read-only";
          smiv2:oid "1.3.6.1.4.1.9.9.168.1.2.1.1.18";
        }

        leaf cntpPeersTransmitTime {
          type CISCO-NTP-MIB:NTPTimeStamp;
          description
           "The local time at which the NTP message departed the
            sender.";
          smiv2:max-access "read-only";
          smiv2:oid "1.3.6.1.4.1.9.9.168.1.2.1.1.19";
        }

        leaf cntpPeersUpdateTime {
          type int32 {
            range "0..2147483647";
          }
          status deprecated;
          description
           "The local time, when the most recent NTP message was
            received from the peer that was used to calculate the
            skew dispersion.  This represents only the 32-bit
            integer part of the NTPTimestamp.";
          smiv2:max-access "read-only";
          smiv2:oid "1.3.6.1.4.1.9.9.168.1.2.1.1.20";
        }

        leaf cntpPeersReach {
          type int32 {
            range "0..255";
          }
          description
           "A shift register of used to determine the
            reachability status of the peer, with bits entering
            from the least significant (rightmost) end.  A peer is
            considered reachable if at least one bit in this
            register is set to one i.e, if the value of this
            object is non-zero.
            The data in the shift register would be populated by
            the NTP protocol procedures.";
          reference
           "D.L. Mills, 'Network Time Protocol (Version 3)',
            RFC-1305, March 1992, Section 3.2.3";
          smiv2:max-access "read-only";
          smiv2:oid "1.3.6.1.4.1.9.9.168.1.2.1.1.21";
        }

        leaf cntpPeersTimer {
          type int32 {
            range "0..2147483647";
          }
          units "seconds";
          description
           "The interval in seconds, between transmitted NTP
            messages from the local host to the peer.";
          reference
           "D.L. Mills, 'Network Time Protocol (Version 3)',
            RFC-1305, March 1992, Section 3.2.3";
          smiv2:max-access "read-only";
          smiv2:oid "1.3.6.1.4.1.9.9.168.1.2.1.1.22";
        }

        leaf cntpPeersOffset {
          type CISCO-NTP-MIB:NTPSignedTimeValue;
          units "seconds";
          description
           "The estimated offset of the peer clock relative to
            the local clock, in seconds.  The host determines the
            value of this object using the NTP clock-filter
            algorithm.";
          reference
           "D.L. Mills, 'Network Time Protocol (Version 3)',
            RFC-1305, March 1992, Section 3.2.5";
          smiv2:max-access "read-only";
          smiv2:oid "1.3.6.1.4.1.9.9.168.1.2.1.1.23";
        }

        leaf cntpPeersDelay {
          type CISCO-NTP-MIB:NTPSignedTimeValue;
          units "seconds";
          description
           "The estimated round-trip delay of the peer clock
            relative to the local clock over the network path
            between them, in seconds.  The host determines the
            value of this object using the NTP clock-filter
            algorithm.";
          reference
           "D.L. Mills, 'Network Time Protocol (Version 3)',
            RFC-1305, March 1992, Section 3.2.5";
          smiv2:max-access "read-only";
          smiv2:oid "1.3.6.1.4.1.9.9.168.1.2.1.1.24";
        }

        leaf cntpPeersDispersion {
          type CISCO-NTP-MIB:NTPUnsignedTimeValue;
          units "seconds";
          description
           "The estimated maximum error of the peer clock
            relative to the local clock over the network path
            between them, in seconds.  The host determines the
            value of this object using the NTP clock-filter
            algorithm.";
          reference
           "D.L. Mills, 'Network Time Protocol (Version 3)',
            RFC-1305, March 1992, Section 3.2.5";
          smiv2:max-access "read-only";
          smiv2:oid "1.3.6.1.4.1.9.9.168.1.2.1.1.25";
        }

        leaf cntpPeersFilterValidEntries {
          type yang:gauge32;
          description
           "The number of valid entries for a peer in the
            Filter Register Table. Since, the Filter Register
            Table is optional, this object will have a value 0
            if the Filter Register Table is not implemented.";
          smiv2:max-access "read-only";
          smiv2:oid "1.3.6.1.4.1.9.9.168.1.2.1.1.26";
        }

        leaf cntpPeersEntryStatus {
          type snmpv2-tc:RowStatus;
          description
           "The status object for this row. When a management
            station is creating a new row, it should set the
            value for cntpPeersPeerAddress at least, before the
            row can be made active(1).";
          smiv2:max-access "read-write";
          smiv2:oid "1.3.6.1.4.1.9.9.168.1.2.1.1.27";
        }

        leaf cntpPeersUpdateTimeRev1 {
          type uint32;
          description
           "The local time, when the most recent NTP message was
            received from the peer that was used to calculate the
            skew dispersion.  This represents only the 32-bit
            integer part of the NTPTimestamp.";
          smiv2:max-access "read-only";
          smiv2:oid "1.3.6.1.4.1.9.9.168.1.2.1.1.28";
        }

        leaf cntpPeersPrefPeer {
          type boolean;
          description
           "This object specifies whether this peer is the
            preferred one over the others. By default, when
            the value of this object is 'false', NTP chooses 
            the peer with which to synchronize the time on 
            the local system. If this object is set
            to 'true', NTP will choose the corresponding
            peer to synchronize the time with. If multiple
            entries have this object set to 'true', NTP will
            choose the first one to be set. This object is
            a means to override the selection of the peer by
            NTP.";
          smiv2:defval "false";
          smiv2:max-access "read-write";
          smiv2:oid "1.3.6.1.4.1.9.9.168.1.2.1.1.29";
        }

        leaf cntpPeersPeerType {
          type inet-address:InetAddressType;
          description
           "Represents the type of the corresponding instance
            of cntpPeersPeerName object.";
          smiv2:defval "ipv4";
          smiv2:max-access "read-write";
          smiv2:oid "1.3.6.1.4.1.9.9.168.1.2.1.1.30";
        }

        leaf cntpPeersPeerName {
          type inet-address:InetAddress;
          description
           "The address of the peer. When creating a new
            association, a value must be set for either this
            object or the corresponding instance of
            cntpPeersPeerAddress object, before the row
            is made active.";
          smiv2:max-access "read-write";
          smiv2:oid "1.3.6.1.4.1.9.9.168.1.2.1.1.31";
        }
      }
    }

    container cntpFilterRegisterTable {
      description
       "The following table contains NTP state variables
        used by the NTP clock filter and selection algorithms.
        This table depicts a shift register.  Each stage in
        the shift register is a 3-tuple consisting of the
        measured clock offset, measured clock delay and
        measured clock dispersion associated with a single
        observation.
        
        An important factor affecting the accuracy and
        reliability of time distribution is the complex of
        algorithms used to reduce the effect of statistical
        errors and falsetickers due to failure of various
        subnet components, reference sources or propagation
        media.  The NTP clock-filter and selection algorithms
        are designed to do exactly this.  The objects in the
        filter register table below are used by these
        algorthims to minimize the error in the calculated
        time.";
      reference
       "D.L. Mills, 'Network Time Protocol (Version 3)',
        RFC-1305, March 1992, Section 3.2.5";
      smiv2:oid "1.3.6.1.4.1.9.9.168.1.3.2";

      list cntpFilterRegisterEntry {
        key "cntpPeersAssocId cntpFilterIndex";
        description
         "Each entry corresponds to one stage of the shift
          register, i.e., one reading of the variables clock
          delay, clock offset and clock dispersion.
          
          Entries are automatically created whenever a peer is
          configured and deleted when the peer is removed.";
        smiv2:oid "1.3.6.1.4.1.9.9.168.1.3.2.1";

        leaf cntpPeersAssocId {
          type leafref {
            path "/CISCO-NTP-MIB:CISCO-NTP-MIB/CISCO-NTP-MIB:cntpPeersVarTable/CISCO-NTP-MIB:cntpPeersVarEntry/CISCO-NTP-MIB:cntpPeersAssocId";
          }
        }

        leaf cntpFilterIndex {
          type int32 {
            range "1..8";
          }
          description
           "An integer value in the specified range that is used
            to index into the table.  The size of the table is
            fixed at 8.  Each entry identifies a particular
            reading of the clock filter variables in the shift
            register.
            
            Entries are added starting at index 1.  The index
            wraps back to 1 when it reaches 8.  When the index
            wraps back, the new entries will overwrite the old
            entries effectively deleting the old entry.";
          smiv2:max-access "not-accessible";
          smiv2:oid "1.3.6.1.4.1.9.9.168.1.3.2.1.1";
        }

        leaf cntpFilterPeersOffset {
          type CISCO-NTP-MIB:NTPSignedTimeValue;
          units "seconds";
          description
           "The offset of the peer clock relative to the
            local clock in seconds.";
          smiv2:max-access "read-only";
          smiv2:oid "1.3.6.1.4.1.9.9.168.1.3.2.1.2";
        }

        leaf cntpFilterPeersDelay {
          type CISCO-NTP-MIB:NTPSignedTimeValue;
          units "seconds";
          description
           "Round-trip delay of the peer clock relative to the
            local clock over the network path between them, in
            seconds.  This variable can take on both positive and
            negative values, depending on clock precision and
            skew-error accumulation.";
          smiv2:max-access "read-only";
          smiv2:oid "1.3.6.1.4.1.9.9.168.1.3.2.1.3";
        }

        leaf cntpFilterPeersDispersion {
          type CISCO-NTP-MIB:NTPUnsignedTimeValue;
          units "seconds";
          description
           "The maximum error of the peer clock relative to the
            local clock over the network path between them, in
            seconds.  Only positive values greater than zero are
            possible.";
          smiv2:max-access "read-only";
          smiv2:oid "1.3.6.1.4.1.9.9.168.1.3.2.1.4";
        }
      }
    }
  }

  notification ciscoNtpSrvStatusChange {
    description
     "This notification is generated whenever the value of
      cntpSysSrvStatus changes.";
    smiv2:oid "1.3.6.1.4.1.9.9.168.0.1";

    container object-1 {

      leaf cntpSysSrvStatus {
        type leafref {
          path "/CISCO-NTP-MIB:CISCO-NTP-MIB/CISCO-NTP-MIB:cntpSystem/CISCO-NTP-MIB:cntpSysSrvStatus";
        }
      }
    }
  }

  notification ciscoNtpHighPriorityConnFailure {
    description
     "A failure to connect with an high priority NTP server
      (e.g. a server at the lowest stratum) is detected.";
    smiv2:oid "1.3.6.1.4.1.9.9.168.0.2";

    container object-1 {

      leaf cntpPeersAssocId {
        type leafref {
          path "/CISCO-NTP-MIB:CISCO-NTP-MIB/CISCO-NTP-MIB:cntpPeersVarTable/CISCO-NTP-MIB:cntpPeersVarEntry/CISCO-NTP-MIB:cntpPeersAssocId";
        }
      }

      leaf cntpPeersPeerAddress {
        type leafref {
          path "/CISCO-NTP-MIB:CISCO-NTP-MIB/CISCO-NTP-MIB:cntpPeersVarTable/CISCO-NTP-MIB:cntpPeersVarEntry/CISCO-NTP-MIB:cntpPeersPeerAddress";
        }
      }
    }
  }

  notification ciscoNtpHighPriorityConnRestore {
    description
     "A connection with an high priority NTP server
      (e.g. a server at the lowest stratum) is restored.";
    smiv2:oid "1.3.6.1.4.1.9.9.168.0.3";

    container object-1 {

      leaf cntpPeersAssocId {
        type leafref {
          path "/CISCO-NTP-MIB:CISCO-NTP-MIB/CISCO-NTP-MIB:cntpPeersVarTable/CISCO-NTP-MIB:cntpPeersVarEntry/CISCO-NTP-MIB:cntpPeersAssocId";
        }
      }

      leaf cntpPeersPeerAddress {
        type leafref {
          path "/CISCO-NTP-MIB:CISCO-NTP-MIB/CISCO-NTP-MIB:cntpPeersVarTable/CISCO-NTP-MIB:cntpPeersVarEntry/CISCO-NTP-MIB:cntpPeersPeerAddress";
        }
      }
    }
  }

  notification ciscoNtpGeneralConnFailure {
    description
     "This trap is sent when the device loses connectivity 
      to all NTP servers.";
    smiv2:oid "1.3.6.1.4.1.9.9.168.0.4";
  }

  notification ciscoNtpGeneralConnRestore {
    description
     "This trap is sent when the connection with at least 
      one NTP server has been restored
      (e.g. after a ciscoNtpGeneralConnFailure).";
    smiv2:oid "1.3.6.1.4.1.9.9.168.0.5";

    container object-1 {

      leaf cntpPeersAssocId {
        type leafref {
          path "/CISCO-NTP-MIB:CISCO-NTP-MIB/CISCO-NTP-MIB:cntpPeersVarTable/CISCO-NTP-MIB:cntpPeersVarEntry/CISCO-NTP-MIB:cntpPeersAssocId";
        }
      }

      leaf cntpPeersPeerAddress {
        type leafref {
          path "/CISCO-NTP-MIB:CISCO-NTP-MIB/CISCO-NTP-MIB:cntpPeersVarTable/CISCO-NTP-MIB:cntpPeersVarEntry/CISCO-NTP-MIB:cntpPeersPeerAddress";
        }
      }
    }
  }

  smiv2:alias "ciscoNtpMIB" {
    smiv2:oid "1.3.6.1.4.1.9.9.168";
  }

  smiv2:alias "ciscoNtpMIBNotifs" {
    smiv2:oid "1.3.6.1.4.1.9.9.168.0";
  }

  smiv2:alias "ciscoNtpMIBObjects" {
    smiv2:oid "1.3.6.1.4.1.9.9.168.1";
  }

  smiv2:alias "cntpSystem" {
    smiv2:oid "1.3.6.1.4.1.9.9.168.1.1";
  }

  smiv2:alias "cntpPeers" {
    smiv2:oid "1.3.6.1.4.1.9.9.168.1.2";
  }

  smiv2:alias "cntpFilter" {
    smiv2:oid "1.3.6.1.4.1.9.9.168.1.3";
  }

  smiv2:alias "ciscoNtpMIBConformance" {
    smiv2:oid "1.3.6.1.4.1.9.9.168.2";
  }

  smiv2:alias "ciscoNtpMIBCompliances" {
    smiv2:oid "1.3.6.1.4.1.9.9.168.2.1";
  }

  smiv2:alias "ciscoNtpMIBGroups" {
    smiv2:oid "1.3.6.1.4.1.9.9.168.2.2";
  }

}
