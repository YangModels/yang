module SNMPv2-MIB {
  namespace "http://tail-f.com/ns/mibs/SNMPv2-MIB/200210160000Z";
  prefix SNMPv2_MIB;
  tailf:id "";
  tailf:snmp-mib-module-name "SNMPv2-MIB";

  import ietf-yang-types {
    prefix yang;
  }
  import tailf-common {
    prefix tailf;
  }
  import SNMPv2-TC {
    prefix SNMPv2_TC;
  }

  revision 2002-10-16 {
    description
      "";
  }

  container SNMPv2-MIB {
    container system {
      tailf:snmp-oid "1.3.6.1.2.1.1";
      leaf sysDescr {
        type sysDescrType;
        tailf:snmp-oid "1.3.6.1.2.1.1.1";
        config false;
      }
      leaf sysObjectID {
        type yang:object-identifier;
        tailf:snmp-oid "1.3.6.1.2.1.1.2";
        config false;
      }
      leaf sysUpTime {
        type yang:timeticks;
        tailf:snmp-oid "1.3.6.1.2.1.1.3";
        config false;
      }
      leaf sysContact {
        type sysContactType;
        tailf:snmp-oid "1.3.6.1.2.1.1.4";
        default "";
      }
      leaf sysName {
        type sysNameType;
        tailf:snmp-oid "1.3.6.1.2.1.1.5";
        default "";
      }
      leaf sysLocation {
        type sysLocationType;
        tailf:snmp-oid "1.3.6.1.2.1.1.6";
        default "";
      }
      leaf sysServices {
        type sysServicesType;
        tailf:snmp-oid "1.3.6.1.2.1.1.7";
        config false;
      }
      leaf sysORLastChange {
        type yang:timestamp;
        tailf:snmp-oid "1.3.6.1.2.1.1.8";
        config false;
      }
    }
    container snmp {
      tailf:snmp-oid "1.3.6.1.2.1.11";
      leaf snmpInPkts {
        type yang:counter32;
        tailf:snmp-oid "1.3.6.1.2.1.11.1";
        config false;
      }
      leaf snmpInBadVersions {
        type yang:counter32;
        tailf:snmp-oid "1.3.6.1.2.1.11.3";
        config false;
      }
      leaf snmpInBadCommunityNames {
        type yang:counter32;
        tailf:snmp-oid "1.3.6.1.2.1.11.4";
        config false;
      }
      leaf snmpInBadCommunityUses {
        type yang:counter32;
        tailf:snmp-oid "1.3.6.1.2.1.11.5";
        config false;
      }
      leaf snmpInASNParseErrs {
        type yang:counter32;
        tailf:snmp-oid "1.3.6.1.2.1.11.6";
        config false;
      }
      leaf snmpEnableAuthenTraps {
        type snmpEnableAuthenTrapsType;
        tailf:snmp-oid "1.3.6.1.2.1.11.30";
        default "disabled";
      }
      leaf snmpSilentDrops {
        type yang:counter32;
        tailf:snmp-oid "1.3.6.1.2.1.11.31";
        config false;
      }
      leaf snmpProxyDrops {
        type yang:counter32;
        tailf:snmp-oid "1.3.6.1.2.1.11.32";
        config false;
      }
    }
    container snmpSet {
      tailf:snmp-oid "1.3.6.1.6.3.1.1.6";
      leaf snmpSetSerialNo {
        type SNMPv2_TC:TestAndIncr;
        config false;
      }
    }
    container sysORTable {
      config false;
      list sysOREntry {
        key "sysORIndex";
        tailf:sort-order "snmp";
        tailf:snmp-oid "1.3.6.1.2.1.1.9";
        leaf sysORIndex {
          type sysORIndexType;
          tailf:snmp-oid "1.3.6.1.2.1.1.9.1.1";
        }
        leaf sysORID {
          type yang:object-identifier;
          tailf:snmp-oid "1.3.6.1.2.1.1.9.1.2";
          config false;
        }
        leaf sysORDescr {
          type string {
            length "0 .. 255";
          }
          tailf:snmp-oid "1.3.6.1.2.1.1.9.1.3";
          config false;
        }
        leaf sysORUpTime {
          type yang:timestamp;
          tailf:snmp-oid "1.3.6.1.2.1.1.9.1.4";
          config false;
        }
      }
    }
  }

  typedef sysDescrType {
    type SNMPv2_TC:DisplayString;
  }

  typedef sysContactType {
    type SNMPv2_TC:DisplayString;
  }

  typedef sysNameType {
    type SNMPv2_TC:DisplayString;
  }

  typedef sysLocationType {
    type SNMPv2_TC:DisplayString;
  }

  typedef sysServicesType {
    type int32 {
      range "0 .. 127";
    }
  }

  typedef snmpEnableAuthenTrapsType {
    type enumeration {
      enum "enabled" {
        value 1;
      }
      enum "disabled" {
        value 2;
      }
    }
  }

  typedef sysORIndexType {
    type int32 {
      range "1 .. 2147483647";
    }
  }
}
