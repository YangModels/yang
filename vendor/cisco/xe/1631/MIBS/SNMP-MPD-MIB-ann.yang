module SNMP-MPD-MIB-ann {
  namespace "urn:dummy";
  prefix dummy;

  import tailf-common {
    prefix tailf;
  }
  import SNMP-MPD-MIB {
    prefix x;
  }

  tailf:annotate "/x:SNMP-MPD-MIB" {
    tailf:callpoint "snmpagent" {
      tailf:internal;
    }
  }


}
