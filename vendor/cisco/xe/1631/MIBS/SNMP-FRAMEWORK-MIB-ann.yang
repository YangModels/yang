module SNMP-FRAMEWORK-MIB-ann {
  namespace "urn:dummy";
  prefix dummy;

  import tailf-common {
    prefix tailf;
  }
  import SNMP-FRAMEWORK-MIB {
    prefix x;
  }

  tailf:annotate "/x:SNMP-FRAMEWORK-MIB" {
    tailf:callpoint "snmpagent" {
      tailf:internal;
    }
  }

}
