module Cisco-IOS-XE-line-actions-rpc {
  yang-version 1.1;
  namespace "http://cisco.com/ns/yang/Cisco-IOS-XE-line-actions-rpc";
  prefix line-actions-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for IOS terminal
     line actions RPC.
     Copyright (c) 2024 by Cisco Systems, Inc.
     All rights reserved.";

  revision 2024-11-01 {
    description
      "Initial revision";
    reference
      "1.0.0";
    cisco-semver:module-version "1.0.0";
  }

  grouping line {
    description
      "IOS terminal line";
    leaf number {
      type uint32;
      mandatory true;
      description
        "Line number";
    }
  }

  rpc clear-line {
    description
      "Clear line action RPC";
    input {
      uses line-actions-rpc:line;
    }
  }
}
