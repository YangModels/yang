module Cisco-IOS-XE-wireless-client-rpc {
  yang-version 1.1;
  namespace "http://cisco.com/ns/yang/Cisco-IOS-XE-wireless-client-rpc";
  prefix wireless-client-rpc;

  import Cisco-IOS-XE-wireless-enum-types {
    prefix wireless-enum-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for wireless client features.
     Copyright (c) 2022 by Cisco Systems, Inc.
     All rights reserved.";

  revision 2024-03-01 {
    description
      "Added RPC for client deauthentication and clear pmk cache";
    reference
      "1.3.0";
    cisco-semver:module-version "1.3.0";
  }
  revision 2023-03-01 {
    description
      "- Zone-id support for clear device-tracking command";
    reference
      "1.2.0";
    cisco-semver:module-version "1.2.0";
  }
  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  typedef client-identifier-type {
    type enumeration {
      enum client-identifier-mac-address {
        value 0;
        description
          "Client MAC address";
      }
      enum client-identifier-ip-address {
        value 1;
        description
          "Client IP address";
      }
      enum client-identifier-username {
        value 2;
        description
          "Client Username";
      }
    }
    description
      "Client identification type";
  }

  grouping apf-ms-delete-all {
    description
      "Delete wireless client based on client MAC or IP address or username";
    leaf zone-id {
      type int32;
      default "0";
      description
        "Binding entry zone-id";
    }
    choice alternative-choice {
      mandatory true;
      description
        "Alternative choice";
      case client-identifier-mac-address {
        leaf mac-addr {
          type yang:mac-address;
          mandatory true;
          description
            "MAC address";
        }
      }
      case client-identifier-ip-address {
        leaf ip-addr {
          type inet:ip-address;
          mandatory true;
          description
            "IP address";
        }
      }
      case client-identifier-username {
        leaf user-name {
          type string;
          mandatory true;
          description
            "Username";
        }
      }
    }
  }

  grouping clear-sisf-binding-state {
    description
      "Delete client binding entry based on client MAC and entry state";
    leaf entry-mac-address {
      type yang:mac-address;
      mandatory true;
      description
        "Wireless Client MAC address";
    }
    leaf binding-state {
      type wireless-enum-types:enm-sisf-binding-state;
      mandatory true;
      description
        "Client binding state";
    }
  }

  grouping clear-sisf-binding-ip {
    description
      "Delete client binding entry based on client MAC and IP address";
    leaf entry-mac-address {
      type yang:mac-address;
      mandatory true;
      description
        "Wireless Client MAC address";
    }
    leaf ip-addr {
      type inet:ip-address;
      mandatory true;
      description
        "Binding entry IP address";
    }
    leaf zone-id {
      type uint32;
      default "0";
      description
        "Binding entry zone-id";
    }
  }

  grouping clear-pmk-cache {
    description
      "Clear client pmk cache";
    leaf address {
      type yang:mac-address;
      mandatory true;
      description
        "Wireless Client MAC address";
    }
  }

  rpc apf-ms-delete-all {
    description
      "Delete wireless client based on client MAC or IP address or username";
    input {
      uses wireless-client-rpc:apf-ms-delete-all;
    }
  }

  rpc clear-sisf-binding-state {
    description
      "Delete client binding entry based on client MAC and entry state";
    input {
      uses wireless-client-rpc:clear-sisf-binding-state;
    }
  }

  rpc clear-sisf-binding-ip {
    description
      "Delete client binding entry based on client MAC and IP address";
    input {
      uses wireless-client-rpc:clear-sisf-binding-ip;
    }
  }

  rpc clear-pmk-cache {
    description
      "Clear client pmk cache";
    input {
      uses wireless-client-rpc:clear-pmk-cache;
    }
  }
}
