module Cisco-IOS-XE-livetools-actions-rpc {
  yang-version 1.1;
  namespace "http://cisco.com/ns/yang/Cisco-IOS-XE-livetools-actions-rpc";
  prefix livetools-ios-actions-rpc;

  import Cisco-IOS-XE-common-types {
    prefix common-types-ios-xe;
  }
  import Cisco-IOS-XE-livetools-common-types {
    prefix livetools-common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for live tools action RPC.
     Copyright (c) 2024 by Cisco Systems, Inc.
     All rights reserved.";

  revision 2024-07-01 {
    description
      "Initial revision";
    reference
      "1.0.0";
    cisco-semver:module-version "1.0.0";
  }

  typedef thrpt-mode {
    type enumeration {
      enum thrpt-mode-avg {
        value 0;
        description
          "Measure throughput in average mode";
      }
      enum thrpt-mode-full {
        value 1;
        description
          "Measure throughput in full mode";
      }
      enum thrpt-mode-peak {
        value 2;
        description
          "Measure throughput in peak mode";
      }
    }
    description
      "Throughput mode measurement options";
  }

  typedef thrpt-proto-type {
    type enumeration {
      enum thrpt-tcp-client {
        value 0;
        description
          "Operate as a TCP client";
      }
    }
    description
      "Protocol-Role combination;
       protocol: TCP/UDP, role: client/server";
  }

  grouping wol-params {
    description
      "WAKE-ON-LAN action RPC input parameters";
    leaf mac-addr {
      type yang:mac-address;
      mandatory true;
      description
        "Destination MAC address";
    }
    leaf vlan {
      type uint16 {
        range "1..4094";
      }
      default "1";
      description
        "Destination VLAN identifier";
    }
    leaf interval {
      type uint16 {
        range "1..3600";
      }
      units "seconds";
      default "120";
      description
        "Interval between retries";
    }
    leaf count {
      type uint8 {
        range "1..255";
      }
      default "1";
      description
        "Number of packets to be sent";
    }
  }

  grouping wol-action-resp {
    description
      "Response to the
       WAKE-ON-LAN action RPC";
    leaf job-id {
      type uint32;
      description
        "The ID is a unique identifier generated per RPC request.
         It is used in conjunction with the WAKE-ON-LAN oper model,
         allowing us to retrieve the operational data associated with a
         specific ID. This is useful for matching an action RPC response ID
         with the corresponding operational data";
    }
  }

  grouping thrpt-input {
    description
      "Parameters to execute test-throughput";
    leaf proto {
      type livetools-ios-actions-rpc:thrpt-proto-type;
      default "thrpt-tcp-client";
      description
        "Role of throughput tool: client/server";
    }
    leaf dest-addr {
      type inet:ip-address;
      description
        "Server IP address";
    }
    leaf ni-type {
      type common-types-ios-xe:net-inst-type;
      default "net-inst-default";
      description
        "Network instance type. Differentiates between the
         default routing instance and VRFs";
    }
    leaf ni-name {
      type string;
      description
        "Network instance name. If the type is
         net-inst-default, the name is not meaningful";
    }
    leaf timeout {
      type uint64;
      units "seconds";
      default "5";
      description
        "Measurement time";
    }
    leaf wnd-span {
      type uint64 {
        range "1..4294967295";
      }
      units "seconds";
      default "1";
      description
        "Duration of measurement window(s)";
    }
    leaf num-wnds {
      type uint32 {
        range "1..4294967295";
      }
      default "5";
      description
        "Number of windows";
    }
    leaf port {
      type uint16;
      description
        "Server transport port";
    }
    leaf dscp {
      type uint8;
      default "0";
      description
        "Numeric value of DSCP used during traffic generation";
    }
    leaf client-rcv {
      type boolean;
      default "false";
      description
        "Flag to indicate that client should receive/read
         data from the server instead of the default mode of writing data to
         the server for throughput measurement";
    }
    leaf mode {
      type livetools-ios-actions-rpc:thrpt-mode;
      default "thrpt-mode-full";
      description
        "Measurement mode";
    }
  }

  grouping thrpt-action-resp {
    description
      "Response to throughput measurement request";
    leaf job-id {
      type uint32;
      description
        "The ID is a unique identifier generated per RPC request.
         It is used in conjunction with the throughput oper model,
         allowing us to retrieve the operational data associated with a
         specific ID. This is useful for matching an action RPC response ID
         with the corresponding operational data";
    }
  }

  grouping ip-tracert {
    description
      "Parameters to execute IP trace route action";
    leaf ni-type {
      type common-types-ios-xe:net-inst-type;
      default "net-inst-default";
      description
        "Network instance type. Differentiates between the
         default routing instance and VRFs";
    }
    leaf ni-name {
      type string;
      description
        "Network instance name. If the type is
         net-inst-default, the name is not meaningful.";
    }
    leaf num-probes {
      type uint8 {
        range "1..5";
      }
      default "3";
      description
        "Number of probes to be sent per hop";
    }
    leaf port {
      type uint32 {
        range "1..65535";
      }
      default "33434";
      description
        "Destination port to send UDP packets";
    }
    leaf timeout {
      type uint32 {
        range "1..3600";
      }
      units "seconds";
      default "3";
      description
        "Probe timeout value";
    }
    leaf min-ttl {
      type uint8 {
        range "0..30";
      }
      default "1";
      description
        "Minimum value of time to live(TTL) for an IP packet";
    }
    leaf max-ttl {
      type uint8 {
        range "1..30";
      }
      default "30";
      description
        "Maximum value of time to live(TTL) for an IP packet";
    }
    choice dscp-choice {
      description
        "Choice for DSCP options to be set";
      case dscp-num {
        leaf dscp-num {
          type uint8 {
            range "0..63";
          }
          mandatory true;
          description
            "DSCP numeric value";
        }
      }
      case dscp-ascii {
        leaf dscp-ascii {
          type livetools-common-types-ios-xe:dscp-options;
          mandatory true;
          description
            "DSCP ascii value selected from a set of known DSCP options";
        }
      }
    }
    choice src-choice {
      description
        "Choice of source for IP trace route request as IP/IPv6 address or interface name";
      case src-if-name {
        leaf src-if {
          type string;
          mandatory true;
          description
            "Source interface name";
        }
      }
      case src-ip-addr {
        leaf src-ip {
          type inet:ip-address;
          mandatory true;
          description
            "Source IP/IPv6 address";
        }
      }
    }
    choice host-choice {
      mandatory true;
      description
        "Choice of destination for IP trace route request as IP/IPv6 address or hostname";
      case host-name {
        leaf host-name {
          type string;
          mandatory true;
          description
            "Destination host name";
        }
      }
      case host-ip-addr {
        leaf host-ip {
          type inet:ip-address;
          mandatory true;
          description
            "Destination host IP address";
        }
      }
    }
  }

  grouping ip-tracert-action-resp {
    description
      "Response to IP trace route request.";
    leaf job-id {
      type uint32;
      description
        "The ID is a unique identifier generated per RPC request.
         It is used in conjunction with the IP trace route,
         allowing us to retrieve the operational data associated with a
         specific ID. This is useful for matching an action RPC response ID
         with the corresponding operational data.";
    }
  }

  grouping ip-ping {
    description
      "Parameters to execute the IP ping operation";
    leaf ni-type {
      type common-types-ios-xe:net-inst-type;
      default "net-inst-default";
      description
        "Network instance type. Differentiates between the
         default routing instance and VRFs";
    }
    leaf ni-name {
      type string;
      description
        "Network instance name. If the type is
         net-inst-default, the name is not meaningful";
    }
    leaf count {
      type uint8 {
        range "1..30";
      }
      default "5";
      description
        "Number of echoes to be sent as part of the IP ping request";
    }
    choice dscp-choice {
      description
        "Choice of DSCP type";
      case dscp-num {
        leaf dscp-num {
          type uint8 {
            range "0..63";
          }
          mandatory true;
          description
            "DSCP numeric value";
        }
      }
      case dscp-ascii {
        leaf dscp-ascii {
          type livetools-common-types-ios-xe:dscp-options;
          mandatory true;
          description
            "DSCP ascii value selected from a set of known DSCP options";
        }
      }
    }
    choice src-choice {
      description
        "Choice of source for ping - source address/interface";
      case src-if-name {
        leaf src-if {
          type string;
          mandatory true;
          description
            "Source interface name";
        }
      }
      case src-ip-addr {
        leaf src-ip {
          type inet:ip-address;
          mandatory true;
          description
            "Source IP address";
        }
      }
    }
    choice host-choice {
      mandatory true;
      description
        "Choice of destination host for ping - IP address/hostname";
      case host-name {
        leaf host-name {
          type string;
          mandatory true;
          description
            "Destination host name";
        }
      }
      case host-ip-addr {
        leaf host-ip {
          type inet:ip-address;
          mandatory true;
          description
            "Destination host IP address";
        }
      }
    }
  }

  grouping ip-ping-action-resp {
    description
      "Response of the IP Ping RPC request";
    leaf job-id {
      type uint32;
      description
        "The ID is a unique identifier generated per RPC request.
         It is used in conjunction with the ping oper model,
         allowing us to retrieve the operational data associated with a
         specific ID";
    }
  }

  grouping mtr-params {
    description
      "Parameters to execute the MTR action";
    leaf ni-type {
      type common-types-ios-xe:net-inst-type;
      default "net-inst-default";
      description
        "Network instance type. Differentiates between the
         default routing instance and VRFs";
    }
    leaf ni-name {
      type string;
      description
        "Network instance name. If the type is
         net-inst-default, the name is not meaningful";
    }
    leaf proto-hint {
      type livetools-common-types-ios-xe:dns-proto-hint;
      default "dns-proto-none";
      description
        "DNS resolution type";
    }
    leaf count {
      type uint8 {
        range "1..10";
      }
      default "10";
      description
        "The number of traceroute/ping probes or packets to be sent to each hop along the traceroute path";
    }
    leaf port {
      type uint16 {
        range "1..65535";
      }
      default "33434";
      description
        "Destination port to send UDP packets";
    }
    leaf timeout {
      type uint16 {
        range "1..3600";
      }
      units "seconds";
      default "3";
      description
        "Probe timeout value";
    }
    leaf min-ttl {
      type uint8 {
        range "0..30";
      }
      default "1";
      description
        "Minimum value of time to live(TTL) for an IP packet";
    }
    leaf max-ttl {
      type uint8 {
        range "1..30";
      }
      default "30";
      description
        "Maximum value of time to live(TTL) for an IP packet";
    }
    choice dscp-choice {
      description
        "Choice for DSCP options to be set";
      case dscp-num {
        leaf dscp-num {
          type uint8 {
            range "0..63";
          }
          mandatory true;
          description
            "DSCP numeric value";
        }
      }
      case dscp-ascii {
        leaf dscp-ascii {
          type livetools-common-types-ios-xe:dscp-options;
          mandatory true;
          description
            "DSCP ASCII value selected from a set of known DSCP options";
        }
      }
    }
    choice src-choice {
      description
        "Choice of source for the MTR request as IP/IPv6 address or interface name";
      case src-if-name {
        leaf src-if {
          type string;
          mandatory true;
          description
            "Source interface name";
        }
      }
      case src-ip-addr {
        leaf src-ip {
          type inet:ip-address;
          mandatory true;
          description
            "Source IP/IPv6 address";
        }
      }
    }
    choice host-choice {
      mandatory true;
      description
        "Choice of destination for the MTR request as IP/IPv6 address or hostname";
      case host-name {
        leaf host-name {
          type string;
          mandatory true;
          description
            "Destination host name";
        }
      }
      case host-ip-addr {
        leaf host-ip {
          type inet:ip-address;
          mandatory true;
          description
            "Destination host IP address";
        }
      }
    }
  }

  grouping mtr-action-resp {
    description
      "Response to the MTR request.";
    leaf job-id {
      type uint32;
      description
        "The ID is a unique identifier generated per RPC request.
         It is used in conjunction with the MTR,
         allowing us to retrieve the operational data associated with a
         specific ID. This is useful for matching an action RPC response ID
         with the corresponding operational data";
    }
  }

  rpc wol-action {
    description
      "This RPC is used to test the WAKE-ON-LAN feature execution and it returns
       with an 'JOB ID' if the RPC execution was successful";
    input {
      uses livetools-ios-actions-rpc:wol-params;
    }
    output {
      uses livetools-ios-actions-rpc:wol-action-resp;
    }
  }

  rpc thrpt-action {
    description
      "Network throughput measurement";
    input {
      uses livetools-ios-actions-rpc:thrpt-input;
    }
    output {
      uses livetools-ios-actions-rpc:thrpt-action-resp;
    }
  }

  rpc ip-tracert-action {
    description
      "This RPC is used to denote an IP trace route operation";
    input {
      uses livetools-ios-actions-rpc:ip-tracert;
    }
    output {
      uses livetools-ios-actions-rpc:ip-tracert-action-resp;
    }
  }

  rpc ip-ping-action {
    description
      "This RPC is used to denote an IP ping operation";
    input {
      uses livetools-ios-actions-rpc:ip-ping;
    }
    output {
      uses livetools-ios-actions-rpc:ip-ping-action-resp;
    }
  }

  rpc mtr-action {
    description
      "This RPC is used to denote a my trace route (MTR) operation";
    input {
      uses livetools-ios-actions-rpc:mtr-params;
    }
    output {
      uses livetools-ios-actions-rpc:mtr-action-resp;
    }
  }
}
