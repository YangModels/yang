module Cisco-IOS-XE-ignition-oper {
  yang-version 1.1;
  namespace "http://cisco.com/ns/yang/Cisco-IOS-XE-ignition-oper";
  prefix ignition-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Ignition Power Management operational data.
     Copyright (c) 2021-2022 by Cisco Systems, Inc.
     All rights reserved.";

  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  typedef ignition-mgmt-state {
    type enumeration {
      enum ignition-pwr-enabled {
        value 0;
        description
          "Ignition Power enabled";
      }
      enum ignition-pwr-disabled {
        value 1;
        description
          "Ignition Power disabled";
      }
    }
    description
      "Status of Ignition Power Management";
  }

  typedef ignition-power-state {
    type enumeration {
      enum ignition-pwr-boot-loader {
        value 0;
        description
          "Ignition at boot loader stage";
      }
      enum ignition-pwr-on {
        value 1;
        description
          "Ignition at Power ON state";
      }
      enum ignition-pwr-shut-low-volt {
        value 2;
        description
          "Ignition shutdown due to low voltage";
      }
      enum ignition-pwr-shut-off {
        value 3;
        description
          "Ignition shutdown due to OFF state";
      }
      enum ignition-pwr-shut-high-volt {
        value 4;
        description
          "Ignition shutdown due to high voltage";
      }
      enum ignition-powering-up {
        value 5;
        description
          "Ignition Powering up";
      }
      enum ignition-pwr-monitor {
        value 6;
        description
          "Ignition at monitor state";
      }
      enum ignition-pwr-sleep {
        value 7;
        description
          "Ignition at sleep state";
      }
      enum ignition-pwr-unknown {
        value 8;
        description
          "Ignition at unknown state";
      }
    }
    description
      "Ignition power status";
  }

  typedef ignition-sense {
    type enumeration {
      enum ignition-sense-enabled {
        value 0;
        description
          "Voltage sense enabled";
      }
      enum ignition-sense-disabled {
        value 1;
        description
          "Voltage sense disabled";
      }
    }
    description
      "Enable/Disable voltage sense";
  }

  typedef ignition-battery-type {
    type enumeration {
      enum ignition-battery-12v {
        value 0;
        description
          "12 Volts battery system";
      }
      enum ignition-battery-24v {
        value 1;
        description
          "24 Volts battery system";
      }
    }
    description
      "Ignition battery type";
  }

  grouping ignition-status {
    description
      "Ignition Status";
    leaf ignition-mgmt {
      type ignition-ios-xe-oper:ignition-mgmt-state;
      description
        "Ignition Management status";
    }
    leaf input-volt {
      type decimal64 {
        fraction-digits 3;
      }
      units "volts";
      description
        "Ignition Input Voltage";
    }
    leaf pwr-state {
      type ignition-ios-xe-oper:ignition-power-state;
      description
        "Ignition power status";
    }
    leaf sense {
      when "../ignition-mgmt = 'ignition-pwr-enabled'";
      type ignition-ios-xe-oper:ignition-sense;
      description
        "Ignition voltage sense state";
    }
    leaf shutdown-time {
      when "(../ignition-mgmt = 'ignition-pwr-enabled') and
            (../pwr-state = 'ignition-pwr-shut-off')";
      type yang:date-and-time;
      description
        "Time when ignition power will be shutdown";
    }
    leaf undervoltage {
      type decimal64 {
        fraction-digits 3;
      }
      units "volts";
      description
        "Under voltage threshold";
    }
    leaf overvoltage {
      type decimal64 {
        fraction-digits 3;
      }
      units "volts";
      description
        "Over voltage threshold";
    }
    leaf undervoltage-time-delay {
      when "(../undervoltage < 9.600) and
            (../pwr-state = 'ignition-pwr-shut-low-volt')";
      type uint8;
      units "seconds";
      description
        "Amount of time device remains powered on before
         shutdown due to ignition under voltage";
    }
    leaf overvoltage-time-delay {
      when "(../overvoltage > 37) and
            (../pwr-state = 'ignition-pwr-shut-high-volt')";
      type uint8;
      units "seconds";
      description
        "Amount of time device remains powered on before
         shutdown due to ignition over voltage";
    }
    leaf ignition-off-time-delay {
      when "../ignition-mgmt = 'ignition-pwr-enabled'";
      type uint16;
      units "seconds";
      description
        "Amount of time device remains powered on after
         ignition off";
    }
    leaf battery-type {
      type ignition-ios-xe-oper:ignition-battery-type;
      description
        "Ignition battery type";
    }
    leaf sense-on-threshold {
      when "(../ignition-mgmt = 'ignition-pwr-enabled') and
            (../sense = 'ignition-sense-enabled')";
      type decimal64 {
        fraction-digits 3;
      }
      units "volts";
      description
        "When input voltage is greater than this ignition
         sense threshold, it powers on the device";
    }
    leaf sense-off-threshold {
      when "(../ignition-mgmt = 'ignition-pwr-enabled') and
            (../sense = 'ignition-sense-enabled')";
      type decimal64 {
        fraction-digits 3;
      }
      units "volts";
      description
        "When input voltage is lower than this ignition
         sense threshold, it powers off the device";
    }
  }

  container ignition-oper-data {
    config false;
    description
      "Operational state of Ignition Power";
    container ignition-status {
      presence "ignition-status";
      description
        "Ignition Power Management";
      uses ignition-ios-xe-oper:ignition-status;
    }
  }
}
