module Cisco-IOS-XE-sdwan-types {
  yang-version 1.1;
  namespace "http://cisco.com/ns/yang/Cisco-IOS-XE-sdwan-types";
  prefix ios-xe-sdwan-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for common types in the Cisco IOS XE SDWAN model.
     Copyright (c) 2024 by Cisco Systems, Inc.
     All rights reserved.";

  revision 2024-11-01 {
    description
      "Initial revision";
    reference
      "1.0.0";
    cisco-semver:module-version "1.0.0";
  }

  typedef sdwan-color-enum {
    type enumeration {
      enum sdwan-color-invalid {
        value 0;
        description
          "Invalid";
      }
      enum sdwan-color-default {
        value 1;
        description
          "Default";
      }
      enum sdwan-color-mpls {
        value 2;
        description
          "MPLS color";
      }
      enum sdwan-color-metro-ethernet {
        value 3;
        description
          "Metro ethernet";
      }
      enum sdwan-color-biz-internet {
        value 4;
        description
          "Biz internet";
      }
      enum sdwan-color-public-internet {
        value 5;
        description
          "Public internet";
      }
      enum sdwan-color-lte {
        value 6;
        description
          "LTE color";
      }
      enum sdwan-color-3-g {
        value 7;
        description
          "3G color";
      }
      enum sdwan-color-red {
        value 8;
        description
          "Red color";
      }
      enum sdwan-color-green {
        value 9;
        description
          "Green color";
      }
      enum sdwan-color-blue {
        value 10;
        description
          "Blue color";
      }
      enum sdwan-color-gold {
        value 11;
        description
          "Gold color";
      }
      enum sdwan-color-silver {
        value 12;
        description
          "Silver";
      }
      enum sdwan-color-bronze {
        value 13;
        description
          "Bronze";
      }
      enum sdwan-color-custom1 {
        value 14;
        description
          "Custom 1";
      }
      enum sdwan-color-custom2 {
        value 15;
        description
          "Custom 2";
      }
      enum sdwan-color-custom3 {
        value 16;
        description
          "Custom 3";
      }
      enum sdwan-color-private1 {
        value 17;
        description
          "Private 1";
      }
      enum sdwan-color-private2 {
        value 18;
        description
          "Private 2";
      }
      enum sdwan-color-private3 {
        value 19;
        description
          "Private 3";
      }
      enum sdwan-color-private4 {
        value 20;
        description
          "Private 4";
      }
      enum sdwan-color-private5 {
        value 21;
        description
          "Private 5";
      }
      enum sdwan-color-private6 {
        value 22;
        description
          "Private 6";
      }
    }
    description
      "The enumeration definition of SDWAN color";
  }

  typedef sdwan-encap-enum {
    type enumeration {
      enum sdwan-encap-default {
        value 0;
        description
          "Default encapsulation";
      }
      enum sdwan-encap-gre {
        value 1;
        description
          "GRE encapsulation";
      }
      enum sdwan-encap-ipsec {
        value 2;
        description
          "IPSec encapsulation";
      }
    }
    description
      "The enumeration definition of SDWAN encapsulation";
  }
}
