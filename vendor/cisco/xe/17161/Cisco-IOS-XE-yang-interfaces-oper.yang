module Cisco-IOS-XE-yang-interfaces-oper {
  yang-version 1.1;
  namespace "http://cisco.com/ns/yang/Cisco-IOS-XE-yang-interfaces-oper";
  prefix yang-interfaces-oper;

  import Cisco-IOS-XE-dmi-common-types {
    prefix dmi-common-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Operational data for YANG model-based interfaces.
     Copyright (c) 2021-2024 by Cisco Systems, Inc.
     All rights reserved.";

  revision 2024-11-01 {
    description
      "Oper model support for NETCONF SSH trustpoint selection";
    reference
      "1.3.0";
    cisco-semver:module-version "1.3.0";
  }
  revision 2023-07-01 {
    description
      "Oper model support for NETCONF SSH algorithms";
    reference
      "1.2.0";
    cisco-semver:module-version "1.2.0";
  }
  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  typedef enm-local-vrf-state {
    type enumeration {
      enum down {
        value 0;
        description
          "Indicates the system is not listening for NETCONF connections on
           local host in the current VRF.";
      }
      enum up {
        value 1;
        description
          "Indicates the system is ready to accept NETCONF connections on
           local host in the current VRF.";
      }
    }
    description
      "List of states of the NETCONF server with respect to connections on
       local host in the current VRF.";
  }

  grouping dmi-ssh-local-vrf-oper {
    description
      "Operational data for NETCONF access on local host in a specific VRF.";
    leaf vrf-name {
      type dmi-common-types:enm-local-vrf-name;
      description
        "Name of the VRF.";
    }
    leaf state {
      type yang-interfaces-oper:enm-local-vrf-state;
      description
        "State of NETCONF server with respect to connections on local host
         is the current VRF.";
    }
  }

  grouping dmi-ssh-hostkey-algorithms-oper {
    description
      "Host key public key algorithms.";
    leaf rsa-sha2-256 {
      type boolean;
      description
        "RSA-SHA2-256 Public key based authentication.";
    }
    leaf rsa-sha2-512 {
      type boolean;
      description
        "RSA-SHA2-512 Public key based authentication.";
    }
    leaf ssh-rsa {
      type boolean;
      description
        "RSA-SHA1 Public key based authentication.";
    }
  }

  grouping dmi-ssh-cipher-algorithms-oper {
    description
      "Encryption algorithms.";
    leaf aes128-ctr {
      type boolean;
      description
        "AES with 128-bit key in CTR mode.";
    }
    leaf aes192-ctr {
      type boolean;
      description
        "AES with 192-bit key in CTR mode.";
    }
    leaf aes256-ctr {
      type boolean;
      description
        "AES with 256-bit key in CTR mode.";
    }
    leaf aes128-cbc {
      type boolean;
      description
        "AES with 128-bit key in CBC mode.";
    }
    leaf aes256-cbc {
      type boolean;
      description
        "AES with 256-bit key in CBC mode.";
    }
  }

  grouping dmi-ssh-mac-algorithms-oper {
    description
      "Message authentication code algorithms.";
    leaf hmac-sha2-256 {
      type boolean;
      description
        "HMAC-SHA2-256.";
    }
    leaf hmac-sha2-512 {
      type boolean;
      description
        "HMAC-SHA2-512.";
    }
    leaf hmac-sha1 {
      type boolean;
      description
        "HMAC-SHA1.";
    }
  }

  grouping dmi-ssh-kex-algorithms-oper {
    description
      "Key exchange algorithms.";
    leaf dh-group14-sha1 {
      type boolean;
      description
        "DH-GROUP-14-SHA1 key exchange algorithm.";
    }
    leaf dh-group14-sha256 {
      type boolean;
      description
        "DH-GROUP-14-SHA256 key exchange algorithm.";
    }
    leaf ecdh-sha2-nistp256 {
      type boolean;
      description
        "Elliptic Curve DH-SHA2-P256 key exchange algorithm.";
    }
    leaf ecdh-sha2-nistp384 {
      type boolean;
      description
        "Elliptic Curve DH-SHA2-P384 key exchange algorithm.";
    }
    leaf ecdh-sha2-nistp521 {
      type boolean;
      description
        "Elliptic Curve DH-SHA2-P521 key exchange algorithm.";
    }
    leaf dh-group16-sha512 {
      type boolean;
      description
        "DH-GROUP-16-SHA512 key exchange algorithm.";
    }
  }

  grouping dmi-ssh-server-oper {
    description
      "SSH server algorithm.";
    container kex-alg {
      description
        "Key exchange algorithms for NETCONF SSH server.";
      uses yang-interfaces-oper:dmi-ssh-kex-algorithms-oper;
    }
    container macs {
      description
        "Message authentication code algorithms for NETCONF SSH server.";
      uses yang-interfaces-oper:dmi-ssh-mac-algorithms-oper;
    }
    container ciphers {
      description
        "Encryption algorithms for NETCONF SSH server.";
      uses yang-interfaces-oper:dmi-ssh-cipher-algorithms-oper;
    }
    container hostkey-alg {
      description
        "Host key algorithms for NETCONF SSH server.";
      uses yang-interfaces-oper:dmi-ssh-hostkey-algorithms-oper;
    }
    leaf tp-name {
      type string;
      description
        "Trustpoint used for NETCONF SSH server.";
    }
  }

  container yang-interfaces-oper-data {
    config false;
    description
      "Configuration for YANG model-based interfaces.";
    list local-vrf {
      key "vrf-name";
      description
        "Operational data for NETCONF access on local host in a specific VRF.";
      uses yang-interfaces-oper:dmi-ssh-local-vrf-oper;
    }
    container ssh-server {
      presence "ssh-server";
      description
        "Operational data for NETCONF SSH server.";
      uses yang-interfaces-oper:dmi-ssh-server-oper;
    }
  }
}
