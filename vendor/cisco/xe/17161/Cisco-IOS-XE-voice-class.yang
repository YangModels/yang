submodule Cisco-IOS-XE-voice-class {
  yang-version 1.1;
  belongs-to Cisco-IOS-XE-voice {
    prefix ios-voice;
  }

  import cisco-semver {
    prefix cisco-semver;
  }
  import Cisco-IOS-XE-native {
    prefix ios;
  }
  import Cisco-IOS-XE-interface-common {
    prefix ios-ifc;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice Class Tenant Yang model.
     Copyright (c) 2021 by Cisco Systems, Inc.
     All rights reserved.";

  revision 2024-11-01 {
    description
      "- Added survivability CLI under voice class tenant support";
    cisco-semver:module-version "3.6.0";
  }
  revision 2024-07-01 {
    description
      "- Added analog-dn and override-hostname
       - Added TLS 1.3 cipher under voice class tls cipher";
    cisco-semver:module-version "3.5.0";
  }
  revision 2024-03-01 {
    description
      "Converted absolute xpath to relative xpath";
    cisco-semver:module-version "3.4.0";
  }
  revision 2022-11-01 {
    description
      "- Update yang-version to 1.1
       - Added voice class tls-cipher
       - Added tls-cipher to tls-profile
       - Added max-forwards, xfer, permit, disable-early-media, g729-annexb, conn-reuse,
         random-contact, handle-replaces, host-registrar, nat, srtp, reason-header,
         notify, retry, timers, error-code-override to voice class tenant";
    cisco-semver:module-version "3.3.0";
  }
  revision 2022-07-01 {
    description
      "- Added voice class sip-options-keepalive";
    cisco-semver:module-version "3.2.0";
  }
  revision 2022-03-01 {
    description
      "- Added listen-port, tls-profile config under voice class tenant";
    cisco-semver:module-version "3.1.0";
  }
  revision 2021-11-01 {
    description
      "- Added srtp crypto support under voice class tenant
       - Added outbound-proxy, redirection, audio forced, block,
         call-route, contact-passing, localhost, refer to passing
         to voice class tenant
       - Added registrar to tenant
       - Added voice class sip-profiles and sip-copylist
       - Added voice class media, voice class sip-hdr-passthrulist and
         voice class sip-event-list config.
       - Added voice class uri, voice class e164-pattern-map and
         voice class server-group
       - Added privacy, privacy-policy, rel1xx, requri-passing,
         update-callerid, url passing to voice class tenant
       - Added anat to voice class tenant
       - Added address-hiding, emergency, silent-discard, asserted-id,
         midcall-signaling, remote-party-id, redirection,
         set pstn-cause, set sip-status, sip-register configurations
       - Added option ping, refresh, early media update block under voice
         class tenant";
    cisco-semver:module-version "3.0.0";
  }
  revision 2021-03-01 {
    description
      "- Added voice class server-group and sip-options-keepalive";
    cisco-semver:module-version "2.0.0";
  }
  revision 2020-07-01 {
    description
      "- Added voice class tenant";
    cisco-semver:module-version "1.0.0";
  }

  typedef config-digit-pattern {
    type string {
      length "1..32";
      pattern '((((\^)?([0-9,#*A-F.?+%()-]|(\\\*)))*T?)($)?)' {
        error-message
          "Incorrect format for number macro pattern,
                   regular expression must be of the form  ^((\\+)?([0-9,#*A-F.]|(\\\\\\*))+)$";
      }
    }
  }

  typedef address-pattern {
    type string {
      length "1..128";
      pattern '(dns:.*)|(ipv4:[0-9]+\.[0-9]+\.[0-9]+\.[0-9]+(:[0-9]+)?)|(ipv6:\[([0-9A-Fa-f.:])+\](:[0-9]+)?)' {
        error-message
          "Ill-formed SIP address. Valid formats are:
               ipv4:[0-255].[0-255].[0-255].[0-255],
               ipv4:[0-255].[0-255].[0-255].[0-255]:[0-65535],
               ipv6:[X:X:X:X::X],
               ipv6:[X:X:X:X::X]:[0-65535],
               dns:host.domain";
      }
    }
  }

  typedef generic-uri-pattern {
    type string {
      length "1..32";
      pattern '(((\[)[(\^)0-9,a-z,A-Z#*.?+%()-]*(\])|[(\^)0-9,a-z,A-Z#*.?+%()-]*)*T?($)?)' {
        error-message "Incorrect regular expression format. Expected format must be of the form ^([][0-9A-Za-z\\|\\/()*+^$&?#--.])*$";
      }
    }
  }

  typedef config-e164-pattern {
    type string {
      pattern '(((\[)[(\^)0-9,A-F#*.?+%()-]*(\])|[(\^)0-9,A-F#*.?+%()-]*)*T?($)?)' {
        error-message "Incorrect format for E.164 Number: regular expression must be of the form ^[][^0-9,A-F#*.?+%()-]*T?($)?$";
      }
    }
  }

  typedef sip-method-type {
    type enumeration {
      enum ACK;
      enum BYE;
      enum CANCEL;
      enum COMET;
      enum INFO;
      enum INVITE;
      enum NOTIFY;
      enum OPTIONS;
      enum PRACK;
      enum PUBLISH;
      enum REFER;
      enum REGISTER;
      enum REINVITE;
      enum SUBSCRIBE;
      enum UPDATE;
    }
  }

  typedef sip-response-type {
    type enumeration {
      enum 100;
      enum 180;
      enum 181;
      enum 183;
      enum 200;
      enum 202;
      enum 300;
      enum 301;
      enum 302;
      enum 305;
      enum 380;
      enum 400;
      enum 401;
      enum 402;
      enum 403;
      enum 404;
      enum 405;
      enum 406;
      enum 407;
      enum 408;
      enum 409;
      enum 410;
      enum 412;
      enum 413;
      enum 414;
      enum 415;
      enum 416;
      enum 417;
      enum 420;
      enum 421;
      enum 422;
      enum 423;
      enum 480;
      enum 481;
      enum 482;
      enum 483;
      enum 484;
      enum 485;
      enum 486;
      enum 487;
      enum 488;
      enum 489;
      enum 491;
      enum 493;
      enum 500;
      enum 501;
      enum 502;
      enum 503;
      enum 504;
      enum 505;
      enum 513;
      enum 580;
      enum 600;
      enum 603;
      enum 604;
      enum 606;
      enum ANY;
    }
  }

  typedef sip-header-type {
    type enumeration {
      enum Accept-Contact;
      enum Accept-Encoding;
      enum Accept-Header;
      enum Accept-Language;
      enum Accept-Resource-Priority;
      enum Alert-Info;
      enum Allow-Events;
      enum Allow-Header;
      enum Also;
      enum Authorization;
      enum CC-Diversion;
      enum CC-Redirect;
      enum CSeq;
      enum Call-ID;
      enum Call-Info;
      enum Cisco-Gcid;
      enum Cisco-Guid;
      enum Contact;
      enum Content-Disposition;
      enum Content-Encoding;
      enum Content-Id;
      enum Content-Length;
      enum Content-Type;
      enum Date;
      enum Diversion;
      enum Event;
      enum Expires;
      enum From;
      enum History-Info;
      enum Location;
      enum MIME-Version;
      enum Max-Forwards;
      enum Min-Expires;
      enum Min-SE;
      enum Orig-dial-plan;
      enum P-Asserted-Identity;
      enum P-Preferred-Identity;
      enum P-RTP-Stat;
      enum Privacy;
      enum Proxy-Authenticate;
      enum Proxy-Authorization;
      enum Proxy-Require;
      enum Rack;
      enum Reason;
      enum Record-Route;
      enum Refer-To;
      enum Referred-By;
      enum Reject-Contact;
      enum Remote-Party-ID;
      enum Replaces;
      enum Request-Disposition;
      enum Requested-By;
      enum Require;
      enum Resource-Priority;
      enum Retry-After;
      enum Route;
      enum Rseq;
      enum SIP-ETag;
      enum SIP-If-Match;
      enum SIP-Req-URI;
      enum SIP-StatusLine;
      enum Server;
      enum Session-Expires;
      enum Session-Header;
      enum Session-ID;
      enum Subscription-State;
      enum Supported;
      enum Term-dial-plan;
      enum Timestamp;
      enum To;
      enum Unsupported;
      enum User-Agent;
      enum Via;
      enum WWW-Authenticate;
      enum Warning;
    }
  }

  typedef sdp-header-type {
    type enumeration {
      enum Attribute;
      enum Audio-Attribute;
      enum Audio-Bandwidth-Info;
      enum Audio-Connection-Info;
      enum Audio-Encryption-Key;
      enum Audio-Media;
      enum Audio-Session-Info;
      enum Bandwidth-Key;
      enum Connection-Info;
      enum Email-Address;
      enum Encrypt-Key;
      enum Phone-Number;
      enum Repeat-Times;
      enum Session-Info;
      enum Session-Name;
      enum Session-Owner;
      enum Time-Adjust-Keyr;
      enum Time-Header;
      enum Url-Descriptor;
      enum Version;
      enum Video-Attribute;
      enum Video-Bandwidth-Info;
      enum Video-Connection-Info;
      enum Video-Encryption-Key;
      enum Video-Media;
      enum Video-Session-Info;
    }
  }

  typedef registrar-ip-address {
    type string {
      length "1..128";
      pattern '(dns:.*)|(ipv4:[0-9]+\.[0-9]+\.[0-9]+\.[0-9]+(:[0-9]+)?)|(ipv6:\[([0-9A-Fa-f.:])+\](:[0-9]+)?)' {
        error-message
          "Ill-formed registrar Server address. Valid formats are:

           ipv4:[0-255].[0-255].[0-255].[0-255],

           ipv4:[0-255].[0-255].[0-255].[0-255]:[0-65535],

           ipv6:[X:X:X:X::X],

           ipv6:[X:X:X:X::X]:[0-65535],

           dns:host.domain";
      }
    }
  }

  grouping config-voice-class-tls-cipher-grouping {
    list tls-cipher {
      description
        "Configure set of TLS cipher suites in preferred order";
      max-elements 10000;
      key "id";
      leaf id {
        description
          "Voice class srtp-crypto tag";
        type uint16 {
          range "1..10000";
        }
      }
      list cipher {
        description
          "TLS cipher-suite";
        unique "type";
        key "preference";
        leaf preference {
          description
            "Set the preference order for the cipher-suite (1 = Highest)";
          type uint8 {
            range "1..13";
          }
        }
        leaf type {
          type enumeration {
            enum DHE_RSA_AES128_GCM_SHA256;
            enum DHE_RSA_AES256_GCM_SHA384;
            enum DHE_RSA_WITH_AES_128_CBC_SHA;
            enum DHE_RSA_WITH_AES_256_CBC_SHA;
            enum ECDHE_ECDSA_AES128_GCM_SHA256;
            enum ECDHE_ECDSA_AES256_GCM_SHA384;
            enum ECDHE_RSA_AES128_GCM_SHA256;
            enum ECDHE_RSA_AES256_GCM_SHA384;
            enum RSA_WITH_AES_128_CBC_SHA;
            enum RSA_WITH_AES_256_CBC_SHA;
            enum AES128_GCM_SHA256;
            enum AES256_GCM_SHA384;
            enum CHACHA20_POLY1305_SHA256;
          }
        }
      }
    }
  }

  grouping config-registrar-grouping {
    container registrar {
      description
        "SIP Registrar config";
      container multiple-registrars {
        list index {
          description
            "Registrar Index Value for configuring multiple registrars";
          max-elements 6;
          key "id";
          leaf id {
            description
              "Specify the rule tag";
            must "not(../../../dhcp-config/dhcp) and not(../../../primary-registrar/registrar-config) and
                  not(../../../secondary-registrar/registrar-config)" {
              error-message "Registrar currently in use; deconfig it 1st";
            }
            type uint8 {
              range "1..6";
            }
          }
          leaf registrar-config {
            type registrar-ip-address;
          }
          uses config-registrar-options-grouping {
            refine "secondary";
          }
        }
      }
      container primary-registrar {
        leaf registrar-config {
          must 'not(../../dhcp-config/dhcp) and not(../../multiple-registrars/index/registrar-config)' {
            error-message "Registrar currently in use; deconfig it 1st";
          }
          type registrar-ip-address;
        }
        uses config-registrar-options-grouping {
          refine "secondary";
        }
      }
      container secondary-registrar {
        leaf registrar-config {
          must 'not(../../dhcp-config/dhcp) and not(../../multiple-registrars/index/registrar-config)' {
            error-message "Registrar currently in use; deconfig it 1st";
          }
          type registrar-ip-address;
        }
        uses config-registrar-options-grouping;
      }
      container dhcp-config {
        leaf dhcp {
          description
            "Registrar Server address provision via DHCP";
          must "not(../../multiple-registrars/index/registrar-config) and
                not(../../primary-registrar/registrar-config) and
                not(../../secondary-registrar/registrar-config)" {
            error-message "Registrar currently in use; deconfig it 1st";
          }
          type empty;
        }
        uses config-registrar-options-grouping {
          refine "secondary";
        }
      }
    }
  }

  grouping config-registrar-options-grouping {
    leaf expires {
      description
        "Default registration expires time";
      type uint16 {
        range "60..65535";
      }
      default "3600";
    }
    leaf auth-realm {
      description
        "Realm for preloaded authorization";
      type string {
        length "1..128";
      }
    }
    leaf refresh-ratio {
      description
        "Default registration refresh ratio";
      type uint8 {
        range "1..100";
      }
    }
    leaf random-contact {
      description
        "Random String Contact Header";
      type empty;
    }
    leaf scheme {
      description
        "URL scheme - sips or sip";
      type enumeration {
        enum sip;
        enum sips;
      }
      default "sip";
    }
    leaf tcp {
      description
        "Use TCP as Transport Layer Protocol (default: UDP)";
      type empty;
    }
    leaf tls {
      description
        "Use TLS encryption over TCP Transport Layer Protocol";
      when '../tcp';
      type empty;
    }
    leaf secondary {
      description
        "Set if this is Secondary Registrar Server address";
      type empty;
    }
  }

  grouping sip-response-method-grouping {
    container method {
      description
        "Map response to requests";
      leaf method {
        type sip-method-type;
      }
      uses request-response-grouping;
    }
  }

  grouping sip-response-choice-grouping {
    container response {
      description
        "sip response";
      leaf sip-responses {
        type sip-response-type;
      }
      uses response-method-choice-grouping;
    }
  }

  grouping sip-request-choice-grouping {
    container request {
      description
        "sip request";
      leaf sip-requests {
        type union {
          type sip-method-type;
          type enumeration {
            enum ANY {
              value 15;
            }
          }
        }
      }
      uses request-response-grouping;
    }
  }

  grouping copy-header-grouping {
    container COPY {
      description
        "Copy a header";
      leaf pattern {
        description
          "Match pattern";
        type string;
      }
      leaf variable {
        description
          "Copy variable <u01-u99>";
        type string {
          pattern '([u|U]+[0-9][0-9])' {
            error-message "Invalid variable name, valid values are <u01-u99>";
          }
        }
      }
    }
  }

  grouping header-choice-grouping {
    choice header-choice {
      case add-case {
        leaf ADD {
          when "(../header != 'To') and
                (../header != 'From') and
                (../header != 'CSeq') and
                (../header != 'Call-ID') and
                (../header != 'Max-Forwards') and
                (../header != 'Via') and
                (../header != 'SIP-Req-URI') and
                (../header != 'SIP-StatusLine') and
                (../header != 'Audio-Media') and
                (../header != 'Session-Name') and
                (../header != 'Session-Owner') and
                (../header != 'Time-Header') and
                (../header != 'Version') and
                (../header != 'Video-Media')";
          description
            "addition of the header";
          type string;
        }
      }
      case modify-case {
        container MODIFY {
          description
            "Modification of a header";
          leaf pattern {
            description
              "Match pattern";
            type string;
          }
          leaf replace-pattern {
            description
              "Replace pattern";
            type string;
          }
        }
      }
      case remove-case {
        leaf REMOVE {
          when "(../header != 'To') and
                (../header != 'From') and
                (../header != 'CSeq') and
                (../header != 'Call-ID') and
                (../header != 'Max-Forwards') and
                (../header != 'Via') and
                (../header != 'SIP-Req-URI') and
                (../header != 'SIP-StatusLine') and
                (../header != 'Audio-Media') and
                (../header != 'Session-Name') and
                (../header != 'Session-Owner') and
                (../header != 'Time-Header') and
                (../header != 'Version') and
                (../header != 'Video-Media')";
          description
            "Removal of a header";
          type empty;
        }
      }
      case copy-case {
        uses copy-header-grouping;
      }
    }
  }

  grouping peer-header-grouping {
    container peer-header {
      description
        "Header to be copied from peer leg";
      choice peer-header-choice {
        case sdp-case {
          container sdp {
            description
              "SDP Line to be copied from peer leg";
            leaf mline-index {
              description
                "Media line index to copy from (use 0 for session level)";
              type uint32 {
                range "0..6";
              }
            }
            uses copy-header-grouping;
          }
        }
        case sip-case {
          container sip {
            description
              "SIP Header to be copied from peer leg";
            choice peer-header-sip-choice {
              case SIPReqURI-case {
                container SIP-Req-URI {
                  description
                    "SIP Request URI to be copied from peer leg";
                  uses copy-header-grouping;
                }
              }
              case SIPStatusLine-case {
                container SIP-StatusLine {
                  description
                    "SIP Status-Line to be copied from peer leg";
                  uses copy-header-grouping;
                }
              }
              case header-name-case {
                container header-name-copy {
                  leaf header {
                    description
                      "Header name from which the values needs to be copied";
                    type string;
                  }
                  uses copy-header-grouping;
                }
              }
            }
          }
        }
      }
    }
  }

  grouping sip-header-grouping {
    container sip-header {
      description
        "SIP header";
      leaf header {
        type union {
          type sip-header-type;
          type string;
        }
      }
      uses header-choice-grouping;
    }
  }

  grouping sdp-header-grouping {
    container sdp-header {
      description
        "SDP header";
      choice sdp-header-choice {
        leaf header {
          type sdp-header-type;
        }
        container mline-index {
          description
            "M-Line index for SDP Line";
          leaf index {
            description
              "M-Line index for SDP Line";
            type uint8 {
              range "0..6";
            }
          }
          leaf substring {
            description
              "Beginning substring of SDP Line without quotes";
            type string;
          }
        }
      }
      uses header-choice-grouping;
    }
  }

  grouping request-response-grouping {
    choice request-response-choice {
      case peer-header-choice {
        uses peer-header-grouping;
      }
      case sdp-header-choice {
        uses sdp-header-grouping;
      }
      case sip-header-choice {
        uses sip-header-grouping;
      }
    }
  }

  grouping response-method-choice-grouping {
    choice response-method-choice {
      case method-case {
        uses sip-response-method-grouping;
      }
      case peer-header-case {
        uses peer-header-grouping;
      }
      case sdp-header-case {
        uses sdp-header-grouping;
      }
      case sip-header-case {
        uses sip-header-grouping;
      }
    }
  }

  grouping config-listen-port-grouping {
    container listen-port {
      description
        "Change UDP/TCP/TLS SIP listen port (have bind configured under
         this tenant for the config to take effect)";
      leaf non-secure {
        description
          "Change UDP/TCP SIP listen port (have bind configured under
           this tenant for the config to take effect)";
        type uint16 {
          range "5000..5500";
        }
      }
      leaf secure {
        description
          "Change TLS SIP listen port (have bind configured under
           this tenant for the config to take effect)";
        type uint16 {
          range "1..65535";
        }
      }
    }
  }

  grouping config-sip-copylist-header-grouping {
    container sip-header {
      leaf SIP-Req-URI {
        description
          "SIP Request URI to be sent to peer leg";
        type empty;
      }
      leaf SIP-StatusLine {
        description
          "SIP Status-Line to be sent to peer leg";
        type empty;
      }
      leaf-list header {
        description
          "Header name of header to be sent to peer leg";
        max-elements 64;
        type string {
          length "1..32";
        }
      }
    }
  }

  grouping config-sip-profiles-grouping {
    container sip-profiles {
      leaf inbound {
        description
          "Turn on inbound SIP profiles feature";
        type empty;
      }
      container outbound-id {
        leaf id {
          description
            "The sip profiles tag number to be linked as global";
          type leafref {
            path "../../../../../ios-voice:class/ios-voice:sip-profiles/ios-voice:id";
          }
        }
      }
      container sip-profiles-inbound {
        leaf id {
          description
            "The sip profiles tag number to be linked as global";
          type leafref {
            path "../../../../../ios-voice:class/ios-voice:sip-profiles/ios-voice:id";
          }
        }
        leaf inbound {
          description
            "Turn on inbound SIP profiles feature";
          type empty;
        }
      }
    }
  }

  grouping config-sip-profiles-tenant-grouping {
    container sip-profiles {
      description
        "SIP Profiles global config";
      leaf id {
        description
          "The sip profiles tag number to be linked as global";
        type leafref {
          path "../../../../ios-voice:class/ios-voice:sip-profiles/ios-voice:id";
        }
      }
      leaf inbound {
        description
          "Set this as inbound SIP Profile";
        type empty;
      }
    }
  }

  grouping config-source-interface-grouping {
    container source-interface {
      description
        "Specify interface for source address of SIP packets";
      container source-interface-std {
        when '/ios:native/sip-ua';
        uses ios-ifc:interface-grouping;
      }
      leaf source-interface-string {
        when 'not (/ios:native/sip-ua)';
        type string;
      }
    }
  }

  grouping config-session-transport-grouping {
    container transport {
      description
        "SIP session transport config";
      choice transport-choice {
        leaf udp {
          description
            "Transport Layer Protocol - UDP";
          type empty;
        }
        container tcp {
          description
            "Transport Layer Protocol - TCP";
          presence "true";
          leaf tls {
            description
              "Transport Layer Protocol - TLS over TCP";
            type empty;
          }
        }
      }
    }
  }

  grouping config-sip-bind-grouping {
    container bind {
      description
        "SIP bind command";
      container control {
        description
          "bind only SIP control packets";
        uses config-source-interface-grouping;
      }
      container media {
        description
          "bind only SIP media packets";
        uses config-source-interface-grouping;
      }
    }
  }

  grouping config-sip-localhost-grouping {
    leaf localhost {
      description
        "Specify the DNS name for the localhost";
      type string {
        length "1..128";
        pattern '(dns:.*)' {
          error-message
            "Ill-formed local host address. Valid formats are:
                 dns:host.domain or dns:domain";
        }
      }
    }
  }

  grouping block-sdp-grouping {
    leaf sdp {
      description
        "Block the response upon SDP presence/absence";
      type enumeration {
        enum absent {
          description
            "Block the response if SDP is absent";
        }
        enum present {
          description
            "Block the response if SDP is present";
        }
      }
    }
  }

  grouping config-sdp-block-grouping {
    container block {
      description
        "Block 18X responses to Invite";
      container one-eighty {
        description
          "Block 180 response to Invite";
        presence "true";
        uses block-sdp-grouping;
      }
      container one-eighty-one {
        description
          "Block 181 response to Invite";
        presence "true";
        uses block-sdp-grouping;
      }
      container one-eighty-three {
        description
          "Block 183 response to Invite";
        presence "true";
        uses block-sdp-grouping;
      }
    }
  }

  grouping config-outbound-proxy-grouping {
    container outbound-proxy {
      description
        "Configure an Outbound Proxy Server";
      choice outbound-proxy-choice {
        case address-choice {
          leaf address {
            description
              "Specify Outbound Proxy Address";
            type address-pattern;
          }
        }
        case dhcp-choice {
          leaf dhcp {
            description
              "Provision SIP outbound proxy using DHCP";
            type empty;
          }
        }
      }
    }
  }

  grouping config-audio-forced-grouping {
    container audio {
      description
        "Configure audio options";
      leaf forced {
        description
          "Allow only audio/fax, drop all other";
        type empty;
      }
    }
  }

  grouping config-call-route-grouping {
    container call-route {
      description
        "Configure call routing options";
      leaf dest-route-string {
        description
          "Route based on dest-route-string";
        type empty;
      }
      leaf history-info {
        description
          "Route based on History-Info";
        type empty;
      }
      leaf p-called-party-id {
        description
          "Route based on P-Called-Party-ID";
        type empty;
      }
      leaf url {
        description
          "Route based on URL";
        type empty;
      }
    }
  }

  grouping pass-thru-grouping {
    container pass-thru {
      description
        "SIP pass-through global config";
      container content {
        description
          "SIP content pass-through config";
        container sdp {
          description
            "Pass-through sdp content";
          presence "true";
          leaf mode {
            description
              "Set Pass-through sdp mode";
            type enumeration {
              enum non-rtp {
                description
                  "Set Pass-through sdp mode to non-rtp";
              }
            }
          }
        }
        leaf custom-sdp {
          description
            "Pass-through Custom SDP using SIP Profiles";
          type empty;
        }
        leaf unsupp {
          description
            "Pass-through all unsupported content";
          type empty;
        }
      }
      container headers {
        description
          "SIP header pass-through config";
        choice headers-choice {
          case sip-hdr-passthrulist-tag-case {
            leaf sip-hdr-passthrulist-tag {
              description
                "The sip-hdr-passthrulist tag number to be linked as global";
              type leafref {
                path "/ios:native/ios-voice:voice/ios-voice:class/ios-voice:sip-hdr-passthrulist/ios-voice:sip-hdr-passthrulist-tag";
              }
            }
          }
          case unsupp-case {
            leaf unsupp {
              description
                "Pass-through all unsupported headers";
              type empty;
            }
          }
        }
      }
      container subscribe-notify-events {
        description
          "Subscribe/Notify event passthrough config";
        choice subscribe-notify-events-choice {
          case sip-event-list-tag-case {
            leaf sip-event-list-tag {
              description
                "The sip-event-list tag number to be linked as global";
              type leafref {
                path "/ios:native/ios-voice:voice/ios-voice:class/ios-voice:sip-event-list/ios-voice:id";
              }
            }
          }
          case sip-event-list-all-case {
            leaf all {
              description
                "Pass-through all subscribe/notify events";
              type empty;
            }
          }
        }
      }
    }
  }

  grouping early-media-update-grouping {
    container early-media {
      description
        "Configure method to handle early-media Update Request";
      when "/ios:native/voice/service[type='voip']/allow-connections/sip/to/sip";
      container update {
        description
          "Early-Media options for SIP Update request";
        container block {
          description
            "Consume SIP Update request with SDP in early-dialog";
          presence "true";
          leaf re-negotiate {
            description
              "Enables end-to-end re-negotiation.";
            type empty;
          }
        }
      }
    }
  }

  grouping options-ping-grouping {
    container options-ping {
      description
        "Send OPTION pings to remote end";
      presence "true";
      leaf interval {
        description
          "Intervals OPTIONS transactions are sent (in seconds)";
        type uint16 {
          range "60..1200";
        }
      }
    }
  }

  grouping config-voice-url-grouping {
    container url {
      description
        "Url configuration for request-line url in outgoing INVITE";
      choice url-type {
        case url-type-sip {
          leaf sip {
            description
              "SIP URL in outgoing request uri";
            type empty;
          }
        }
        case url-type-sips {
          leaf sips {
            description
              "SECURE SIP (sips) URL in outgoing request uri";
            type empty;
          }
        }
        case url-type-tel {
          container tel {
            description
              "TEL URL in outgoing request uri";
            presence "true";
            leaf phone-context {
              description
                "Append phone-context to tel url";
              type empty;
            }
          }
        }
      }
    }
  }

  grouping config-voice-relxx-grouping {
    container rel1xx {
      description
        "Type of reliable provisional response support";
      choice rel1xx-type {
        default "rel1xx-supported";
        case rel1xx-disable {
          leaf disable {
            description
              "Disables reliable-provisional responses";
            type empty;
          }
        }
        case rel1xx-require {
          leaf require {
            description
              "Requires reliable-provisional responses";
            type string {
              length "1..50";
            }
          }
        }
        case rel1xx-supported {
          leaf supported {
            description
              "Supports reliable-provisional responses";
            type string {
              length "1..50";
            }
          }
        }
      }
    }
  }

  grouping config-voice-privacy-policy-grouping {
    container privacy-policy {
      description
        "Set privacy behavior for outgoing SIP messages";
      leaf passthru {
        description
          "Pass through privacy values received from peer leg";
        type empty;
      }
      leaf send-always {
        description
          "Privacy header is always sent";
        type empty;
      }
      container strip {
        description
          "Strip the following header received from peer leg";
        leaf diversion {
          description
            "Strip diversion header(s) received from peer leg";
          type empty;
        }
        leaf history-info {
          description
            "Strip history-info header(s) received from peer leg";
          type empty;
        }
      }
    }
  }

  grouping config-voice-privacy-grouping {
    container privacy {
      description
        "Configure SIP UA privacy settings";
      choice privacy-choice {
        case others-case {
          leaf privacy-type {
            description
              "Select the level of privacy";
            type enumeration {
              enum header {
                description
                  "Privacy at header level";
              }
              enum history {
                description
                  "Privacy for history-info header";
              }
              enum id {
                description
                  "Privacy at identity level";
              }
              enum session {
                description
                  "Privacy at session level";
              }
              enum user {
                description
                  "Privacy at user level";
              }
            }
          }
          uses privacy-options-grouping;
        }
        case pstn-case {
          leaf pstn {
            description
              "Use default pstn rules for privacy";
            type empty;
          }
        }
      }
    }
  }

  grouping privacy-options-grouping {
    container privacy-options {
      description
        "Configure SIP UA privacy settings";
      leaf critical {
        description
          "Privacy at critical level";
        type empty;
      }
      leaf header {
        description
          "Privacy at header level";
        when "../../privacy-type != 'header'";
        type empty;
      }
      leaf history {
        description
          "Privacy for history-info header";
        when "../../privacy-type != 'history'";
        type empty;
      }
      leaf id {
        description
          "Privacy at identity level";
        when "../../privacy-type != 'id'";
        type empty;
      }
      leaf session {
        description
          "Privacy at session level";
        when "../../privacy-type != 'session'";
        type empty;
      }
      leaf user {
        description
          "Privacy at user level";
        when "../../privacy-type != 'user'";
        type empty;
      }
    }
  }

  grouping config-voice-class-tenant-grouping {
    list tenant {
      description
        "Tenant group";
      max-elements 10000;
      key "id";
      leaf id {
        description
          "Voice class tenant tag";
        type uint16 {
          range "1..10000";
        }
      }
      uses config-connection-reuse-grouping;
      uses config-early-offer-grouping {
        when "/ios:native/voice/service[type='voip']/allow-connections/sip/to/sip";
      }
      leaf header-passing {
        description
          "SIP Headers need to be passed to Applications";
        type empty;
      }
      leaf error-passthru {
        description
          "SIP error response pass-thru functionality";
        type empty;
      }
      uses pass-thru-grouping;
      uses config-sip-bind-grouping;
      container session {
        description
          "SIP Voice Protocol session config";
        uses config-session-transport-grouping;
      }
      leaf sip-server {
        description
          "Configure a SIP Server Interface";
        type address-pattern;
      }
      uses config-sip-localhost-grouping;
      uses config-outbound-proxy-grouping;
      uses config-audio-forced-grouping;
      uses config-sdp-block-grouping;
      uses config-call-route-grouping;
      uses config-sip-profiles-tenant-grouping;
      leaf copy-list {
        description
          "Configure list of entities to be sent to peer leg";
        type leafref {
          path "../../../ios-voice:class/ios-voice:sip-copylist/ios-voice:id";
        }
      }
      leaf redirection {
        description
          "Enable call redirection (3XX) handling";
        type empty;
      }
      leaf contact-passing {
        description
          "302 contact needs to be passed through for CFWD";
        type empty;
      }
      leaf referto-passing {
        description
          "Refer-To needs to be passed through for transfer";
        type empty;
      }
      leaf srtp-crypto {
        description
          "Configure the voice class srtp-crypto tag";
        type leafref {
          path "../../../class/srtp-crypto/id";
        }
      }
      uses config-registrar-grouping;
      leaf remote-party-id {
        description
          "Enable Remote-Party-ID support in SIP User Agent calls";
        when "/ios:native/voice/service[type='voip']/allow-connections/sip/to/sip";
        type boolean;
      }
      uses config-asserted-id-grouping;
      uses config-midcall-signaling-grouping {
        refine "midcall-signaling/passthru" {
          presence "true";
        }
      }
      uses config-asymmetric-grouping;
      uses config-voice-privacy-grouping;
      uses config-voice-privacy-policy-grouping;
      uses config-voice-relxx-grouping;
      uses config-voice-url-grouping;
      leaf requri-passing {
        description
          "Request URI needs to be passed through";
        type empty;
      }
      leaf update-callerid {
        description
          "Enable sending updates for callerid";
        type empty;
      }
      leaf anat {
        description
          "allow alternative network address types IPv4 and IPv6";
        type boolean;
        default "false";
      }
      leaf tls-profile {
        description
          "Specify the tls-profile tag number";
        type uint16 {
          range "1..10000";
        }
      }
      leaf random-contact {
        description
          "Use Random Contact for outgoing calls, if available";
        type empty;
      }
      uses options-ping-grouping;
      uses early-media-update-grouping;
      uses config-listen-port-grouping;
      leaf override-hostname {
        description
          "Override registrar hostname with resolved IP address in SIP message headers";
        type boolean;
        default "false";
      }
      container analog-dn {
        description
          "On-Prem SIP Line analog DN configuration";
        leaf dn {
          description
            "A string representing the directory number to register";
          type string {
            pattern '[0-9A-F]{4,32}';
          }
        }
        leaf dial-peer-tag {
          description
            "POTS dial peer tag";
          type uint32 {
            range "1..1073741823";
          }
        }
      }
      container survivability {
        description
          "Survivability configuration";
        leaf fallback-timer {
          description
            "WxC SIP Line survivability fallback-timer";
          type uint16 {
            range "0..65535";
          }
          default "30";
        }
        leaf outbound-proxy {
          description
            "WxC SIP Line survivability outbound proxy";
          type string {
            length "1..255";
            pattern '(dns:.*)' {
              error-message
                "Ill-formed host address. Valid formats are:
                     dns:host.domain or dns:domain";
            }
          }
        }
        leaf test-mode {
          description
            "Enable survivability test-mode";
          type boolean;
          default "false";
        }
      }
    }
  }

  grouping config-voice-class-dpg-grouping {
    list dpg {
      description
        "dial-peer group";
      max-elements 10000;
      key "id";
      leaf id {
        description
          "Voice class dialpeer group tag";
        type uint16 {
          range "1..10000";
        }
      }
      list dial-peer {
        description
          "Add a dialpeer to the group";
        max-elements 1073741823;
        key "id";
        leaf id {
          description
            "Voice dial-peer tag";
          type leafref {
            path "../../../../../../ios:native/ios-voice:dial-peer/ios-voice:voice/ios-voice:dialpeertag";
          }
        }
        leaf preference {
          description
            "Preference order of this dialpeer in a group";
          type uint8 {
            range "0..10";
          }
          default "0";
        }
      }
      leaf shutdown {
        description
          "Put dial-peer group to inactive state";
        type empty;
      }
    }
  }

  grouping config-voice-class-stun-usage-grouping {
    list stun-usage {
      description
        "Set stun-usage global parameters";
      key "id";
      max-elements 10000;
      leaf id {
        description
          "Voice class dialpeer group tag";
        type uint16 {
          range "1..10000";
        }
      }
      container stun {
        description
          "Stun parameters";
        container usage {
          description
            "usage parameters";
          container firewall-traversal {
            description
              "name of Class of Restriction";
            leaf flowdata {
              description
                "use flowdata";
              type empty;
            }
          }
          container ice {
            description
              "Enable ICE";
            leaf lite {
              description
                "Configure ICE in Ice-Lite Mode";
              type empty;
            }
          }
        }
      }
    }
  }

  grouping config-voice-class-srtp-crypto-grouping {
    list srtp-crypto {
      description
        "Configure set of SRTP cipher suites in preferred order";
      max-elements 10000;
      key "id";
      leaf id {
        description
          "Voice class srtp-crypto tag";
        type uint16 {
          range "1..10000";
        }
      }
      list crypto {
        description
          "Configure preferred SRTP cipher-suite";
        unique "type";
        key "id";
        leaf id {
          description
            "Set the preference order for the cipher-suite (1 = Highest)";
          type uint8 {
            range "1..4";
          }
        }
        leaf type {
          type enumeration {
            enum AEAD_AES_128_GCM;
            enum AEAD_AES_256_GCM;
            enum AES_CM_128_HMAC_SHA1_32;
            enum AES_CM_128_HMAC_SHA1_80;
          }
        }
      }
    }
  }

  grouping config-voice-class-server-group-grouping {
    list server-group {
      description
        "IP Server Group";
      must '(count(ipv4-address/ipv4/address) + count(ipv4-address/ipv4-addr-port/ipv4/address) + count(ipv6-address/ipv6/address) + count(ipv6-address/ipv6-addr-port/ipv6/address)) < 6' {
        error-message "Maximum 5 addresses allowed";
      }
      max-elements 10000;
      key "id";
      leaf id {
        description
          "Voice class server group tag";
        type uint16 {
          range "1..10000";
        }
      }
      leaf description {
        description
          "Description of a dialpeer group";
        type string {
          length "1..80";
        }
      }
      leaf shutdown {
        description
          "Put server group to inactive state";
        type boolean;
        default "false";
      }
      container hunt-scheme {
        description
          "List of IP targets hunt method";
        leaf round-robin {
          description
            "Servers are sorted in round robin";
          type empty;
        }
      }
      list huntstop {
        description
          "Stop hunting for particular response codes";
        max-elements 1000;
        key "id";
        leaf id {
          description
            "Huntstop Identifier tag";
          type uint16 {
            range "1..1000";
          }
        }
        container resp-code {
          description
            "SIP Response codes";
          leaf resp-code-start-range {
            description
              "Response code value";
            type uint16 {
              range "400..599";
            }
          }
          leaf to {
            description
              "Configure SIP Response code range";
            type empty;
          }
          leaf resp-code-end-range {
            must '../resp-code-start-range <= . ' {
              error-message "Invalid SIP response code range configured for hunt-stop";
            }
            type uint16 {
              range "400..599";
            }
          }
        }
      }
      container ipv4-address {
        list ipv4 {
          key "address";
          leaf address {
            description
              "set the Call Manager configuration download TFTP server address/name";
            type inet:ipv4-address;
          }
          leaf preference {
            description
              "Preference order of this server in a group";
            type uint8 {
              range "0..5";
            }
          }
        }
        container ipv4-addr-port {
          list ipv4 {
            key "address port";
            leaf address {
              description
                "set the Call Manager configuration download TFTP server address/name";
              type inet:ipv4-address;
            }
            leaf port {
              description
                "IP Address Port";
              type uint16 {
                range "1..65535";
              }
            }
            leaf preference {
              description
                "Preference order of this server in a group";
              type uint8 {
                range "0..5";
              }
            }
          }
        }
      }
      container ipv6-address {
        list ipv6 {
          key "address";
          leaf address {
            description
              "set the Call Manager configuration download TFTP server address/name";
            type inet:ipv6-address;
          }
          leaf preference {
            description
              "Preference order of this server in a group";
            type uint8 {
              range "0..5";
            }
          }
        }
        container ipv6-addr-port {
          list ipv6 {
            key "address port";
            leaf address {
              description
                "set the Call Manager configuration download TFTP server address/name";
              type inet:ipv6-address;
            }
            leaf port {
              description
                "IP Address Port";
              type uint16 {
                range "1..65535";
              }
            }
            leaf preference {
              description
                "Preference order of this server in a group";
              type uint8 {
                range "0..5";
              }
            }
          }
        }
      }
    }
  }

  grouping config-voice-class-e164-pattern-map-grouping {
    list e164-pattern-map {
      description
        "e164 pattern map";
      max-elements 10000;
      key "id";
      leaf id {
        description
          "Voice class e164-pattern-map tag";
        type uint16 {
          range "1..10000";
        }
      }
      leaf description {
        description
          "e164 pattern map specific description";
        type string {
          length "1..80";
        }
      }
      list e164 {
        description
          "Set E164 pattern for the map";
        max-elements 100;
        key "WORD";
        leaf WORD {
          description
            "Add an E164 into the map";
          must 'not (../../url) ' {
            error-message "need to remove existing url on map";
          }
          type config-e164-pattern;
        }
      }
      leaf url {
        description
          "Set the URL of the file for the map";
        must 'not (../e164) ' {
          error-message "need to remove existing e164 on map";
        }
        type string {
          pattern '(((bootflash:)|(flash:)|(nvram:)|(webui:)).*)' {
            error-message "Invalid URL, not added to map";
          }
        }
      }
    }
  }

  grouping config-sip-options-keepalive-interval-grouping {
    leaf down-interval {
      description
        "OPTIONS keepalive timer interval for DOWN endpoint";
      type uint16 {
        range "5..1200";
      }
      default "30";
    }
    leaf up-interval {
      description
        "OPTIONS keepalive timer interval for UP endpoint";
      type uint16 {
        range "5..1200";
      }
      default "60";
    }
    leaf retry {
      description
        "Retry count for OPTIONS keepalive retransmission";
      type uint8 {
        range "1..10";
      }
      default "5";
    }
  }

  grouping config-voice-class-sip-options-keepalive-grouping {
    list sip-options-keepalive {
      description
        "SIP Options Keepalive Profile setup";
      max-elements 10000;
      key "id";
      leaf id {
        description
          "Voice class sip-options-keepalive tag";
        type uint16 {
          range "1..10000";
        }
      }
      leaf description {
        description
          "Description of a options-keepalive profile";
        type string {
          length "1..80";
        }
      }
      leaf shutdown {
        description
          "Put sip-options-keepalive to inactive state";
        type boolean;
        default "false";
      }
      uses config-sip-options-keepalive-interval-grouping;
      leaf sip-profiles {
        description
          "Voice Class SIP Profiles";
        type leafref {
          path "../../../ios-voice:class/ios-voice:sip-profiles/ios-voice:id";
        }
      }
      uses config-session-transport-grouping;
    }
  }

  grouping config-voice-class-media-grouping {
    list media {
      description
        "Media settings for voip calls";
      max-elements 10000;
      key "media-tag";
      leaf media-tag {
        description
          "Voice class media tag";
        type uint16 {
          range "1..10000";
        }
      }
      container media {
        description
          "Media setting for voip calls in this voice class";
        leaf anti-trombone {
          description
            "Media Anti-trombone functionality";
          type empty;
        }
        leaf forking {
          description
            "Enable media forking";
          type empty;
        }
        leaf monitor-video {
          description
            "Enable video quality monitoring";
          type empty;
        }
        leaf stats-disconnect {
          description
            "Defer BYE for last call stats at disconnect";
          type empty;
        }
        leaf flow-through-or-around {
          description
            "choice of flow case gateway";
          type enumeration {
            enum flow-through {
              description
                "The media is to flow through the gateway";
            }
            enum flow-around {
              description
                "The media is to flow around the gateway";
            }
          }
          default "flow-through";
        }
      }
    }
  }

  grouping config-voice-class-sip-profiles-grouping {
    list sip-profiles {
      description
        "Voice Class SIP Profiles";
      max-elements 10000;
      key "id";
      leaf id {
        description
          "Voice class sip profiles tag";
        type uint16 {
          range "1..10000";
        }
      }
      leaf description {
        description
          "Description of a sip-profile";
        type string;
      }
      list rule {
        description
          "Specify the rule";
        max-elements 1073741823;
        key "id";
        leaf id {
          description
            "Specify the rule tag";
          type uint64 {
            range "1..1073741823";
          }
        }
        container rule-response-request {
          choice rule-choice {
            case response-case {
              uses sip-response-choice-grouping;
            }
            case request-case {
              uses sip-request-choice-grouping;
            }
          }
        }
      }
    }
  }

  grouping config-voice-class-uri-grouping {
    container uri {
      description
        "Voice URI class configuration commands";
      list uri {
        max-elements 10000;
        key "uritag";
        leaf uritag {
          description
            "Voice URI Class tag";
          type string {
            length "1..32";
            pattern '([0-9,A-Z,a-z]*T?)';
          }
        }
        leaf type {
          description
            "sip: URI class";
          when "../uritag != 'sip'";
          type enumeration {
            enum sip;
            enum tel;
          }
        }
        leaf-list host {
          description
            "Match the Host portion of the URI";
          when "../type = 'sip'";
          must 'not (../pattern)' {
            error-message "Please remove Pattern before proceeding";
          }
          max-elements 10;
          type address-pattern;
        }
        leaf pattern {
          description
            "Match the entire URI";
          when "../type = 'sip' or ../type = 'tel'";
          must 'not ((../host) or (../user-id) or (../phone/context))' {
            error-message "Please remove the other patterns before proceeding";
          }
          type string {
            length "1..128";
            pattern '(((\[)[(\^)0-9,a-z,A-Z#*.@:;~!?+%()-]*(\])|[(\^)0-9,a-z,A-Z#*.@;:~!?+%()-]*)*T?($)?)';
          }
        }
        leaf user-id {
          description
            "Match the User ID portion of the URI";
          when "../type = 'sip'";
          must 'not (../pattern) ' {
            error-message "Please remove pattern before proceeding";
          }
          type generic-uri-pattern;
        }
        container phone {
          description
            "Match the phone number portion of the URI";
          when "../type = 'sip' or ../type = 'tel'";
          leaf context {
            description
              "Match the phone-context attribute of the URI";
            must 'not (../../pattern) ' {
              error-message "Please remove pattern before proceeding";
            }
            type generic-uri-pattern;
          }
          leaf number {
            description
              "Match the phone-number attribute of the URI";
            when "../../type = 'tel'";
            must 'not (../../pattern) ' {
              error-message "Please remove pattern before proceeding";
            }
            type generic-uri-pattern;
          }
        }
      }
      container sip {
        description
          "Configure SIP URI class properties";
        container preference {
          description
            "Assign preference to the match patterns";
          choice preference {
            case host-option {
              container host {
                description
                  "Host pattern match length";
                presence "true";
                leaf user-id {
                  description
                    "User-ID pattern match length";
                  type empty;
                }
              }
            }
            case user-id-option {
              container user-id {
                description
                  "User ID pattern match length";
                presence "true";
                leaf host {
                  description
                    "Host pattern match length";
                  type empty;
                }
              }
            }
          }
        }
      }
    }
  }

  grouping config-asserted-id-grouping {
    container asserted-id {
      description
        "Configure SIP UA privacy identity settings";
      choice asserted-id-choice {
        case pai-case {
          leaf pai {
            description
              "Use privacy asserted identity";
            type empty;
          }
        }
        case ppi-case {
          leaf ppi {
            description
              "Use privacy preferred identity";
            type empty;
          }
        }
      }
    }
  }

  grouping config-midcall-signaling-grouping {
    container midcall-signaling {
      description
        "Configure method to handle midcall signaling";
      leaf block {
        description
          "Block all SIP messages in midcall";
        must 'not(../passthru/media-change)' {
          error-message "Remove 'midcall-signaling passthru media-change' before configuring 'midcall-signaling block'.";
        }
        type empty;
      }
      container passthru {
        description
          "Passthrough SIP messages from one IP leg to another IP leg";
        leaf media-change {
          description
            "Only passthrough SIP messages which involve media-change";
          must 'not(../../block)' {
            error-message "Remove 'midcall-signaling block' before configuring 'midcall-signaling passthru media-change'.";
          }
          type empty;
        }
      }
      leaf preserve-codec {
        description
          "preserve initial negotiated codec i.e. midcall codec change denial";
        type empty;
      }
    }
  }

  grouping config-voice-class-sip-hdr-passthrulist-grouping {
    list sip-hdr-passthrulist {
      description
        "Configure list of headers to be passed thru";
      max-elements 10000;
      key "sip-hdr-passthrulist-tag";
      leaf sip-hdr-passthrulist-tag {
        description
          "Voice class sip-hdr-passthrulist tag";
        type uint16 {
          range "1..10000";
        }
      }
      leaf-list passthru-hdr {
        description
          "Add hdr in the list of hdrs to be passed thru";
        max-elements 25;
        type string {
          length "1..128";
        }
      }
      leaf passthru-hdr-unsupp {
        description
          "Enable the pass-thru of all unsupported headers";
        type empty;
      }
    }
  }

  grouping config-early-offer-grouping {
    container early-offer {
      description
        "Configure sending Early-Offer";
      container forced {
        description
          "Forcefully Send Early-Offer";
        presence "true";
        container re-negotiate {
          description
            "Enables end-to-end re-negotiation for variable quality codecs";
          presence "true";
          leaf always {
            description
              "Enables end-to-end re-negotiation for all codecs";
            type empty;
          }
        }
      }
    }
  }

  grouping config-connection-reuse-grouping {
    container connection-reuse {
      description
        "Use listener port for sending requests over UDP";
      presence "true";
      leaf via-port {
        description
          "Send responses to port present in Via header";
        type empty;
      }
    }
  }

  grouping config-asymmetric-grouping {
    container asymmetric {
      description
        "Configure global SIP asymmetric payload support";
      container payload {
        description
          "Type of asymmetric payload support";
        choice payload-case {
          case dtmf-case {
            leaf dtmf {
              description
                "Asymmetric Support for dtmf payloads only";
              type empty;
            }
          }
          case dynamic-codecs-case {
            leaf dynamic-codecs {
              description
                "Asymmetric Support for dynamic codec payloads only";
              type empty;
            }
          }
          case full-case {
            leaf full {
              description
                "Asymmetric Support for dynamic codec and dtmf payloads";
              type empty;
            }
          }
        }
      }
    }
  }

  grouping config-voice-class-sip-event-list-grouping {
    list sip-event-list {
      description
        "Configure list of events to be passed thru";
      max-elements 10000;
      key "id";
      leaf id {
        description
          "Voice class sip-event-list tag";
        type uint16 {
          range "1..10000";
        }
      }
      leaf-list event {
        description
          "Add event in the list of events to be passed thru";
        max-elements 25;
        type string {
          length "1..128";
        }
      }
    }
  }
}
