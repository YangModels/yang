module Cisco-IOS-XE-rsvp {
  yang-version 1.1;
  namespace "http://cisco.com/ns/yang/Cisco-IOS-XE-rsvp";
  prefix ios-rsvp;

  import cisco-semver {
    prefix cisco-semver;
  }
  import ietf-inet-types {
    prefix inet;
  }
  import Cisco-IOS-XE-types {
    prefix ios-types;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Resource Reservation Protocol (RSVP) Yang model.
     Copyright (c) 2017, 2019 by Cisco Systems, Inc.
     All rights reserved.";

  revision 2024-07-01 {
    description
      "- Added default value for ip rsvp authentication lifetime";
    cisco-semver:module-version "2.0.0";
  }
  revision 2022-11-01 {
    description
      "- Update yang-version to 1.1";
    cisco-semver:module-version "1.2.0";
  }
  revision 2021-07-01 {
    description
      "- Modelling of ip rsvp bandwidth percent ";
    cisco-semver:module-version "1.1.0";
  }
  revision 2019-11-01 {
    description
      "- Fix copyright statement";
    cisco-semver:module-version "1.0.1";
  }
  revision 2019-07-01 {
    description
      "Establish semantic version baseline";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-02-07 {
    description
      "Initial revision";
  }

  grouping rsvp-authentication-grouping {
    leaf challenge {
      description
        "Perform challenge/response handshake with new neighbor(s)";
      type empty;
    }
    leaf key-chain {
      description
        "Name of key chain to use (as created by global 'key chain' command)";
      type string;
    }
    container lifetime {
      description
        "Maximum lifetime of neighbor authentication state";
      leaf hh-mm-ss {
        description
          "Lifetime in hh:mm:ss format";
        type ios-types:hhmmss-type;
        default "00:30:00";
      }
    }
    leaf type {
      description
        "Type of authentication algorithm (default = md5)";
      type enumeration {
        enum md5;
        enum sha-1;
      }
    }
    leaf window-size {
      description
        "Maximum number of messages allowed in receive window (default = 1)";
      type uint8 {
        range "1..64";
      }
    }
  }

  grouping config-interface-ip-rsvp-grouping {
    container rsvp {
      description
        "RSVP Interface Commands";
      container authentication {
        description
          "Enables RSVP neighbor authentication (RFC 2747)";
        presence "true";
        leaf key {
          description
            "Password (8 to 40 characters, spaces allowed)";
          type string;
        }
        uses rsvp-authentication-grouping;
      }
      container bandwidth {
        description
          "RSVP Reservable Bandwidth (kbps)";
        presence "true";
        container value {
          leaf value {
            description
              "Reservable Bandwidth (kbps)";
            type uint32 {
              range "1..10000000";
            }
          }
          leaf sub-pool {
            description
              "Reservable Bandwidth for Tunnel using sub (BC1) pool (kbps)";
            type uint32 {
              range "1..10000000";
            }
          }
        }
        leaf percent {
          description
            "Percentage of interface bandwidth. Values higher than 100 represent overbooking";
          type uint16 {
            range "1..1000";
          }
        }
        container mam {
          description
            "Use bandwidth with MAM model of DSTE";
          container max-reservable-bw {
            description
              "Maximum Reservable bandwidth for MAM";
            presence "true";
            leaf value {
              description
                "Reservable Bandwidth (kbps)";
              type uint32 {
                range "1..10000000";
              }
            }
            leaf bc0 {
              description
                "Reservable Bandwidth from global (BC0) pool (kbps)";
              type uint32 {
                range "0..10000000";
              }
            }
            leaf bc1 {
              description
                "Reservable Bandwidth from sub pool (kbps)";
              type uint32 {
                range "0..10000000";
              }
            }
          }
        }
      }
      container neighbor {
        description
          "Select permissible RSVP neighbors";
        presence "true";
        leaf acl-number {
          description
            "Access list";
          type uint8 {
            range "1..199";
          }
        }
      }
      container precedence {
        description
          "RSVP precedence setting";
        leaf conform {
          description
            "Precedence for packets conforming to RSVP flowspec bandwidth";
          type uint8 {
            range "0..7";
          }
        }
        leaf exceed {
          description
            "Precedence for packets over RSVP flowspec bandwidth";
          type uint8 {
            range "0..7";
          }
        }
      }
      container signalling {
        description
          "RSVP signalling";
        leaf dscp {
          description
            "DSCP for RSVP signalling messages";
          type uint8 {
            range "0..63";
          }
        }
        container fast-local-repair {
          description
            "Fast Local Repair parameters";
          leaf wait-time {
            description
              "Wait Time for start of Fast Local Repair in msec";
            type uint16 {
              range "0..5000";
            }
          }
        }
        container hello {
          description
            "Enable neighbor-down detection";
          presence "true";
          leaf bfd {
            description
              "Configure BFD trigger for MPLS/TE FRR";
            type empty;
          }
          leaf dscp {
            description
              "DSCP for RSVP Hello messages";
            type uint8 {
              range "0..63";
            }
          }
          container fast-reroute {
            description
              "Configure RSVP Hello refresh behavior for Fast-Reroute";
            leaf dscp {
              description
                "DSCP for RSVP Hello messages";
              type uint8 {
                range "0..63";
              }
            }
            container refresh {
              description
                "Configure RSVP Hello refresh behavior for Fast-Reroute";
              leaf interval {
                description
                  "Hello interval in msec";
                type uint16 {
                  range "10..30000";
                }
              }
              leaf misses {
                description
                  "Number of missed Hello Acks which triggers neighbor down";
                type uint8 {
                  range "4..10";
                }
              }
            }
          }
          leaf graceful-restart {
            description
              "Configure RSVP Graceful Restart";
            type empty;
          }
          container refresh {
            description
              "Configure RSVP Hello refresh behavior for Fast-Reroute";
            leaf interval {
              description
                "Hello interval in msec";
              type uint16 {
                range "10..30000";
              }
            }
            leaf misses {
              description
                "Number of missed Hello Acks which triggers neighbor down";
              type uint8 {
                range "4..10";
              }
            }
          }
          container reroute {
            description
              "Configure RSVP Hello refresh behavior for Reroute";
            leaf dscp {
              description
                "DSCP for RSVP Hello messages";
              type uint8 {
                range "0..63";
              }
            }
            container refresh {
              description
                "Configure RSVP Reroute Hello refresh behavior";
              leaf interval {
                description
                  "Hello Reroute interval in msec";
                type uint16 {
                  range "1000..30000";
                }
              }
              leaf misses {
                description
                  "Number of missed Hello Acks which triggers neighbor down";
                type uint8 {
                  range "4..10";
                }
              }
            }
          }
        }
      }
      container tos {
        description
          "RSVP TOS setting";
        leaf conform {
          description
            "TOS for packets conforming to RSVP flowspec bandwidth";
          type uint8 {
            range "0..31";
          }
        }
        leaf exceed {
          description
            "TOS for packets over RSVP flowspec bandwidth";
          type uint8 {
            range "0..31";
          }
        }
      }
    }
  }

  grouping config-ip-rsvp-grouping {
    container rsvp {
      description
        "IP RSVP";
      container authentication {
        description
          "Enables RSVP neighbor authentication (RFC 2747)";
        presence "true";
        container neighbor {
          description
            "Specific neighbor(s) to authenticate";
          container access-list {
            description
              "Specify neighbor by IP access list";
            list number {
              key "acl-number";
              leaf acl-number {
                description
                  "standard IP access list number";
                type uint8 {
                  range "1..99";
                }
              }
              uses rsvp-authentication-grouping;
            }
            list name {
              key "acl-name";
              leaf acl-name {
                description
                  "standard IP access list name";
                type string;
              }
              uses rsvp-authentication-grouping;
            }
          }
          container address {
            description
              "Specify neighbor by IP address";
            list ipv4 {
              key "ipv4-address";
              leaf ipv4-address {
                description
                  "Neighbor's IP address";
                type inet:ipv4-address;
              }
              uses rsvp-authentication-grouping;
            }
          }
        }
        uses rsvp-authentication-grouping;
      }
      container signalling {
        description
          "IP RSVP signalling";
        container fast-local-repair {
          description
            "Configure RSVP Fast Local Repair";
          leaf notifications {
            description
              "Number of notifications to process before suspend";
            type uint16 {
              range "10..10000";
            }
          }
          leaf rate {
            description
              "Fast Local Repair state refresh/repair rate in messages/sec";
            type uint16 {
              range "1..2500";
            }
          }
        }
        container hello {
          description
            "Enable neighbor-down detection";
          presence "true";
          leaf bfd {
            description
              "Enable BFD detection for fast-reroute";
            type empty;
          }
          container graceful-restart {
            description
              "Configure RSVP Graceful Restart";
            leaf dscp {
              description
                "RSVP Graceful Restart Hello Messages DSCP value";
              type uint8 {
                range "0..63";
              }
            }
            container mode {
              description
                "Select Graceful Restart capabilities";
              leaf full {
                description
                  "Capable of recovering self, and helping neighbor recover";
                type empty;
              }
              leaf help-neighbor {
                description
                  "Capable of helping neighbor recover";
                type empty;
              }
            }
            container refresh {
              description
                "Configure RSVP Hello refresh behavior for Graceful Restart";
              leaf interval {
                description
                  "Hello interval in msec";
                type uint16 {
                  range "1000..30000";
                }
              }
              leaf misses {
                description
                  "Number of missed Hello Acks which triggers neighbor down";
                type uint8 {
                  range "4..10";
                }
              }
            }
            container send {
              description
                "Configure parameters in outgoing Hello msgs";
              leaf recovery-time {
                description
                  "recovery-time in msec";
                type uint32 {
                  range "0..3600000";
                }
              }
            }
          }
          leaf statistics {
            description
              "Enables Hello extensions statistics";
            type empty;
          }
        }
        leaf initial-retransmit-delay {
          description
            "Initial retransmit delay (msecs)";
          type uint16 {
            range "500..30000";
          }
        }
        container patherr {
          description
            "Path Error State Removal for LSP sessions";
          container state-removal {
            description
              "Enable state removal";
            presence "true";
            leaf neighbor {
              description
                "Access list number identifying neighbor(s)";
              type uint8 {
                range "1..99";
              }
            }
          }
        }
        container rate-limit {
          description
            "Limit rate at which RSVP msgs are sent to neighbors";
          presence "true";
          leaf burst {
            description
              "Number of messages sent each period from the queue, normally";
            type uint16 {
              range "1..5000";
            }
          }
          leaf limit {
            description
              "Max number of msgs sent each period from the queue, when behind";
            type uint16 {
              range "1..5000";
            }
          }
          leaf maxsize {
            description
              "Maximum queue depth";
            type uint16 {
              range "1..5000";
            }
          }
          leaf period {
            description
              "Every interval (msec) send burst number of messages";
            type uint16 {
              range "10..5000";
            }
          }
        }
        container refresh {
          description
            "Configure RSVP refresh behavior";
          leaf interval {
            description
              "Refresh interval in milliseconds";
            type uint32 {
              range "5000..2147483647";
            }
          }
          leaf misses {
            description
              "Number of missed refreshes which trigger state timeout";
            type uint8 {
              range "2..10";
            }
          }
          container reduction {
            description
              "Configure refresh reduction";
            presence "true";
            leaf ack-delay {
              description
                "Time to wait to accumulate ACKs (msecs)";
              type uint16 {
                range "100..10000";
              }
            }
          }
        }
      }
    }
  }

  augment "/ios:native/ios:ip" {
    uses config-ip-rsvp-grouping;
  }

  augment "/ios:native/ios:interface/ios:BDI/ios:ip" {
    uses config-interface-ip-rsvp-grouping;
  }

  augment "/ios:native/ios:interface/ios:FastEthernet/ios:ip" {
    uses config-interface-ip-rsvp-grouping;
  }

  augment "/ios:native/ios:interface/ios:GigabitEthernet/ios:ip" {
    uses config-interface-ip-rsvp-grouping;
  }

  augment "/ios:native/ios:interface/ios:TenGigabitEthernet/ios:ip" {
    uses config-interface-ip-rsvp-grouping;
  }

  augment "/ios:native/ios:interface/ios:FiveGigabitEthernet/ios:ip" {
    uses config-interface-ip-rsvp-grouping;
  }

  augment "/ios:native/ios:interface/ios:AppGigabitEthernet/ios:ip" {
    uses config-interface-ip-rsvp-grouping;
  }

  augment "/ios:native/ios:interface/ios:TwentyFiveGigE/ios:ip" {
    uses config-interface-ip-rsvp-grouping;
  }

  augment "/ios:native/ios:interface/ios:TwoGigabitEthernet/ios:ip" {
    uses config-interface-ip-rsvp-grouping;
  }

  augment "/ios:native/ios:interface/ios:FortyGigabitEthernet/ios:ip" {
    uses config-interface-ip-rsvp-grouping;
  }

  augment "/ios:native/ios:interface/ios:HundredGigE/ios:ip" {
    uses config-interface-ip-rsvp-grouping;
  }

  augment "/ios:native/ios:interface/ios:Port-channel/ios:ip" {
    uses config-interface-ip-rsvp-grouping;
  }

  augment "/ios:native/ios:interface/ios:Loopback/ios:ip" {
    uses config-interface-ip-rsvp-grouping;
  }

  augment "/ios:native/ios:interface/ios:Tunnel/ios:ip" {
    uses config-interface-ip-rsvp-grouping;
  }
}
