module Cisco-IOS-XE-ha-oper {
  yang-version 1.1;
  namespace "http://cisco.com/ns/yang/Cisco-IOS-XE-ha-oper";
  prefix ha-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for High Availability (HA) operational state data.
     Copyright (c) 2017-2019, 2022 by Cisco Systems, Inc.
     All rights reserved.";

  revision 2024-11-01 {
    description
      "Added switchover experienced count and standby failures count";
    reference
      "1.4.0";
    cisco-semver:module-version "1.4.0";
  }
  revision 2022-11-01 {
    description
      "Update yang-version to 1.1";
    reference
      "1.3.0";
    cisco-semver:module-version "1.3.0";
  }
  revision 2019-11-01 {
    description
      "Modified ha enabled to provide whether system is running in HA";
    reference
      "1.2.1";
    cisco-semver:module-version "1.2.1";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-05-02 {
    description
      "Initial revision";
    reference
      "1.0.0";
    cisco-semver:module-version "1.0.0";
  }

  typedef rf-states {
    type enumeration {
      enum db-rf-unknown {
        value 0;
        description
          "RF HA state is unknown";
      }
      enum db-rf-disabled {
        value 1;
        description
          "RF HA state is disabled";
      }
      enum db-rf-initialization {
        value 2;
        description
          "RF HA state is initialization";
      }
      enum db-rf-negotiation {
        value 3;
        description
          "RF HA state is negotiation";
      }
      enum db-rf-standby-cold {
        value 4;
        description
          "RF HA state is standby cold";
      }
      enum db-rf-standby-config {
        value 5;
        description
          "RF HA state is standby config";
      }
      enum db-rf-standby-filesys {
        value 6;
        description
          "RF HA state is standby filesys";
      }
      enum db-rf-standby-bulk {
        value 7;
        description
          "RF HA state is standby bulk";
      }
      enum db-rf-standby-hot {
        value 8;
        description
          "RF HA state is standby hot";
      }
      enum db-rf-active-fast {
        value 9;
        description
          "RF HA state is active fast";
      }
      enum db-rf-active-drain {
        value 10;
        description
          "RF HA state is active drain";
      }
      enum db-rf-active-preconfig {
        value 11;
        description
          "RF HA state is active preconfig";
      }
      enum db-rf-active-postconfig {
        value 12;
        description
          "RF HA state is active postconfig";
      }
      enum db-rf-active {
        value 13;
        description
          "RF HA state is active";
      }
      enum db-rf-active-extraload {
        value 14;
        description
          "RF HA state is active extraload";
      }
      enum db-rf-active-handback {
        value 15;
        description
          "RF HA state is active handback";
      }
      enum db-rf-standby-warm {
        value 16;
        description
          "RF HA state is standby warm";
      }
      enum db-rf-issu-negotiation {
        value 17;
        description
          "RF HA state is ISSU negotiation";
      }
      enum db-rf-standby-issu-negotiation-late {
        value 18;
        description
          "RF HA state is standby ISSU negotiation late";
      }
      enum db-rf-platform-sync {
        value 19;
        description
          "RF HA state is platform sync";
      }
    }
    description
      "HA peer states and local peer states";
  }

  grouping ha-infra-content {
    description
      "HA infrastructure status grouping";
    leaf ha-state {
      type ha-ios-xe-oper:rf-states;
      description
        "State for local peer";
    }
    leaf peer-state {
      type ha-ios-xe-oper:rf-states;
      description
        "State for remote peer";
    }
    leaf last-switchover-time {
      type yang:date-and-time;
      description
        "System last switchover time";
    }
    leaf last-switchover-reason {
      type string;
      description
        "System last switchover reason";
    }
    leaf image-version {
      type string;
      description
        "System image version";
    }
    leaf leaf-mode {
      type string;
      description
        "System running redundancy mode";
    }
    leaf ha-enabled {
      type boolean;
      description
        "System ready for switchover";
    }
    leaf has-switchover-occured {
      type boolean;
      description
        "System switchover happened before or not";
    }
    leaf switchover-count {
      type uint32;
      description
        "Count of experienced system switchover";
    }
    leaf standby-failure-count {
      type uint32;
      description
        "Count of standby system failures";
    }
  }

  container ha-oper-data {
    config false;
    description
      "HA infrastructure status operational data";
    container ha-infra {
      presence "ha-infra";
      description
        "HA infrastructure status";
      uses ha-ios-xe-oper:ha-infra-content;
    }
  }
}
