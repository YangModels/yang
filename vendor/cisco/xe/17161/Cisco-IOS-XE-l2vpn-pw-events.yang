module Cisco-IOS-XE-l2vpn-pw-events {
  yang-version 1.1;
  namespace "http://cisco.com/ns/yang/Cisco-IOS-XE-l2vpn-pw-events";
  prefix l2vpn-pw-ios-xe-events;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for L2VPN PW status change Notification.
     Copyright (c) 2020, 2022 by Cisco Systems, Inc.
     All rights reserved.";

  revision 2022-11-01 {
    description
      "Update yang-version to 1.1";
    reference
      "1.1.0";
    cisco-semver:module-version "1.1.0";
  }
  revision 2021-03-01 {
    description
      "Initial revision";
    reference
      "1.0.0";
    cisco-semver:module-version "1.0.0";
  }

  typedef pw-vc-status {
    type enumeration {
      enum pw-vc-up {
        value 0;
        description
          "L2VPN PW VC status Up";
      }
      enum pw-vc-down {
        value 1;
        description
          "L2VPN PW VC status DOWN";
      }
    }
    description
      "PW VC status change";
  }

  grouping l2vpn-pw-vc-status-data {
    description
      "L2vpn PW status change";
    leaf vc-status {
      type l2vpn-pw-ios-xe-events:pw-vc-status;
      description
        "VC status";
    }
    leaf vc-id {
      type uint32;
      description
        "VC Identifier";
    }
    leaf peer-ip {
      type inet:ip-address;
      description
        "Peer IP address";
    }
  }

  notification l2vpn-pw-vc-status {
    description
      "L2vpn PW status change Notification";
    uses l2vpn-pw-ios-xe-events:l2vpn-pw-vc-status-data;
  }
}
