module Cisco-IOS-XE-sslproxy-cfg {
  yang-version 1.1;
  namespace "http://cisco.com/ns/yang/Cisco-IOS-XE-sslproxy-cfg";
  prefix sslproxy-ios-xe-cfg;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for SSL proxy configuration data.
     Copyright (c) 2023 by Cisco Systems, Inc.
     All rights reserved.";

  revision 2024-03-01 {
    description
      "Initial revision";
    reference
      "1.0.0";
    cisco-semver:module-version "1.0.0";
  }

  grouping sslproxy-settings {
    description
      "Advanced settings for SSL Proxy";
    leaf expired-cert {
      type string {
        pattern '(drop|decrypt)';
      }
      description
        "Action for expired certificates";
    }
    leaf untrusted-cert {
      type string {
        pattern '(drop|decrypt)';
      }
      description
        "Action for untrusted certificates";
    }
    leaf unknown-status {
      type string {
        pattern '(drop|decrypt)';
      }
      description
        "Action for unknown certificate status";
    }
    leaf cert-rev-check {
      type string {
        pattern '(ocsp|none)';
      }
      description
        "Certificate revocation check";
    }
    leaf us-proto-ver {
      type string {
        pattern '(drop|no-decrypt)';
      }
      description
        "Action for unsupported protocol version";
    }
    leaf us-cipher-suite {
      type string {
        pattern '(drop|no-decrypt)';
      }
      description
        "Action for unsupported cipher suite";
    }
    leaf failure-mode {
      type string {
        pattern '(open|close)';
      }
      description
        "Action for failure mode";
    }
    leaf min-tls-ver {
      type string {
        pattern '(TLSv1|TLSv1.1|TLSv1.2)';
      }
      description
        "Minimum TLS version for SSL Proxy";
    }
  }

  grouping sslproxy-config {
    description
      "SSL proxy configuration";
    leaf enable {
      type boolean;
      default "false";
      description
        "Enable SSL proxy configuration";
    }
    leaf ca-cert-bundle {
      type string {
        length "1..232";
      }
      description
        "Filename of CA certificate bundle";
    }
    leaf rsa-key-modulus {
      type uint32 {
        range "1024 .. 4096";
      }
      default "2048";
      description
        "RSA key length";
    }
    leaf cert-lifetime {
      type uint32 {
        range "1 .. 4294967295";
      }
      default "730";
      description
        "Certificate lifetime in days";
    }
    leaf eckey-type {
      type string {
        pattern '(P256|P384|P521)';
      }
      default "P256";
      description
        "EC key type for SSL Proxy";
    }
    leaf ca-tp-label {
      type string {
        length "1..128";
      }
      default "PROXY-SIGNING-CA";
      description
        "Default Trustpoint label for SSL Proxy";
    }
    container settings {
      description
        "Advanced settings for SSL Proxy";
      uses sslproxy-ios-xe-cfg:sslproxy-settings;
    }
  }

  container sslproxy-cfg-data {
    description
      "SSL proxy configuration";
    container sslproxy-config {
      presence "sslproxy-config";
      description
        "SSL proxy configuration";
      uses sslproxy-ios-xe-cfg:sslproxy-config;
    }
  }
}
