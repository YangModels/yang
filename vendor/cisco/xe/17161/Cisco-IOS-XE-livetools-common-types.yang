module Cisco-IOS-XE-livetools-common-types {
  yang-version 1.1;
  namespace "http://cisco.com/ns/yang/Cisco-IOS-XE-livetools-common-types";
  prefix livetools-common-types-ios-xe;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for live tools common operational data.
     Copyright (c) 2024 by Cisco Systems, Inc.
     All rights reserved.";

  revision 2024-07-01 {
    description
      "Initial revision";
    reference
      "1.0.0";
    cisco-semver:module-version "1.0.0";
  }

  typedef job-status {
    type enumeration {
      enum job-queued {
        value 0;
        description
          "Job is still in queue; yet to be started";
      }
      enum job-in-progress {
        value 1;
        description
          "Job execution is in progress";
      }
      enum job-completed {
        value 2;
        description
          "Job execution is completed";
      }
      enum job-failed {
        value 3;
        description
          "Job execution is failed";
      }
    }
    description
      "Action RPC job's current execution status";
  }

  typedef lt-ip-host-type {
    type enumeration {
      enum host-name {
        value 0;
        description
          "IP host is identified using hostname";
      }
      enum host-ip-addr {
        value 1;
        description
          "IP host is identified using IP address";
      }
    }
    description
      "Type of IP host";
  }

  typedef lt-ip-source-type {
    type enumeration {
      enum src-ip-none {
        value 0;
        description
          "IP source not specified";
      }
      enum src-if-name {
        value 1;
        description
          "IP source interface name";
      }
      enum src-ip-addr {
        value 2;
        description
          "IP source address";
      }
    }
    description
      "Type of IP source";
  }

  typedef dscp-type {
    type enumeration {
      enum dscp-none {
        value 0;
        description
          "No DSCP option specified";
      }
      enum dscp-num {
        value 1;
        description
          "DSCP option is specified as numeric value";
      }
      enum dscp-ascii {
        value 2;
        description
          "DSCP value selected from a set of known DSCP options";
      }
    }
    description
      "Type of DSCP";
  }

  typedef dns-proto-hint {
    type enumeration {
      enum dns-proto-none {
        value 0;
        description
          "No DNS resolution required";
      }
      enum dns-proto-ipv4 {
        value 1;
        description
          "IPV4 DNS resolution";
      }
      enum dns-proto-ipv6 {
        value 2;
        description
          "IPV6 DNS resolution";
      }
    }
    description
      "DNS resolution type";
  }

  typedef dscp-options {
    type enumeration {
      enum opt-dscp-af11 {
        value 0;
        description
          "DSCP type Assured-Forwarding-11";
      }
      enum opt-dscp-af12 {
        value 1;
        description
          "DSCP type Assured-Forwarding-12";
      }
      enum opt-dscp-af13 {
        value 2;
        description
          "DSCP type Assured-Forwarding-13";
      }
      enum opt-dscp-af21 {
        value 3;
        description
          "DSCP type Assured-Forwarding-21";
      }
      enum opt-dscp-af22 {
        value 4;
        description
          "DSCP type Assured-Forwarding-22";
      }
      enum opt-dscp-af23 {
        value 5;
        description
          "DSCP type Assured-Forwarding-23";
      }
      enum opt-dscp-af31 {
        value 6;
        description
          "DSCP type Assured-Forwarding-31";
      }
      enum opt-dscp-af32 {
        value 7;
        description
          "DSCP type Assured-Forwarding-32";
      }
      enum opt-dscp-af33 {
        value 8;
        description
          "DSCP type Assured-Forwarding-33";
      }
      enum opt-dscp-af41 {
        value 9;
        description
          "DSCP type Assured-Forwarding-41";
      }
      enum opt-dscp-af42 {
        value 10;
        description
          "DSCP type Assured-Forwarding-42";
      }
      enum opt-dscp-af43 {
        value 11;
        description
          "DSCP type Assured-Forwarding-43";
      }
      enum opt-dscp-cs1 {
        value 12;
        description
          "DSCP type Class-Selector-1";
      }
      enum opt-dscp-cs2 {
        value 13;
        description
          "DSCP type Class-Selector-2";
      }
      enum opt-dscp-cs3 {
        value 14;
        description
          "DSCP type Class-Selector-3";
      }
      enum opt-dscp-cs4 {
        value 15;
        description
          "DSCP type Class-Selector-4";
      }
      enum opt-dscp-cs5 {
        value 16;
        description
          "DSCP type Class-Selector-5";
      }
      enum opt-dscp-cs6 {
        value 17;
        description
          "DSCP type Class-Selector-6";
      }
      enum opt-dscp-cs7 {
        value 18;
        description
          "DSCP type Class-Selector-7";
      }
      enum opt-dscp-ef {
        value 19;
        description
          "DSCP type Expedited Forwarding";
      }
    }
    description
      "DSCP options";
  }

  grouping job-response {
    description
      "Job related data for the action RPC execution";
    leaf request-time {
      type yang:date-and-time;
      description
        "Time when the job is submitted";
    }
    leaf end-time {
      type yang:date-and-time;
      description
        "Time when the job is completed";
    }
    leaf status {
      type livetools-common-types-ios-xe:job-status;
      description
        "Job's current status";
    }
  }
}
