module Cisco-IOS-XE-avb {
  yang-version 1.1;
  namespace "http://cisco.com/ns/yang/Cisco-IOS-XE-avb";
  prefix ios-avb;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Audio Video Bridge Yang Model.
     Copyright (c) 2016-2017 by Cisco Systems, Inc.
     All rights reserved.";

  revision 2022-11-01 {
    description
      "- Update yang-version to 1.1";
    cisco-semver:module-version "1.1.0";
  }
  revision 2019-07-01 {
    description
      "Establish semantic version baseline";
    cisco-semver:module-version "1.0.0";
  }
  revision 2017-09-19 {
    description
      "Initial revision";
  }

  grouping config-avb-grouping {
    leaf strict {
      type empty;
    }
  }

  augment "/ios:native/ios:avb" {
    uses config-avb-grouping;
  }
}
