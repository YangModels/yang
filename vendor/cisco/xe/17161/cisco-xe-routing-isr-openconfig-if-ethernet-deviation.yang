module cisco-xe-routing-isr-openconfig-if-ethernet-deviation {
  namespace "http://openconfig.net/yang/cisco-xe-routing-isr-openconfig-if-ethernet-deviation";
  prefix cisco-xe-routing-isr-oc-if-eth-devs;

  import openconfig-interfaces {
    prefix oc-if;
  }
  import openconfig-if-ethernet {
    prefix oc-if-eth;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-if-ethernet module for IOS XE Routing ISR devices.";

  revision 2021-07-01 {
    description
      "Deviated leafs not supported under 17.6 release";
  }
  revision 2018-09-30 {
    description
      "ISR PD Ethernet feature deviations";
    reference
      "RFC 6020: YANG - A Data Modeling Language for the
       Network Configuration Protocol (NETCONF)";
  }

  deviation "/oc-if:interfaces/oc-if:interface/oc-if-eth:ethernet/oc-if-eth:config/oc-if-eth:enable-flow-control" {
    deviate not-supported;
    description
      "Explicit enabling/disabling of the flow-control is not supported on ISR platform .";
  }

  deviation "/oc-if:interfaces/oc-if:interface/oc-if-eth:ethernet/oc-if-eth:state/oc-if-eth:counters/oc-if-eth:in-undersize-frames" {
    deviate not-supported;
    description
      "Not supported in 17.6 release.";
  }

  deviation "/oc-if:interfaces/oc-if:interface/oc-if-eth:ethernet/oc-if-eth:state/oc-if-eth:counters/oc-if-eth:in-block-errors" {
    deviate not-supported;
    description
      "Not supported in 17.6 release.";
  }
}
