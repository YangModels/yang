module Cisco-IOS-XE-alarm-profile {
  yang-version 1.1;
  namespace "http://cisco.com/ns/yang/Cisco-IOS-XE-alarm-profile";
  prefix ios-ap;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Alarm Profile Yang model.
     Copyright (c) 2021 by Cisco Systems, Inc.
     All rights reserved.";

  revision 2024-07-01 {
    description
      "- Updated default value for alarm-profile key-leaf,
       - Supporting config model for notifies, syslog and alarm for interface failure";
    cisco-semver:module-version "1.2.0";
  }
  revision 2022-11-01 {
    description
      "- Update yang-version to 1.1";
    cisco-semver:module-version "1.1.0";
  }
  revision 2021-07-01 {
    description
      "- Alarm Profile config yang model supports chassis profile, IM profile
         and ethernet port profile
       - Changed the model structure from alarm list to container. Fixed the secondary-admin-state with cases
       - Fixed Sync issue on Alarm Subtypes
       - Added default value for secondary admin state and few minor changes";
    cisco-semver:module-version "1.0.0";
  }

  grouping alarm-config-grouping {
    container alarm-config {
      leaf ains {
        type empty;
      }
      container alarm {
        container ds1 {
          presence "true";
          container ds1-ais {
            uses alarm-severity-suppress-grouping;
          }
          container ds1-bert-mt-alarm {
            uses alarm-severity-suppress-grouping;
          }
          container ds1-lof {
            uses alarm-severity-suppress-grouping;
          }
          container ds1-los {
            uses alarm-severity-suppress-grouping;
          }
          container ds1-rai {
            uses alarm-severity-suppress-grouping;
          }
        }
        container ds3 {
          presence "true";
          container ds3-bert-mt-alarm {
            uses alarm-severity-suppress-grouping;
          }
          container ds3-ds1-ais {
            uses alarm-severity-suppress-grouping;
          }
          container ds3-ds1-los {
            uses alarm-severity-suppress-grouping;
          }
          container ds3-ds1-oof {
            uses alarm-severity-suppress-grouping;
          }
          container ds3-ds1-rai {
            uses alarm-severity-suppress-grouping;
          }
          container ds3-rx-ais {
            uses alarm-severity-suppress-grouping;
          }
          container ds3-rx-lof {
            uses alarm-severity-suppress-grouping;
          }
          container ds3-rx-los {
            uses alarm-severity-suppress-grouping;
          }
          container ds3-rx-rai {
            uses alarm-severity-suppress-grouping;
          }
        }
        container gig {
          presence "true";
          container ethernet-port-admin-down {
            uses alarm-severity-suppress-grouping;
          }
          container ethernet-port-link-down {
            uses alarm-severity-suppress-grouping;
          }
          container ethernet-port-not-configured {
            uses alarm-severity-suppress-grouping;
          }
          container lof {
            uses alarm-severity-suppress-grouping;
          }
          container lom {
            uses alarm-severity-suppress-grouping;
          }
          container los {
            uses alarm-severity-suppress-grouping;
          }
          container odu-ais {
            uses alarm-severity-suppress-grouping;
          }
          container odu-bdi {
            uses alarm-severity-suppress-grouping;
          }
          container odu-bip {
            uses alarm-severity-suppress-grouping;
          }
          container odu-lck {
            uses alarm-severity-suppress-grouping;
          }
          container odu-oci {
            uses alarm-severity-suppress-grouping;
          }
          container odu-ptim {
            uses alarm-severity-suppress-grouping;
          }
          container odu-tim {
            uses alarm-severity-suppress-grouping;
          }
          container oof {
            uses alarm-severity-suppress-grouping;
          }
          container otu-ais {
            uses alarm-severity-suppress-grouping;
          }
          container otu-bdi {
            uses alarm-severity-suppress-grouping;
          }
          container otu-bip {
            uses alarm-severity-suppress-grouping;
          }
          container otu-iae {
            uses alarm-severity-suppress-grouping;
          }
          container otu-tim {
            uses alarm-severity-suppress-grouping;
          }
        }
        container sonet-sdh {
          presence "true";
          container ds1-ais {
            uses alarm-severity-suppress-grouping;
          }
          container ds1-los {
            uses alarm-severity-suppress-grouping;
          }
          container ds1-oof {
            uses alarm-severity-suppress-grouping;
          }
          container ds1-rai {
            uses alarm-severity-suppress-grouping;
          }
          container ds3-rx-ais {
            uses alarm-severity-suppress-grouping;
          }
          container ds3-rx-lof {
            uses alarm-severity-suppress-grouping;
          }
          container ds3-rx-los {
            uses alarm-severity-suppress-grouping;
          }
          container ds3-rx-rai {
            uses alarm-severity-suppress-grouping;
          }
          container lais {
            uses alarm-severity-suppress-grouping;
          }
          container lom {
            uses alarm-severity-suppress-grouping;
          }
          container lp-ais {
            uses alarm-severity-suppress-grouping;
          }
          container lp-ber-sd {
            uses alarm-severity-suppress-grouping;
          }
          container lp-ber-sf {
            uses alarm-severity-suppress-grouping;
          }
          container lp-lop {
            uses alarm-severity-suppress-grouping;
          }
          container lp-plm {
            uses alarm-severity-suppress-grouping;
          }
          container lp-rdi {
            uses alarm-severity-suppress-grouping;
          }
          container lp-rfi {
            uses alarm-severity-suppress-grouping;
          }
          container lp-uneq {
            uses alarm-severity-suppress-grouping;
          }
          container lrdi {
            uses alarm-severity-suppress-grouping;
          }
          container pais {
            uses alarm-severity-suppress-grouping;
          }
          container plop {
            uses alarm-severity-suppress-grouping;
          }
          container pplm {
            uses alarm-severity-suppress-grouping;
          }
          container prdi {
            uses alarm-severity-suppress-grouping;
          }
          container puneq {
            uses alarm-severity-suppress-grouping;
          }
          container sd {
            uses alarm-severity-suppress-grouping;
          }
          container sd-b3 {
            uses alarm-severity-suppress-grouping;
          }
          container sf {
            uses alarm-severity-suppress-grouping;
          }
          container sf-b3 {
            uses alarm-severity-suppress-grouping;
          }
          container slof {
            uses alarm-severity-suppress-grouping;
          }
          container slos {
            uses alarm-severity-suppress-grouping;
          }
          container sonet-bert-mt-alarm {
            uses alarm-severity-suppress-grouping;
          }
          container tca-b1 {
            uses alarm-severity-suppress-grouping;
          }
          container tca-b2 {
            uses alarm-severity-suppress-grouping;
          }
          container tca-b3 {
            uses alarm-severity-suppress-grouping;
          }
        }
      }
    }
  }

  grouping alarm-profile-grouping {
    list alarm-profile {
      key "alarm-profile-name";
      leaf alarm-profile-name {
        type string {
          length "1..32";
        }
      }
      container notifies {
        description
          "SNMP notification alarm trigger parameter.";
        leaf not-operating {
          description
            "SNMP notification alarm trigger for interface failure.";
          type empty;
        }
      }
      container syslog {
        description
          "syslog notification alarm trigger parameter.";
        leaf not-operating {
          description
            "syslog notification alarm trigger for interface failure.";
          type empty;
        }
      }
      container alarm {
        description
          "Relay alarm trigger parameter.";
        leaf not-operating {
          description
            "Relay alarm notification trigger for interface failure.";
          type empty;
        }
      }
      choice alarm-profile-choice {
        container card {
          presence "true";
          uses alarm-config-grouping;
        }
        container chassis {
          presence "true";
          uses alarm-config-grouping;
        }
        container port {
          presence "true";
          uses alarm-config-grouping;
        }
      }
      container attach {
        choice attach-choice {
          leaf card {
            must '../../card' {
              error-message "Card Profile should exist before attaching or detaching its profile";
            }
            type string {
              pattern '[0-9]/([1][0-5]|[0-9])';
            }
          }
          leaf chassis {
            must '../../chassis' {
              error-message "Chassis Profile should exist before attaching or detaching its profile";
            }
            type empty;
          }
        }
      }
    }
  }

  grouping alarm-severity-suppress-grouping {
    leaf severity {
      type enumeration {
        enum info;
        enum minor;
        enum major;
        enum critical;
      }
    }
    leaf suppress {
      type empty;
    }
  }

  grouping hw-module-grouping {
    container hw-module {
      container configuration {
        list hw-module {
          key "hw-module";
          leaf hw-module {
            type string {
              pattern '[0-9]/([1][0-5]|[0-9])';
            }
          }
          leaf transceiver {
            type uint32 {
              range "1..64";
            }
          }
          leaf secondary-admin-state {
            type enumeration {
              enum auto-in-service;
              enum in-service;
            }
          }
          leaf pid {
            type string;
          }
        }
      }
    }
  }

  grouping secondary-admin-state-grouping {
    container attach {
      leaf profile {
        type leafref {
          path "/ios:native/ios-ap:alarm-profile/ios-ap:alarm-profile-name";
        }
        must '/ios:native/ios-ap:alarm-profile[ios-ap:alarm-profile-name=current()/../profile]/ios-ap:port' {
          error-message "Profile not exist or attached profile may not be a port profile";
        }
      }
    }
    container secondary-admin-state {
      when '../attach/profile';
      choice secondary-admin-state-choice {
        default "in-service-case";
        case auto-in-service-case {
          container auto-in-service {
            presence "true";
            leaf hours {
              type uint8 {
                range "1..48";
              }
            }
            leaf minutes {
              type uint8 {
                range "0 | 15 | 30 | 45";
              }
            }
          }
        }
        case in-service-case {
          leaf in-service {
            type boolean;
            default "true";
          }
        }
        case maintenance-case {
          leaf maintenance {
            type empty;
          }
        }
      }
    }
  }

  augment "/ios:native" {
    uses alarm-profile-grouping;
  }

  augment "/ios:native/ios:platform" {
    uses hw-module-grouping;
  }

  augment "/ios:native/ios:interface/ios:GigabitEthernet" {
    uses secondary-admin-state-grouping;
  }

  augment "/ios:native/ios:interface/ios:TenGigabitEthernet" {
    uses secondary-admin-state-grouping;
  }
}
