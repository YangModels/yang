module Cisco-IOS-XE-interfaces-wlc-deviation {
  yang-version 1.1;
  namespace "http://cisco.com/ns/yang/Cisco-IOS-XE-interfaces-wlc-deviation";
  prefix ios-interfaces-wlc-d;

  import Cisco-IOS-XE-native {
    prefix ios;
  }

  organization
    "Cisco Systems";
  description
    "Cisco XE Interfaces Deviation YANG module for WLC
     Copyright (c) 2024 by Cisco Systems, Inc.
     All rights reserved.";

  revision 2024-11-01 {
    description
      "- Added ip proxy-arp deviation";
  }

  deviation "/ios:native/ios:interface/ios:Vlan/ios:ip/ios:proxy-arp" {
    deviate replace {
      default "false";
    }
  }
}
