module Cisco-IOS-XE-nbar {
  yang-version 1.1;
  namespace "http://cisco.com/ns/yang/Cisco-IOS-XE-nbar";
  prefix ios-nbar;

  import cisco-semver {
    prefix cisco-semver;
  }
  import Cisco-IOS-XE-native {
    prefix ios;
  }
  import ietf-inet-types {
    prefix inet;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Network-Based Application Recognition (NBAR) Yang model.
     Copyright (c) 2016-2017, 2019-2023 by Cisco Systems, Inc.
     All rights reserved.";

  revision 2024-07-01 {
    description
      "- reopen direction and port custom CLIs";
    cisco-semver:module-version "6.1.0";
  }
  revision 2024-03-01 {
    description
      "- obsolete classify-by-domain";
    cisco-semver:module-version "6.0.0";
  }
  revision 2023-11-01 {
    description
      "- Added ip nbar protocol-map CLI support";
    cisco-semver:module-version "5.0.0";
  }
  revision 2023-07-01 {
    description
      "- ip traffic mode support";
    cisco-semver:module-version "4.0.0";
  }
  revision 2022-11-01 {
    description
      "- Update yang-version to 1.1";
    cisco-semver:module-version "3.1.0";
  }
  revision 2022-07-01 {
    description
      "obsolete ip nbar classification sampling";
    cisco-semver:module-version "3.0.0";
  }
  revision 2022-03-01 {
    description
      " - Tunnel type VXLAN support
        - dns learning domain support
        - deprecate ip nbar ip nbar classification sampling
        - cache-ttl-zero has tailf:cli-trim-default attribute";
    cisco-semver:module-version "2.4.0";
  }
  revision 2021-11-01 {
    description
      "- cache-ttl-zero support
       - Add internal semantic version";
    cisco-semver:module-version "2.3.0";
  }
  revision 2021-04-28 {
    description
      "Virtual-Template support";
    cisco-semver:module-version "2.2.0";
  }
  revision 2020-09-28 {
    description
      "port-channel-subinterface support.
       classify-by-domain type modification";
    cisco-semver:module-version "2.1.0";
  }
  revision 2020-03-08 {
    description
      "Fix attribute-set sequence bug";
    cisco-semver:module-version "2.0.0";
  }
  revision 2019-12-08 {
    description
      "Fix backward compatibility";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2018-12-13 {
    description
      "Added support for below fields:
        - ip nbar attribute application-family
        - ip nbar attribute-map attribute application-family
        - ip nbar attribute-map attribute p2p-technology
        - ip nbar ip nbar classification sampling <1-100>";
  }
  revision 2018-11-16 {
    description
      "Cleanup spelling errors in description statements";
  }
  revision 2018-11-02 {
    description
      "This revision has changes for dialer, ethernet, service-engine, LISP,
       and ATM interface addition";
  }
  revision 2018-09-05 {
    description
      "This revision has changes for Multilink, cellular
       and Serial interfaces addition";
  }
  revision 2018-06-06 {
    description
      "Added source-interface and application-updates fields under 'sd-services'.
       Removed dns-as under 'avc'";
  }
  revision 2017-11-27 {
    description
      "Added Change 25GE name";
  }
  revision 2017-11-14 {
    description
      "This revision has changes for new 40 and 100GE interface addition";
  }
  revision 2017-09-15 {
    description
      "This revision has changes for new 2gig interface addition";
  }
  revision 2017-08-16 {
    description
      "This revision has changes for new 5gig and 25gig interfaces addition";
  }
  revision 2017-07-31 {
    description
      "Added ip nbar classification CLI's";
  }
  revision 2017-07-13 {
    description
      "Support for dynamically updated protocol-pack, sd-avc, and missing CLI's";
  }
  revision 2017-02-07 {
    description
      "Initial revision";
  }

  grouping config-custom-grouping {
    container dscp {
      description
        "DSCP in IPv4 and IPv6 packets";
      leaf range {
        description
          "Differentiated services code point value";
        type uint8 {
          range "0..63";
        }
      }
      leaf af11 {
        description
          "Match packets with AF11 dscp (001010)";
        type empty;
      }
      leaf af12 {
        description
          "Match packets with AF12 dscp (001100)";
        type empty;
      }
      leaf af13 {
        description
          "Match packets with AF13 dscp (001110)";
        type empty;
      }
      leaf af21 {
        description
          "Match packets with AF21 dscp (010010)";
        type empty;
      }
      leaf af22 {
        description
          "Match packets with AF22 dscp (010100)";
        type empty;
      }
      leaf af23 {
        description
          "Match packets with AF23 dscp (010110)";
        type empty;
      }
      leaf af31 {
        description
          "Match packets with AF31 dscp (011010)";
        type empty;
      }
      leaf af32 {
        description
          "Match packets with AF32 dscp (011100)";
        type empty;
      }
      leaf af33 {
        description
          "Match packets with AF33 dscp (011110)";
        type empty;
      }
      leaf af41 {
        description
          "Match packets with AF41 dscp (100010)";
        type empty;
      }
      leaf af42 {
        description
          "Match packets with AF42 dscp (100100)";
        type empty;
      }
      leaf af43 {
        description
          "Match packets with AF43 dscp (100110)";
        type empty;
      }
      leaf cs1 {
        description
          "Match packets with CS1(precedence 1) dscp (001000)";
        type empty;
      }
      leaf cs2 {
        description
          "Match packets with CS2(precedence 2) dscp (010000)";
        type empty;
      }
      leaf cs3 {
        description
          "Match packets with CS3(precedence 3) dscp (011000)";
        type empty;
      }
      leaf cs4 {
        description
          "Match packets with CS4(precedence 4) dscp (100000)";
        type empty;
      }
      leaf cs5 {
        description
          "Match packets with CS5(precedence 5) dscp (101000)";
        type empty;
      }
      leaf cs6 {
        description
          "Match packets with CS6(precedence 6) dscp (110000)";
        type empty;
      }
      leaf cs7 {
        description
          "Match packets with CS7(precedence 7) dscp (111000)";
        type empty;
      }
      leaf default {
        description
          "Match packets with default dscp (000000)";
        type empty;
      }
      leaf ef {
        description
          "Match packets with EF dscp (101110)";
        type empty;
      }
    }
    container ip {
      description
        "ip address";
      list address {
        description
          "ip address list";
        key "address0";
        leaf address0 {
          description
            "List of up to 8 IPs separated by white-spaces";
          type inet:ipv4-address;
        }
        leaf address1 {
          description
            "List of up to 8 IPs separated by white-spaces";
          type inet:ipv4-address;
        }
        leaf address2 {
          description
            "List of up to 8 IPs separated by white-spaces";
          type inet:ipv4-address;
        }
        leaf address3 {
          description
            "List of up to 8 IPs separated by white-spaces";
          type inet:ipv4-address;
        }
        leaf address4 {
          description
            "List of up to 8 IPs separated by white-spaces";
          type inet:ipv4-address;
        }
        leaf address5 {
          description
            "List of up to 8 IPs separated by white-spaces";
          type inet:ipv4-address;
        }
        leaf address6 {
          description
            "List of up to 8 IPs separated by white-spaces";
          type inet:ipv4-address;
        }
        leaf address7 {
          description
            "List of up to 8 IPs separated by white-spaces";
          type inet:ipv4-address;
        }
      }
      container subnet {
        description
          "Subnet IP/mask length";
        leaf subnet {
          description
            "Subnet IP";
          type inet:ipv4-address;
        }
        leaf mask {
          type uint8 {
            range "0..32";
          }
        }
      }
    }
    container ipv6 {
      description
        "ipv6 address";
      list address {
        description
          "ipv6 address list";
        key "address0";
        leaf address0 {
          description
            "List of up to 8 IPs separated by white-spaces";
          type inet:ipv6-address;
        }
        leaf address1 {
          description
            "List of up to 8 IPs separated by white-spaces";
          type inet:ipv6-address;
        }
        leaf address2 {
          description
            "List of up to 8 IPs separated by white-spaces";
          type inet:ipv6-address;
        }
        leaf address3 {
          description
            "List of up to 8 IPs separated by white-spaces";
          type inet:ipv6-address;
        }
        leaf address4 {
          description
            "List of up to 8 IPs separated by white-spaces";
          type inet:ipv6-address;
        }
        leaf address5 {
          description
            "List of up to 8 IPs separated by white-spaces";
          type inet:ipv6-address;
        }
        leaf address6 {
          description
            "List of up to 8 IPs separated by white-spaces";
          type inet:ipv6-address;
        }
        leaf address7 {
          description
            "List of up to 8 IPs separated by white-spaces";
          type inet:ipv6-address;
        }
      }
      container subnet {
        description
          "Subnet IP/mask length";
        leaf subnet {
          description
            "Subnet IP";
          type inet:ipv6-address;
        }
        leaf mask {
          type uint8 {
            range "0..128";
          }
        }
      }
    }
    container direction {
      description
        "Flow direction";
      status obsolete;
      leaf any {
        description
          "Any Direction";
        status obsolete;
        type empty;
      }
      leaf destination {
        description
          "Destination Direction";
        status obsolete;
        type empty;
      }
      leaf source {
        description
          "Source Direction";
        status obsolete;
        type empty;
      }
    }
    container direction-reopen {
      description
        "Flow direction";
      leaf any {
        description
          "Any Direction";
        type empty;
      }
      leaf destination {
        description
          "Destination Direction";
        type empty;
      }
      leaf source {
        description
          "Source Direction";
        type empty;
      }
    }
    container port {
      description
        "ports";
      status obsolete;
      list port-numbers {
        status obsolete;
        key "port-number0";
        leaf port-number0 {
          description
            "Up to 8 port numbers separated by white-spaces";
          status obsolete;
          type uint16 {
            range "1..65535";
          }
        }
        leaf port-number1 {
          description
            "Up to 8 port numbers separated by white-spaces";
          status obsolete;
          type uint16 {
            range "1..65535";
          }
        }
        leaf port-number2 {
          description
            "Up to 8 port numbers separated by white-spaces";
          status obsolete;
          type uint16 {
            range "1..65535";
          }
        }
        leaf port-number3 {
          description
            "Up to 8 port numbers separated by white-spaces";
          status obsolete;
          type uint16 {
            range "1..65535";
          }
        }
        leaf port-number4 {
          description
            "Up to 8 port numbers separated by white-spaces";
          status obsolete;
          type uint16 {
            range "1..65535";
          }
        }
        leaf port-number5 {
          description
            "Up to 8 port numbers separated by white-spaces";
          status obsolete;
          type uint16 {
            range "1..65535";
          }
        }
        leaf port-number6 {
          description
            "Up to 8 port numbers separated by white-spaces";
          status obsolete;
          type uint16 {
            range "1..65535";
          }
        }
        leaf port-number7 {
          description
            "Up to 8 port numbers separated by white-spaces";
          status obsolete;
          type uint16 {
            range "1..65535";
          }
        }
      }
      container range {
        description
          "Range of maximum 1000 Ports. With IP option use maximum range of 8.";
        status obsolete;
        leaf start-range {
          description
            "Enter Start port number for Range";
          status obsolete;
          type uint16 {
            range "1..65535";
          }
        }
        leaf end-range {
          description
            "Enter Start port number for Range";
          status obsolete;
          type uint16 {
            range "1..65535";
          }
        }
      }
    }
    container port-reopen {
      description
        "ports";
      list port-numbers {
        key "port-number0";
        leaf port-number0 {
          description
            "Up to 8 port numbers separated by white-spaces";
          type uint16 {
            range "1..65535";
          }
        }
        leaf port-number1 {
          description
            "Up to 8 port numbers separated by white-spaces";
          type uint16 {
            range "1..65535";
          }
        }
        leaf port-number2 {
          description
            "Up to 8 port numbers separated by white-spaces";
          type uint16 {
            range "1..65535";
          }
        }
        leaf port-number3 {
          description
            "Up to 8 port numbers separated by white-spaces";
          type uint16 {
            range "1..65535";
          }
        }
        leaf port-number4 {
          description
            "Up to 8 port numbers separated by white-spaces";
          type uint16 {
            range "1..65535";
          }
        }
        leaf port-number5 {
          description
            "Up to 8 port numbers separated by white-spaces";
          type uint16 {
            range "1..65535";
          }
        }
        leaf port-number6 {
          description
            "Up to 8 port numbers separated by white-spaces";
          type uint16 {
            range "1..65535";
          }
        }
        leaf port-number7 {
          description
            "Up to 8 port numbers separated by white-spaces";
          type uint16 {
            range "1..65535";
          }
        }
      }
      container range {
        description
          "Range of maximum 1000 Ports. With IP option use maximum range of 8.";
        leaf start-range {
          description
            "Enter Start port number for Range";
          type uint16 {
            range "1..65535";
          }
        }
        leaf end-range {
          description
            "Enter Start port number for Range";
          type uint16 {
            range "1..65535";
          }
        }
      }
    }
  }

  grouping config-avc-grouping {
    container sd-service {
      description
        "SD-AVC service";
      presence "true";
      leaf segment {
        description
          "Segment name identifying a group of devices sharing the same application services";
        type string;
      }
      container controller {
        description
          "Controller connectivity parameters";
        presence "true";
        container address {
          description
            "Export destination configuration";
          list ipv4 {
            key "ipv4";
            leaf ipv4 {
              description
                "Primary controller's IPv4 address";
              type inet:ipv4-address;
            }
            leaf ipv40 {
              description
                "Secondary controller's IPv4 address or hostname";
              type inet:ipv4-address;
            }
          }
          list ipv4-or-hostname {
            status obsolete;
            key "ipv4-or-hostname";
            leaf ipv4-or-hostname {
              status obsolete;
              description
                "Primary controller's IPv4 address or hostname";
              type inet:host;
            }
            leaf ipv4-or-hostname0 {
              status obsolete;
              description
                "Secondary controller's IPv4 address or hostname";
              type inet:host;
            }
          }
        }
        container hostname {
          description
            "SD-AVC controller hostname";
          list hostname {
            key "hostname";
            leaf hostname {
              description
                "Primary controller's hostname";
              type string;
            }
            leaf hostname0 {
              description
                "Secondary controller's hostname";
              type string;
            }
          }
        }
        container destination-ports {
          description
            "Ports used for communication with controller";
          leaf application-updates {
            description
              "TCP port used for application-updates";
            type uint16 {
              range "1..65535";
            }
          }
          leaf sensor-exporter {
            description
              "UDP port used for sensor messages";
            type uint16 {
              range "1..65535";
            }
          }
        }
        leaf dscp {
          description
            "DSCP marking";
          type uint8 {
            range "0..63";
          }
        }
        container source-interface {
          description
            "Interface of source address used for communication with controller";
          uses ios-ifc:interface-grouping;
        }
        leaf vrf {
          description
            "VRF Label";
          type string;
        }
        container transport {
          description
            "Transport protocols used for communication with controller";
          container application-updates {
            description
              "Transport protocol used for application-updates";
            container http {
              description
                "HTTP protocol";
              presence "true";
              leaf url-prefix {
                description
                  "URL-prefix for application-updates";
                type string;
              }
            }
            container https {
              description
                "HTTPS protocol";
              presence "true";
              leaf url-prefix {
                description
                  "URL-prefix for application-updates";
                type string;
              }
            }
            container ftp {
              description
                "FTP protocol";
              presence "true";
              status obsolete;
              leaf url-prefix {
                description
                  "URL-prefix for application-updates";
                status obsolete;
                type string;
              }
            }
          }
        }
      }
    }
  }

  grouping ip-nbar-attribute-custom-grouping {
    list custom {
      description
        "Custom group to be created for this attribute";
      key "name";
      leaf name {
        description
          "Custom group value";
        type string;
      }
      leaf help {
        description
          "Help string";
        type string;
      }
    }
  }

  grouping config-interface-ip-nbar-grouping {
    container nbar {
      description
        "Network-Based Application Recognition";
      container protocol-discovery {
        description
          "Enable protocol discovery for both ipv4 and ipv6";
        presence "true";
        leaf ipv4-ipv6 {
          status obsolete;
          type enumeration {
            enum ipv4;
            enum ipv6;
          }
        }
      }
    }
  }

  grouping config-interface-ip-nbar-grouping-obsolete {
    container nbar {
      status obsolete;
      description
        "Network-Based Application Recognition";
      container protocol-discovery {
        status obsolete;
        description
          "Enable protocol discovery for both ipv4 and ipv6";
        presence "true";
        leaf ipv4-ipv6 {
          status obsolete;
          type enumeration {
            enum ipv4;
            enum ipv6;
          }
        }
      }
    }
  }

  grouping config-ip-nbar-grouping {
    container nbar {
      description
        "NBAR - Network Based Application Recognition";
      container attribute {
        description
          "Attribute for which custom group value can be created";
        container application-family {
          description
            "Application-family attribute";
          uses ip-nbar-attribute-custom-grouping;
        }
        container application-group {
          description
            "Application-group attribute";
          uses ip-nbar-attribute-custom-grouping;
        }
        container application-set {
          description
            "Application-set attribute";
          uses ip-nbar-attribute-custom-grouping;
        }
        container category {
          description
            "Category attribute";
          uses ip-nbar-attribute-custom-grouping;
        }
        container sub-category {
          description
            "Sub-category attribute";
          uses ip-nbar-attribute-custom-grouping;
        }
      }
      list attribute-map {
        description
          "Attribute Map";
        key "name";
        leaf name {
          type string;
        }
        container attribute {
          description
            "Attribute Name";
          leaf application-family {
            description
              "Application-family attribute";
            type string;
          }
          leaf application-group {
            description
              "Application-group attribute";
            type string;
          }
          leaf application-set {
            description
              "Application-set attribute";
            type string;
          }
          leaf business-relevance {
            description
              "Application business-relevance";
            type string;
          }
          leaf category {
            description
              "Category attribute";
            type string;
          }
          leaf encrypted {
            description
              "Encrypted applications";
            type string;
          }
          leaf p2p-technology {
            description
              "Applications based on p2p-technology";
            status obsolete;
            type string;
          }
          leaf sub-category {
            description
              "Sub-category attribute";
            type string;
          }
          leaf traffic-class {
            description
              "SRND class";
            type string;
          }
          leaf tunnel {
            description
              "Tunnelled applications";
            type string;
          }
        }
      }
      list attribute-set {
        description
          "Set attribute Map";
        key "protocol-name";
        leaf protocol-name {
          description
            "Protocol Name";
          type string;
        }
        leaf profile-name {
          description
            "Attribute Profile Name";
          type leafref {
            path "../../attribute-map/name";
          }
        }
      }
      container classification {
        description
          "NBAR Classification";
        container auto-learn {
          description
            "Statistics on unknown or generic traffic";
          presence "true";
          leaf top-asymmetric-socket {
            description
              "Statistics on asymmetric socket";
            type empty;
          }
          container top-hosts {
            description
              "Statistics on generic traffic per host";
            presence "true";
            leaf sample-rate {
              description
                "configure sampling rate";
              type uint16 {
                range "1..8192";
              }
            }
          }
          container top-ports {
            description
              "Statistics on unknown traffic per port";
            presence "true";
            leaf sample-rate {
              description
                "configure sampling rate";
              type uint16 {
                range "1..8192";
              }
            }
          }
        }
        container dns {
          description
            "dns classification";
          leaf classify-by-domain-with-default {
            description
              "dns classification by domain";
            type boolean;
            default "true";
          }
          leaf classify-by-domain {
            status obsolete;
            description
              "obsolete dns classification by domain";
            type empty;
          }
          container learning {
            description
              "dns learning";
            presence "true";
            leaf guard {
              description
                "dns guard prevents learning from responses only";
              type empty;
            }
            leaf cache-ttl-zero {
              description
                "Cache DNS responses with TTL = 0 for 1 second";
              type boolean;
              default "true";
            }
            leaf domains {
              description
                "Collect domain names";
              type boolean;
              default "true";
            }
          }
        }
        container granularity {
          description
            "Force granularity mode";
          leaf coarse-grain {
            description
              "Force coarse-grain classification mode";
            type empty;
          }
          container fine-grain {
            description
              "Force fine-grain classification mode";
            presence "true";
            container attribute {
              description
                "Force granularity for a single attribute";
              list application-family {
                description
                  "Application-family attribute";
                key "name";
                leaf name {
                  type string;
                }
              }
              list application-group {
                description
                  "Application-group attribute";
                key "name";
                leaf name {
                  type string;
                }
              }
              list application-set {
                description
                  "Application-set attribute";
                key "name";
                leaf name {
                  type string;
                }
              }
              list business-relevance {
                description
                  "Application business-relevance";
                key "name";
                leaf name {
                  type string;
                }
              }
              list category {
                description
                  "Category attribute";
                key "name";
                leaf name {
                  type string;
                }
              }
              list encrypted {
                description
                  "Encrypted applications";
                key "name";
                leaf name {
                  type string;
                }
              }
              list sub-category {
                description
                  "Sub-category attribute";
                key "name";
                leaf name {
                  type string;
                }
              }
              list traffic-class {
                description
                  "SRND class";
                key "name";
                leaf name {
                  type string;
                }
              }
              list tunnel {
                description
                  "Tunnelled applications";
                key "name";
                leaf name {
                  type string;
                }
              }
            }
            container protocol {
              description
                "Force granularity for a single protocol";
              list protocols-list {
                key "name";
                leaf name {
                  type string;
                }
              }
            }
          }
        }
        leaf sampling {
          description
            "Enable NBAR sampling mode";
          type uint8 {
            range "1..100";
          }
          status obsolete;
        }
        container tunneled-traffic {
          description
            "Classify tunneled traffic";
          leaf capwap {
            description
              "Tunnel type CAPWAP";
            type empty;
          }
          leaf ipv6inip {
            description
              "Tunnel type IPv6 in IPv4";
            type empty;
          }
          leaf teredo {
            description
              "Tunnel type TEREDO";
            type empty;
          }
          leaf vxlan {
            description
              "Tunnel type VXLAN";
            type empty;
          }
        }
        leaf ip-traffic {
          type enumeration {
            enum all-caches;
            enum no-caches;
          }
        }
      }
      list custom {
        description
          "Custom PDL (protocol description language) Module";
        key "name";
        leaf name {
          description
            "Name of the User defined Protocol";
          type string;
        }
        container composite {
          description
            "Custom protocols based on multiple underlying protocols";
          list server-name {
            description
              "Match the server name based on various protocols";
            key "name";
            leaf name {
              description
                "Enter String Format - cannot exceed 30 characters";
              type string;
            }
            leaf id {
              description
                "Enter Selector ID";
              type uint16 {
                range "1..65535";
              }
            }
            leaf extends {
              description
                "Extend existing protocol";
              type string;
            }
          }
        }
        container dns {
          description
            "Custom protocols based on dns parameters";
          list domain-name {
            description
              "Domain name";
            key "name";
            leaf name {
              description
                "Enter String Format - cannot exceed 30 characters";
              type string;
            }
            leaf id {
              description
                "Selector ID";
              type uint16 {
                range "1..65535";
              }
            }
            leaf extends {
              description
                "Extend existing protocol";
              type string;
            }
          }
        }
        container http {
          description
            "Custom protocols based on http parameters";
          leaf cookie {
            description
              "HTTP Cookie";
            type string;
          }
          leaf host {
            description
              "Host name of Origin Server containing resource";
            type string;
          }
          leaf method {
            description
              "HTTP method";
            type string;
          }
          leaf referer {
            description
              "Address the resource request was obtained from";
            type string;
          }
          choice http-uv {
            case url-case {
              leaf url {
                description
                  "Uniform Resource Locator path";
                type string;
              }
            }
            case user-agent-case {
              leaf user-agent {
                description
                  "Software used by agent sending the request";
                type string;
              }
            }
            case version-case {
              leaf version {
                description
                  "HTTP version";
                type string;
              }
            }
            case via-case {
              leaf via {
                description
                  "HTTP via field";
                type string;
              }
            }
          }
          leaf id {
            description
              "Selector ID";
            type uint16 {
              range "1..65535";
            }
          }
        }
        container ssl {
          description
            "Custom protocols based on ssl parameters";
          list unique-name {
            description
              "SSL Server Name Indication (SNI) or Common Name (CN)";
            key "name";
            leaf name {
              description
                "Enter String Format - cannot exceed 30 characters";
              type string;
            }
            leaf id {
              description
                "Enter Selector ID";
              type uint16 {
                range "1..65535";
              }
            }
          }
        }
        container transport {
          description
            "Custom protocols based on the transport layer and below";
          container tcp {
            description
              "TCP transport";
            presence "true";
            leaf id {
              description
                "Selector ID";
              type uint16 {
                range "1..65535";
              }
            }
            uses config-custom-grouping;
          }
          container udp {
            description
              "UDP transport";
            presence "true";
            leaf id {
              description
                "Selector ID";
              type uint16 {
                range "1..65535";
              }
            }
            uses config-custom-grouping;
          }
          container udp-tcp {
            description
              "UDP or TCP transport";
            presence "true";
            leaf id {
              description
                "Selector ID";
              type uint16 {
                range "1..65535";
              }
            }
            uses config-custom-grouping;
          }
        }
        container ip {
          description
            "Custom protocols based on the transport layer and below";
          container any {
            description
              "TCP transport";
            presence "true";
            leaf id {
              description
                "Selector ID";
              type uint16 {
                range "1..65535";
              }
            }
            uses config-custom-grouping;
          }
        }
      }
      container protocol-pack {
        description
          "Protocol Pack";
        list filepath {
          key "filepath";
          leaf filepath {
            description
              "Path of protocol pack to load";
            type string;
          }
          leaf force {
            description
              "Force";
            type empty;
          }
        }
      }
      container protocol-map {
        status deprecated;
        description
          "Protocol map";
        list id_and_name {
          status deprecated;
          key "protoname";
          leaf protoname {
            status deprecated;
            description
              "protocol name";
            type string;
          }
          leaf id {
            status deprecated;
            description
              "protocol id";
            type uint16 {
              range "1..65535";
            }
          }
        }
      }
      list protocol-map-list {
        description
          "Protocol map";
        key "protoname";
        leaf protoname {
          description
            "protocol name";
          type string;
        }
        leaf id {
          description
            "protocol id";
          mandatory true;
          type uint16 {
            range "1..65535";
          }
        }
      }
      container resources {
        status obsolete;
        description
          "NBAR resources";
        container flow {
          status obsolete;
          description
            "Flow details";
          leaf max-session {
            status obsolete;
            description
              "Max allowed session";
            type uint32 {
              range "50000..10000000";
            }
          }
        }
        list protocol {
          status obsolete;
          description
            "Protocol resources";
          key "protocol-name";
          leaf protocol-name {
            status obsolete;
            description
              "Protocol Name";
            type string;
          }
          leaf link-age {
            status obsolete;
            description
              "Link age greater than system link age (secs.)";
            type uint32 {
              range "1..100000000";
            }
          }
        }
      }
      leaf http-services {
        description
          "Enable HTTP services";
        type empty;
      }
    }
  }

  augment "/ios:native/ios:ip" {
    uses config-ip-nbar-grouping;
  }

  augment "/ios:native/ios:interface/ios:FastEthernet/ios:ip" {
    uses config-interface-ip-nbar-grouping;
  }

  augment "/ios:native/ios:interface/ios:GigabitEthernet/ios:ip" {
    uses config-interface-ip-nbar-grouping;
  }

  augment "/ios:native/ios:interface/ios:TenGigabitEthernet/ios:ip" {
    uses config-interface-ip-nbar-grouping;
  }

  augment "/ios:native/ios:interface/ios:FiveGigabitEthernet/ios:ip" {
    uses config-interface-ip-nbar-grouping;
  }

  augment "/ios:native/ios:interface/ios:AppGigabitEthernet/ios:ip" {
    uses config-interface-ip-nbar-grouping;
  }

  augment "/ios:native/ios:interface/ios:TwentyFiveGigabitEthernet/ios:ip" {
    uses config-interface-ip-nbar-grouping-obsolete;
  }

  augment "/ios:native/ios:interface/ios:TwentyFiveGigE/ios:ip" {
    uses config-interface-ip-nbar-grouping;
  }

  augment "/ios:native/ios:interface/ios:TwoGigabitEthernet/ios:ip" {
    uses config-interface-ip-nbar-grouping;
  }

  augment "/ios:native/ios:interface/ios:FortyGigabitEthernet/ios:ip" {
    uses config-interface-ip-nbar-grouping;
  }

  augment "/ios:native/ios:interface/ios:HundredGigE/ios:ip" {
    uses config-interface-ip-nbar-grouping;
  }

  augment "/ios:native/ios:interface/ios:Port-channel/ios:ip" {
    uses config-interface-ip-nbar-grouping;
  }

  augment "/ios:native/ios:interface/ios:Port-channel-subinterface/ios:Port-channel/ios:ip" {
    uses config-interface-ip-nbar-grouping;
  }

  augment "/ios:native/ios:interface/ios:Loopback/ios:ip" {
    uses config-interface-ip-nbar-grouping;
  }

  augment "/ios:native/ios:interface/ios:Tunnel/ios:ip" {
    uses config-interface-ip-nbar-grouping;
  }

  augment "/ios:native/ios:interface/ios:Vlan/ios:ip" {
    uses config-interface-ip-nbar-grouping;
  }

  augment "/ios:native/ios:interface/ios:Serial/ios:ip" {
    uses config-interface-ip-nbar-grouping;
  }

  augment "/ios:native/ios:interface/ios:Multilink/ios:ip" {
    uses config-interface-ip-nbar-grouping;
  }

  augment "/ios:native/ios:interface/ios:Cellular/ios:ip" {
    uses config-interface-ip-nbar-grouping;
  }

  augment "/ios:native/ios:interface/ios:Service-Engine/ios:ip" {
    uses config-interface-ip-nbar-grouping;
  }

  augment "/ios:native/ios:interface/ios:Embedded-Service-Engine/ios:ip" {
    uses config-interface-ip-nbar-grouping;
  }

  augment "/ios:native/ios:interface/ios:ATM/ios:ip" {
    uses config-interface-ip-nbar-grouping;
  }

  augment "/ios:native/ios:interface/ios:Dialer/ios:ip" {
    uses config-interface-ip-nbar-grouping;
  }

  augment "/ios:native/ios:interface/ios:LISP/ios:ip" {
    uses config-interface-ip-nbar-grouping;
  }

  augment "/ios:native/ios:interface/ios:Ethernet/ios:ip" {
    uses config-interface-ip-nbar-grouping;
  }

  augment "/ios:native/ios:interface/ios:Virtual-Template/ios:ip" {
    uses config-interface-ip-nbar-grouping;
  }

  augment "/ios:native/ios:avc" {
    uses config-avc-grouping;
  }
}
