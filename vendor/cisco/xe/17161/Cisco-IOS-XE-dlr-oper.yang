module Cisco-IOS-XE-dlr-oper {
  yang-version 1.1;
  namespace "http://cisco.com/ns/yang/Cisco-IOS-XE-dlr-oper";
  prefix dlr-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for DLR operational data.
     Copyright (c) 2023 by Cisco Systems, Inc.
     All rights reserved.";

  revision 2023-11-01 {
    description
      "Initial revision";
    reference
      "1.0.0";
    cisco-semver:module-version "1.0.0";
  }

  typedef dlr-device-mode {
    type enumeration {
      enum dlr-active-supervisor-mode {
        value 0;
        description
          "DLR Ring is in Active Supervisor mode";
      }
      enum dlr-backup-supervisor-mode {
        value 1;
        description
          "DLR Ring is in Backup Supervisor mode";
      }
      enum dlr-beacon-node-mode {
        value 2;
        description
          "DLR Ring is in beacon-node mode";
      }
    }
    description
      "Device mode in DLR Ring";
  }

  typedef dlr-nw-topo {
    type enumeration {
      enum dlr-topology-linear {
        value 0;
        description
          "DLR topology is open";
      }
      enum dlr-topology-ring {
        value 1;
        description
          "DLR topology is closed";
      }
    }
    description
      "Network Topology in DLR Ring";
  }

  typedef dlr-nw-status {
    type enumeration {
      enum dlr-network-normal {
        value 0;
        description
          "DLR ring status is normal";
      }
      enum dlr-network-fault {
        value 1;
        description
          "DLR ring status is fault";
      }
      enum dlr-network-unexpected-loop {
        value 2;
        description
          "DLR ring has detected unexpected loop";
      }
      enum dlr-network-partial-fault {
        value 3;
        description
          "DLR ring is in partial network fault";
      }
      enum dlr-network-rapid-fault {
        value 4;
        description
          "DLR ring has detected rapid fault/restore cycle";
      }
    }
    description
      "Network status of DLR Ring";
  }

  typedef dlr-device-state {
    type enumeration {
      enum dlr-supervisor-idle-state {
        value 0;
        description
          "DLR Supervisor in Idle state";
      }
      enum dlr-backup-supervisor-fault-state {
        value 1;
        description
          "DLR Backup Supervisor in Fault state";
      }
      enum dlr-backup-supervisor-normal-state {
        value 2;
        description
          "DLR Backup Supervisor in Normal state";
      }
      enum dlr-active-supervisor-fault-state {
        value 3;
        description
          "DLR Active Supervisor in Fault state";
      }
      enum dlr-active-supervisor-normal-state {
        value 4;
        description
          "DLR Active Supervisor in Normal state";
      }
      enum dlr-supervisor-mode-not-supported {
        value 5;
        description
          "DLR Supervisor mode not supported";
      }
      enum dlr-supervisor-rapid-fault-state {
        value 6;
        description
          "DLR Supervisor in Rapid Fault state";
      }
      enum dlr-supervisor-partial-fault-state {
        value 7;
        description
          "DLR Supervisor in Partial Fault state";
      }
      enum dlr-supervisor-none-state {
        value 8;
        description
          "DLR Supervisor in None state";
      }
      enum dlr-beacon-node-idle-state {
        value 9;
        description
          "DLR beacon node in Idle state";
      }
      enum dlr-beacon-node-fault-state {
        value 10;
        description
          "DLR beacon node in Fault state";
      }
      enum dlr-beacon-node-normal-state {
        value 11;
        description
          "DLR beacon node in Normal state";
      }
      enum dlr-beacon-node-none-state {
        value 12;
        description
          "DLR beacon node in None state";
      }
      enum dlr-beacon-node-invalid-state {
        value 13;
        description
          "DLR beacon node in Invalid state";
      }
    }
    description
      "DLR device state";
  }

  typedef dlr-gw-status {
    type enumeration {
      enum dlr-status-non-gateway {
        value 0;
        description
          "Non-gateway device";
      }
      enum dlr-status-backup-gateway {
        value 1;
        description
          "DLR backup gateway";
      }
      enum dlr-status-active-gateway {
        value 2;
        description
          "DLR active gateway";
      }
      enum dlr-status-fault {
        value 3;
        description
          "DLR gateway fault";
      }
      enum dlr-status-not-support-gateway {
        value 4;
        description
          "DLR gateway not supported";
      }
      enum dlr-gateway-partial-network-fault {
        value 5;
        description
          "DLR gateway partial network fault";
      }
    }
    description
      "DLR gateway status";
  }

  grouping dlr-ring-port {
    description
      "Information of ports configured in the DLR Ring";
    leaf if-name {
      type string;
      description
        "Name of DLR port";
    }
    leaf vlan-id {
      type uint32;
      description
        "VLAN identity associated with the port";
    }
    leaf link-state {
      type boolean;
      description
        "State of the port belonging to the DLR Ring";
    }
    leaf lbrp {
      type boolean;
      description
        "Last Beacon Received Port";
    }
  }

  grouping dlr-sup-params {
    description
      "DLR Supervisor parameters";
    leaf beacon-intvl {
      type uint32;
      units "microseconds";
      description
        "beacon interval in microseconds";
    }
    leaf beacon-timeout {
      type uint32;
      units "microseconds";
      description
        "beacon timeout in microseconds";
    }
    leaf dlr-vlan-id {
      type uint32;
      description
        "DLR VLAN identity";
    }
    leaf precedence {
      type uint32;
      description
        "Supervisor precedence";
    }
  }

  grouping dlr-node-id {
    description
      "DLR device identity";
    leaf node-mac-addr {
      type yang:mac-address;
      description
        "DLR Device MAC address";
    }
    leaf node-ip-addr {
      type inet:ip-address;
      description
        "DLR Device IP address";
    }
  }

  grouping dlr-fault-stats {
    description
      "DLR ring fault statistics";
    leaf num-faults {
      type uint32;
      description
        "Number of ring faults since last power up";
    }
    leaf last-fault-time {
      type yang:date-and-time;
      description
        "Time of last ring fault";
    }
  }

  grouping dlr-gw-params {
    description
      "DLR gateway parameters";
    leaf ad-intvl {
      type uint32;
      units "microseconds";
      description
        "Gateway advertisement interval in microseconds";
    }
    leaf ad-timeout {
      type uint32;
      units "microseconds";
      description
        "Gateway advertisement timeout in microseconds";
    }
    leaf precedence {
      type uint32;
      description
        "Gateway precedence";
    }
    leaf lrn-update {
      type boolean;
      description
        "Gateway learning update feature";
    }
  }

  grouping dlr-ring-summary {
    description
      "Summary of the DLR Ring parameters";
    leaf dlr-ring-id {
      type uint32;
      description
        "DLR ring identity";
    }
    leaf mode {
      type dlr-ios-xe-oper:dlr-device-mode;
      description
        "DLR mode of device";
    }
    leaf topo {
      type dlr-ios-xe-oper:dlr-nw-topo;
      description
        "DLR network topology";
    }
    leaf ring-status {
      type dlr-ios-xe-oper:dlr-nw-status;
      description
        "DLR ring status";
    }
    leaf device-state {
      type dlr-ios-xe-oper:dlr-device-state;
      description
        "DLR device state";
    }
    container my-node-id {
      description
        "Current device identity";
      uses dlr-ios-xe-oper:dlr-node-id;
    }
    list ring-port {
      description
        "DLR ring ports";
      uses dlr-ios-xe-oper:dlr-ring-port;
    }
    container active-sup-params {
      description
        "DLR active Supervisor parameters";
      uses dlr-ios-xe-oper:dlr-sup-params;
    }
    container active-sup-id {
      description
        "Device identity of Active Supervisor node";
      uses dlr-ios-xe-oper:dlr-node-id;
    }
    container local-sup-params {
      description
        "Current device Supervisor parameters";
      uses dlr-ios-xe-oper:dlr-sup-params;
    }
    leaf ring-partpnt-count {
      type uint8;
      description
        "Number of nodes participating in the ring";
    }
    list ring-partpnt-id {
      description
        "Device identities of all the participant nodes";
      uses dlr-ios-xe-oper:dlr-node-id;
    }
    container ring-fault-stats {
      description
        "DLR ring fault statistics";
      uses dlr-ios-xe-oper:dlr-fault-stats;
    }
    container last-active-node-on-p1 {
      description
        "Last node on P1 side that is reachable";
      uses dlr-ios-xe-oper:dlr-node-id;
    }
    container last-active-node-on-p2 {
      description
        "Last node on P2 side that is reachable";
      uses dlr-ios-xe-oper:dlr-node-id;
    }
    leaf gw-status {
      type dlr-ios-xe-oper:dlr-gw-status;
      description
        "DLR gateway status";
    }
    leaf-list uplink-port-if-name {
      type string;
      ordered-by user;
      description
        "DLR gateway/uplink ports";
    }
    container active-gw-params {
      description
        "DLR Active gateway parameters";
      uses dlr-ios-xe-oper:dlr-gw-params;
    }
    container active-gw-id {
      description
        "DLR Active gateway device identity";
      uses dlr-ios-xe-oper:dlr-node-id;
    }
    container gw-fault-stats {
      description
        "DLR gateway fault statistics";
      uses dlr-ios-xe-oper:dlr-fault-stats;
    }
    container local-gw-params {
      description
        "DLR local gateway parameters";
      uses dlr-ios-xe-oper:dlr-gw-params;
    }
  }

  container dlr-oper-data {
    config false;
    description
      "DLR operational data";
    list dlr-ring-summary {
      key "dlr-ring-id";
      description
        "Summary of the DLR Ring parameters";
      uses dlr-ios-xe-oper:dlr-ring-summary;
    }
  }
}
