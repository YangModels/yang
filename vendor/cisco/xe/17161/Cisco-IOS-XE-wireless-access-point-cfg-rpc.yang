module Cisco-IOS-XE-wireless-access-point-cfg-rpc {
  yang-version 1.1;
  namespace "http://cisco.com/ns/yang/Cisco-IOS-XE-wireless-access-point-cfg-rpc";
  prefix wireless-access-point-cfg-rpc;

  import Cisco-IOS-XE-wireless-enum-types {
    prefix wireless-enum-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2019-2023 by Cisco Systems, Inc.
     All rights reserved.";

  revision 2024-07-01 {
    description
      "- Added ranging support for group of APs";
    reference
      "6.1.0";
    cisco-semver:module-version "6.1.0";
  }
  revision 2024-03-01 {
    description
      "- Added a range constraint for floor parameter in set-ap-floor RPC";
    reference
      "6.0.0";
    cisco-semver:module-version "6.0.0";
  }
  revision 2023-11-01 {
    description
      "- Added AP ranging band";
    reference
      "5.1.0";
    cisco-semver:module-version "5.1.0";
  }
  revision 2023-07-01 {
    description
      "- Added RPC to configure AP coordinate, floor and ranging
       - Added must constraint on leaf slot-id within container set-ap-slot-admin-state";
    reference
      "5.0.0";
    cisco-semver:module-version "5.0.0";
  }
  revision 2023-03-01 {
    description
      "- Modified mandatory leafs Sniffer IP address and Sniffer Channel in dual-band-role to non-mandatory
       - Added range constraint for LED brightness level
       - Added change in band range to support 6 GHz
       - Added range constraint for leaf vlan-id
       - Deprecated configuring new channel using 802.11h channel announcement
       - Added range constraint for leaf external-antenna-gain
       - Added must condition to antenna selection set RPC to avoid invalid combination of band and slot-id values
       - Deprecated RPC set-rad-slot-phy-ht-chan
       - Deprecated RPC set-ap-cleanair
       - Added range constraint for BSS color mode RPC
       - Added constraint to set auto RF RPC to avoid invalid combination of band and slot-id
       - Added must constraint to set dual radio mode RPC
       - Modified band as optional input for FRA revert RPC";
    reference
      "4.5.0";
    cisco-semver:module-version "4.5.0";
  }
  revision 2022-11-01 {
    description
      "- Update yang-version to 1.1
       - Added RPC to configure BSS color mode
       - Added RPC to configure channel mode
       - Added RPC to configure dot11n antenna selection
       - Added RPC to configure channel width
       - Added RPC for FRA configuration to configure XOR TX RX radios.";
    reference
      "4.4.0";
    cisco-semver:module-version "4.4.0";
  }
  revision 2022-07-01 {
    description
      "- Added RPC for dual band channel configuration
       - Added RPC for dual radio mode configuration
       - Added RPC for BSS color mode configuration
       - Added rpc set-ap-band-cleanair to enable cleanair in access point
       - Added RPC for channel configuration and to configure new channel using 802.11h channel announcement.
       - Added RPC for AP reset and mDNS AP config
       - Added rpc set-ap-indoor-enable to configure AP indoor mode
       - Added RPC for AP VLAN tagging configuration";
    reference
      "4.3.0";
    cisco-semver:module-version "4.3.0";
  }
  revision 2022-03-01 {
    description
      "- Added RPC to configure dual-band radio role
       - Added RPC to configure AP sensor admin state
       - Modified band and channel range of dual-band-role";
    reference
      "4.2.0";
    cisco-semver:module-version "4.2.0";
  }
  revision 2021-11-01 {
    description
      "Added AP LED flash configuration";
    reference
      "4.1.0";
    cisco-semver:module-version "4.1.0";
  }
  revision 2021-07-01 {
    description
      "- Modified slot and band range on applicable paths
       - Added option to configure either name or IP address in rpc set-ap-controller";
    reference
      "4.0.0";
    cisco-semver:module-version "4.0.0";
  }
  revision 2021-03-01 {
    description
      "- Changed the pattern for AP name, location and country code.
       - Added AP LAN port configuration";
    reference
      "3.0.0";
    cisco-semver:module-version "3.0.0";
  }
  revision 2020-07-01 {
    description
      "- Added rpc set-ap-controller to configure controller information in access point
       - Added rpc set-ap-cleanair to enable cleanair in access point
       - Added rpc set-ap-slot-phy-ht-customize to configure auto channel selection in access point
       - Added rpc set-ap-slot-phy-ht-chan to configure static channel
       - Added rpc set-ap-mode to configure AP mode.
       - Added must constraint for antenna-band-mode
       - Added range restrictions on leafs slot-id and band on all applicable paths.";
    reference
      "2.0.0";
    cisco-semver:module-version "2.0.0";
  }
  revision 2020-03-01 {
    description
      "Initial revision";
    reference
      "1.0.0";
    cisco-semver:module-version "1.0.0";
  }

  typedef ap-identifier {
    type enumeration {
      enum ap-identifier-name {
        value 0;
        description
          "Alternative AP name";
      }
      enum ap-identifier-mac-address {
        value 1;
        description
          "Alternative MAC address";
      }
    }
    description
      "Access point identifier";
  }

  grouping set-ap-vlan-tag {
    description
      "Configures VLAN tagging for non-bridge AP";
    leaf vlan-id {
      type uint32 {
        range "0..4094";
      }
      mandatory true;
      description
        "Configure VLAN-ID";
    }
    choice alternative-choice {
      mandatory true;
      description
        "AP name or AP MAC address";
      case ap-identifier-name {
        leaf ap-name {
          type string;
          mandatory true;
          description
            "AP name for VLAN tagging";
        }
      }
      case ap-identifier-mac-address {
        leaf mac-addr {
          type yang:mac-address;
          mandatory true;
          description
            "MAC address of AP for VLAN tagging";
        }
      }
    }
  }

  grouping set-ap-vlan-tag-all {
    description
      "Configure VLAN tagging for all non-bridge APs";
    leaf vlan-id {
      type uint32 {
        range "0..4094";
      }
      mandatory true;
      description
        "Configure VLAN ID. VLAN ID 0 will disable VLAN tagging for all non-bridge APs";
    }
  }

  grouping set-ap-monitor-mode-chnl-optimize {
    description
      "Channel scanning optimization for AP";
    leaf mode {
      type wireless-enum-types:lomm-mode-type;
      mandatory true;
      description
        "Select AP mode (none, tracking mode, WIPS mode, all)";
    }
    choice alternative-choice {
      mandatory true;
      description
        "AP name or AP MAC address";
      case ap-identifier-name {
        leaf ap-name {
          type string;
          mandatory true;
          description
            "AP name for channel scanning optimization";
        }
      }
      case ap-identifier-mac-address {
        leaf mac-addr {
          type yang:mac-address;
          mandatory true;
          description
            "MAC address of AP for channel scanning optimization";
        }
      }
    }
  }

  grouping set-ap-mode {
    description
      "Configures AP mode";
    leaf clear-mode {
      type boolean;
      description
        "Restores AP to site tag mode";
    }
    leaf mode {
      type wireless-types:enm-ewlc-spam-ap-modes;
      must "(../clear-mode = 'false')" {
        error-message "disable clear mode while configuring mode.";
        error-app-tag "must-violation";
      }
      must "(../mode != 'mode-sensor')" {
        error-message "Sensor mode not supported";
        error-app-tag "must-violation";
      }
      description
        "Specifies mode of AP";
    }
    choice alternative-choice {
      mandatory true;
      description
        "AP name or AP MAC address";
      case ap-identifier-name {
        leaf ap-name {
          type string;
          mandatory true;
          description
            "Name of AP to configure AP mode";
        }
      }
      case ap-identifier-mac-address {
        leaf mac-addr {
          type yang:mac-address;
          mandatory true;
          description
            "MAC address of AP to configure AP mode";
        }
      }
    }
  }

  grouping set-lrad-led-state {
    description
      "Configure LED state for Cisco AP";
    leaf ledstate {
      type boolean;
      mandatory true;
      description
        "Led state of AP can be enabled (true) or disabled (false)";
    }
    choice alternative-choice {
      mandatory true;
      description
        "AP name or AP MAC address";
      case ap-identifier-name {
        leaf ap-name {
          type string;
          mandatory true;
          description
            "Name of AP to configure LED state";
        }
      }
      case ap-identifier-mac-address {
        leaf mac-addr {
          type yang:mac-address;
          mandatory true;
          description
            "MAC address of AP to configure LED state";
        }
      }
    }
  }

  grouping set-lrad-led-flash {
    description
      "AP LED flash configuration";
    leaf flash-sec {
      when "../config-type = 'set-led-flash-duration'";
      type uint16 {
        range "0 .. 3600";
      }
      units "seconds";
      mandatory true;
      description
        "LED flashing duration";
    }
    leaf led-flash-state {
      when "../config-type = 'set-led-flash-state'";
      type boolean;
      mandatory true;
      description
        "LED flash can be enabled (true) or disabled (false)";
    }
    leaf config-type {
      type wireless-enum-types:enm-led-flash-config-type;
      mandatory true;
      description
        "LED flash parameter to configure";
    }
    choice alternative-choice {
      mandatory true;
      description
        "AP name or AP MAC address";
      case ap-identifier-name {
        leaf ap-name {
          type string;
          mandatory true;
          description
            "Name of AP to configure LED flash";
        }
      }
      case ap-identifier-mac-address {
        leaf mac-addr {
          type yang:mac-address;
          mandatory true;
          description
            "MAC address of AP to configure LED flash";
        }
      }
    }
  }

  grouping set-ap-location {
    description
      "Configure AP location";
    leaf location {
      type string {
        length "1..256";
        pattern '[ -~]+';
      }
      mandatory true;
      description
        "AP location (example sector A or room A)";
    }
    choice alternative-choice {
      mandatory true;
      description
        "AP name or AP MAC address";
      case ap-identifier-name {
        leaf ap-name {
          type string;
          mandatory true;
          description
            "AP name for location change";
        }
      }
      case ap-identifier-mac-address {
        leaf mac-addr {
          type yang:mac-address;
          mandatory true;
          description
            "MAC address of AP for location change";
        }
      }
    }
  }

  grouping set-ap-name {
    description
      "Configure a new AP name";
    leaf name {
      type string {
        length "1..32";
        pattern '[!-~]+';
      }
      mandatory true;
      description
        "New AP name";
    }
    choice alternative-choice {
      mandatory true;
      description
        "AP name or AP MAC address";
      case ap-identifier-name {
        leaf ap-name {
          type string;
          mandatory true;
          description
            "Existing name of AP to be renamed";
        }
      }
      case ap-identifier-mac-address {
        leaf mac-addr {
          type yang:mac-address;
          mandatory true;
          description
            "MAC address of AP to be renamed";
        }
      }
    }
  }

  grouping set-ap-antenna-band-mode {
    description
      "Configure antenna band mode";
    leaf band-val {
      type wireless-enum-types:ant-band-mode;
      must "../band-val != 'ant-band-mode-unknown'" {
        error-message "ant-band-mode-unknown is not permitted";
        error-app-tag "must-violation";
      }
      mandatory true;
      description
        "Band value can be single or dual";
    }
    choice alternative-choice {
      mandatory true;
      description
        "AP name or AP MAC address";
      case ap-identifier-name {
        leaf ap-name {
          type string;
          mandatory true;
          description
            "Name of AP to configure the antenna band mode";
        }
      }
      case ap-identifier-mac-address {
        leaf mac-addr {
          type yang:mac-address;
          mandatory true;
          description
            "MAC address of AP to configure the antenna band mode";
        }
      }
    }
  }

  grouping set-ap-country {
    description
      "Configure the country of operation";
    leaf country-string {
      type string {
        length "1..4";
        pattern '[ -~]+';
      }
      mandatory true;
      description
        "Country code for country of operation (i.e. US for United States)";
    }
    choice alternative-choice {
      mandatory true;
      description
        "Alternative AP name and MAC address";
      case ap-identifier-name {
        leaf ap-name {
          type string;
          mandatory true;
          description
            "AP name for configuring country of operation";
        }
      }
      case ap-identifier-mac-address {
        leaf mac-addr {
          type yang:mac-address;
          mandatory true;
          description
            "MAC address of AP for configuring country of operation";
        }
      }
    }
  }

  grouping set-11-hphy-ofdm-chan {
    description
      "Configures new channel using 802.11h channel announcement";
    leaf chan {
      type uint32 {
        range "0..233";
      }
      mandatory true;
      description
        "Channel number
         1 - 173: Dual band
         1 - 14: 2.4 GHz
         36 - 173: 5 Ghz
         1 - 233 : 6 Ghz";
    }
    leaf slot-id {
      type uint8 {
        range "1..3";
      }
      mandatory true;
      description
        "Slot ID of AP to configure new channel ";
    }
    choice alternative-choice {
      mandatory true;
      description
        "AP name or AP MAC address";
      case ap-identifier-name {
        leaf ap-name {
          type string;
          mandatory true;
          description
            "Name of AP to configure channel number";
        }
      }
      case ap-identifier-mac-address {
        leaf mac-addr {
          type yang:mac-address;
          mandatory true;
          description
            "MAC address of AP to configure channel number";
        }
      }
    }
  }

  grouping set-ap-slot-ext-antenna-gain {
    description
      "Configures the external antenna gain of AP";
    leaf external-antenna-gain {
      type uint8 {
        range "0..40";
      }
      units "dBm";
      mandatory true;
      description
        "External antenna gain value in multiple of .5 decibel isotropic units (i.e. An integer value 4 means 4 x 0.5 = 2 decibel isotropic units of gain)";
    }
    leaf slot-id {
      type uint8 {
        range "0..3";
      }
      mandatory true;
      description
        "Slot ID of AP to configure the external antenna gain. Valid value range is 0-3";
    }
    leaf band {
      when '(current()/../slot-id = 3)';
      type wireless-enum-types:enm-radio-band;
      default "band-6-ghz";
      description
        "Radio frequency band to configure external antenna gain.
         1 - 2.4 GHz
         2 - 5 GHz
         3 - Dual band
         4 - 6 Ghz";
    }
    choice alternative-choice {
      mandatory true;
      description
        "AP name or AP MAC address";
      case ap-identifier-name {
        leaf ap-name {
          type string;
          mandatory true;
          description
            "Name of AP to configure the external antenna gain";
        }
      }
      case ap-identifier-mac-address {
        leaf mac-addr {
          type yang:mac-address;
          mandatory true;
          description
            "MAC address of AP to configure the external antenna gain";
        }
      }
    }
  }

  grouping set-rad-slot-phy-ht-chan {
    description
      "Configures Radio channel";
    leaf chan {
      type uint8 {
        range "0..233";
      }
      mandatory true;
      description
        "Channel number
         1 - 173: Dual band
         1 - 14: 2.4 GHz
         36 - 173: 5 Ghz
         1 - 233 : 6 Ghz";
    }
    leaf slot-id {
      type uint8 {
        range "0..3";
      }
      mandatory true;
      description
        "Slot ID of AP to configure channel number";
    }
    leaf band {
      type uint32 {
        range "1..4";
      }
      mandatory true;
      description
        "Band of AP to configure channel number
         1 - 2.4 GHz
         2 - 5 GHz
         3 - Dual band
         4 - 6 GHz";
    }
    choice alternative-choice {
      mandatory true;
      description
        "AP name or AP MAC address";
      case ap-identifier-name {
        leaf ap-name {
          type string;
          mandatory true;
          description
            "Name of AP to configure channel number";
        }
      }
      case ap-identifier-mac-address {
        leaf mac-addr {
          type yang:mac-address;
          mandatory true;
          description
            "MAC address of AP to configure channel number";
        }
      }
    }
  }

  grouping set-ap-slot-phy-ht-chan {
    description
      "Configures static channel on a radio interface of AP";
    leaf chan {
      type uint8;
      mandatory true;
      description
        "Specifies channel number";
    }
    leaf slot-id {
      type uint8 {
        range "0..2";
      }
      mandatory true;
      description
        "Specifies slot id of a radio band";
    }
    leaf band {
      type wireless-enum-types:enm-radio-band;
      must "current() != 'band-dualband-radio'" {
        error-message "Dual band is not supported for this action";
        error-app-tag "must-violation";
      }
      mandatory true;
      description
        "Specifies radio band information of access point";
    }
    choice alternative-choice {
      mandatory true;
      description
        "AP name or AP MAC address";
      case ap-identifier-name {
        leaf ap-name {
          type string;
          mandatory true;
          description
            "Name of AP to configure static channel";
        }
      }
      case ap-identifier-mac-address {
        leaf mac-addr {
          type yang:mac-address;
          mandatory true;
          description
            "Mac address of AP to configure static channel";
        }
      }
    }
  }

  grouping set-ap-slot-phy-ht-customize {
    description
      "Enables auto channel selection for a radio band of access point";
    leaf slot-id {
      type uint8 {
        range "0 .. 3";
      }
      must "((../band = 'band-2-dot-4-ghz' and current() != '1' and current() != '2' and current() != '3') or (../band != 'band-2-dot-4-ghz')) and
            ((../band = 'band-5-ghz' and current() != '0' and current() != '3') or (../band != 'band-5-ghz')) and
            ((../band = 'band-dualband-radio' and current() != '1' and current() != '3') or (../band != 'band-dualband-radio')) and
            ((../band = 'band-6-ghz' and current() != '0' and current() != '1') or (../band != 'band-6-ghz'))" {
        error-message "Invalid combination of band and slot-id";
        error-app-tag "must-violation";
      }
      mandatory true;
      description
        "Specifies slot id of a radio band";
    }
    leaf band {
      type wireless-enum-types:enm-radio-band;
      must "current() != 'band-dualband-radio'" {
        error-message "Dual band is not supported for this action";
        error-app-tag "must-violation";
      }
      mandatory true;
      description
        "Specifies radio band information of access point";
    }
    choice alternative-choice {
      mandatory true;
      description
        "AP name or AP MAC address";
      case ap-identifier-name {
        leaf ap-name {
          type string;
          mandatory true;
          description
            "Name of AP to configure auto channel selection";
        }
      }
      case ap-identifier-mac-address {
        leaf mac-addr {
          type yang:mac-address;
          mandatory true;
          description
            "MAC address of AP to configure auto selection";
        }
      }
    }
  }

  grouping set-ap-cleanair {
    description
      "Configures clean air functionality on radio band of access point";
    leaf mode {
      type boolean;
      mandatory true;
      description
        "Enables/Disables clear air functionality";
    }
    leaf slot-id {
      type uint8 {
        range "0..2";
      }
      mandatory true;
      description
        "Specifies slot id of a radio band";
    }
    choice alternative-choice {
      mandatory true;
      description
        "AP name or AP MAC address";
      case ap-identifier-name {
        leaf ap-name {
          type string;
          mandatory true;
          description
            "Name of AP to configure clean air";
        }
      }
      case ap-identifier-mac-address {
        leaf mac-addr {
          type yang:mac-address;
          mandatory true;
          description
            "MAC address of AP to configure clean air";
        }
      }
    }
  }

  grouping set-rad-slot-dual-radio-mode {
    description
      "Configures the 802.11a dual-radio mode";
    leaf mode {
      type uint8 {
        range "0..2";
      }
      must "((../dual-radio-mode-op = '1' and current() != '1'  and current() != '2') or
             (../dual-radio-mode-op != '1') )" {
        error-message "Dual radio mode can be enabled/disabled only when dual radio mode of operation is selected as manual";
        error-app-tag "must-violation";
      }
      mandatory true;
      description
        "DUAL RADIO MODE status
           0 - None
           1 - Enable
           2 - Disable";
    }
    leaf dual-radio-mode-op {
      type uint8 {
        range "0..2";
      }
      mandatory true;
      description
        "DUAL RADIO MODE operation
           0 - None
           1 - Auto
           2 - Manual";
    }
    leaf slot-id {
      type uint8 {
        range "1..2";
      }
      mandatory true;
      description
        "Slot ID of AP to configure the 802.11 Dual radio mode";
    }
    choice alternative-choice {
      mandatory true;
      description
        "AP name or AP MAC address";
      case ap-identifier-name {
        leaf ap-name {
          type string;
          mandatory true;
          description
            "Name of AP to configure Dual radio mode";
        }
      }
      case ap-identifier-mac-address {
        leaf mac-addr {
          type yang:mac-address;
          mandatory true;
          description
            "MAC address of AP to configure Dual radio mode";
        }
      }
    }
  }

  grouping set-slot-chan-width-label {
    description
      "Configure channel width";
    leaf chan-width {
      type wireless-enum-types:chan-width;
      mandatory true;
      description
        "channel width";
    }
    leaf slot-id {
      type uint8;
      mandatory true;
      description
        "Slot ID of AP to configure the 802.11 channel width";
    }
    leaf band {
      type wireless-enum-types:enm-radio-band;
      mandatory true;
      description
        "Current band of AP
         1 - 2.4 GHz
         2 - 5 GHz
         3 - Dual band
         4 - 6 GHz";
    }
    choice alternative-choice {
      mandatory true;
      description
        "AP name or AP MAC address";
      case ap-identifier-name {
        leaf ap-name {
          type string;
          mandatory true;
          description
            "Name of AP to configure channel width";
        }
      }
      case ap-identifier-mac-address {
        leaf mac-addr {
          type yang:mac-address;
          mandatory true;
          description
            "MAC address of AP to configure channel width";
        }
      }
    }
  }

  grouping set-ap-band-cleanair {
    description
      "Configures clean air functionality on radio band of access point";
    leaf mode {
      type boolean;
      mandatory true;
      description
        "Enables/Disables clear air functionality";
    }
    leaf band {
      type uint32 {
        range "1..3";
      }
      mandatory true;
      description
        "Band of AP to configure clean air
         1 - 2.4 GHz
         2 - 5 Ghz
         3 - 6 Ghz";
    }
    choice alternative-choice {
      mandatory true;
      description
        "AP name or AP MAC address";
      case ap-identifier-name {
        leaf ap-name {
          type string;
          mandatory true;
          description
            "Name of AP to configure clean air";
        }
      }
      case ap-identifier-mac-address {
        leaf mac-addr {
          type yang:mac-address;
          mandatory true;
          description
            "MAC address of AP to configure clean air";
        }
      }
    }
  }

  grouping dual-band-role {
    description
      "Configure the radio role";
    leaf slot-id {
      type uint8 {
        range "0..3";
      }
      mandatory true;
      description
        "Slot ID of AP to configure the 802.11 radio current band.";
    }
    leaf band {
      type uint32 {
        range "1..3";
      }
      mandatory true;
      description
        "Current band of AP
         1 - 2.4 GHz
         2 - 5 GHz
         3 - Dual band";
    }
    leaf mode {
      type uint32 {
        range "1..4";
      }
      must '../sub-mode = 2' {
        error-message "Mode change is only allowed when sub-mode is Manual";
        error-app-tag "must-violation";
      }
      mandatory true;
      description
        "Mode of an AP radio slot
         1 - Local
         2 - Monitor
         4 - Sniffer";
    }
    leaf sub-mode {
      type uint32 {
        range "0..2";
      }
      mandatory true;
      description
        "Sub Mode of an AP radio slot
         0 - None
         1 - Auto
         2 - Manual";
    }
    leaf chan {
      type uint8 {
        range "1..165";
      }
      must '../mode = 4' {
        error-message "Channel is only allowed when mode is Sniffer";
        error-app-tag "must-violation";
      }
      must "((../band = 2 and ../chan >= 36 and ../chan <= 165) or
            (../band = 1 and ../chan >= 1 and ../chan <= 14) or (../band = 3 and ../chan >= 1 and ../chan <= 165))" {
        error-message "Band and Channel combination is invalid";
        error-app-tag "must-violation";
      }
      description
        "Channel to be sniffed
         1 - 165: Dual band
         1 - 14: 5 GHz
         36 - 165: 2.4 Ghz";
    }
    leaf ip-addr {
      type inet:ip-address;
      must '../mode = 4' {
        error-message "IP address is only allowed when mode is Sniffer";
        error-app-tag "must-violation";
      }
      description
        "Sniffer Server IP";
    }
    choice alternative-choice {
      mandatory true;
      description
        "AP name or AP MAC address";
      case ap-identifier-name {
        leaf ap-name {
          type string;
          mandatory true;
          description
            "Name of AP to configure the radio role";
        }
      }
      case ap-identifier-mac-address {
        leaf mac-addr {
          type yang:mac-address;
          mandatory true;
          description
            "MAC address of AP to configure the radio role";
        }
      }
    }
  }

  grouping fra-revert-data {
    description
      "Configure XOR TX RX radios";
    leaf fra-revert-auto-only {
      type boolean;
      mandatory true;
      description
        "TRUE : Revert only XOR radios currently in automatic band selection.
         FALSE : Revert all XOR radios";
    }
    leaf fra-revert-mode {
      type boolean;
      mandatory true;
      description
        "TRUE:  Put XOR radios in automatic band selection.
         FALSE: Put XOR radios in static 2.4GHz/5GHz/6GHz band";
    }
    leaf band {
      type wireless-enum-types:enm-radio-band;
      description
        "Current band of AP
         1 - 2.4 GHz
         2 - 5 GHz
         3 - Dual band
         4 - 6 GHz";
    }
  }

  grouping set-rad-slot-he-bss-color {
    description
      "Configures BSS color";
    leaf bss-color {
      type uint8 {
        range "0..63";
      }
      mandatory true;
      description
        "BSS color";
    }
    leaf radiotype-check {
      type uint8 {
        range "0..2";
      }
      mandatory true;
      description
        "Radio type check
           0 - no radiotype check
           1 - non dual-band
           2 - dual-band";
    }
    leaf slot-id {
      type uint8 {
        range "1..2";
      }
      mandatory true;
      description
        "Slot ID of AP to configure BSS color";
    }
    choice alternative-choice {
      mandatory true;
      description
        "AP name or AP MAC address";
      case ap-identifier-name {
        leaf ap-name {
          type string;
          mandatory true;
          description
            "Name of AP to configure BSS color";
        }
      }
      case ap-identifier-mac-address {
        leaf mac-addr {
          type yang:mac-address;
          mandatory true;
          description
            "MAC address of AP to configure BSS color";
        }
      }
    }
  }

  grouping set-rad-slot-bss-col-mode {
    description
      "Configure BSS color mode";
    leaf mode {
      type uint8 {
        range "1 .. 2";
      }
      mandatory true;
      description
        "BSS color mode
         1: auto
         2: static";
    }
    leaf radiotype-check {
      type wireless-enum-types:enm-radiotype-check;
      mandatory true;
      description
        " Indicates whether  it is dual band radio or dedicated band radio
         0 : no radiotype check
         1 : non dual-band
         2 : dual-band";
    }
    leaf slot-id {
      type uint8 {
        range "0 .. 3";
      }
      mandatory true;
      description
        "Slot ID of AP to configure BSS color mode";
    }
    choice alternative-choice {
      mandatory true;
      description
        "AP name or AP MAC address";
      case ap-identifier-name {
        leaf ap-name {
          type string;
          mandatory true;
          description
            "Name of AP to configure BSS color mode";
        }
      }
      case ap-identifier-mac-address {
        leaf mac-addr {
          type yang:mac-address;
          mandatory true;
          description
            "MAC address of AP to configure BSS color mode";
        }
      }
    }
  }

  grouping spam-rad-slot-ant-sel-set {
    description
      "Configure 802.11n antenna selection";
    leaf ant-id {
      type uint8;
      mandatory true;
      description
        " Antenna port selection
         1 : Antenna port A
         2 : Antenna port B
         3 : Antenna port C
         4 : Antenna port D
         5 : Antenna port E
         6 : Antenna port F
         7 : Antenna port G
         8 : Antenna port H";
    }
    leaf enable {
      type boolean;
      mandatory true;
      description
        "Enable or disable antenna";
    }
    leaf slot-id {
      type uint8 {
        range "0..3";
      }
      must "(../band = 'band-dualband-radio' and current() != '1' and current() != '3' ) or (../band != 'band-dualband-radio')" {
        error-message "Slot-id 1 and 3 are not valid for dual band";
        error-app-tag "must-violation";
      }
      mandatory true;
      description
        "Slot ID of AP configure 802.11n antenna selection";
    }
    leaf band {
      type wireless-enum-types:enm-radio-band;
      mandatory true;
      description
        "Current band of AP
         1 - 2.4 GHz
         2 - 5 GHz
         3 - Dual band
         4 - 6 GHz";
    }
    choice alternative-choice {
      mandatory true;
      description
        "AP name or AP MAC address";
      case ap-identifier-name {
        leaf ap-name {
          type string;
          mandatory true;
          description
            "Name of AP to configure 802.11n antenna selection";
        }
      }
      case ap-identifier-mac-address {
        leaf mac-addr {
          type yang:mac-address;
          mandatory true;
          description
            "MAC address of AP to configure 802.11n antenna selection";
        }
      }
    }
  }

  grouping set-rad-slot-db-chan-mode {
    description
      "Configure channel mode";
    leaf slot-id {
      type wireless-enum-types:slot-id-type;
      must "(../band = 'radio-80211abgn' and current() != 'slot-1' and current() != 'slot-3' ) or (../band != 'radio-80211abgn')" {
        error-message "Slot-id 1 and 3 are not valid for dual band";
        error-app-tag "must-violation";
      }
      mandatory true;
      description
        "Slot ID of AP to configure the 802.11 Dual band";
    }
    leaf band {
      type wireless-enum-types:enm-radio-type;
      must "current() = 'radio-80211abgn'" {
        error-message "This RPC is valid only for dual band radio";
        error-app-tag "must-violation";
      }
      mandatory true;
      description
        "Current band of AP";
    }
    choice alternative-choice {
      mandatory true;
      description
        "AP name or AP MAC address";
      case ap-identifier-name {
        leaf ap-name {
          type string;
          mandatory true;
          description
            "Name of AP to configure channel mode";
        }
      }
      case ap-identifier-mac-address {
        leaf mac-addr {
          type yang:mac-address;
          mandatory true;
          description
            "MAC address of AP to configure channel mode";
        }
      }
    }
  }

  grouping set-rad-slot-db-chan-number {
    description
      "Configure dual band channel";
    leaf slot-id {
      type wireless-enum-types:slot-id-type;
      mandatory true;
      description
        "Slot ID of AP to configure the 802.11 Dual band";
    }
    leaf chan {
      type uint32 {
        range "1..233";
      }
      mandatory true;
      description
        "Channel to be configured
         1 - 173: Dual band
         1 - 14: 2.4 GHz
         36 - 173: 5 Ghz
         1 - 233 : 6 Ghz";
    }
    leaf band {
      type uint32 {
        range "1..4";
      }
      mandatory true;
      description
        "Current band of AP
         1 - 2.4 GHz
         2 - 5 GHz
         3 - Dual band
         4 - 6 GHz";
    }
    choice alternative-choice {
      mandatory true;
      description
        "AP name or AP MAC address";
      case ap-identifier-name {
        leaf ap-name {
          type string;
          mandatory true;
          description
            "Name of AP to configure channel number";
        }
      }
      case ap-identifier-mac-address {
        leaf mac-addr {
          type yang:mac-address;
          mandatory true;
          description
            "MAC address of AP to configure channel number";
        }
      }
    }
  }

  grouping dual-band-radio-band {
    description
      "Configures the 802.11 dual-band radio's current band i.e 2.4GHz/5GHz";
    leaf slot-id {
      type uint8 {
        range "0..2";
      }
      mandatory true;
      description
        "Slot ID of AP to configure the 802.11 dual-band radio's current band. Valid value range is 0-2";
    }
    leaf band {
      type uint32 {
        range "1..3";
      }
      mandatory true;
      description
        "Current band of AP
         1 - 2.4 GHz
         2 - 5 GHz
         3 - Dual band";
    }
    leaf toband {
      type uint32 {
        range "1..2";
      }
      mandatory true;
      description
        "New band to switch AP to from current band
         1 - 2.4 GHz
         2 - 5 GHz";
    }
    choice alternative-choice {
      mandatory true;
      description
        "AP name or AP MAC address";
      case ap-identifier-name {
        leaf ap-name {
          type string;
          mandatory true;
          description
            "Name of AP to configure the 802.11 dual-band radio's current band";
        }
      }
      case ap-identifier-mac-address {
        leaf mac-addr {
          type yang:mac-address;
          mandatory true;
          description
            "MAC address of AP to configure the 802.11 dual-band radio's current band";
        }
      }
    }
  }

  grouping lan-port-config-enable {
    description
      "AP LAN port configuration";
    leaf port-id {
      type wireless-enum-types:enm-lan-port-id;
      mandatory true;
      description
        "LAN port identification number";
    }
    leaf mode {
      when "../port-config-type = 'set-port-mode'";
      type boolean;
      mandatory true;
      description
        "LAN port can be enabled (true) or disabled (false)";
    }
    leaf poe-enabled {
      when "../port-config-type = 'set-poe-state'";
      type boolean;
      mandatory true;
      description
        "PoE of the LAN port can be enabled (true) or disabled (false)";
    }
    leaf power-level-id {
      when "../port-config-type = 'set-power-level'";
      type uint8 {
        range "1..4";
      }
      mandatory true;
      description
        "Power level of the LAN port";
    }
    leaf port-config-type {
      type wireless-enum-types:enm-lan-port-config;
      mandatory true;
      description
        "Port parameter to configure";
    }
    choice alternative-choice {
      mandatory true;
      description
        "AP name or AP MAC address";
      case ap-identifier-name {
        leaf ap-name {
          type string;
          mandatory true;
          description
            "Name of AP to configure AP LAN port";
        }
      }
      case ap-identifier-mac-address {
        leaf mac-addr {
          type yang:mac-address;
          mandatory true;
          description
            "MAC address of AP to configure AP LAN port";
        }
      }
    }
  }

  grouping set-ap-indoor-enable {
    description
      "Configure indoor or outdoor mode of AP";
    leaf enable {
      type uint32;
      mandatory true;
      description
        "Indoor mode of an AP can be enabled(true) or disabled(false)";
    }
    choice alternative-choice {
      mandatory true;
      description
        "AP name or AP MAC address";
      case ap-identifier-name {
        leaf ap-name {
          type string;
          mandatory true;
          description
            "Name of AP to configure the indoor or outdoor mode of AP";
        }
      }
      case ap-identifier-mac-address {
        leaf mac-addr {
          type yang:mac-address;
          mandatory true;
          description
            "MAC address of AP to configure the indoor or outdoor mode of AP";
        }
      }
    }
  }

  grouping set-ap-controller {
    description
      "Configures controller information in AP";
    leaf mode {
      type wireless-enum-types:enm-controller-name-status;
      must "(current() = 'controller-name-disable') or (string-length(../controller-name) > 0) or (string-length(../ipaddr) > 0)" {
        error-message "Either controller-name or ipaddr need to be configured";
        error-app-tag "must-violation";
      }
      mandatory true;
      description
        "Configures/clears controller information in AP";
    }
    leaf controller-name {
      type string {
        length "1..31";
        pattern '[a-zA-Z0-9_\-]*';
      }
      description
        "Specifies controller name";
    }
    leaf index {
      type wireless-enum-types:enm-controller-index;
      mandatory true;
      description
        "Specifies primary/secondary/tertiary configuration";
    }
    leaf ipaddr {
      type inet:ip-address;
      description
        "Specifies IP address of controller";
    }
    choice alternative-choice {
      mandatory true;
      description
        "AP name or AP MAC address";
      case ap-identifier-name {
        leaf ap-name {
          type string;
          mandatory true;
          description
            "Name of AP to configure controller information ";
        }
      }
      case ap-identifier-mac-address {
        leaf mac-addr {
          type yang:mac-address;
          mandatory true;
          description
            "MAC address of AP to configure controller information ";
        }
      }
    }
  }

  grouping set-ap-site-reset {
    description
      "Reset all APs in a site";
    leaf site-tag-name {
      type string;
      mandatory true;
      description
        "Site tag on which all APs need to reboot";
    }
  }

  grouping set-ap-led-brightness-level {
    description
      "Configure the LED brightness level";
    leaf led-brightness-level {
      type uint8 {
        range "1..8";
      }
      mandatory true;
      description
        "LED brightness level (1..8)";
    }
    choice alternative-choice {
      mandatory true;
      description
        "AP name or AP MAC address";
      case ap-identifier-name {
        leaf ap-name {
          type string;
          mandatory true;
          description
            "Name of AP to configure the led brightness level";
        }
      }
      case ap-identifier-mac-address {
        leaf mac-addr {
          type yang:mac-address;
          mandatory true;
          description
            "MAC address of AP to configure the led brightness level";
        }
      }
    }
  }

  grouping set-ap-slot-tx-power-level {
    description
      "Modify transmit power level of an AP slot (band)";
    leaf tx-power-level {
      type uint8 {
        range "1 .. 8";
      }
      units "dBm";
      mandatory true;
      description
        "Transmit power level (1..8)";
    }
    leaf slot-id {
      type uint8 {
        range "0..3";
      }
      mandatory true;
      description
        "Slot ID of AP to configure transmit power level. Valid value range is 0-3.";
    }
    leaf band {
      type uint32 {
        range "1..4";
      }
      mandatory true;
      description
        "Band of AP to configure transmit power level
         1 - 2.4 GHz
         2 - 5 GHz
         3 - Dual band
         4 - 6 GHz";
    }
    choice alternative-choice {
      mandatory true;
      description
        "Alternative choice AP name and MAC address";
      case ap-identifier-name {
        leaf ap-name {
          type string;
          mandatory true;
          description
            "AP name for configuring transmit power level";
        }
      }
      case ap-identifier-mac-address {
        leaf mac-addr {
          type yang:mac-address;
          mandatory true;
          description
            "MAC address of AP for configuring transmit power level";
        }
      }
    }
  }

  grouping set-ap-slot-antenna-mode {
    description
      "Configures the antenna mode of the AP";
    leaf antenna-mode {
      type wireless-enum-types:enm-antenna-mode;
      mandatory true;
      description
        "Supported antenna mode";
    }
    leaf slot-id {
      type uint8 {
        range "0..2";
      }
      mandatory true;
      description
        "Slot ID of AP to configure the antenna mode. Valid value range is 0-2";
    }
    choice alternative-choice {
      mandatory true;
      description
        "AP name or AP MAC address";
      case ap-identifier-name {
        leaf ap-name {
          type string;
          mandatory true;
          description
            "Name of AP to configure the antenna mode";
        }
      }
      case ap-identifier-mac-address {
        leaf mac-addr {
          type yang:mac-address;
          mandatory true;
          description
            "MAC address of AP to configure the antenna mode";
        }
      }
    }
  }

  grouping set-ap-admin-state {
    description
      "Disable/Enable AP admin state";
    leaf mode {
      type wireless-enum-types:enm-admin-status;
      mandatory true;
      description
        "Mode for AP admin state";
    }
    choice alternative-choice {
      mandatory true;
      description
        "AP name or AP MAC address";
      case ap-identifier-name {
        leaf ap-name {
          type string;
          mandatory true;
          description
            "AP name for changing AP admin state";
        }
      }
      case ap-identifier-mac-address {
        leaf mac-addr {
          type yang:mac-address;
          mandatory true;
          description
            "MAC address of AP for changing AP admin state";
        }
      }
    }
  }

  grouping set-ap-slot-admin-state {
    description
      "Configure admin state of AP slot";
    leaf mode {
      type wireless-enum-types:enm-admin-status;
      mandatory true;
      description
        "Mode of AP to configure admin state";
    }
    leaf slot-id {
      type uint8 {
        range "0..3";
      }
      must '(../band=1 and ../slot-id=0) or (../band=2 and (../slot-id=1 or ../slot-id=2)) or (../band=3 and (../slot-id=0 or ../slot-id=2)) or (../band=4 and (../slot-id=2 or ../slot-id=3))' {
        error-message "Invalid slot ID selected for the band";
        error-app-tag "must-violation";
      }
      mandatory true;
      description
        "AP slot ID to configure admin state
          Allowed slot ID for bands are
            1 - slot ID 0
            2 - slot ID 1 and slot ID 2
            3 - slot ID 0 and slot ID 2
            4 - slot ID 2 and slot ID 3";
    }
    leaf band {
      type uint32 {
        range "1..4";
      }
      mandatory true;
      description
        "Radio frequency band of AP to configure admin state.
          1 - 2.4 GHz
          2 - 5 GHz
          3 - Dual band
          4 - 6 GHz";
    }
    choice alternative-choice {
      mandatory true;
      description
        "AP name or AP MAC address";
      case ap-identifier-name {
        leaf ap-name {
          type string;
          mandatory true;
          description
            "Name of AP to configure admin state";
        }
      }
      case ap-identifier-mac-address {
        leaf mac-addr {
          type yang:mac-address;
          mandatory true;
          description
            "MAC address of AP to configure admin state";
        }
      }
    }
  }

  grouping set-ap-slot-tx-power-customize {
    description
      "Enables auto RF on a slot";
    leaf mode {
      type wireless-types:w-config-type;
      mandatory true;
      description
        "Select mode as CONFIG AUTO to configure transmit power of AP";
    }
    leaf slot-id {
      type uint8 {
        range "0 .. 3";
      }
      must "((../band = '1' and current() != '1' and current() != '2' and current() != '3') or (../band != '1')) and
            ((../band = '2' and current() != '0' and current() != '3') or (../band != '2')) and
            ((../band = '3' and current() != '1' and current() != '3') or (../band != '3')) and
            ((../band = '4' and current() != '0' and current() != '1') or (../band != '4'))" {
        error-message "Invalid combination of band and slot-id";
        error-app-tag "must-violation";
      }
      mandatory true;
      description
        "Slot ID of AP radio on which to configure transmit power. Valid value range is 0-3.";
    }
    leaf band {
      type uint32 {
        range "1 .. 4";
      }
      mandatory true;
      description
        "Radio frequency band to configure transmit power on.
          1 - 2.4 GHz
          2 - 5 GHz
          3 - Dual band
          4 - 6 Ghz";
    }
    choice alternative-choice {
      mandatory true;
      description
        "AP name or AP MAC address";
      case ap-identifier-name {
        leaf ap-name {
          type string;
          mandatory true;
          description
            "Name of AP to configure transmit power of AP";
        }
      }
      case ap-identifier-mac-address {
        leaf mac-addr {
          type yang:mac-address;
          mandatory true;
          description
            "MAC address of AP to configure transmit power of AP";
        }
      }
    }
  }

  grouping mdns-ap-config {
    description
      "Add or delete vlan from mDNS AP";
    leaf mdns-ap-cli-mode {
      type wireless-enum-types:mdns-ap-cli-mode;
      mandatory true;
      description
        "Select add or delete operation";
    }
    leaf vlan {
      type uint16;
      description
        "VLAN ID to be added/deleted";
    }
    choice alternative-choice {
      mandatory true;
      description
        "Choice between AP name or AP radio MAC address";
      case ap-identifier-name {
        leaf ap-name {
          type string;
          mandatory true;
          description
            "Name of the mDNS AP on which to enable/disable VLAN";
        }
      }
      case ap-identifier-mac-address {
        leaf mac-addr {
          type yang:mac-address;
          mandatory true;
          description
            "Radio MAC address of the AP on which to enable/disable VLAN";
        }
      }
    }
  }

  grouping set-ap-sensor-cfg {
    description
      "AP sensor configuration";
    leaf sensor-type {
      type wireless-enum-types:enm-ap-sensor-type;
      mandatory true;
      description
        "Type of the AP sensor";
    }
    leaf admin-state {
      type wireless-enum-types:enm-ap-sensor-state;
      mandatory true;
      description
        "AP sensor administrative state";
    }
    choice alternative-choice {
      mandatory true;
      description
        "AP name or AP radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-ap-ranging {
    description
      "Configures ranging of the AP";
    leaf site-tag-name {
      type string;
      mandatory true;
      description
        "Send ranging information to all AP's under site-tag";
    }
    leaf all-aps {
      type boolean;
      mandatory true;
      description
        "Send ranging information to all AP's";
    }
    leaf ranging-mode {
      type wireless-enum-types:enm-ranging-mode;
      mandatory true;
      description
        "Set ranging mode of all AP's";
    }
    leaf ranging-band {
      type wireless-enum-types:enm-ranging-band;
      must "../ranging-mode = 'ranging-disruptive'" {
        error-message "Ranging band filtering is only supported for disruptive ranging";
        error-app-tag "must-violation";
      }
      default "ranging-all-bands";
      description
        "Set ranging band of all AP's";
    }
    leaf ranging-method {
      type wireless-enum-types:enm-ranging-method;
      description
        "Set ranging method of all APs";
    }
  }

  grouping set-ap-coordinates {
    description
      "Configures AP coordinate";
    leaf latitude {
      type string;
      mandatory true;
      description
        "Configure latitude of AP";
    }
    leaf longitude {
      type string;
      mandatory true;
      description
        "Configure longitude of AP";
    }
    choice alternative-choice {
      mandatory true;
      description
        "AP name or AP MAC address";
      case ap-identifier-name {
        leaf ap-name {
          type string;
          mandatory true;
          description
            "AP name for configuring AP coordinate";
        }
      }
      case ap-identifier-mac-address {
        leaf mac-addr {
          type yang:mac-address;
          mandatory true;
          description
            "MAC address of AP for configuring AP coordinate";
        }
      }
    }
  }

  grouping set-ap-floor {
    description
      "Configures floor of the AP";
    leaf floor {
      type int32 {
        range "-511 .. 511";
      }
      mandatory true;
      description
        "Configure floor id";
    }
    choice alternative-choice {
      mandatory true;
      description
        "AP name or AP MAC address";
      case ap-identifier-name {
        leaf ap-name {
          type string;
          mandatory true;
          description
            "Name of the AP for configuring floor";
        }
      }
      case ap-identifier-mac-address {
        leaf mac-addr {
          type yang:mac-address;
          mandatory true;
          description
            "MAC address of AP for configuring floor";
        }
      }
    }
  }

  grouping set-ap-group-ranging {
    description
      "AP group ranging";
    leaf ranging-group-name {
      type string;
      mandatory true;
      description
        "Ranging group name";
    }
    leaf-list mac-addr {
      type yang:mac-address;
      ordered-by user;
      description
        "AP's radio MAC address";
    }
    leaf ranging-mode {
      type wireless-enum-types:enm-ranging-mode;
      mandatory true;
      description
        "Set ranging mode";
    }
    leaf ranging-band {
      type wireless-enum-types:enm-ranging-band;
      must "../ranging-mode = 'ranging-disruptive'" {
        error-message "Ranging band filtering is only supported for disruptive ranging";
        error-app-tag "must-violation";
      }
      default "ranging-all-bands";
      description
        "Set ranging band";
    }
    leaf ranging-method {
      type wireless-enum-types:enm-ranging-method;
      description
        "Set ranging method";
    }
  }

  rpc set-ap-vlan-tag {
    description
      "Configure VLAN tagging for non-bridge AP";
    input {
      uses wireless-access-point-cfg-rpc:set-ap-vlan-tag;
    }
  }

  rpc set-ap-vlan-tag-all {
    description
      "Configure VLAN tagging for all non-bridge APs";
    input {
      uses wireless-access-point-cfg-rpc:set-ap-vlan-tag-all;
    }
  }

  rpc set-ap-monitor-mode-chnl-optimize {
    description
      "Configure channel scanning optimization for AP";
    input {
      uses wireless-access-point-cfg-rpc:set-ap-monitor-mode-chnl-optimize;
    }
  }

  rpc set-ap-mode {
    description
      "Configures AP mode";
    input {
      uses wireless-access-point-cfg-rpc:set-ap-mode;
    }
  }

  rpc set-lrad-led-state {
    description
      "Set LED-state for Cisco AP";
    input {
      uses wireless-access-point-cfg-rpc:set-lrad-led-state;
    }
  }

  rpc set-lrad-led-flash {
    description
      "AP LED flash configuration";
    input {
      uses wireless-access-point-cfg-rpc:set-lrad-led-flash;
    }
  }

  rpc set-ap-location {
    description
      "Configure AP location";
    input {
      uses wireless-access-point-cfg-rpc:set-ap-location;
    }
  }

  rpc set-ap-name {
    description
      "Configure AP name";
    input {
      uses wireless-access-point-cfg-rpc:set-ap-name;
    }
  }

  rpc set-ap-antenna-band-mode {
    description
      "Configure antenna band mode";
    input {
      uses wireless-access-point-cfg-rpc:set-ap-antenna-band-mode;
    }
  }

  rpc set-ap-country {
    description
      "Configure the country of operation";
    input {
      uses wireless-access-point-cfg-rpc:set-ap-country;
    }
  }

  rpc set-11-hphy-ofdm-chan {
    status deprecated;
    description
      "New channel using 802.11h channel announcement";
    input {
      uses wireless-access-point-cfg-rpc:set-11-hphy-ofdm-chan;
    }
  }

  rpc set-ap-slot-ext-antenna-gain {
    description
      "Configures the external antenna gain of AP";
    input {
      uses wireless-access-point-cfg-rpc:set-ap-slot-ext-antenna-gain;
    }
  }

  rpc set-rad-slot-phy-ht-chan {
    status deprecated;
    description
      "Channel configuration";
    input {
      uses wireless-access-point-cfg-rpc:set-rad-slot-phy-ht-chan;
    }
  }

  rpc set-ap-slot-phy-ht-chan {
    description
      "Configures static channel on a radio interface of access point";
    input {
      uses wireless-access-point-cfg-rpc:set-ap-slot-phy-ht-chan;
    }
  }

  rpc set-ap-slot-phy-ht-customize {
    description
      "Enables auto channel selection for a radio band of AP";
    input {
      uses wireless-access-point-cfg-rpc:set-ap-slot-phy-ht-customize;
    }
  }

  rpc set-ap-cleanair {
    status deprecated;
    description
      "Configures clean air functionality on radio band of access point";
    input {
      uses wireless-access-point-cfg-rpc:set-ap-cleanair;
    }
  }

  rpc set-rad-slot-dual-radio-mode {
    description
      "Dual radio mode configuration";
    input {
      uses wireless-access-point-cfg-rpc:set-rad-slot-dual-radio-mode;
    }
  }

  rpc set-slot-chan-width-label {
    description
      "Configures channel width";
    input {
      uses wireless-access-point-cfg-rpc:set-slot-chan-width-label;
    }
  }

  rpc set-ap-band-cleanair {
    description
      "Configures clean air functionality on radio band of access point";
    input {
      uses wireless-access-point-cfg-rpc:set-ap-band-cleanair;
    }
  }

  rpc dual-band-role {
    description
      "Configures the radio role of AP";
    input {
      uses wireless-access-point-cfg-rpc:dual-band-role;
    }
  }

  rpc fra-revert-data {
    description
      "FRA configuration";
    input {
      uses wireless-access-point-cfg-rpc:fra-revert-data;
    }
  }

  rpc set-rad-slot-he-bss-color {
    description
      "BSS color configuration";
    input {
      uses wireless-access-point-cfg-rpc:set-rad-slot-he-bss-color;
    }
  }

  rpc set-rad-slot-bss-col-mode {
    description
      "Configures BSS color mode";
    input {
      uses wireless-access-point-cfg-rpc:set-rad-slot-bss-col-mode;
    }
  }

  rpc spam-rad-slot-ant-sel-set {
    description
      "Configure 802.11n antenna selection";
    input {
      uses wireless-access-point-cfg-rpc:spam-rad-slot-ant-sel-set;
    }
  }

  rpc set-rad-slot-db-chan-mode {
    description
      "Configures channel mode";
    input {
      uses wireless-access-point-cfg-rpc:set-rad-slot-db-chan-mode;
    }
  }

  rpc set-rad-slot-db-chan-number {
    description
      "Dual band configuration";
    input {
      uses wireless-access-point-cfg-rpc:set-rad-slot-db-chan-number;
    }
  }

  rpc dual-band-radio-band {
    description
      "Configures the 802.11 dual-band radio's current band i.e 2.4GHz/5GHz";
    input {
      uses wireless-access-point-cfg-rpc:dual-band-radio-band;
    }
  }

  rpc lan-port-config-enable {
    description
      "AP LAN port configuration";
    input {
      uses wireless-access-point-cfg-rpc:lan-port-config-enable;
    }
  }

  rpc set-ap-indoor-enable {
    description
      "Configure indoor or outdoor mode of AP";
    input {
      uses wireless-access-point-cfg-rpc:set-ap-indoor-enable;
    }
  }

  rpc set-ap-controller {
    description
      "Configures controller information in access point";
    input {
      uses wireless-access-point-cfg-rpc:set-ap-controller;
    }
  }

  rpc set-ap-site-reset {
    description
      "Reset all APs in a site";
    input {
      uses wireless-access-point-cfg-rpc:set-ap-site-reset;
    }
  }

  rpc set-ap-led-brightness-level {
    description
      "Configure the led brightness level";
    input {
      uses wireless-access-point-cfg-rpc:set-ap-led-brightness-level;
    }
  }

  rpc set-ap-slot-tx-power-level {
    description
      "Modify slot transmit power level";
    input {
      uses wireless-access-point-cfg-rpc:set-ap-slot-tx-power-level;
    }
  }

  rpc set-ap-slot-antenna-mode {
    description
      "Configures the 802.11a antenna mode";
    input {
      uses wireless-access-point-cfg-rpc:set-ap-slot-antenna-mode;
    }
  }

  rpc set-ap-admin-state {
    description
      "Enable/Disable AP admin state";
    input {
      uses wireless-access-point-cfg-rpc:set-ap-admin-state;
    }
  }

  rpc set-ap-slot-admin-state {
    description
      "Configure slot admin state";
    input {
      uses wireless-access-point-cfg-rpc:set-ap-slot-admin-state;
    }
  }

  rpc set-ap-slot-tx-power-customize {
    description
      "Enable auto RF on a slot";
    input {
      uses wireless-access-point-cfg-rpc:set-ap-slot-tx-power-customize;
    }
  }

  rpc mdns-ap-config {
    description
      "Add or delete vlan from mDNS AP";
    input {
      uses wireless-access-point-cfg-rpc:mdns-ap-config;
    }
  }

  rpc set-ap-sensor-cfg {
    description
      "AP sensor configuration";
    input {
      uses wireless-access-point-cfg-rpc:set-ap-sensor-cfg;
    }
  }

  rpc set-ap-ranging {
    description
      "Configure AP ranging";
    input {
      uses wireless-access-point-cfg-rpc:set-ap-ranging;
    }
  }

  rpc set-ap-coordinates {
    description
      "Configure coordinate of the AP";
    input {
      uses wireless-access-point-cfg-rpc:set-ap-coordinates;
    }
  }

  rpc set-ap-floor {
    description
      "Configure AP floor";
    input {
      uses wireless-access-point-cfg-rpc:set-ap-floor;
    }
  }

  rpc set-ap-group-ranging {
    description
      "AP group ranging";
    input {
      uses wireless-access-point-cfg-rpc:set-ap-group-ranging;
    }
  }
}
