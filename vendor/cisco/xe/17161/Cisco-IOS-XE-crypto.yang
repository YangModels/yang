module Cisco-IOS-XE-crypto {
  yang-version 1.1;
  namespace "http://cisco.com/ns/yang/Cisco-IOS-XE-crypto";
  prefix ios-crypto;

  import cisco-semver {
    prefix cisco-semver;
  }
  import ietf-inet-types {
    prefix inet;
  }
  import Cisco-IOS-XE-native {
    prefix ios;
  }
  import Cisco-IOS-XE-types {
    prefix ios-types;
  }
  import Cisco-IOS-XE-features {
    prefix ios-features;
  }
  import Cisco-IOS-XE-interface-common {
    prefix ios-ifc;
  }
  import Cisco-IOS-XE-tunnel {
    prefix ios-tun;
  }
  import Cisco-IOS-XE-aaa {
    prefix ios-aaa;
  }
  import Cisco-IOS-XE-snmp {
    prefix ios-snmp;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Crypto Yang Model.
     Copyright (c) 2016-2023 by Cisco Systems, Inc.
     All rights reserved.";

  revision 2024-11-01 {
    description
      "- Added http username/password under pki enrollment profile
       - Obsolete node which is deprecated without Mapping
       - Changed default hash value form 256 to 512 under crypto pki trustpoint configuration
       - Deprecated isakmp profile match identity IPv6
       - Update yang models for monitor event-trace dmvpn and flexvpn tunnels
       - Added new container for nhrp in monitor-event-trace-tunnel-common
       - Added model change for match address local in ikev2 profile
       - Obsolete few nodes that are deprecated before 17.11
       - Deprecated ssl profile aaa authorization override and user-pass
       - Added default for crypto isakmp keepalive cli
       - Added new container for primary and secondary under cluster-options container";
    cisco-semver:module-version "16.0.0";
  }
  revision 2024-07-01 {
    description
      "- Added new leaf type enum for aes under algorithm
       - Added tailf suppress mode for split-dns list
       - Added cli-reset-container for bind-ip-address
       - Deprecated leaf IPv4 and added leaf-list of IPv4 addresses under crypto GDOI redundancy peer address configuration
       - Moved tailf alternative name trust-point and certificate to annotation file
       - Added presence true for auto-enroll container in pki trustpoint
       - Remove cli-reset-container from lifetime container
       - Moved tailf alternative name back to yang file due to functionality breakage
       - Added model for IPv6 crypto maps
       - Moved tailf alternative name back to yang file due to functionality breakage
       - Added model for IPv6 crypto maps
       - Modified the isakmp key-address and key-host container to list to hold multiple entries of key
       - Obsolete master key nodes
       - Added create and delete case for ipv6 crypto map configuration due to vmanage issue
       - Added support for monitor event-trace crypto|gdoi
       - Deprecated leaf address and added leaf-list of IPv4 addresses under crypto map ipsec-isakmp configuration
       - Remove must statement for tunnel protection default ipsec profile
       - Deprecated leaf match-identity-group under crypto-isakmp-profile-grouping and created a leaf-list
       - Added tailf:cli-reset-container for isakmp self-identity
       - Added create before/delete after for isakmp match certificate
       - Added tailf:cli-flatten-container and tailf:cli-compact-syntax for crypto isakmp profile configuration
       - Changed must constraint for proposal under ikev2 policy to allow configuration of default proposal
       - Deprecated leaf value and added leaf-list of value-id under crypto GDOI server local identifier configuration
       - Augment crypto feature under interface Virtual-PPP
       - Added delete of container on deletion of IKE liveness
       - Obsolete crypto pki certificate chain
       - Augment crypto feature under interface Virtual-PPP
       - Added cli-trim-default & default for all missing CLI
       - Deprecated leaf seconds and leaf days and added a choice for these leafs under the crypto map ipsec-isakmp configuration
       - Obsolete node which is deprecated without Mapping
       - Deprecated isakmp profile match certificate IPv4 leaf and add leaf list
       - Changed must constraint for shutdown under crypto tls-tunnel to check xpath of tls-local-interface
       - Added delete container and reset container under tunnel protection, profile-option";
    cisco-semver:module-version "15.0.0";
  }
  revision 2024-03-01 {
    description
      "- Added refine for isakmp
       - Addition of snmp-server traps for gdoi
       - Added presence true under gdoi group server local
       - Added cli-preformatted for crypt map description to avoid double
         quotes for some special character
       - Added tail drop name for virtual-template-option
       - Added cli-delete-when-empty to serial-number container
       - Added default value and cli-show-with-default to pfs container
       - Added cli-reset-container for ip-address container
       - Added presence true and tailf cli-full-command statement for crypto gdoi redundancy config
       - Added must condition for set group under crypto map to check the gdoi group
         exist or not before mapping to crypto map policy
       - Modified the type of client bypass-policy from empty to boolean
       - Modified the key of local interface to priority under tls-tunnel
       - Deprecated lifetime certificate and added lifetime certificate-profile to support default
       - Changed leafs ipsec profile and ikev2-profile deprecated in 17.6 or before to obsolete
       - Changed leaf shared for tunnel protection ipsec profile
       - Moved auto-trigger to end of the trustpoint yang model
       - Added must condition for sa ipsec profile configuration and fixed ordering issues
       - Added Deprecate for leaf trust-point and changed to leaf-list trust-point-ca under isakmp profile";
    cisco-semver:module-version "14.0.0";
  }
  revision 2023-11-01 {
    description
      "- Added disable-scep node under pki trustpoint
       - Added ike sa-strength-enforcement under crypto ipsec
        for CC strong ike enforcement feature support
       - Added default value for port under server ipv4 in tls-tunnel
       - Added must condition for PFS and tailf sequencing commands for G-IKEv2 and PFS
        under server local in gdoi group
       - Added tailf annotation for match fvrf
        under crypto ikev2 policy
       - Moved tailf under enrollment-method to ann file";
    cisco-semver:module-version "13.0.0";
  }
  revision 2023-07-01 {
    description
      "- Updated match url pattern and added aaa authorization password under ssl profile
       - Added missing enum to ipsec transform-set, added tailf statement to
         ensure that the user enters correct leaf values in transform-set list,
         moved default under transform-set to obsolete
       - Moved must condition under leaf proposals, added must condition for incomplete proposal
       - Added shutdown node under tls-tunnel
       - Removed must statements which caused dmi crash";
    cisco-semver:module-version "12.0.0";
  }
  revision 2023-03-01 {
    description
      "- Updated rsakeypair length range lower value from 360 to 512
       - Corrected the aaa accounting leafref xpath to accounting list,
         which earlier was wrongly referring the path to authorisation list
       - Changed the tailf statement for leaf list transform-set under ipsec profile";
    cisco-semver:module-version "11.0.0";
  }
  revision 2022-11-01 {
    description
      "- Update yang-version to 1.1
       - Updated leaf filename and sequence under a list under crypto vpn anyconnect
       - Update ip address and interface as a choice under ssl policy
       - Added crypto ikev2 profile aaa authentication/accounting list option
       - Added crypto engine compliance shield disable option";
    cisco-semver:module-version "10.0.0";
  }
  revision 2022-07-01 {
    description
      "- Added leaf inbound-only under IKEv2 policy match statement
       - Added crypto ssl CLI commands
       - Updated PKI enrollment container to fix enrollment method
       - Updated leaf profile-name and file under a list under crypto vpn anyconnect
       - Changed crypto pki certificate map from list with a single key to a list with two keys
       - Changed cli under crypto pki certificate map from leaf to list
       - Added serial number,valid-start and expires-on cli under crypto pki certificate map
       - Default CLI s under crypto pki have been made obsolete
       - Changed crypto ikev2 profile aaa authorization list from list to container";
    cisco-semver:module-version "9.0.0";
  }
  revision 2022-03-01 {
    description
      "- updated leaf override under aaa authorization group to a container override for ikev2 profile
       - Updated type empty to type boolean for leaf cert under crypto ikev2 http-url
       - Updated type empty to type boolean for leaf shutdown under crypto ikev2 cluster";
    cisco-semver:module-version "8.0.0";
  }
  revision 2021-11-01 {
    description
      "- Added Peer certificate attributes support
       - Added dependency between pki server and pki trustpoint, password constraint updated
       - Updated container aes and leaf des as a choice under crypto isakmp policy";
    cisco-semver:module-version "7.0.0";
  }
  revision 2021-07-01 {
    description
      "- updated server leaves lifetime days and shutdown with proper range and type
       - Updated must statement for leaf dynamic for ikev2 profile settings
       - Added MUST statement for key-string under key chain
       - Modified crypto ssl policy from leaf to list
       - updated leaf to leaf-list for match identity remote email name , domain and key-id";
    cisco-semver:module-version "6.0.0";
  }
  revision 2021-03-01 {
    description
      "- Hardening key chain tcp commands
       - Updated valid range values for cli's:
       - crypto ipsec security-association lifetime days
       - crypto ipsec security-association lifetime seconds
       - Modified list and its other child attributes as obsolete as the key is obsolete
       - Updated valid range for crypto ikev2 authorization policy dhcp timeout";
    cisco-semver:module-version "5.0.0";
  }
  revision 2020-11-01 {
    description
      "- Modified match identity remote fqdn from leaf to leaf-list";
    cisco-semver:module-version "4.2.0";
  }
  revision 2020-07-01 {
    description
      "- Reverse obsolescence of domain-name and domain-match";
    cisco-semver:module-version "4.0.0";
  }
  revision 2020-03-01 {
    description
      "- Added additional configuration under tls-tunnel
       - Not supporting crypto key commands without a NO prefix
       - Added additional configuration under crypto group";
    cisco-semver:module-version "3.0.0";
  }
  revision 2019-11-01 {
    description
      "
       - Added tcp ao specific key chain changes
       - Added values for higher range in GETVPN identifier configuration";
    cisco-semver:module-version "2.0.0";
  }
  revision 2019-07-01 {
    description
      "- Establish semantic version baseline
       - Added leaf prefix under crypto ikev2 authorization policy ipv6
       - Updated comparison statement against keyring under ISAKMP profile
       - Added support for tunnel protection ipsec policy cli config model
       - Added content under ISAKMP configuration
       - Added support for gaps in crypto ikev2 configuration
       - Added support for reverse-route and session key under IPSec configuration
       - Added support for gaps in crypto global configuration
       - Added support for gaps in GETVPN configuration";
    cisco-semver:module-version "1.0.0";
  }
  revision 2019-03-13 {
    description
      "Rearranged transform-set";
  }
  revision 2019-02-12 {
    description
      "Added range under 'key' cli";
  }
  revision 2019-01-30 {
    description
      "Added 'key config-key' cli";
  }
  revision 2019-01-25 {
    description
      "Add accept-lifetime and send-lifetime to key chain submode. Fix MACSEC
       lifetime container and obsolete existing lifetime container.";
  }
  revision 2019-01-22 {
    description
      "Added leaf for App-hosting Gigabit Ethernet interface";
  }
  revision 2019-01-14 {
    description
      "Added 'quit' exit command for 'crypto pki certificate chain'";
  }
  revision 2018-12-14 {
    description
      "added esn leaf under ipsec transform-set";
  }
  revision 2018-12-13 {
    description
      "Fix for single transaction removal issues in IPSec, ISAKMP, IKEv2 profiles and other similar issues";
  }
  revision 2018-12-12 {
    description
      "Corrected crypto pki server type, trustpool policy presence";
  }
  revision 2018-12-10 {
    description
      "added route-map leaf under route set";
  }
  revision 2018-12-03 {
    description
      "Fixed trustpoint ip-extension, revocation-check and crl cache";
  }
  revision 2018-11-21 {
    description
      "Cleanup spelling errors in description statements";
  }
  revision 2018-11-19 {
    description
      "Added module for container ipv6 under crypto ikev2 authorization policy";
  }
  revision 2018-11-11 {
    description
      "Fix for keyring dependency issues";
  }
  revision 2018-11-09 {
    description
      "Fix ordering issue for crypto ikev2-profile,isakmp-profile,proposal,keyring,transform-set";
  }
  revision 2018-11-02 {
    description
      "Added container local, container remote and container access-list under crypto ikev2
       authorization policy route set";
  }
  revision 2018-10-30 {
    description
      "Added self-signed container under crypto pki certificate";
  }
  revision 2018-10-17 {
    description
      "Disabled the hex mode under crypto pki temporarily";
  }
  revision 2018-10-15 {
    description
      "Added password as container under crypto ikev2 profile aaa authorization anyconnect";
  }
  revision 2018-10-12 {
    description
      "Added missing containers for crypto pki config commands";
  }
  revision 2018-10-09 {
    description
      "Added def-domain leaf under crypto ikev2 authorisation policy and Added multi-sn leaf under
       crypto ipsec security-association.";
  }
  revision 2018-09-19 {
    description
      "Added leaf reactive, leaf gateway, container password, container reconnect and leaf dns under crypto ikev2.";
  }
  revision 2018-08-29 {
    description
      "Moved pki trust-point before pki certificate";
  }
  revision 2018-08-13 {
    description
      "Added model for usage";
  }
  revision 2018-08-07 {
    description
      "Added name mangler list and cluster container under crypto ikev2, backup container under client, name mangler
       container under profile authorisation and added fileds for ikev2 authorization policy.";
  }
  revision 2018-07-27 {
    description
      "Added Authorization container under trustpoint configuration.";
  }
  revision 2018-07-26 {
    description
      "Added certificate chain storage support under trustpoint configuration";
  }
  revision 2018-07-10 {
    description
      "Add .* to cli-preformatted, apply input validation to disallow new lines";
  }
  revision 2018-06-28 {
    description
      "Added must constraints for deleting vrf";
  }
  revision 2018-05-21 {
    description
      "Add 'cli-preformatted' to pre-shared-key";
  }
  revision 2018-02-14 {
    description
      "Fix Ordering issue for crypto keyring and crypto isakmp profile";
  }
  revision 2018-02-06 {
    description
      "Change 'crypto pki trustpool import url' to string";
  }
  revision 2018-01-04 {
    description
      "Change crypto map sequence to list";
  }
  revision 2017-11-27 {
    description
      "Added Change 25GE name";
  }
  revision 2017-11-14 {
    description
      "Add 40 and 100GE support";
  }
  revision 2017-10-06 {
    description
      "Add pki server submod support";
  }
  revision 2017-08-16 {
    description
      "This revision has changes for new 5gig and 25gig interfaces addition";
  }
  revision 2017-08-08 {
    description
      "crypto pki trustpoint is missing fqdn node";
  }
  revision 2017-08-04 {
    description
      "add lifetime container support under key chain";
  }
  revision 2017-05-24 {
    description
      "Modified container ipv4-addr and address under container
       pre-shared-key to list address to support multiple
       pre-shared-key commands.";
  }
  revision 2017-05-10 {
    description
      "inet:ipv6-prefix changed to ios-types:ipv6-prefix";
  }
  revision 2017-05-09 {
    description
      "adding dependency tailf extension in crypto-map container
       to add ability to configure multiple crypto commands and interface
       commands in single RPC";
  }
  revision 2017-03-28 {
    description
      "modified name of map-ipv4 container to generic name
       crypto-map container for ipv4 type crypto maps";
  }
  revision 2017-03-27 {
    description
      "get-config only gets one config though multiple configurations exist on device";
  }
  revision 2017-03-24 {
    description
      "Remove banner";
  }
  revision 2017-03-02 {
    description
      "crypto ikev2 is missing ipv6 address leaf in the model";
  }
  revision 2017-02-07 {
    description
      "Initial revision";
  }

  grouping database-password-grouping {
    container password {
      description
        "Passphrase to protect the private key archive";
      leaf encryption-type {
        type uint8 {
          range "0..9";
        }
      }
      leaf passphrase {
        type string {
          length "8..200";
        }
      }
    }
  }

  grouping database-username-password-grouping {
    container username {
      description
        "username";
      leaf username-value {
        type string;
      }
      container password-ext {
        uses database-password-grouping;
      }
    }
  }

  grouping lifetime-grouping {
    container lifetime-group {
      status obsolete;
      leaf hh-mm-ss {
        status obsolete;
        type ios-types:hhmmss-type;
      }
      choice date-month {
        status obsolete;
        case date1 {
          status obsolete;
          leaf date1 {
            status obsolete;
            type uint8 {
              range "1..31";
            }
          }
        }
        case month1 {
          status obsolete;
          leaf month1 {
            status obsolete;
            type string;
          }
        }
      }
      choice month-date {
        status obsolete;
        case date2 {
          status obsolete;
          leaf date2 {
            status obsolete;
            when '../month1';
            type uint8 {
              range "1..31";
            }
          }
        }
        case month2 {
          status obsolete;
          leaf month2 {
            status obsolete;
            when '../date1';
            type string;
          }
        }
      }
      leaf year {
        status obsolete;
        type uint16 {
          range "1993..2035";
        }
      }
      leaf duration {
        status obsolete;
        description
          "Set key lifetime duration";
        type uint32 {
          range "1..864000";
        }
      }
      leaf hh-mm-ss1 {
        status obsolete;
        type ios-types:hhmmss-type;
      }
      choice date-month1 {
        status obsolete;
        case date3 {
          status obsolete;
          leaf date3 {
            status obsolete;
            type uint8 {
              range "1..31";
            }
          }
        }
        case month3 {
          status obsolete;
          leaf month3 {
            status obsolete;
            type string;
          }
        }
      }
      choice month-date1 {
        status obsolete;
        case date4 {
          status obsolete;
          leaf date4 {
            status obsolete;
            when '../month3';
            type uint8 {
              range "1..31";
            }
          }
        }
        case month4 {
          status obsolete;
          leaf month4 {
            status obsolete;
            when '../date3';
            type string;
          }
        }
      }
      leaf year1 {
        status obsolete;
        type uint16 {
          range "1993..2035";
        }
      }
      leaf infinite {
        status obsolete;
        description
          "Never expires";
        type empty;
      }
    }
  }

  grouping lifetime-grouping-v1 {
    container lifetime-group-v1 {
      description
        "Key lifetime definition";
      leaf local {
        description
          "Specify time in local timezone";
        type empty;
      }
      leaf start-hh-mm-ss {
        description
          "Key lifetime start time";
        type ios-types:hhmmss-type;
      }
      leaf start-month {
        description
          "Key lifetime start month";
        type ios-types:month-type;
      }
      leaf start-day {
        description
          "Key lifetime start day";
        type uint8 {
          range "1..31";
        }
      }
      leaf start-year {
        description
          "Key lifetime start year";
        type uint16 {
          range "1993..2035";
        }
        must '../duration or ../infinite or ../end-hh-mm-ss' {
          error-message "Must have expiration time set";
        }
      }
      choice lifetime-end-choice {
        case duration {
          leaf duration {
            description
              "Key lifetime duration (in seconds)";
            type uint32 {
              range "1..2147483646";
            }
            must '../start-hh-mm-ss' {
              error-message "Must have start time set";
            }
          }
        }
        case infinite {
          leaf infinite {
            description
              "Infinite lifetime";
            type empty;
            must '../start-hh-mm-ss' {
              error-message "Must have start time set";
            }
          }
        }
        case time-date {
          leaf end-hh-mm-ss {
            description
              "Key lifetime end time";
            type ios-types:hhmmss-type;
            must '../start-hh-mm-ss' {
              error-message "Must have start time set";
            }
          }
          leaf end-month {
            description
              "Key lifetime end month";
            type ios-types:month-type;
          }
          leaf end-day {
            description
              "Key lifetime end day";
            type uint8 {
              range "1..31";
            }
          }
          leaf end-year {
            description
              "Key lifetime end year";
            type uint16 {
              range "1993..2035";
            }
          }
        }
      }
    }
  }

  grouping crypto-local-address-grouping {
    container bind-ip-address {
      description
        "Specify an IP address to bind to";
      leaf ip-address {
        description
          "Specify an IP address to bind to";
        type inet:ip-address;
      }
      leaf vrf {
        description
          "F-VRF of the address";
        type string;
      }
    }
    uses ios-ifc:interface-grouping;
  }

  grouping crypto-pki-token-grouping {
    container removal {
      description
        "actions to take after token removal";
      leaf timeout {
        description
          "seconds after token removal at which keys from the token are cleared";
        type uint16 {
          range "0..480";
        }
      }
    }
  }

  grouping reverse-route-common-grouping {
    container reverse-route {
      description
        "Reverse Route Injection.";
      presence "true";
      choice remote-peer-static {
        case remote-peer-case {
          container remote-peer-conatiner {
            leaf remote-peer {
              description
                "Create route in route table for remote tunnel endpoint";
              type inet:ip-address;
            }
            leaf gateway {
              description
                "Force encrypted traffic via this preferred gateway";
              type empty;
            }
            leaf static {
              description
                "Create routes based on static ACLs permanently";
              type empty;
            }
          }
        }
        case static-case {
          leaf static {
            description
              "Create routes based on static ACLs permanently";
            type empty;
          }
        }
      }
    }
  }

  grouping obsolete-reverse-route-common-grouping {
    container reverse-route {
      description
        "Reverse Route Injection.";
      status obsolete;
      presence "true";
      choice remote-peer-static {
        status obsolete;
        case remote-peer-case {
          status obsolete;
          container remote-peer-conatiner {
            status obsolete;
            leaf remote-peer {
              description
                "Create route in route table for remote tunnel endpoint";
              status obsolete;
              type inet:ip-address;
            }
            leaf gateway {
              description
                "Force encrypted traffic via this preferred gateway";
              status obsolete;
              type empty;
            }
            leaf static {
              description
                "Create routes based on static ACLs permanently";
              status obsolete;
              type empty;
            }
          }
        }
        case static-case {
          status obsolete;
          leaf static {
            description
              "Create routes based on static ACLs permanently";
            status obsolete;
            type empty;
          }
        }
      }
    }
  }

  grouping crypto-map-common-grouping {
    leaf description {
      description
        "Description of the crypto map statement policy";
      type string;
    }
    container dialer {
      description
        "Dialer related commands";
      leaf pre-classify {
        description
          "Enable dialer list classification before initiating IKE";
        type empty;
      }
    }
    container match {
      description
        "Match values";
      leaf address {
        description
          "Match address of packets to encrypt";
        type ios-types:ext-acl-type;
      }
    }
    container qos {
      description
        "Quality of Service related commands";
      leaf pre-classify {
        description
          "Enable QOS classification before packets are tunnel encapsulated";
        type empty;
      }
    }
    uses reverse-route-common-grouping;
  }

  grouping obsolete-crypto-map-common-grouping {
    leaf description {
      description
        "Description of the crypto map statement policy";
      status obsolete;
      type string;
    }
    container dialer {
      description
        "Dialer related commands";
      status obsolete;
      leaf pre-classify {
        description
          "Enable dialer list classification before initiating IKE";
        status obsolete;
        type empty;
      }
    }
    container match {
      description
        "Match values";
      status obsolete;
      leaf address {
        description
          "Match address of packets to encrypt";
        status obsolete;
        type ios-types:ext-acl-type;
      }
    }
    container qos {
      description
        "Quality of Service related commands";
      status obsolete;
      leaf pre-classify {
        description
          "Enable QOS classification before packets are tunnel encapsulated";
        status obsolete;
        type empty;
      }
    }
    uses obsolete-reverse-route-common-grouping;
  }

  grouping crypto-map-common-set-security-association-grouping {
    leaf dfbit {
      description
        "Handling of encapsulated DF bit.";
      type enumeration {
        enum clear;
        enum copy;
        enum set;
      }
    }
    container dummy {
      description
        "Enable transmitting dummy packets";
      leaf pps {
        description
          "Simulated traffic rate (in pps)";
        type uint8 {
          range "0..25";
        }
      }
      leaf seconds {
        description
          "Simulated traffic rate (in seconds)";
        type uint16 {
          range "1..3600";
        }
      }
    }
    leaf ecn {
      description
        "Handling of ECN bit";
      type enumeration {
        enum discard;
        enum propagate;
      }
    }
    container idle-time-container {
      leaf idle-time {
        description
          "Automatically delete IPSec SAs after a given idle period.";
        type uint32 {
          range "60..86400";
        }
      }
      leaf default {
        description
          "All SAs idle-out reset to default peer";
        type empty;
      }
    }
    container lifetime {
      description
        "security association lifetime";
      choice days-seconds {
        case days {
          leaf days-case {
            description
              "Time-based key duration in days";
            type uint8 {
              range "1";
            }
          }
        }
        case seconds {
          leaf seconds-case {
            description
              "Time-based key duration in seconds";
            type uint64 {
              range "120..2592000";
            }
          }
        }
      }
      leaf days {
        status deprecated;
        description
          "Time-based key duration in days";
        type uint8 {
          range "1..30";
        }
      }
      leaf kilobytes {
        description
          "Volume-based key duration";
        type union {
          type uint64 {
            range "2560..4294967295";
          }
          type enumeration {
            enum disable;
          }
        }
      }
      leaf seconds {
        status deprecated;
        description
          "Time-based key duration in seconds";
        type uint64 {
          range "120..2592000";
        }
      }
    }
    container replay {
      description
        "Set replay checking.";
      leaf disable {
        description
          "Disable replay checking";
        type empty;
      }
      leaf window-size {
        description
          "Set replay window size.";
        type enumeration {
          enum 1024;
          enum 128;
          enum 256;
          enum 512;
          enum 64;
        }
      }
    }
  }

  grouping obsolete-crypto-map-common-set-security-association-grouping {
    leaf dfbit {
      description
        "Handling of encapsulated DF bit.";
      status obsolete;
      type enumeration {
        enum clear;
        enum copy;
        enum set;
      }
    }
    container dummy {
      description
        "Enable transmitting dummy packets";
      status obsolete;
      leaf pps {
        description
          "Simulated traffic rate (in pps)";
        status obsolete;
        type uint8 {
          range "0..25";
        }
      }
      leaf seconds {
        description
          "Simulated traffic rate (in seconds)";
        status obsolete;
        type uint16 {
          range "1..3600";
        }
      }
    }
    leaf ecn {
      description
        "Handling of ECN bit";
      status obsolete;
      type enumeration {
        enum discard;
        enum propagate;
      }
    }
    container idle-time-container {
      status obsolete;
      leaf idle-time {
        description
          "Automatically delete IPSec SAs after a given idle period.";
        status obsolete;
        type uint32 {
          range "60..86400";
        }
      }
      leaf default {
        description
          "All SAs idle-out reset to default peer";
        status obsolete;
        type empty;
      }
    }
    container lifetime {
      description
        "security association lifetime";
      status obsolete;
      leaf days {
        description
          "Time-based key duration in days";
        status obsolete;
        type uint8 {
          range "1..30";
        }
      }
      leaf kilobytes {
        description
          "Volume-based key duration";
        status obsolete;
        type union {
          type uint64 {
            range "2560..4294967295";
          }
          type enumeration {
            enum disable;
          }
        }
      }
      leaf seconds {
        description
          "Time-based key duration in seconds";
        status obsolete;
        type uint64 {
          range "120..2592000";
        }
      }
    }
    container replay {
      description
        "Set replay checking.";
      status obsolete;
      leaf disable {
        description
          "Disable replay checking";
        status obsolete;
        type empty;
      }
      leaf window-size {
        description
          "Set replay window size.";
        status obsolete;
        type enumeration {
          enum 1024;
          enum 128;
          enum 256;
          enum 512;
          enum 64;
        }
      }
    }
  }

  grouping ipsec-common-set-grouping {
    leaf identity {
      description
        "Identity restriction";
      type string;
    }
    choice isakmp_profile-ikev2_profile {
      case ikev2-profile-case {
        leaf ikev2-profile {
          description
            "Specify ikev2 Profile";
          must '/ios:native/ios:crypto/ikev2/profile[name=current()]' {
            error-message "It seems IKEv2 profile doesn't exist or attempted to delete when actively referred by IPSec profile";
          }
          type string;
        }
      }
      case isakmp-profile-case {
        leaf isakmp-profile {
          description
            "Specify isakmp Profile";
          must '/ios:native/ios:crypto/isakmp/profile[name=current()]' {
            error-message "It seems ISAKMP profile doesn't exist or attempted to delete when actively referred by IPSec profile";
          }
          type string;
        }
      }
    }
    container peer {
      description
        "Allowed Encryption/Decryption peer.";
      status obsolete;
      leaf address {
        status obsolete;
        type union {
          type inet:ipv4-address;
          type string;
          type inet:ipv6-address;
        }
      }
      leaf default {
        description
          "Reset to default peer in list in the event of a failure";
        status obsolete;
        type empty;
      }
      leaf dynamic {
        description
          "Resolve the peer address at the time of negotiation";
        status obsolete;
        type empty;
      }
    }
    container pfs {
      description
        "Specify pfs settings";
      presence "true";
      leaf group {
        description
          "List of supported DH groups";
        default "group14";
        type enumeration {
          enum group1;
          enum group14;
          enum group15;
          enum group16;
          enum group19;
          enum group2;
          enum group20;
          enum group21;
          enum group24;
          enum group5;
        }
      }
    }
    container reverse-route {
      description
        "Reverse Route Injection";
      leaf distance {
        description
          "Distance metric for this static route";
        type uint8 {
          range "1..255";
        }
      }
      leaf tag {
        description
          "Create route and tag it";
        type uint64 {
          range "1..4294967295";
        }
      }
      leaf gateway {
        description
          "Force encrypted traffic via this preferred gateway";
        type union {
          type inet:ipv4-address;
          type inet:ipv6-address;
        }
      }
    }
    leaf-list transform-set {
      description
        "Specify list of transform sets in priority order";
      must '/ios:native/ios:crypto/ipsec/transform-set[tag=current()]' {
        error-message "It seems transform set doesn't exist or attempted to delete when actively referred by IPSec profile";
      }
      type string;
    }
  }

  grouping crypto-map-common-set-grouping {
    leaf group {
      description
        "Set the san group parameters";
      must '(/ios:native/ios:crypto/gkm/group[name=current()]) or (/ios:native/ios:crypto/gdoi/group[name=current()])' {
        error-message "GDOI or GKM group doesn't exist or attempted to delete when actively referred by crypto map";
      }
      type string;
    }
    leaf identity {
      description
        "Identity restriction";
      type string;
    }
    choice isakmp_profile-ikev2_profile {
      case ikev2-profile-case {
        leaf ikev2-profile {
          description
            "Specify ikev2 Profile";
          must '/ios:native/ios:crypto/ikev2/profile[name=current()]' {
            error-message "It seems IKEv2 profile doesn't exist or attempted to delete when actively referred by IPSec profile";
          }
          type string;
        }
      }
      case isakmp-profile-case {
        leaf isakmp-profile {
          description
            "Specify isakmp Profile";
          must '/ios:native/ios:crypto/isakmp/profile[name=current()]' {
            error-message "It seems ISAKMP profile doesn't exist or attempted to delete when actively referred by IPSec profile";
          }
          type string;
        }
      }
    }
    container peer {
      description
        "Allowed Encryption/Decryption peer.";
      leaf-list addresses {
        description
          "List of IPv4 and IPv6 peer addresses";
        type union {
          type inet:ipv4-address;
          type string;
          type inet:ipv6-address;
        }
      }
      leaf address {
        status deprecated;
        type union {
          type inet:ipv4-address;
          type string;
          type inet:ipv6-address;
        }
      }
      leaf default {
        description
          "Reset to default peer in list in the event of a failure";
        type empty;
      }
      leaf dynamic {
        description
          "Resolve the peer address at the time of negotiation";
        type empty;
      }
    }
    container pfs {
      description
        "Specify pfs settings";
      presence "true";
      leaf group {
        type enumeration {
          enum group1;
          enum group14;
          enum group15;
          enum group16;
          enum group19;
          enum group2;
          enum group20;
          enum group21;
          enum group24;
          enum group5;
        }
      }
    }
    container reverse-route {
      description
        "Reverse Route Injection";
      leaf distance {
        description
          "Distance metric for this static route";
        type uint8 {
          range "1..255";
        }
      }
      leaf tag {
        description
          "Create route and tag it";
        type uint64 {
          range "1..4294967295";
        }
      }
      leaf gateway {
        description
          "Force encrypted traffic via this preferred gateway";
        type union {
          type inet:ipv4-address;
          type inet:ipv6-address;
        }
      }
    }
    leaf-list transform-set {
      description
        "Specify list of transform sets in priority order";
      type string;
    }
  }

  grouping obsolete-crypto-map-common-set-grouping {
    leaf group {
      description
        "Set the san group parameters";
      status obsolete;
      type string;
    }
    leaf identity {
      description
        "Identity restriction";
      status obsolete;
      type string;
    }
    choice isakmp_profile-ikev2_profile {
      status obsolete;
      case ikev2-profile-case {
        status obsolete;
        leaf ikev2-profile {
          description
            "Specify ikev2 Profile";
          status obsolete;
          must '/ios:native/ios:crypto/ikev2/profile[name=current()]' {
            error-message "It seems IKEv2 profile doesn't exist or attempted to delete when actively referred by IPSec       profile";
          }
          type string;
        }
      }
      case isakmp-profile-case {
        status obsolete;
        leaf isakmp-profile {
          description
            "Specify isakmp Profile";
          status obsolete;
          must '/ios:native/ios:crypto/isakmp/profile[name=current()]' {
            error-message "It seems ISAKMP profile doesn't exist or attempted to delete when actively referred by IPSec      profile";
          }
          type string;
        }
      }
    }
    container peer {
      description
        "Allowed Encryption/Decryption peer.";
      status obsolete;
      leaf address {
        status obsolete;
        type union {
          type inet:ipv4-address;
          type string;
          type inet:ipv6-address;
        }
      }
      leaf default {
        description
          "Reset to default peer in list in the event of a failure";
        status obsolete;
        type empty;
      }
      leaf dynamic {
        description
          "Resolve the peer address at the time of negotiation";
        status obsolete;
        type empty;
      }
    }
    container pfs {
      description
        "Specify pfs settings";
      status obsolete;
      presence "true";
      leaf group {
        status obsolete;
        type enumeration {
          enum group1;
          enum group14;
          enum group15;
          enum group16;
          enum group19;
          enum group2;
          enum group20;
          enum group21;
          enum group24;
          enum group5;
        }
      }
    }
    container reverse-route {
      description
        "Reverse Route Injection";
      status obsolete;
      leaf distance {
        description
          "Distance metric for this static route";
        status obsolete;
        type uint8 {
          range "1..255";
        }
      }
      leaf tag {
        description
          "Create route and tag it";
        status obsolete;
        type uint64 {
          range "1..4294967295";
        }
      }
      leaf gateway {
        description
          "Force encrypted traffic via this preferred gateway";
        status obsolete;
        type union {
          type inet:ipv4-address;
          type inet:ipv6-address;
        }
      }
    }
    leaf-list transform-set {
      description
        "Specify list of transform sets in priority order";
      status obsolete;
      type string;
    }
  }

  grouping crypto-dynamic-map-grouping {
    uses crypto-map-common-grouping;
    container set {
      description
        "Set values for encryption/decryption";
      uses crypto-map-common-set-grouping;
      container ip {
        description
          "Interface Internet Protocol config commands";
        leaf access-group {
          description
            "Specify access control for packets";
          type ios-types:exp-acl-type;
        }
        leaf direction {
          type enumeration {
            enum in;
            enum out;
          }
        }
      }
      container ip-in {
        status obsolete;
        container ip {
          description
            "Interface Internet Protocol config commands";
          status obsolete;
          leaf access-group {
            description
              "Specify access control for packets";
            status obsolete;
            type ios-types:exp-acl-type;
          }
          leaf in {
            description
              "inbound packets";
            status obsolete;
            type empty;
          }
        }
      }
      container ip-out {
        status obsolete;
        container ip {
          description
            "Interface Internet Protocol config commands";
          status obsolete;
          leaf access-group {
            description
              "Specify access control for packets";
            status obsolete;
            type ios-types:exp-acl-type;
          }
          leaf out {
            description
              "outbound packets";
            status obsolete;
            type empty;
          }
        }
      }
      container nat {
        description
          "Set NAT translation";
        leaf demux {
          description
            "Set NAT demultiplexing";
          type empty;
        }
      }
      container peer-container {
        status obsolete;
        leaf peer {
          description
            "Allowed Encryption/Decryption peer.";
          status obsolete;
          type inet:host;
        }
        leaf default {
          description
            "Reset to default peer in list in the event of a failure";
          status obsolete;
          type empty;
        }
      }
      container security-association {
        description
          "Security association parameters";
        uses crypto-map-common-set-security-association-grouping;
      }
    }
  }

  grouping crypto-dynamic-map-default-grouping {
    leaf description {
      description
        "Description of the crypto map statement policy";
      type empty;
    }
    container dialer {
      description
        "Dialer related commands";
      leaf pre-classify {
        description
          "Enable dialer list classification before initiating IKE";
        type empty;
      }
    }
    leaf disable {
      description
        "Disable this crypto-map-statement";
      type empty;
    }
    container match {
      description
        "Match values";
      leaf address {
        description
          "Match address of packets to encrypt";
        type empty;
      }
    }
    container qos {
      description
        "Quality of Service related commands";
      leaf pre-classify {
        description
          "Enable QOS classification before packets are tunnel encapsulated";
        type empty;
      }
    }
    container reverse-route {
      description
        "Reverse Route Injection.";
      presence "true";
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      container ip {
        description
          "Interface Internet Protocol config commands";
        leaf access-group {
          description
            "Specify access control for packets";
          type ios-types:exp-acl-type;
        }
        leaf direction {
          type enumeration {
            enum in;
            enum out;
          }
        }
      }
      leaf isakmp-profile {
        description
          "Specify isakmp Profile";
        type string;
      }
      container nat {
        description
          "Set NAT translation";
        leaf demux {
          description
            "Set NAT demultiplexing";
          type empty;
        }
      }
      container peer-container {
        leaf peer {
          description
            "Allowed Encryption/Decryption peer.";
          type inet:host;
        }
        leaf default {
          description
            "Reset to default peer in list in the event of a failure";
          type empty;
        }
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          leaf idle-time {
            description
              "Automatically delete IPSec SAs after a given idle period.";
            type empty;
          }
          leaf default {
            description
              "All SAs idle-out reset to default peer";
            type empty;
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      leaf transform-set {
        description
          "Specify list of transform sets in priority order";
        type empty;
      }
    }
  }

  grouping crypto-gkm-local-server-id-grouping {
    container range {
      description
        "Assign range of Key Server Sender IDs (unique in entire group)";
      leaf lowest {
        type uint8 {
          range "0..127";
        }
      }
      leaf hyphen {
        type empty;
      }
      leaf highest {
        type uint8 {
          range "0..127";
        }
      }
    }
    leaf-list value-id {
      description
        "Assign Key Server Sender ID (unique in entire group)";
      type uint8 {
        range "0..127";
      }
    }
    leaf value {
      description
        "DEPRECATED leaf value";
      status deprecated;
      type uint8 {
        range "0..127";
      }
    }
  }

  grouping crypto-gdoi-coop-ks-config-grouping {
    container local {
      description
        "Local key server configurations";
      presence "true";
      leaf priority {
        description
          "Set local server priority";
        type uint8;
      }
    }
    container peer {
      description
        "Peer server configurations";
      container address {
        description
          "Peer server address";
        leaf-list ipv4-addr {
          description
            "Peer server IPv4 addresses";
          type inet:ipv4-address;
        }
        leaf ipv4 {
          status deprecated;
          description
            "Peer server IPv4 address";
          type inet:ipv4-address;
        }
      }
    }
    container protocol {
      description
        "Specify various protocol operational values";
      presence "true";
      leaf pdu {
        description
          "Maximum size of COOP messages";
        type uint32 {
          range "1..65000";
        }
      }
      leaf version {
        description
          "Set COOP ANN version";
        type enumeration {
          enum base;
          enum optimize;
        }
      }
    }
  }

  grouping crypto-gkm-sa-ipsec-grouping {
    container match {
      description
        "Match characteristics of packets to encrypt";
      container address {
        description
          "Match addresses of packets to encrypt";
        leaf ipv4 {
          description
            "Match ipv4 packets";
          type ios-types:ext-acl-type;
        }
        leaf ipv6 {
          description
            "Match ipv6 packets";
          type string;
        }
      }
    }
    leaf profile {
      description
        "Configure an ipsec profile for the SA";
      must '/ios:native/ios:crypto/ipsec/profile[name=current()]' {
        error-message "It seems ipsec profile doesn't exist or attempted to delete when actively referred by gdoi group";
      }
      type string;
    }
    container replay {
      description
        "Set replay method";
      container counter {
        description
          "Enable anti-replay check for single source traffic by using sequence number";
        presence "true";
        leaf window-size {
          description
            "Set replay window size.";
          type enumeration {
            enum 1024;
            enum 128;
            enum 256;
            enum 512;
            enum 64;
          }
        }
      }
      container time {
        description
          "Enable anti-replay check for any traffic by using time";
        presence "true";
        leaf window-size {
          description
            "Time based replay window size";
          type uint8 {
            range "1..100";
          }
        }
      }
    }
    container tag {
      description
        "Set inline tagging method";
      container cts {
        description
          "Cisco Trust Security";
        leaf sgt {
          description
            "Security Group Tag";
          type empty;
        }
      }
    }
  }

  grouping crypto-gkm-sa-ipsec-default-grouping {
    container match {
      description
        "Match characteristics of packets to encrypt";
      container address {
        description
          "Match addresses of packets to encrypt";
        presence "true";
      }
    }
    leaf profile {
      description
        "Configure an ipsec profile for the SA";
      type empty;
    }
    container replay {
      description
        "Set replay method";
      presence "true";
    }
    container tag {
      description
        "Set inline tagging method";
      presence "true";
    }
  }

  grouping crypto-gkm-local-server-grouping {
    container address {
      description
        "Configure server source address";
      leaf ipv4 {
        description
          "Set ipv4 address of local server";
        type inet:ipv4-address;
      }
    }
    leaf pfs {
      description
        "Enable/Disable PFS on KS, By Default its disabled";
      must '../gikev2' {
        error-message "GIKEv2 must be configured for pfs";
      }
      type empty;
    }
    container authorization {
      description
        "Configure authorization for the group";
      container address {
        description
          "Set authorization by address";
        leaf ipv4 {
          description
            "Set authorization by address";
          type union {
            type uint16 {
              range "1..99";
            }
            type string;
          }
        }
      }
      leaf identity {
        description
          "Set authorization by identity";
        type string;
      }
    }
    leaf gdoi {
      description
        "Enable GDOI (ISAKMP) Protocol for Registration & Rekey";
      type empty;
    }
    leaf gikev2 {
      description
        "Enable G-IKEv2 (IKEv2) Protocol for Registration & Rekey";
      type string;
    }
    container group {
      description
        "Configure parameters for the group (e.g. Suite-B)";
      container size {
        description
          "Set Group Size for Suite-B counter transforms (SID length)";
        leaf large {
          description
            "32-bit Sender ID (FIPS 140-2 Operating Mode)";
          type empty;
        }
        leaf medium {
          description
            "24-bit Sender ID (Default)";
          type empty;
        }
        leaf small {
          description
            "Interoperable with GDOI / G-IKEv2 Standard";
          type enumeration {
            enum 12;
            enum 16;
            enum 8;
          }
        }
      }
    }
    container identifier {
      description
        "Enter Suite-B KSSID (Key Server Sender ID) config mode";
      container default {
        description
          "Set a command to its defaults";
        uses crypto-gkm-local-server-id-grouping;
      }
      uses crypto-gkm-local-server-id-grouping;
    }
    container redundancy {
      description
        "Enter cooperative key server configuration mode";
      presence "true";
      container default {
        description
          "Set a command to its defaults";
        uses crypto-gdoi-coop-ks-config-grouping;
      }
      uses crypto-gdoi-coop-ks-config-grouping;
    }
    container registration {
      description
        "Configure registration for the group";
      leaf interface {
        description
          "Identify an interface on which to respond to GKM registrations";
        type string;
      }
      container periodic {
        description
          "Define periodic registrations for the group";
        container crl {
          description
            "On every new CRL";
          leaf trustpoint {
            description
              "For a PKI trustpoint";
            type string;
          }
        }
      }
    }
    container rekey {
      description
        "Configure rekey policy for the group";
      leaf acknowledgement {
        description
          "Request group members to acknowledge rekeys";
        type enumeration {
          enum any;
          enum cisco;
          enum interoperable;
        }
      }
      container address {
        description
          "Define the rekey packet format";
        leaf ipv4 {
          description
            "Match ipv4 packets";
          type ios-types:ext-acl-type;
        }
      }
      container algorithm {
        description
          "Set the rekey encryption algorithm";
        leaf a3des-cbc {
          description
            "Triple DES in CBC mode";
          type empty;
        }
        leaf aes {
          description
            "aes encryption methods";
          type enumeration {
            enum 128;
            enum 192;
            enum 256;
          }
        }
        leaf aes-128 {
          status deprecated;
          description
            "128 bit AES";
          type empty;
        }
        leaf aes-192 {
          status deprecated;
          description
            "192 bit AES";
          type empty;
        }
        leaf aes-256 {
          status deprecated;
          description
            "256 bit AES";
          type empty;
        }
        leaf des-cbc {
          description
            "DES in CBC mode";
          type empty;
        }
      }
      container authentication {
        description
          "Identify the rekey authentication keypair";
        container mypubkey {
          description
            "Identify a keypair associated with this device";
          leaf rsa {
            description
              "Identify an RSA keypair";
            type string;
          }
        }
      }
      container lifetime {
        description
          "Define the rekey lifetime";
        leaf days {
          description
            "Time-based key duration in days";
          type uint8 {
            range "1..30";
          }
        }
        leaf seconds {
          description
            "Time-based key duration in seconds";
          type uint64 {
            range "300..2592000";
          }
        }
      }
      container retransmit {
        description
          "Define the rekey retransmission parameters";
        leaf seconds {
          type uint8 {
            range "10..60";
          }
        }
        choice number-periodic {
          case number-case {
            leaf number {
              description
                "Retransmit this many times";
              type uint8;
            }
          }
          case periodic-case {
            leaf periodic {
              description
                "Periodically send retransmit rekeys";
              type empty;
            }
          }
        }
      }
      container sig-hash {
        description
          "Set rekey signature-hash parameters";
        leaf algorithm {
          description
            "Set the rekey signature-hash algorithm";
          type enumeration {
            enum sha;
            enum sha256;
            enum sha384;
            enum sha512;
          }
        }
      }
      container transport {
        description
          "Specify the rekey distribution method";
        leaf unicast {
          description
            "specify unicast rekey distribution";
          type empty;
        }
      }
    }
    container sa {
      description
        "Configure a security association";
      container d3p {
        description
          "Enable IP delivery delay detection protocol for all SAs within the group";
        container window {
          description
            "IP-D3P window size";
          leaf msec {
            description
              "IP-D3P window size in milliseconds";
            type uint32 {
              range "1000..100000";
            }
          }
          leaf sec {
            description
              "IP-D3P window size in seconds";
            type uint8;
          }
        }
      }
      list ipsec {
        description
          "Configure an IPsec SA";
        key "sequence";
        leaf sequence {
          type uint16;
        }
        container default {
          description
            "Set a command to its defaults";
          uses crypto-gkm-sa-ipsec-default-grouping;
        }
        uses crypto-gkm-sa-ipsec-grouping;
      }
      container pair-wise-keying {
        description
          "Enable KGS pair-wise-keying";
        leaf safety-limit {
          description
            "KGS safety limit";
          type uint8;
        }
      }
      leaf receive-only {
        description
          "Configure SA to work only in inbound direction";
        type empty;
      }
    }
  }

  grouping crypto-gkm-local-server-default-grouping {
    container address {
      description
        "Configure server source address";
      presence "true";
    }
    container authorization {
      description
        "Configure authorization for the group";
      container address {
        description
          "Set authorization by address";
        leaf ipv4 {
          description
            "Set authorization by address";
          type empty;
        }
      }
      leaf identity {
        description
          "Set authorization by identity";
        type empty;
      }
    }
    leaf gdoi {
      description
        "Enable GDOI (ISAKMP) Protocol for Registration & Rekey";
      type empty;
    }
    leaf gikev2 {
      description
        "Enable G-IKEv2 (IKEv2) Protocol for Registration & Rekey";
      type empty;
    }
    container group {
      description
        "Configure parameters for the group (e.g. Suite-B)";
      container size {
        description
          "Set Group Size for Suite-B counter transforms (SID length)";
        presence "true";
      }
    }
    container identifier {
      description
        "Enter Suite-B KSSID (Key Server Sender ID) config mode";
      presence "true";
    }
    container redundancy {
      description
        "Enter cooperative key server configuration mode";
      presence "true";
    }
    container registration {
      description
        "Configure registration for the group";
      leaf interface {
        description
          "Identify an interface on which to respond to GKM registrations";
        type string;
      }
      container periodic {
        description
          "Define periodic registrations for the group";
        container crl {
          description
            "On every new CRL";
          leaf trustpoint {
            description
              "For a PKI trustpoint";
            type empty;
          }
        }
      }
    }
    container rekey {
      description
        "Configure rekey policy for the group";
      leaf acknowledgement {
        description
          "Request group members to acknowledge rekeys";
        type empty;
      }
      container address {
        description
          "Define the rekey packet format";
        presence "true";
      }
      container algorithm {
        description
          "Set the rekey encryption algorithm";
        presence "true";
      }
      container authentication {
        description
          "Identify the rekey authentication keypair";
        presence "true";
      }
      container lifetime {
        description
          "Define the rekey lifetime";
        leaf days {
          description
            "Time-based key duration in days";
          type empty;
        }
        leaf seconds {
          description
            "Time-based key duration in seconds";
          type empty;
        }
      }
      container retransmit {
        description
          "Define the rekey retransmission parameters";
        presence "true";
      }
      container sig-hash {
        description
          "Set rekey signature-hash parameters";
        leaf algorithm {
          description
            "Set the rekey signature-hash algorithm";
          type empty;
        }
      }
      container transport {
        description
          "Specify the rekey distribution method";
        leaf unicast {
          description
            "specify unicast rekey distribution";
          type empty;
        }
      }
    }
    container sa {
      description
        "Configure a security association";
      container d3p {
        description
          "Enable IP delivery delay detection protocol for all SAs within the group";
        presence "true";
      }
      list ipsec {
        description
          "Configure an IPsec SA";
        key "sequence";
        leaf sequence {
          type uint16;
        }
      }
      container pair-wise-keying {
        description
          "Enable KGS pair-wise-keying";
        presence "true";
      }
      leaf receive-only {
        description
          "Configure SA to work only in inbound direction";
        type empty;
      }
    }
  }

  grouping crypto-gdio-grouping {
    container client {
      description
        "Set the group client parameters";
      leaf bypass-policy-new {
        description
          "Allow group-key management traffic sent to this GM only";
        type boolean;
        default "true";
      }
      leaf bypass-policy {
        status deprecated;
        description
          "Allow group-key management traffic sent to this GM only";
        type empty;
      }
      leaf pfs {
        description
          "Enable/Disable PFS on GM, By Default its enabled";
        type empty;
      }
      container fail-close {
        description
          "Enable/Disable Fail-Close revert feature on GM";
        leaf revert {
          description
            "Revert to Fail-Close policy in case of Registration Failure";
          type empty;
        }
      }
      container protocol {
        description
          "Group Member Registration & Rekey Protocol";
        leaf gdoi {
          description
            "Use GDOI (ISAKMP) Protocol for Registration & Rekey";
          type empty;
        }
        leaf gikev2 {
          description
            "Use G-IKEv2 Protocol for Registration & Rekey";
          type string;
        }
      }
      container recovery-check {
        description
          "Specify GM recovery check parameters";
        leaf interval {
          description
            "Waiting period(sec) between consecutive recovery registrations";
          type uint16 {
            range "100..1000";
          }
        }
      }
      container registration {
        description
          "Set the group client management/register interface";
        leaf interface {
          description
            "Set the group client management/register interface";
          type string;
        }
      }
      container rekey {
        description
          "Set the group client acceptable rekey ciphers and hashs";
        container encryption {
          description
            "Set the group client acceptable rekey ciphers";
          leaf rekey-3des-cbc {
            type empty;
          }
          leaf aes-128 {
            description
              "128 bit AES";
            type empty;
          }
          leaf aes-192 {
            description
              "192 bit AES";
            type empty;
          }
          leaf aes-256 {
            description
              "256 bit AES";
            type empty;
          }
          leaf des-cbc {
            description
              "DES in CBC mode";
            type empty;
          }
        }
        container hash {
          description
            "Set the group client acceptable rekey hash";
          leaf sha {
            description
              "Secure Hash Standard";
            type empty;
          }
          leaf sha256 {
            description
              "Secure Hash Standard 2 (256 bit)";
            type empty;
          }
          leaf sha384 {
            description
              "Secure Hash Standard 2 (384 bit)";
            type empty;
          }
          leaf sha512 {
            description
              "Secure Hash Standard 2 (512 bit)";
            type empty;
          }
        }
      }
      container status {
        description
          "group-member status";
        container active-sa {
          description
            "TEK SA with positive remaining lifetime";
          leaf track {
            description
              "enable stub tracking object";
            type uint16 {
              range "1..1000";
            }
          }
        }
      }
      leaf-list transform-sets {
        description
          "Specify list of group client acceptable transform sets";
        type string;
      }
      leaf transport-encrypt-key {
        description
          "Enforce group or pair-wise keying";
        type enumeration {
          enum group-key;
          enum pair-wise-key;
        }
      }
    }
    container identity {
      description
        "Set the identity of the group";
      container address {
        description
          "Set the identity of the group as an address";
        leaf ipv4 {
          description
            "Set the identity of the group as an IPv4 address";
          type inet:ipv4-address;
        }
      }
      leaf number {
        description
          "Set the identity of the group as a number";
        type uint64;
      }
    }
    leaf passive {
      description
        "Set the group in passive mode";
      type empty;
    }
    container server {
      description
        "Set the group server for of the group";
      container address {
        description
          "Identify the group server by address";
        leaf-list ipv4 {
          description
            "Set the IPv4 address of the group server";
          type inet:ipv4-address;
        }
        leaf-list ipv6 {
          description
            "Set the IPv6 address of the group server";
          type inet:ipv6-address;
        }
      }
      container hostname {
        description
          "Identify the group server by hostname";
        leaf ipv4 {
          description
            "Set the IPv4 hostname of the group server";
          type string;
        }
        leaf ipv6 {
          description
            "Set the IPv6 hostname of the group server";
          type string;
        }
      }
      container local {
        description
          "Configure GKM group server defined locally";
        presence "true";
        uses crypto-gkm-local-server-grouping;
        container default {
          description
            "Set a command to its defaults";
          uses crypto-gkm-local-server-default-grouping;
        }
      }
    }
  }

  grouping crypto-gdio-default-grouping {
    container client {
      description
        "Set the group client parameters";
      leaf bypass-policy-new {
        description
          "Allow group-key management traffic sent to this GM only";
        type boolean;
        default "true";
      }
      leaf bypass-policy {
        status deprecated;
        description
          "Allow group-key management traffic sent to this GM only";
        type empty;
      }
      leaf pfs {
        description
          "Enable/Disable PFS on GM, By Default its enabled";
        type empty;
      }
      container protocol {
        description
          "Group Member Registration & Rekey Protocol";
        presence "true";
      }
      container recovery-check {
        description
          "Specify GM recovery check parameters";
        presence "true";
      }
      container registration {
        description
          "Set the group client management/register interface";
        leaf interface {
          description
            "Set the group client management/register interface";
          type empty;
        }
      }
      container rekey {
        description
          "Set the group client acceptable rekey ciphers and hashs";
        container encryption {
          description
            "Set the group client acceptable rekey ciphers";
          presence "true";
        }
        container hash {
          description
            "Set the group client acceptable rekey hash";
          presence "true";
        }
      }
      container status {
        description
          "group-member status";
        container active-sa {
          description
            "TEK SA with positive remaining lifetime";
          presence "true";
        }
      }
      leaf transform-sets {
        description
          "Specify list of group client acceptable transform sets";
        type empty;
      }
      leaf transport-encrypt-key {
        description
          "Enforce group or pair-wise keying";
        type enumeration {
          enum group-key;
          enum pair-wise-key;
        }
      }
    }
    container identity {
      description
        "Set the identity of the group";
      presence "true";
    }
    leaf passive {
      description
        "Set the group in passive mode";
      type empty;
    }
    container server {
      description
        "Set the group server for of the group";
      container address {
        description
          "Identify the group server by address";
        leaf ipv4 {
          description
            "Set the IPv4 address of the group server";
          type inet:ipv4-address;
        }
      }
      container hostname {
        description
          "Identify the group server by hostname";
        leaf ipv4 {
          description
            "Set the IPv4 hostname of the group server";
          type string;
        }
      }
      leaf local {
        description
          "Configure GKM group server defined locally";
        type empty;
      }
    }
  }

  grouping crypto-identity-grouping {
    leaf description {
      description
        "Description of the crypto identity";
      type string;
    }
    leaf dn {
      description
        "Distinguished name identifier";
      type string;
    }
    leaf fqdn {
      description
        "Fully qualified distinguished name identifier";
      type string;
    }
  }

  grouping crypto-identity-default-grouping {
    leaf description {
      description
        "Description of the crypto identity";
      type empty;
    }
    leaf dn {
      description
        "Distinguished name identifier";
      type string;
    }
    leaf fqdn {
      description
        "Fully qualified distinguished name identifier";
      type string;
    }
  }

  grouping crypto-ikev2-keyring-peer-pre-shared-key-grouping {
    choice encryption-hex {
      case encryption-case {
        leaf encryption {
          type enumeration {
            enum 0;
            enum 6;
          }
        }
        leaf key {
          type string {
            pattern '.*';
          }
        }
      }
      case hex-case {
        leaf hex {
          description
            "Key entered in hex string";
          type string;
        }
      }
    }
  }

  grouping crypto-ikev2-keyring-peer-grouping {
    container address {
      description
        "Specify IPv4/IPv6 address of peer";
      choice ipv4-ipv6 {
        case ipv4-case {
          container ipv4 {
            leaf ipv4-address {
              type inet:ipv4-address;
            }
            leaf ipv4-mask {
              type inet:ipv4-address;
            }
          }
        }
        case ipv6-case {
          leaf ipv6-prefix {
            type ios-types:ipv6-prefix;
          }
        }
      }
    }
    leaf description {
      description
        "Specify a description of this peer";
      type string;
    }
    leaf hostname {
      description
        "Hostname of peer";
      type string;
    }
    container identity {
      description
        "Specify IKE identity to use";
      choice identity {
        case address {
          leaf address-type {
            description
              "IP address";
            type union {
              type inet:ipv4-address;
              type inet:ipv6-address;
            }
          }
        }
        case email {
          container email-option {
            description
              "Use email address";
            choice name-domain {
              case name {
                leaf name {
                  description
                    "Specify the name string";
                  type string;
                }
              }
              case domain {
                leaf domain {
                  description
                    "email Domain Name";
                  type string;
                }
              }
            }
          }
        }
        case fqdn {
          container fqdn-option {
            description
              "Use FQDN";
            choice name-domain {
              case name {
                leaf name {
                  description
                    "Specify the name string";
                  type string;
                }
              }
              case domain {
                leaf domain {
                  description
                    "email Domain Name";
                  type string;
                }
              }
            }
          }
        }
        case key-id {
          leaf key-id-number {
            description
              "proprietary types of identification (ID KEY ID)";
            type string;
          }
        }
      }
      leaf address {
        description
          "IP address";
        status obsolete;
        type union {
          type inet:ipv4-address;
          type inet:ipv6-address;
        }
      }
      container email {
        description
          "Use email address";
        status obsolete;
        leaf name {
          status obsolete;
          type string;
        }
        leaf domain {
          description
            "email Domain Name";
          status obsolete;
          type string;
        }
      }
      container fqdn {
        description
          "Use FQDN";
        status obsolete;
        leaf name {
          status obsolete;
          type string;
        }
        leaf domain {
          description
            "email Domain Name";
          status obsolete;
          type string;
        }
      }
      leaf key-id {
        description
          "proprietary types of identification (ID KEY ID)";
        status obsolete;
        type string;
      }
    }
    container pre-shared-key {
      description
        "specify the pre-shared key";
      container local-option {
        description
          "specify signing key";
        uses crypto-ikev2-keyring-peer-pre-shared-key-grouping;
      }
      leaf local {
        description
          "specify signing key";
        status obsolete;
        type empty;
      }
      container remote-option {
        description
          "specify verifying key";
        uses crypto-ikev2-keyring-peer-pre-shared-key-grouping;
      }
      leaf remote {
        description
          "specify verifying key";
        status obsolete;
        type empty;
      }
      uses crypto-ikev2-keyring-peer-pre-shared-key-grouping;
    }
  }

  grouping crypto-ikev2-profile-aaa-auth-passwd-grouping-deprecated {
    container password {
      status deprecated;
      description
        "Specify the AAA password";
      leaf encryption {
        status deprecated;
        type enumeration {
          enum 0;
          enum 6;
        }
      }
      leaf key {
        status deprecated;
        type string;
      }
    }
  }

  grouping crypto-ikev2-profile-aaa-auth-passwd-grouping {
    container password {
      description
        "Specify the AAA password";
      leaf encryption {
        type enumeration {
          enum 0;
          enum 6;
        }
      }
      leaf key {
        type string;
      }
    }
  }

  grouping crypto-ikev2-profile-aaa-authorization-grouping {
    container list-v2 {
      description
        "AAA method list";
      leaf name {
        type string;
      }
      container aaa-config {
        choice user-config {
          case username-config {
            container username {
              leaf username {
                type string;
              }
              choice user-type {
                case local-type {
                  leaf local {
                    when '../username';
                    type empty;
                  }
                }
                case password-type {
                  container password {
                    when '../username';
                    uses crypto-ikev2-profile-aaa-auth-passwd-grouping;
                  }
                }
              }
            }
          }
          case name-mangler-config {
            container name-mangler {
              leaf name {
                description
                  "name of a configured name mangler";
                type leafref {
                  path "/ios:native/ios:crypto/ios-crypto:ikev2/ios-crypto:name-mangler/ios-crypto:name";
                }
              }
              uses crypto-ikev2-profile-aaa-auth-passwd-grouping;
            }
          }
          case password-config {
            uses crypto-ikev2-profile-aaa-auth-passwd-grouping;
          }
        }
      }
    }
    list list {
      status deprecated;
      description
        "AAA method list";
      key "name";
      leaf name {
        type string;
      }
      uses crypto-ikev2-profile-aaa-auth-passwd-grouping-deprecated;
      leaf username {
        type string;
      }
      leaf local {
        description
          "Local AAA Authorization";
        when '../username';
        type empty;
      }
      container name-mangler {
        status deprecated;
        description
          "Specify the name-mangler to derive AAA username";
        leaf name {
          description
            "mangler name";
          type leafref {
            path "/ios:native/ios:crypto/ios-crypto:ikev2/ios-crypto:name-mangler/ios-crypto:name";
          }
        }
        uses crypto-ikev2-profile-aaa-auth-passwd-grouping-deprecated;
      }
    }
  }

  grouping crypto-ikev2-profile-authentication-grouping {
    leaf username {
      description
        "EAP username";
      type string;
    }
    container password {
      description
        "EAP password";
      leaf encryption {
        type enumeration {
          enum 0;
          enum 6;
        }
      }
      leaf key {
        type string;
      }
    }
  }

  grouping crypto-ikev2-profile-authentication-key-grouping {
    container key {
      description
        "specify key";
      leaf encryption {
        type enumeration {
          enum 0;
          enum 6;
        }
      }
      leaf key {
        type string;
      }
    }
  }

  grouping aaa-authorization-grouping {
    container anyconnect-eap {
      description
        "AAA list to use when IKEv2 remote auth method is anyconnect eap based";
      uses crypto-ikev2-profile-aaa-authorization-grouping;
    }
    container cert {
      description
        "AAA list to use when IKEv2 remote auth method is certificate based";
      uses crypto-ikev2-profile-aaa-authorization-grouping;
    }
    container eap {
      description
        "AAA list to use when IKEv2 remote auth method is EAP";
      uses crypto-ikev2-profile-aaa-authorization-grouping;
    }
    container psk {
      description
        "AAA list to use when IKEv2 remote auth method is PSK";
      uses crypto-ikev2-profile-aaa-authorization-grouping;
    }
    container any {
      description
        "AAA list to use when no IKEv2 remote auth method is configured";
      uses crypto-ikev2-profile-aaa-authorization-grouping;
    }
  }

  grouping crypto-ikev2-profile-grouping {
    container aaa {
      description
        "Specify AAA related configuration";
      container accounting {
        description
          "AAA accounting";
        leaf anyconnect-eap {
          description
            "AAA list to use when IKEv2 remote auth method is AnyConnect EAP";
          type string;
        }
        leaf cert {
          description
            "AAA list to use when IKEv2 remote auth method is certificate based";
          type string;
        }
        leaf eap {
          description
            "AAA list to use when IKEv2 remote auth method is EAP";
          type string;
        }
        leaf psk {
          description
            "AAA list to use when IKEv2 remote auth method is PSK";
          type string;
        }
        leaf list {
          description
            "Common AAA list to be used for accounting";
          type leafref {
            path "/ios:native/ios:aaa/ios-aaa:accounting/ios-aaa:network/ios-aaa:id";
          }
        }
      }
      container authentication {
        description
          "AAA authentication";
        leaf anyconnect-eap {
          description
            "AAA AnyConnect EAP authentication";
          type string;
        }
        leaf eap {
          description
            "AAA EAP authentication";
          type string;
        }
        leaf list {
          description
            "Common AAA list to be used for all auth methods";
          type leafref {
            path "/ios:native/ios:aaa/ios-aaa:authorization/ios-aaa:network/ios-aaa:id";
          }
        }
      }
      container authorization {
        description
          "AAA authorization";
        container group {
          description
            "AAA group authorization";
          container override-container {
            description
              "Override user authorization with group authorization.By default, group authorization is overridden with user     authorization";
            uses aaa-authorization-grouping;
          }
          leaf override {
            description
              "Override user authorization with group authorization.By default, group authorization is overridden with user     authorization";
            status obsolete;
            type empty;
          }
          uses aaa-authorization-grouping;
        }
        container user {
          description
            "AAA user authorization";
          container anyconnect-eap {
            description
              "AAA list to use when IKEv2 remote auth method is anyconnect eap based";
            leaf cached {
              description
                "Use cached attributes from EAP authentication or AAA pre-shared key fetch";
              type empty;
            }
            uses crypto-ikev2-profile-aaa-authorization-grouping;
          }
          container cert {
            description
              "AAA list to use when IKEv2 remote auth method is certificate based";
            uses crypto-ikev2-profile-aaa-authorization-grouping;
          }
          container eap {
            description
              "AAA list to use when IKEv2 remote auth method is EAP";
            leaf cached {
              description
                "Use cached attributes from EAP authentication or AAA pre-shared key fetch";
              type empty;
            }
            uses crypto-ikev2-profile-aaa-authorization-grouping;
          }
          container psk {
            description
              "AAA list to use when IKEv2 remote auth method is PSK";
            leaf cached {
              description
                "Use cached attributes from EAP authentication or AAA pre-shared key fetch";
              type empty;
            }
            uses crypto-ikev2-profile-aaa-authorization-grouping;
          }
          container any {
            description
              "AAA list to use when no IKEv2 remote auth method is configured";
            leaf cached {
              description
                "Use cached attributes from EAP authentication or AAA pre-shared key fetch";
              type empty;
            }
            uses crypto-ikev2-profile-aaa-authorization-grouping;
          }
        }
      }
    }
    container anyconnect {
      description
        "Enable profile for anyconnect profile download";
      leaf profile {
        description
          "Anyconnect profile name";
        type string;
      }
    }
    container authentication {
      description
        "Set authentication method";
      container local {
        description
          "Set local authentication method";
        leaf dynamic {
          description
            "authentication local dynamic";
          must '../../../match/inbound-only' {
            error-message "It seems 'match inbound-only' is not configured or attempted to delete while 'authentication local dynamic' is configured under ikev2 profile";
          }
          type empty;
        }
        container eap {
          description
            "Extended Authentication Protocol";
          presence "true";
          container gtc {
            description
              "eap method gtc credentials";
            uses crypto-ikev2-profile-authentication-grouping;
          }
          container md5 {
            description
              "eap method md5 credentials";
            uses crypto-ikev2-profile-authentication-grouping;
          }
          container mschapv2 {
            description
              "eap method mschapv2 credentials";
            uses crypto-ikev2-profile-authentication-grouping;
          }
        }
        leaf ecdsa-sig {
          description
            "ECDSA Signature";
          type empty;
        }
        container pre-share {
          description
            "Pre-Shared Key";
          presence "true";
          uses crypto-ikev2-profile-authentication-key-grouping;
        }
        leaf rsa-sig {
          description
            "Rivest-Shamir-Adleman Signature";
          type empty;
        }
      }
      container remote {
        description
          "Set remote authentication method";
        container anyconnect-eap {
          description
            "AnyConnect EAP";
          container aggregate {
            description
              "use aggregate auth for anyconnect eap";
            presence "true";
            leaf cert-request {
              description
                "use double authentication during anyconnect eap";
              type empty;
            }
          }
        }
        container eap {
          description
            "Extended Authentication Protocol";
          presence "true";
          leaf query-identity {
            description
              "query EAP identity from peer";
            type empty;
          }
          leaf timeout {
            description
              "timeout";
            type uint8 {
              range "45..180";
            }
          }
        }
        leaf ecdsa-sig {
          description
            "ECDSA Signature";
          type empty;
        }
        container pre-share {
          description
            "Pre-Shared Key";
          presence "true";
          uses crypto-ikev2-profile-authentication-key-grouping;
        }
        leaf rsa-sig {
          description
            "Rivest-Shamir-Adleman Signature";
          type empty;
        }
      }
    }
    container config-exchange {
      description
        "config-exchange options";
      leaf request-1 {
        description
          "enable config-exchange request";
        type boolean;
        default "true";
      }
      leaf request {
        description
          "enable config-exchange request";
        status obsolete;
        type empty;
      }
      leaf set {
        description
          "config-exchange set options";
        type enumeration {
          enum accept;
          enum send;
        }
      }
    }
    leaf description {
      description
        "Specify a description of this profile";
      type string;
    }
    container dpd {
      description
        "Enable IKE liveness check for peers";
      leaf interval {
        must '(../retry)';
        type uint16 {
          range "10..3600";
        }
      }
      leaf retry {
        must '(../query)';
        type uint8 {
          range "2..60";
        }
      }
      leaf query {
        type enumeration {
          enum on-demand;
          enum periodic;
        }
      }
    }
    leaf dynamic {
      description
        "Indicates the IKEv2 profile settings are dynamic";
      must "((not(../authentication/local/pre-share)) and
             (not(../authentication/remote/pre-share)) and
             (not(../identity/local/address)) and
             (not(../identity/local/dn)) and
             (not(../identity/local/email)) and
             (not(../identity/local/fqdn)) and
             (not(../identity/local/key-id)) and
             (not(../match/identity/remote/key-id)) and
             (not(../match/identity/remote/fqdn/ios-crypto:fqdn-name)) and
             (not(../match/identity/remote/fqdn/ios-crypto:domain)) and
             (not(../match/identity/remote/email/ios-crypto:name)) and
             (not(../match/identity/remote/email/domain)) and
             (not(../match/identity/remote/any)) and
             (count(../match/identity/ios-crypto:remote/ios-crypto:address/ios-crypto:ipv6-prefix)=0) and
             (count(../match/identity/remote/address/ios-crypto:ipv4)=0))" {
        error-message
          "Cannot configure dynamic while there is existing static local or remote identity or authentication configuration in the profile.
           Please unconfigure existing static local or remote identity or authentication configuration in the profile";
      }
      type empty;
    }
    container identity {
      description
        "Specify IKE identity to use";
      container local {
        description
          "Specify the local IKE identity to use for the negotiation";
        choice identity {
          case address-case {
            leaf address {
              description
                "address";
              type inet:ip-address;
            }
          }
          case dn-case {
            leaf dn {
              description
                "Distinguished Name";
              type empty;
            }
          }
          case email-case {
            leaf email {
              description
                "Fully qualified email string
                 email <user@domain>";
              type string;
            }
          }
          case fqdn-case {
            leaf fqdn {
              description
                "Fully qualified domain name string
                 FQDN <host.domain>";
              type string;
            }
          }
          case key-id-case {
            leaf key-id {
              description
                "key-id opaque string - proprietary types of identification
                 key-id string";
              type string;
            }
          }
        }
      }
    }
    container initial-contact {
      description
        "initial-contact processing options";
      leaf force {
        description
          "Enforces initial-contact based clean-up";
        type empty;
      }
    }
    leaf ivrf {
      description
        "I-VRF of the profile";
      must "(/ios:native/ios:vrf/ios:definition[ios:name=current()] and
            /ios:native/ios:vrf/ios:definition[ios:name=current()]/ios:address-family/ios:ipv4) or
            /ios:native/ios:ip/ios:vrf[ios:name=current()]" {
        error-message "% vrf with address-family does not exist. Create first";
      }
      type string;
    }
    container keyring {
      description
        "Specify keyring to use";
      list aaa {
        description
          "AAA based keyring";
        key "name";
        leaf name {
          type string;
        }
        leaf name-mangler {
          description
            "Specify the name-mangler to derive username";
          must '/ios:native/ios:crypto/ios-crypto:ikev2/ios-crypto:name-mangler[ios-crypto:name=current()]' {
            error-message "% name-mangler does not exist";
          }
          type string;
        }
        container password {
          description
            "Specify the AAA password";
          leaf encryption {
            type enumeration {
              enum 0;
              enum 6;
            }
          }
          leaf key {
            type string;
          }
        }
      }
      container local {
        description
          "Local keyring";
        leaf name {
          description
            "Keyring name";
          type leafref {
            path "/ios:native/ios:crypto/ios-crypto:ikev2/ios-crypto:keyring/ios-crypto:name";
          }
        }
      }
    }
    container lifetime {
      description
        "Set lifetime for ISAKMP security association";
      leaf seconds {
        type uint32 {
          range "120..86400";
        }
      }
      leaf certificate-profile {
        description
          "Enable certificate based lifetime";
        type boolean;
        default "true";
      }
      leaf certificate {
        status deprecated;
        description
          "Enable certificate based lifetime";
        type empty;
      }
    }
    container match {
      description
        "Match values of peer";
      leaf inbound-only {
        description
          "Match the profile for incoming connections only";
        type empty;
      }
      container address {
        description
          "IP address";
        container local {
          description
            "Local address";
          leaf-list ip-address {
            type inet:ip-address;
          }
          leaf ip {
            status deprecated;
            type inet:ip-address;
          }
          container interface-options-local {
            description
              "Specify an interface";
            uses ios-ifc:interface-grouping-list;
          }
          container interface-options {
            description
              "DEPRECATED Specify an interface";
            status deprecated;
            uses ios-ifc:interface-deprecated-grouping;
          }
          leaf interface {
            description
              "OBSOLETE Specify an interface";
            status obsolete;
            type string;
          }
        }
      }
      leaf-list certificate-map {
        description
          "Peer certificate attributes";
        type string;
      }
      leaf certificate {
        description
          "Deprecated, please use certificate-map";
        status deprecated;
        type string;
      }
      container fvrf {
        description
          "fvrf of the profile";
        leaf name {
          must "(/ios:native/ios:vrf/ios:definition[ios:name=current()] and
                /ios:native/ios:vrf/ios:definition[ios:name=current()]/ios:address-family/ios:ipv4) or
                /ios:native/ios:ip/ios:vrf[ios:name=current()]" {
            error-message "% vrf with address-family does not exist. Create first";
          }
          type string;
        }
        leaf any {
          description
            "Any fvrf";
          type empty;
        }
      }
      container identity {
        description
          "IKE identity";
        container remote {
          description
            "Remote identity";
          container address {
            description
              "IP address(es)";
            list ipv4 {
              key "ipv4-address";
              leaf ipv4-address {
                type inet:ipv4-address;
              }
              leaf ipv4-mask {
                type inet:ipv4-address;
              }
            }
            leaf-list ipv6-prefix {
              type ios-types:ipv6-prefix;
            }
          }
          leaf any {
            description
              "match any peer identity";
            type empty;
          }
          container email {
            description
              "Fully qualified email string [Max. 255 char(s)]";
            leaf-list names {
              type string;
            }
            leaf name {
              status deprecated;
              description
                "Email address (DEPRECATED, use names)";
              type string;
            }
            leaf-list domains {
              description
                "match domain instead of exact";
              type string;
            }
            leaf domain {
              description
                "Email domain (DEPRECATED, use domains)";
              status deprecated;
              type string;
            }
          }
          container fqdn {
            description
              "Fully qualified domain name string [Max. 255 char(s)]";
            leaf name {
              status obsolete;
              type string;
            }
            leaf-list fqdn-name {
              type string;
            }
            leaf-list domains {
              description
                "match domain instead of exact";
              type string;
            }
            leaf domain {
              description
                "Email domain (DEPRECATED, use domains)";
              status deprecated;
              type string;
            }
          }
          leaf-list key-ids {
            description
              "key-id opaque string";
            type string;
          }
          leaf key-id {
            description
              "key-id opaque string (DEPRECATED, use key-ids)";
            status deprecated;
            type string;
          }
        }
      }
    }
    container nat {
      description
        "NAT-transparency";
      leaf force-encap {
        description
          "Enforce NAT ESP encap always";
        type empty;
      }
      leaf keepalive {
        description
          "NAT keepalive interval";
        type uint16 {
          range "5..3600";
        }
      }
    }
    container pki {
      description
        "Specify certificate authorities to trust";
      list trust-points {
        description
          "Cert authority trustpoint for RSA sig";
        key "name";
        leaf name {
          type string;
        }
        leaf uses {
          type enumeration {
            enum sign;
            enum verify;
          }
        }
      }
      leaf trustpoint {
        description
          "DEPRECATED (use trust-points)";
        status deprecated;
        type string;
      }
      leaf use {
        description
          "DEPRECATED (use trust-points - uses)";
        status deprecated;
        type enumeration {
          enum sign;
          enum verify;
        }
      }
    }
    container reconnect {
      description
        "Enable profile for auto re-connect";
      presence "true";
      leaf timeout {
        description
          "timeout value for session in reconnect state";
        type uint32 {
          range "600..86400";
        }
      }
    }
    container redirect {
      description
        "IKEv2 Redirect Mechanism for load-balancing";
      container gateway {
        description
          "Enables Redirect Mechanism on Gateway";
        leaf auth {
          description
            "Redirect at SA authentication";
          type empty;
        }
      }
    }
    leaf shutdown {
      description
        "shutdown the IKEv2 profile";
      type empty;
    }
    container virtual-template {
      description
        "Specify the virtual-template for dynamic interface creation.";
      leaf number {
        type uint16 {
          range "1..4095";
        }
      }
      leaf mode {
        description
          "Enabling Tunnel Auto Mode";
        type enumeration {
          enum auto;
        }
      }
    }
  }

  grouping crypto-ikev2-authorization-route-set-local-grouping {
    leaf next-hop {
      description
        "next-hop address";
      type union {
        type inet:ipv4-address;
        type inet:ipv6-address;
      }
    }
    leaf vrf {
      description
        "vrf name";
      must "(/ios:native/ios:vrf/ios:definition[ios:name=current()] and
            /ios:native/ios:vrf/ios:definition[ios:name=current()]/ios:address-family/ios:ipv4) or
            /ios:native/ios:ip/ios:vrf[ios:name=current()]" {
        error-message "% vrf with address-family does not exist. Create first";
      }
      type string;
    }
    leaf tag {
      description
        "tag-value";
      type uint32 {
        range "1..497777";
      }
    }
    leaf distance {
      description
        "distance-value";
      type uint16 {
        range "1..255";
      }
    }
  }

  grouping crypto-ikev2-grouping {
    container authorization {
      description
        "IKEv2 authorization";
      list policy {
        description
          "IKEv2 authorization policy";
        key "policy-name";
        leaf policy-name {
          type string;
        }
        leaf banner {
          description
            "Specify mode config banner";
          type string;
        }
        container configuration {
          description
            "Push configuration to the client";
          leaf url {
            description
              "URL for the client to fetch configuration";
            type string {
              pattern "(((bootflash:)|(cns:)|(flash:)|(ftp:)|(http:)|(https:)|(null:)|(nvram:)|(pram:)|(rcp:)|(scp:
                       )|(sftp:)|(system:)|(tar:)|(tftp:)|(tmpsys:)|(webui:)).*)";
            }
          }
          leaf version {
            description
              "version of the configuration available at the URL";
            type uint32 {
              range "1..32767";
            }
          }
        }
        leaf include-local-lan {
          description
            "Enable Local LAN Access with no split tunnel";
          type empty;
        }
        container ipsec {
          description
            "Specify ipsec parameters";
          leaf flow-limit {
            description
              "ipsec flow-limit per multi-sa session";
            type uint32 {
              range "0..50000";
            }
          }
        }
        container mobileopt-serv {
          description
            "Specify Mobile Optimization Server Addr and Port";
          leaf A.B.C.D {
            description
              "Mobile Optimization Server IPv4 address";
            type inet:ipv4-address;
          }
          leaf port-number {
            description
              "Optional Mobile Optimization Server Port Number, Default is 9540";
            type uint32 {
              range "1..65535";
            }
          }
        }
        leaf netmask {
          description
            "Specify netmask of the config address";
          type inet:ipv4-address;
        }
        leaf pfs {
          description
            "The client should propose PFS";
          type empty;
        }
        container route {
          container set {
            container interface {
              leaf interface-default {
                type empty;
              }
              container interface-name-list {
                uses ios-ifc:interface-grouping;
              }
              list interface-list {
                status obsolete;
                key "interface-name";
                leaf interface-name {
                  status obsolete;
                  type string;
                }
              }
            }
            container access-list {
              description
                "Specify the route access-list";
              leaf access-list-range {
                type union {
                  type uint16 {
                    range "1..99";
                  }
                  type uint16 {
                    range "1300..1999";
                  }
                  type string;
                }
              }
              container ipv6 {
                description
                  "ipv6 access-list";
                leaf name {
                  description
                    "access-list name";
                  type string;
                }
              }
            }
            container remote {
              description
                "Specify routes to be pushed to peer";
              list ipv4 {
                description
                  "ipv4 route";
                key "prefix";
                leaf prefix {
                  description
                    "IP address prefix";
                  type inet:ipv4-address;
                }
                leaf ipv4-mask {
                  description
                    "specify mask";
                  type inet:ipv4-address;
                }
              }
              list ipv6 {
                description
                  "pv6 route";
                key "prefix";
                leaf prefix {
                  description
                    "IPv6 address/prefix-length";
                  type ios-types:ipv6-prefix;
                }
              }
            }
            container local {
              description
                "Specify route set local parameters";
              list ipv4 {
                description
                  "ipv4 route";
                key "prefix";
                leaf prefix {
                  description
                    "IP address prefix";
                  type inet:ipv4-address;
                }
                leaf ipv4-mask {
                  description
                    "specify mask";
                  type inet:ipv4-address;
                }
                uses crypto-ikev2-authorization-route-set-local-grouping;
              }
              list ipv6 {
                description
                  "ipv6 route";
                key "prefix";
                leaf prefix {
                  description
                    "IPv6 address/prefix-length";
                  type ios-types:ipv6-prefix;
                }
                uses crypto-ikev2-authorization-route-set-local-grouping;
              }
            }
          }
          container accept {
            description
              "Route accept parameters";
            container any-option {
              description
                "Accept all subnets from peer";
              presence "true";
              leaf tag {
                description
                  "Specify tag for routes to remote subnets";
                type uint64 {
                  range "1..497777";
                }
              }
              leaf distance {
                description
                  "Specify distance for routes to remote subnets";
                type uint16 {
                  range "1..255";
                }
              }
            }
            container any {
              description
                "Accept all subnets from peer";
              status obsolete;
              choice distance-tag {
                status obsolete;
                case distance {
                  status obsolete;
                  leaf distance {
                    description
                      "Specify distance for routes to remote subnets";
                    status obsolete;
                    type uint16 {
                      range "1..255";
                    }
                  }
                }
                case tag {
                  status obsolete;
                  leaf tag {
                    description
                      "Specify tag for routes to remote subnets";
                    status obsolete;
                    type uint64 {
                      range "1..497777";
                    }
                  }
                }
              }
            }
            leaf route-map {
              description
                "Route map reference";
              type string;
            }
          }
        }
        container ipv6 {
          description
            "Specify the ipv6 attributes";
          container dns {
            description
              "Specify DNS Addresses";
            leaf primary {
              description
                "Primary DNS IPv6 address";
              type inet:ipv6-address;
            }
            leaf secondary {
              description
                "Secondary DNS IPv6 address";
              when '../primary';
              type inet:ipv6-address;
            }
          }
          container pool {
            description
              "Specify local address pool";
            leaf pool-name {
              description
                "address pool name";
              type string;
            }
          }
          leaf prefix {
            description
              "Specify ipv6 prefix length of the config address";
            type uint8 {
              range "1..128";
            }
          }
        }
        container pool {
          description
            "Specify local address pool";
          leaf pool-name {
            type string;
          }
        }
        container aaa {
          description
            "Specify aaa attribute list";
          container attribute {
            description
              "AAA attribute list";
            leaf list {
              description
                "AAA attribute list";
              type string;
            }
            leaf aaa-attribute-list {
              description
                "AAA attribute list";
              status obsolete;
              type string;
            }
          }
        }
        list split-dns {
          description
            "Split DNS names";
          key "name";
          leaf name {
            description
              "DNS extension";
            type string;
          }
        }
        leaf backup-gateway {
          description
            "Specify backup gateway";
          type union {
            type inet:ipv4-address;
            type string;
          }
        }
        leaf def-domain {
          description
            "Set default domain name to send to client";
          type string;
        }
        container dns {
          description
            "Specify DNS Addresses";
          leaf primary {
            description
              "Primary DNS IP address";
            type inet:ipv4-address;
          }
          leaf secondary {
            description
              "Secondary DNS IP address";
            type inet:ipv4-address;
          }
        }
        container dhcp {
          description
            "Specify DHCP server for config address";
          leaf giaddr {
            description
              "Specify giaddr for dhcp scope";
            type inet:ip-address;
          }
          leaf server {
            description
              "Specify dhcp server addresses";
            type union {
              type inet:ipv4-address;
              type string;
            }
          }
          leaf timeout {
            description
              "Specify DHCP response timeout in seconds";
            type uint8 {
              range "4..30";
            }
          }
        }
        leaf session-lifetime {
          description
            "Specify maximum session lifetime";
          type uint64 {
            range "120..25920000";
          }
        }
        leaf smartcard-removal-disconnect {
          description
            "Enables smartcard-removal-disconnect";
          type empty;
        }
        container wins {
          description
            "Specify WINS Addresses";
          leaf primary {
            description
              "Primary WINS IP address";
            type inet:ipv4-address;
          }
          leaf secondary {
            description
              "Secondary WINS IP address";
            when '../primary';
            type inet:ipv4-address;
          }
        }
      }
    }
    leaf certificate-cache {
      description
        "Cache for storing certs fetched from HTTP URLs";
      type uint16;
    }
    container client {
      description
        "IKEv2 client configuration";
      list flexvpn {
        key "flexvpn-name";
        leaf flexvpn-name {
          description
            "Configure an IKEv2 FlexVPN client";
          type string;
        }
        container peer {
          description
            "Allowed Encryption/Decryption Peer";
          list peer-id-list {
            description
              "peer sequence number";
            key "peer-id";
            leaf peer-id {
              type uint8;
            }
            container peer-id-container-option {
              choice address-fqdn {
                case peer-address {
                  leaf peer-address {
                    description
                      "ip address";
                    type inet:ip-address;
                  }
                  leaf track {
                    description
                      "Peer track object";
                    type uint16 {
                      range "0..1000";
                    }
                  }
                  leaf up-down {
                    type enumeration {
                      enum up;
                      enum down;
                    }
                  }
                }
                case fqdn {
                  container fqdn {
                    leaf fqdn {
                      description
                        "Peer host name";
                      type string;
                    }
                    leaf dynamic {
                      description
                        "Dynamic host name";
                      type empty;
                    }
                    leaf ipv6 {
                      description
                        "IPv6 host name";
                      type empty;
                    }
                    leaf track {
                      description
                        "Peer track object";
                      type uint16 {
                        range "0..1000";
                      }
                    }
                    leaf up-down {
                      type enumeration {
                        enum up;
                        enum down;
                      }
                    }
                  }
                }
              }
            }
            container peer-id-container {
              status obsolete;
              leaf peer-address {
                description
                  "ip address";
                status obsolete;
                type inet:ip-address;
              }
              leaf track {
                description
                  "Peer track object";
                status obsolete;
                type uint16 {
                  range "0..1000";
                }
              }
              leaf up-down {
                status obsolete;
                type enumeration {
                  enum up;
                  enum down;
                }
              }
            }
          }
          leaf reactivate {
            description
              "Re-activate peer enabled";
            type empty;
          }
        }
        container connect {
          leaf auto {
            description
              "Enable FlexVPN in Automatic mode";
            type empty;
          }
          leaf manual {
            description
              "Enable FlexVPN in Manual mode";
            type empty;
          }
          leaf track {
            type uint16 {
              range "0..1000";
            }
          }
          leaf up-down {
            type enumeration {
              enum up;
              enum down;
            }
          }
        }
        list source {
          key "source-id";
          leaf source-id {
            type uint8 {
              range "1..255";
            }
          }
          container interface-name {
            uses ios-ifc:interface-grouping;
            leaf track {
              type uint16 {
                range "1..1000";
              }
            }
          }
          container source-id-container {
            status obsolete;
            leaf interface-name {
              status obsolete;
              type string;
            }
            leaf track {
              status obsolete;
              type uint16 {
                range "1..1000";
              }
            }
          }
        }
        container client {
          container connect {
            leaf Tunnel {
              type uint32 {
                range "0..2147483647";
              }
            }
          }
          container inside {
            description
              "inside interface";
            uses ios-ifc:interface-grouping;
          }
        }
        container backup {
          description
            "Backup Configuration";
          container group {
            description
              "Group";
            choice group-number-default {
              case group-number-case {
                leaf group-number {
                  type uint16 {
                    range "1..255";
                  }
                }
              }
              case default-case {
                leaf default {
                  description
                    "Default Group";
                  type boolean;
                  default "true";
                }
              }
            }
          }
        }
      }
    }
    container cluster-options {
      description
        "Cluster load-balancer settings";
      presence "true";
      leaf fqdn {
        description
          "Fully qualified domain name string";
        type string;
      }
      leaf holdtime {
        description
          "Hold time interval";
        type uint32 {
          range "100..120000";
        }
      }
      container primary {
        description
          "Primary settings";
        leaf overload-limit {
          description
            "Threshold load of cluster";
          type uint8 {
            range "50..99";
          }
        }
        container weight {
          description
            "Weight of a load attribute";
          leaf crypto-load {
            description
              "IKE and IPsec SA load. Default is 100.";
            type uint8 {
              range "0..100";
            }
          }
          leaf system-load {
            description
              "CPU and memory usage load. Default is 100.";
            type uint8 {
              range "0..100";
            }
          }
        }
      }
      container master {
        description
          "Master settings";
        leaf overload-limit {
          description
            "Threshold load of cluster";
          type uint8 {
            range "50..99";
          }
        }
        container weight {
          description
            "Weight of a load attribute";
          leaf crypto-load {
            description
              "IKE and IPsec SA load. Default is 100.";
            type uint8 {
              range "0..100";
            }
          }
          leaf system-load {
            description
              "CPU and memory usage load. Default is 100.";
            type uint8 {
              range "0..100";
            }
          }
        }
      }
      leaf port {
        description
          "Load feed port";
        type uint32 {
          range "1..65535";
        }
      }
      container secondary {
        description
          "Secondary settings";
        leaf hello {
          description
            "Hello time interval";
          type uint32 {
            range "100..30000";
          }
        }
        leaf max-session {
          description
            "Maximum SAs (IKE and IPsec)";
          type uint32 {
            range "1..100000";
          }
        }
        leaf priority {
          description
            "Priority";
          type uint16 {
            range "1..100";
          }
        }
        leaf load-normalization {
          description
            "Load-normalization factor";
          type uint16 {
            range "1..100";
          }
          default "5";
        }
        leaf update {
          description
            "Load update time interval";
          type uint32 {
            range "100..60000";
          }
        }
      }
      container slave {
        description
          "Slave settings";
        leaf hello {
          description
            "Hello time interval";
          type uint32 {
            range "100..30000";
          }
        }
        leaf max-session {
          description
            "Maximum SAs (IKE and IPsec)";
          type uint32 {
            range "1..100000";
          }
        }
        leaf priority {
          description
            "Priority";
          type uint16 {
            range "1..100";
          }
        }
        leaf update {
          description
            "Load update time interval";
          type uint32 {
            range "100..60000";
          }
        }
      }
      container standby-group {
        description
          "HSRP group";
        leaf name {
          description
            "HSRP group name";
          type string;
        }
      }
      leaf shutdown-cluster {
        description
          "Shutdown the cluster";
        type boolean;
        default "true";
      }
      leaf shutdown {
        description
          "This node is deprecated and replaced by shutdown-cluster";
        status deprecated;
        type empty;
      }
    }
    container cluster {
      description
        "Cluster load-balancer settings";
      status deprecated;
      container slave {
        description
          "Slave settings";
        status obsolete;
        leaf hello {
          description
            "Hello time interval";
          status obsolete;
          type uint32 {
            range "100..30000";
          }
        }
        leaf max-session {
          description
            "Maximum SAs (IKE and IPsec)";
          status obsolete;
          type uint32 {
            range "1..100000";
          }
        }
        leaf priority {
          description
            "Priority";
          status obsolete;
          type uint16 {
            range "1..100";
          }
        }
        leaf update {
          description
            "Load update time interval";
          status obsolete;
          type uint32 {
            range "100..60000";
          }
        }
      }
      container standby-group {
        description
          "HSRP group";
        status deprecated;
        leaf name {
          description
            "HSRP group name";
          status deprecated;
          type string;
        }
      }
    }
    leaf cookie-challenge {
      description
        "Set Cookie-challenge watermark";
      type uint16 {
        range "0..1000";
      }
    }
    container cts {
      description
        "Cisco Trust Security";
      leaf sgt {
        description
          "Security Group Tag";
        type empty;
      }
    }
    container diagnose {
      description
        "IKEV2 diagnose";
      leaf error {
        description
          "Start IKEv2 error trace debug";
        type uint16 {
          range "1..1000";
        }
      }
    }
    leaf disconnect-revoked-peers {
      description
        "Disconnect Crypto Session with Cert Revoked Peer";
      type empty;
    }
    container dpd-container {
      leaf dpd {
        description
          "Enable IKE liveness check for peers";
        type uint16 {
          range "10..3600";
        }
      }
      leaf retry-interval {
        type uint8 {
          range "2..60";
        }
      }
      leaf dpd-query {
        type enumeration {
          enum on-demand;
          enum periodic;
        }
      }
    }
    container fragmentation {
      description
        "Enable fragmentation of ikev2 packets";
      presence "true";
      leaf mtu {
        description
          "MTU size for fragmentation";
        type uint16 {
          range "68..1500";
        }
        default "576";
      }
    }
    container http-url {
      description
        "Enable http URL lookup";
      leaf cert-leaf {
        description
          "Enable certificate lookup based on HTTP-based URL";
        type boolean;
        default "true";
      }
      leaf cert {
        description
          "Enable certificate lookup based on HTTP-based URL";
        status deprecated;
        type empty;
      }
      leaf bundle {
        description
          "Enable bundle lookup based on HTTP-based URL";
        type empty;
      }
    }
    list keyring {
      description
        "Define IKEv2 Keyring";
      key "name";
      leaf name {
        type string;
      }
      list peer {
        description
          "Configure a Peer and associated keys";
        key "name";
        leaf name {
          type string;
        }
        uses crypto-ikev2-keyring-peer-grouping;
      }
    }
    container limit {
      description
        "Limit the number of maximum and negotiating sa";
      container max-neg-sa {
        leaf max-in-negotation-sa {
          description
            "Limit the maximum number of negotiating SA";
          type uint32 {
            range "1..9999";
          }
        }
        leaf direction {
          type enumeration {
            enum incoming;
            enum outgoing;
          }
        }
      }
      leaf max-sa {
        description
          "Limit the maximum number of SA allowed";
        type uint32 {
          range "1..9999";
        }
      }
      container queue {
        description
          "Limit size of queue";
        leaf sa-init {
          description
            "Limit size of LOW Q (incoming SA INIT requests)";
          type uint32 {
            range "100..100000";
          }
          default "5000";
        }
      }
    }
    list name-mangler {
      description
        "Name mangler";
      key "name";
      leaf name {
        type string;
      }
      leaf dn {
        description
          "Derive name from DN identity";
        type enumeration {
          enum common-name;
          enum country;
          enum domain;
          enum locality;
          enum organization;
          enum organization-unit;
          enum state;
        }
      }
      container eap {
        description
          "Derive name from EAP identity";
        choice eap-options {
          case dn {
            leaf dn {
              description
                "Derive name from DN identity";
              type enumeration {
                enum common-name;
                enum country;
                enum domain;
                enum locality;
                enum organization;
                enum organization-unit;
                enum state;
              }
            }
          }
          case all {
            leaf all {
              description
                "entire portion of the identity";
              type empty;
            }
          }
          case prefix {
            container prefix {
              description
                "prefix portion of eap identity";
              container delimiter {
                description
                  "Specify the delimiter";
                choice delimeter-choice {
                  leaf dot {
                    type empty;
                  }
                  leaf at-sign {
                    type empty;
                  }
                  leaf slash-sign {
                    type empty;
                  }
                }
              }
            }
          }
          case suffix {
            container suffix {
              description
                "suffix portion of eap identity";
              container delimiter {
                description
                  "Specify the delimiter";
                choice delimeter-choice {
                  leaf dot {
                    type empty;
                  }
                  leaf at-sign {
                    type empty;
                  }
                  leaf slash-sign {
                    type empty;
                  }
                }
              }
            }
          }
        }
      }
      leaf email {
        description
          "Derive name from EMAIL identity";
        type enumeration {
          enum all;
          enum domain;
          enum username;
        }
      }
      leaf fqdn {
        description
          "Derive name from FQDN identity";
        type enumeration {
          enum all;
          enum domain;
          enum hostname;
        }
      }
    }
    container nat {
      description
        "NAT-transparency";
      leaf keepalive {
        description
          "Set NAT keepalive interval";
        type uint16 {
          range "5..3600";
        }
      }
    }
    list policy {
      description
        "Define IKEV2 policies";
      key "name";
      leaf name {
        type string;
      }
      container match {
        description
          "Match values of local fields";
        leaf inbound-only {
          description
            "inbound only for controller";
          type empty;
        }
        container address {
          description
            "Specify the address to match";
          leaf-list local-ip {
            description
              "Local address";
            type inet:ip-address;
          }
          leaf local {
            description
              "DEPRECATED (use local-ip)";
            status deprecated;
            type inet:ip-address;
          }
        }
        container fvrf {
          description
            "Specify fvrf";
          leaf name {
            type string;
          }
          leaf any {
            description
              "Any fvrf";
            type empty;
          }
        }
      }
      list proposal {
        description
          "Specify Proposal";
        key "proposals";
        leaf proposals {
          must "(.='default') or (((/ios:native/ios:crypto/ikev2/proposal[name=current()]/group/one or /ios:native/ios:crypto/ikev2/proposal[name=current()]/group/fourteen or /ios:native/ios:crypto/ikev2/proposal[name=current()]/group/fifteen or /ios:native/ios:crypto/ikev2/proposal[name=current()]/group/sixteen or /ios:native/ios:crypto/ikev2/proposal[name=current()]/group/nineteen or /ios:native/ios:crypto/ikev2/proposal[name=current()]/group/two or /ios:native/ios:crypto/ikev2/proposal[name=current()]/group/twenty or /ios:native/ios:crypto/ikev2/proposal[name=current()]/group/twenty-one or /ios:native/ios:crypto/ikev2/proposal[name=current()]/group/twenty-four or /ios:native/ios:crypto/ikev2/proposal[name=current()]/group/five) and (/ios:native/ios:crypto/ikev2/proposal[name=current()]/encryption/en-3des or /ios:native/ios:crypto/ikev2/proposal[name=current()]/encryption/aes-cbc-128 or /ios:native/ios:crypto/ikev2/proposal[name=current()]/encryption/aes-cbc-192 or /ios:native/ios:crypto/ikev2/proposal[name=current()]/encryption/aes-cbc-256 or /ios:native/ios:crypto/ikev2/proposal[name=current()]/encryption/des) and (/ios:native/ios:crypto/ikev2/proposal[name=current()]/integrity/md5 or /ios:native/ios:crypto/ikev2/proposal[name=current()]/integrity/sha1 or /ios:native/ios:crypto/ikev2/proposal[name=current()]/integrity/sha256 or /ios:native/ios:crypto/ikev2/proposal[name=current()]/integrity/sha384 or /ios:native/ios:crypto/ikev2/proposal[name=current()]/integrity/sha512)) or ((/ios:native/ios:crypto/ikev2/proposal[name=current()]/group/one or /ios:native/ios:crypto/ikev2/proposal[name=current()]/group/fourteen or /ios:native/ios:crypto/ikev2/proposal[name=current()]/group/fifteen or /ios:native/ios:crypto/ikev2/proposal[name=current()]/group/sixteen or /ios:native/ios:crypto/ikev2/proposal[name=current()]/group/nineteen or /ios:native/ios:crypto/ikev2/proposal[name=current()]/group/two or /ios:native/ios:crypto/ikev2/proposal[name=current()]/group/twenty or /ios:native/ios:crypto/ikev2/proposal[name=current()]/group/twenty-one or /ios:native/ios:crypto/ikev2/proposal[name=current()]/group/twenty-four or /ios:native/ios:crypto/ikev2/proposal[name=current()]/group/five) and (/ios:native/ios:crypto/ikev2/proposal[name=current()]/encryption/aes-gcm-128 or /ios:native/ios:crypto/ikev2/proposal[name=current()]/encryption/aes-gcm-256) and (/ios:native/ios:crypto/ikev2/proposal[name=current()]/prf/md5 or /ios:native/ios:crypto/ikev2/proposal[name=current()]/prf/sha1 or /ios:native/ios:crypto/ikev2/proposal[name=current()]/prf/sha256 or /ios:native/ios:crypto/ikev2/proposal[name=current()]/prf/sha384 or /ios:native/ios:crypto/ikev2/proposal[name=current()]/prf/sha512)))" {
            error-message "IKEv2 policy MUST have only complete proposals attached";
          }
          type string;
        }
      }
    }
    list profile {
      description
        "Define IKEV2 profiles";
      key "name";
      leaf name {
        type string;
      }
      uses crypto-ikev2-profile-grouping;
    }
    list proposal {
      description
        "Define IKEV2 proposals";
      key "name";
      leaf name {
        type string;
      }
      container encryption {
        description
          "Set encryption algorithm(s) for proposal";
        leaf en-3des {
          description
            "3DES";
          type empty;
        }
        leaf aes-cbc-128 {
          description
            "AES-CBC-128";
          type empty;
        }
        leaf aes-cbc-192 {
          description
            "AES-CBC-192";
          type empty;
        }
        leaf aes-cbc-256 {
          description
            "AES-CBC-256";
          type empty;
        }
        leaf aes-gcm-128 {
          description
            "Combined-mode,128 bit key,16 byte ICV(Authentication Tag)";
          type empty;
        }
        leaf aes-gcm-256 {
          description
            "Combined-mode,256 bit key,16 byte ICV(Authentication Tag)";
          type empty;
        }
        leaf des {
          description
            "DES";
          type empty;
        }
      }
      container group {
        description
          "Set the Diffie-Hellman group(s)";
        leaf one {
          description
            "DH 768 MODP";
          type empty;
        }
        leaf fourteen {
          description
            "DH 2048 MODP";
          type empty;
        }
        leaf fifteen {
          description
            "DH 3072 MODP";
          type empty;
        }
        leaf sixteen {
          description
            "DH 4096 MODP";
          type empty;
        }
        leaf nineteen {
          description
            "DH 256 ECP";
          type empty;
        }
        leaf two {
          description
            "DH 1024 MODP";
          type empty;
        }
        leaf twenty {
          description
            "DH 384 ECP";
          type empty;
        }
        leaf twenty-one {
          description
            "DH 521 ECP";
          type empty;
        }
        leaf twenty-four {
          description
            "DH 2048 (256 subgroup) MODP";
          type empty;
        }
        leaf five {
          description
            "DH 1536 MODP";
          type empty;
        }
      }
      container integrity {
        description
          "Set integrity hash algorithm(s) for proposal";
        leaf md5 {
          description
            "Message Digest 5";
          type empty;
        }
        leaf sha1 {
          description
            "Secure Hash Standard";
          type empty;
        }
        leaf sha256 {
          description
            "Secure Hash Standard 2 (256 bit)";
          type empty;
        }
        leaf sha384 {
          description
            "Secure Hash Standard 2 (384 bit)";
          type empty;
        }
        leaf sha512 {
          description
            "Secure Hash Standard 2 (512 bit)";
          type empty;
        }
      }
      container prf {
        description
          "Set prf algorithm(s) for proposal";
        leaf md5 {
          description
            "Message Digest 5";
          type empty;
        }
        leaf sha1 {
          description
            "Secure Hash Standard";
          type empty;
        }
        leaf sha256 {
          description
            "Secure Hash Standard 2 (256 bit)";
          type empty;
        }
        leaf sha384 {
          description
            "Secure Hash Standard 2 (384 bit)";
          type empty;
        }
        leaf sha512 {
          description
            "Secure Hash Standard 2 (512 bit)";
          type empty;
        }
      }
    }
    container reconnect {
      description
        "Cluster Reconnect";
      list key {
        description
          "Cluster Reconnect key";
        max-elements 2;
        key "key-index";
        leaf key-index {
          type uint8 {
            range "1..2";
          }
        }
        leaf active {
          description
            "Current active cluster reconnect key";
          type empty;
        }
        leaf key-value {
          type string {
            length "1..128";
          }
        }
      }
    }
    container redirect {
      description
        "IKEv2 Redirect Mechanism for load-balancing";
      container client {
        description
          "Enables Redirect Mechanism on Client";
        presence "true";
        leaf max-redirects {
          description
            "Redirect loop detection";
          type uint8 {
            range "1..255";
          }
        }
      }
      leaf gateway {
        description
          "Enables Redirect Mechanism on Gateway";
        type enumeration {
          enum auth;
          enum init;
        }
      }
    }
    leaf window {
      description
        "IKEV2 window size";
      type uint8 {
        range "1..200";
      }
      default "5";
    }
  }

  grouping crypto-ipsec-profile-grouping {
    leaf description {
      description
        "Description of the crypto map statement policy";
      type string;
    }
    container dialer {
      description
        "Dialer related commands";
      leaf pre-classify {
        description
          "Enable dialer list classification before initiating IKE";
        type empty;
      }
    }
    container redundancy {
      description
        "Configure HA for this ipsec profile";
      leaf name {
        type string;
      }
      leaf stateful {
        description
          "enable stateful failover";
        type empty;
      }
    }
    leaf responder-only {
      description
        "Do not initiate SAs from this device";
      type empty;
    }
    uses reverse-route-common-grouping;
    container set {
      description
        "Set values for encryption/decryption";
      leaf group {
        description
          "Set the san group parameters";
        status obsolete;
        type string;
      }
      uses ipsec-common-set-grouping;
      leaf mixed-mode {
        description
          "Turn on IPSec mixed-mode";
        type empty;
      }
      container security-association {
        description
          "Security association parameters";
        uses crypto-map-common-set-security-association-grouping;
        leaf level {
          description
            "specify a security association granularity level for identities";
          type enumeration {
            enum per-host;
          }
        }
      }
      container security-policy {
        description
          "Maximum number of Security Policy entries that can be negotiated with the peer";
        leaf limit {
          description
            "limit  0 - 50000";
          type uint32 {
            range "0..50000";
          }
        }
      }
    }
  }

  grouping crypto-ipsec-profile-default-grouping {
    leaf description {
      description
        "Description of the crypto map statement policy";
      type empty;
    }
    container dialer {
      description
        "Dialer related commands";
      leaf pre-classify {
        description
          "Enable dialer list classification before initiating IKE";
        type empty;
      }
    }
    leaf redundancy {
      description
        "Configure HA for this ipsec profile";
      type empty;
    }
    leaf responder-only {
      description
        "Do not initiate SAs from this device";
      type empty;
    }
    container set {
      description
        "Set values for encryption/decryption";
      leaf group {
        description
          "Set the san group parameters";
        status obsolete;
        type empty;
      }
      leaf identity {
        description
          "Identity restriction";
        type empty;
      }
      leaf ikev2-profile {
        description
          "Specify ikev2 Profile";
        type string;
      }
      leaf isakmp-profile {
        description
          "Specify isakmp Profile";
        type empty;
      }
      leaf mixed-mode {
        description
          "Turn on IPSec mixed-mode";
        type empty;
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          leaf idle-time {
            description
              "Automatically delete IPSec SAs after a given idle period.";
            type empty;
          }
          leaf default {
            description
              "All SAs idle-out reset to default peer";
            type empty;
          }
        }
        leaf level {
          description
            "specify a security association granularity level for identities";
          type enumeration {
            enum per-host;
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      container security-policy {
        description
          "Maximum number of Security Policy entries that can be negotiated with the peer";
        leaf limit {
          description
            "limit  0 - 50000";
          type uint32 {
            range "0..50000";
          }
        }
      }
      leaf-list transform-set {
        description
          "Specify list of transform sets in priority order";
        type string;
      }
    }
  }

  grouping crypto-ipsec-grouping {
    leaf df-bit {
      description
        "Handling of encapsulated DF bit.";
      type enumeration {
        enum clear;
        enum copy;
        enum set;
      }
    }
    container exclude {
      description
        "LI exclude list";
      container peer-list {
        description
          "LI peer";
        list ipv4 {
          description
            "ipv4-address";
          key "address";
          leaf address {
            type inet:ipv4-address;
          }
        }
        list ipv6 {
          description
            "IPv6  address";
          key "address";
          leaf address {
            type inet:ipv6-address;
          }
        }
      }
    }
    leaf fragmentation {
      description
        "Handling of fragmentation of near-MTU sized packets";
      type enumeration {
        enum after-encryption;
        enum before-encryption;
      }
    }
    leaf ipv4-deny {
      description
        "Configure global ipv4 deny policy.";
      type enumeration {
        enum clear;
        enum drop;
        enum jump;
      }
    }
    leaf nat-transparency {
      description
        "IPsec NAT transparency model";
      type enumeration {
        enum spi-matching;
        enum udp-encapsulation;
      }
      default "udp-encapsulation";
    }
    container optional {
      description
        "Enable optional encryption for IPSec";
      presence "true";
      leaf retry {
        description
          "Configure length of IPSec retry interval";
        type uint32 {
          range "60..86400";
        }
        default "300";
      }
    }
    list transform-set {
      description
        "Define transform and settings";
      key "tag";
      leaf tag {
        type string;
      }
      leaf ah-hmac {
        type enumeration {
          enum ah-md5-hmac;
          enum ah-sha-hmac;
          enum ah-sha256-hmac;
          enum ah-sha384-hmac;
          enum ah-sha512-hmac;
        }
      }
      leaf comp-lzs {
        description
          "IP Compression using the LZS compression algorithm";
        type empty;
      }
      leaf esp {
        when 'not(../ah-hmac)';
        type enumeration {
          enum esp-3des;
          enum esp-aes;
          enum esp-des;
          enum esp-gcm;
          enum esp-gmac;
          enum esp-null;
          enum esp-seal;
          enum esp-192-aes;
          enum esp-256-aes;
        }
      }
      leaf key-bit {
        when "../esp != 'esp-3des' and ../esp != 'esp-des' and ../esp != 'esp-null' and ../esp != 'esp-seal' and ../esp !=   'esp-192-aes' and ../esp != 'esp-256-aes'";
        type enumeration {
          enum 128;
          enum 192;
          enum 256;
        }
      }
      leaf esp-hmac {
        when "../esp != 'esp-gcm' and ../esp != 'esp-gmac'";
        type enumeration {
          enum esp-md5-hmac;
          enum esp-sha-hmac;
          enum esp-sha256-hmac;
          enum esp-sha384-hmac;
          enum esp-sha512-hmac;
        }
      }
      container default {
        status obsolete;
        description
          "Set a command to its defaults";
        leaf mode {
          status obsolete;
          description
            "encapsulation mode (transport/tunnel)";
          type empty;
        }
      }
      leaf esn {
        when '../ah-hmac or ../esp';
        description
          "extended Sequence number";
        type empty;
      }
      container mode {
        when '../ah-hmac or ../esp';
        description
          "encapsulation mode (transport/tunnel)";
        choice mode-type {
          case transport-case {
            container transport-choice {
              description
                "transport (payload encapsulation) mode";
              presence "true";
              leaf require {
                description
                  "Accept only the configured encapsulation mode.";
                type empty;
              }
            }
          }
          case tunnel-case {
            leaf tunnel-choice {
              description
                "tunnel (datagram encapsulation) mode";
              type empty;
            }
          }
        }
        container transport {
          status deprecated;
          description
            "DEPRECATED (use mode-type transport)";
          presence "true";
          leaf require {
            status deprecated;
            description
              "DEPRECATED (use mode-type transport require) ";
            type empty;
          }
        }
        leaf tunnel {
          status deprecated;
          description
            "DEPRECATED (use mode-type tunnel)";
          type empty;
        }
      }
    }
    list profile {
      description
        "Configure an ipsec policy profile";
      key "name";
      leaf name {
        type string;
      }
      container default {
        description
          "Set a command to its defaults";
        uses crypto-ipsec-profile-default-grouping;
      }
      uses crypto-ipsec-profile-grouping;
    }
    container security-association {
      description
        "Security association parameters";
      container dummy {
        description
          "Enable transmitting dummy packets";
        leaf pps {
          description
            "Simulated traffic rate (in pps)";
          type uint8 {
            range "0..25";
          }
        }
        leaf seconds {
          description
            "Simulated traffic rate (in seconds)";
          type uint16 {
            range "1..3600";
          }
        }
      }
      leaf ecn {
        description
          "Handling of ECN bit";
        type enumeration {
          enum discard;
          enum propagate;
        }
        default "discard";
      }
      leaf idle-time {
        description
          "Automatically delete IPSec SAs after a given idle period.";
        type uint32 {
          range "60..86400";
        }
      }
      container lifetime {
        description
          "security association lifetime";
        leaf days {
          description
            "Time-based key duration in days";
          type uint8 {
            range "1";
          }
        }
        leaf kilobytes {
          description
            "Volume-based key duration";
          type union {
            type uint64 {
              range "2560..4294967295";
            }
            type enumeration {
              enum disable;
            }
          }
          default "4608000";
        }
        leaf seconds {
          description
            "Time-based key duration in seconds";
          type uint64 {
            range "120..86400";
          }
          default "3600";
        }
      }
      leaf multi-sn {
        description
          "Enable multiple sequence number per IPSec SA";
        type empty;
      }
      container replay {
        description
          "Set replay checking.";
        leaf disable {
          description
            "Disable replay checking";
          type empty;
        }
        leaf window-size {
          description
            "Set replay window size.";
          type enumeration {
            enum 1024;
            enum 128;
            enum 256;
            enum 512;
            enum 64;
          }
          default "64";
        }
      }
    }
    container session-key {
      description
        "security association parameters";
      container dummy {
        description
          "Enable transmitting dummy packets";
        leaf pps {
          description
            "Simulated traffic rate (in pps)";
          type uint8 {
            range "0..25";
          }
        }
        leaf seconds {
          description
            "Simulated traffic rate (in seconds)";
          type uint16 {
            range "1..3600";
          }
        }
      }
      leaf ecn {
        description
          "Handling of ECN bit";
        type enumeration {
          enum discard;
          enum propagate;
        }
      }
      leaf idle-time {
        description
          "Automatically delete IPSec SAs after a given idle period";
        type uint32 {
          range "60..86400";
        }
      }
      container lifetime {
        description
          "security association lifetime";
        leaf days {
          description
            "Time-based key duration in days";
          type uint8 {
            range "1..30";
          }
        }
        leaf kilobytes {
          description
            "Volume-based key duration";
          type union {
            type uint32 {
              range "2560..4294967295";
            }
            type enumeration {
              enum disable;
            }
          }
        }
        leaf seconds {
          description
            "Time-based key duration in seconds";
          type uint32 {
            range "120..2592000";
          }
        }
      }
      leaf multi-sn {
        description
          "Enable multiple sequence number per IPSec SA";
        type empty;
      }
      container replay {
        description
          "Set replay checking";
        leaf disable {
          description
            "Disable replay checking";
          type empty;
        }
        leaf window-size {
          description
            "Set replay window size";
          type enumeration {
            enum 1024;
            enum 512;
            enum 256;
            enum 128;
            enum 64;
          }
        }
      }
    }
    container ike {
      description
        "Common global config for ISAKMP and IKEv2";
      leaf sa-strength-enforcement {
        description
          "Ensures IKE encryption cipher strength is higher than
           the strength of its child IPsec SA's encryption ciphers";
        type empty;
      }
    }
  }

  grouping crypto-isakmp-policy-grouping {
    leaf authentication {
      description
        "Set authentication method for protection suite";
      type enumeration {
        enum pre-share;
        enum rsa-encr;
        enum rsa-sig;
      }
    }
    container encryption {
      description
        "Set encryption algorithm for protection suite";
      leaf aes-192 {
        description
          "AES - Advanced Encryption Standard (192 bit keys)";
        type empty;
      }
      leaf aes-256 {
        description
          "AES - Advanced Encryption Standard (256 bit keys)";
        type empty;
      }
      leaf a3des {
        type empty;
      }
      choice encryption-type {
        case aes-case {
          container aes-choice {
            description
              "AES - Advanced Encryption Standard.";
            presence "true";
            leaf key-type {
              type enumeration {
                enum 128;
                enum 192;
                enum 256;
              }
            }
          }
        }
        case des-case {
          leaf des-choice {
            description
              "DES - Data Encryption Standard (56 bit keys).";
            type empty;
          }
        }
      }
      container aes {
        status deprecated;
        description
          "DEPRECATED (use encryption-type aes)";
        presence "true";
        leaf key {
          status deprecated;
          description
            "DEPRECATED (use encryption-type aes key)";
          type enumeration {
            enum 128;
            enum 192;
            enum 256;
          }
        }
      }
      leaf des {
        status deprecated;
        description
          "DEPRECATED (use encryption-type des)";
        type empty;
      }
    }
    leaf group {
      description
        "Set the Diffie-Hellman group";
      type enumeration {
        enum 1;
        enum 14;
        enum 15;
        enum 16;
        enum 19;
        enum 2;
        enum 20;
        enum 21;
        enum 24;
        enum 5;
      }
    }
    leaf hash {
      description
        "Set hash algorithm for protection suite";
      type enumeration {
        enum md5;
        enum sha;
        enum sha256;
        enum sha384;
        enum sha512;
      }
    }
  }

  grouping crypto-keyring-grouping {
    leaf description {
      description
        "Specify a description about this keyring";
      type string;
    }
    container local-address {
      description
        "Limit the keyring usage to a local address";
      uses crypto-local-address-grouping;
    }
    container pre-shared-key {
      description
        "Pre-Shared Key";
      container address {
        description
          "pre shared key by address";
        choice ipv4-ipv6 {
          case ipv4 {
            list ipv4 {
              description
                "address prefix";
              key "ipv4-addr";
              leaf ipv4-addr {
                type inet:ipv4-address;
              }
              leaf mask {
                description
                  "address prefix mask";
                type inet:ipv4-address;
              }
              uses crypto-keyring-key-grouping {
                refine "key";
              }
            }
          }
          case ipv6 {
            list ipv6 {
              description
                "define shared key with IPv6 address";
              key "ipv6-addr";
              leaf ipv6-addr {
                description
                  "IPv6 address prefix";
                type ios-types:ipv6-prefix;
              }
              uses crypto-keyring-key-grouping {
                refine "key";
              }
            }
          }
        }
      }
      list hostname {
        description
          "hostname  define peer policy for hostname";
        key "name";
        leaf name {
          type string;
        }
        uses crypto-keyring-key-grouping;
      }
    }
    container rsa-pubkey {
      description
        "Peer RSA public key chain management";
      list address {
        description
          "Public key associated with an address";
        key "addr";
        leaf addr {
          description
            "Public key associated with an address";
          type inet:ipv4-address;
        }
        leaf way {
          type enumeration {
            enum encryption;
            enum signature;
          }
        }
        uses rsa-key-grouping;
      }
      container addr {
        status obsolete;
        leaf address {
          description
            "Public key associated with an address";
          status obsolete;
          type inet:ipv4-address;
        }
        leaf way {
          status obsolete;
          type enumeration {
            enum encryption;
            enum signature;
          }
        }
      }
      list name {
        key "hostname";
        leaf hostname {
          description
            "Public key associated with a hostname";
          type string;
        }
        leaf way {
          type enumeration {
            enum encryption;
            enum signature;
          }
        }
        uses rsa-key-grouping;
      }
      container hostname {
        status obsolete;
        leaf name {
          description
            "Public key associated with a hostname";
          status obsolete;
          type string;
        }
        leaf way {
          status obsolete;
          type enumeration {
            enum encryption;
            enum signature;
          }
        }
      }
    }
  }

  grouping rsa-key-grouping {
    list address {
      description
        "Assign an address";
      key "ip";
      leaf ip {
        type inet:ipv4-address;
      }
    }
    container key-string {
      description
        "Key data";
      leaf hex-data {
        type string;
      }
      leaf quit {
        description
          "Exit data entry mode";
        type empty;
      }
    }
    leaf serial-number {
      description
        "Serial number of the device";
      type string;
    }
  }

  grouping crypto-isakmp-profile-grouping {
    leaf accounting {
      description
        "Enable AAA Accounting for IPSec Sessions";
      type string;
    }
    container ca {
      description
        "Specify certificate authorities to trust";
      leaf-list trust-point-ca {
        description
          "Certificate authority trustpoint for RSA signature";
        type string;
      }
      leaf trust-point {
        description
          "Cert authority trustpoint for RSA sig";
        status deprecated;
        type string;
      }
    }
    container client {
      description
        "Specify client configuration settings";
      container authentication {
        description
          "Use Extended Authentication";
        leaf list {
          description
            "AAA authentication list to use";
          type string;
        }
        leaf password {
          description
            "Password to use for authentication";
          type string;
        }
        leaf username {
          description
            "Username to use for authentication";
          type string;
        }
      }
      container configuration {
        description
          "Specify client configuration settings";
        leaf address {
          description
            "Specify client network address configuration";
          type enumeration {
            enum initiate;
            enum respond;
          }
        }
        leaf group {
          description
            "Specify group profile attributes for client";
          type string;
        }
      }
      container pki {
        description
          "Use username in the crypto certificate for authorization";
        container authorization {
          description
            "User authorization parameters";
          leaf list {
            description
              "AAA user authorization list";
            type string;
          }
          container password {
            description
              "AAA password";
            leaf encryption {
              type enumeration {
                enum 0;
                enum 6;
              }
            }
            leaf user-password {
              type string;
            }
          }
        }
      }
    }
    leaf description {
      description
        "Specify a description of this profile";
      type string;
    }
    container initiate {
      description
        "Initiator property";
      container mode {
        description
          "Phase 1 negotiation mode to use";
        presence "true";
        leaf mode-name {
          description
            "main mode (default)/aggressive mode";
          type enumeration {
            enum aggressive;
            enum main;
          }
        }
        leaf aggressive {
          description
            "Start agressive mode negotiation";
          status obsolete;
          type empty;
        }
      }
    }
    container isakmp {
      description
        "ISAKMP Authorization command";
      container authorization {
        description
          "Authorization parameters.";
        leaf list {
          description
            "AAA authorization list to use";
          type string;
        }
        container password {
          description
            "AAA password";
          leaf encryption {
            type enumeration {
              enum 0;
              enum 6;
            }
          }
          leaf user-password {
            type string;
          }
        }
      }
    }
    container keepalive {
      description
        "Set a keepalive interval for use with IOS peers";
      leaf number {
        type uint16 {
          range "10..3600";
        }
      }
      leaf retry {
        description
          "Retry interval if keepalive fails";
        type uint8 {
          range "2..60";
        }
      }
    }
    list keyring {
      description
        "Specify keyring to use";
      key "name";
      leaf name {
        must "../../../../keyring[name=current()] or /ios:native/ios:crypto/isakmp/profile/keyring[ios-crypto:name='default']" {
          error-message "keyring must be created first and deleted last";
        }
        type union {
          type enumeration {
            enum default;
          }
          type string;
        }
      }
    }
    container local-address {
      description
        "Interface to use for local address for this isakmp profile";
      uses crypto-local-address-grouping;
    }
    container match {
      description
        "Match values of peer";
      leaf-list certificate-map {
        description
          "Peer certificate attributes";
        type string;
      }
      leaf certificate {
        description
          "DEPRECATED Peer certificate attributes";
        status deprecated;
        type string;
      }
      container identity {
        description
          "Peer identity";
        list address {
          description
            "IP Address(es)";
          key "ip mask";
          leaf ip {
            description
              "IP Address(es)";
            type inet:ipv4-address;
          }
          leaf mask {
            type inet:ipv4-address;
          }
          leaf vrf {
            type string;
          }
        }
        container peer-address {
          list address {
            description
              "IP Address(es)";
            key "ipv6";
            leaf ipv6 {
              description
                "IPv6 Address(es)";
              type ios-types:ipv6-prefix;
            }
            leaf vrf {
              description
                "Specify the F VRF";
              type string;
            }
          }
        }
        list ipv6-address {
          description
            "DEPRECATED IP Address(es)";
          status deprecated;
          key "ipv6";
          leaf ipv6 {
            description
              "DEPRECATED IPv6 Address(es)";
            status deprecated;
            type ios-types:ipv6-prefix;
          }
          leaf vrf {
            status deprecated;
            type string;
          }
        }
        leaf-list groups {
          description
            "Group name";
          type string;
        }
        leaf group {
          description
            "DEPRECATED Group name";
          status deprecated;
          type string;
        }
        container host {
          description
            "match a hostname/domain";
          list domain-name-1 {
            key "name";
            leaf name {
              must 'not(/ios:native/ios:crypto/isakmp/profile/match/identity/host/domain[domain-list = current()])' {
                error-message "Already found same match identity statement in this profile";
              }
              type string;
            }
            list vrf {
              key "vrf";
              leaf vrf {
                must '/ios:native/ios:vrf/ios:definition[ios:name=current()] or /ios:native/ios:ip/ios:vrf[ios:name=current()]' {
                  error-message "VRF must be created 1st, deleted last";
                }
                type string;
              }
            }
          }
          list domain {
            key "domain-list";
            leaf domain-list {
              description
                "match domain instead of exact";
              must 'not(/ios:native/ios:crypto/isakmp/profile/match/identity/host/domain-name-1[name=current()])' {
                error-message "Already found same match identity statement in this profile";
              }
              type string;
            }
            list vrf {
              key "vrf";
              leaf vrf {
                must '/ios:native/ios:vrf/ios:definition[ios:name=current()] or /ios:native/ios:ip/ios:vrf[ios:name=current()]' {
                  error-message "VRF must be created 1st, deleted last";
                }
                type string;
              }
            }
          }
          container domain-name {
            status deprecated;
            leaf name {
              status deprecated;
              type string;
            }
            leaf vrf {
              status deprecated;
              type string;
            }
          }
          container domain-match {
            status deprecated;
            leaf domain {
              description
                "match domain instead of exact";
              status deprecated;
              type string;
            }
            leaf vrf {
              status deprecated;
              type string;
            }
          }
        }
        container user-fqdn {
          description
            "match a hostname/domain";
          container domain-name {
            leaf name {
              type string;
            }
            leaf vrf {
              type string;
            }
          }
          container domain-match {
            leaf domain {
              description
                "match domain instead of exact";
              type string;
            }
            leaf vrf {
              type string;
            }
          }
        }
      }
    }
    leaf qos-group {
      description
        "Apply a Qos policy class map for this profile";
      type uint16 {
        range "1..1023";
      }
    }
    leaf rekey {
      description
        "Rekey ISAKMP SA initiated by us";
      type empty;
    }
    container self-identity {
      description
        "Specify Identity to use";
      container address {
        description
          "Use IPv4 address";
        presence "true";
        leaf ipv6 {
          description
            "Use IPv6 address";
          type empty;
        }
      }
      container fqdn {
        description
          "Use FQDN";
        presence "true";
        leaf id {
          type string;
        }
      }
      leaf user-fqdn {
        description
          "Use user FQDN";
        type string;
      }
    }
    container virtual-template-option {
      description
        "Specify the virtual-template for dynamic interface creation";
      leaf virtual-template-number {
        description
          "Virtual-template Number";
        type uint16 {
          range "1..4095";
        }
      }
      leaf per-user {
        description
          "add per user attributes";
        type empty;
      }
    }
    leaf virtual-template {
      description
        "Specify the virtual-template for dynamic interface creation.";
      status deprecated;
      type empty;
    }
    leaf vrf {
      description
        "Specify the VRF it is related to";
      type string;
    }
  }

  grouping crypto-isakmp-profile-default-grouping {
    leaf accounting {
      description
        "Enable AAA Accounting for IPSec Sessions";
      type empty;
    }
    container ca {
      description
        "Specify certificate authorities to trust";
      leaf-list trust-point-ca {
        description
          "Certificate authority trustpoint for RSA signature";
        type string;
      }
      leaf trust-point {
        description
          "Cert authority trustpoint for RSA sig";
        status deprecated;
        type string;
      }
    }
    container client {
      description
        "Specify client configuration settings";
      container authentication {
        description
          "Use Extended Authentication";
        leaf list {
          description
            "AAA authentication list to use";
          type empty;
        }
      }
      container configuration {
        description
          "Specify client configuration settings";
        leaf address {
          description
            "Specify client network address configuration";
          type enumeration {
            enum initiate;
            enum respond;
          }
        }
        leaf group {
          description
            "Specify group profile attributes for client";
          type string;
        }
      }
      container pki {
        description
          "Use username in the crypto certificate for authorization";
        container authorization {
          description
            "User authorization parameters";
          presence "true";
        }
      }
    }
    leaf description {
      description
        "Specify a description of this profile";
      type string;
    }
    container initiate {
      description
        "Initiator property";
      container mode {
        description
          "Phase 1 negotiation mode to use";
        presence "true";
      }
    }
    container isakmp {
      description
        "ISAKMP Authorization command";
      container authorization {
        description
          "Authorization parameters.";
        leaf list {
          description
            "AAA authorization list to use";
          type empty;
        }
      }
    }
    container keepalive {
      description
        "Set a keepalive interval for use with IOS peers";
      presence "true";
    }
    list keyring {
      description
        "Specify keyring to use";
      key "keys";
      leaf keys {
        type union {
          type string;
          type enumeration {
            enum default;
          }
        }
      }
    }
    leaf local-address {
      description
        "Interface to use for local address for this isakmp profile";
      type empty;
    }
    container match {
      description
        "Match values of peer";
      leaf certificate {
        description
          "Peer certificate attributes";
        type string;
      }
      container identity {
        description
          "Peer identity";
        container ipv4-address {
          leaf address {
            description
              "IP Address(es)";
            type inet:ipv4-address;
          }
          leaf mask {
            type inet:ipv4-address;
          }
          leaf vrf {
            type string;
          }
        }
        container address {
          description
            "IP Address(es)";
          leaf ipv6 {
            description
              "IPv6 Address(es)";
            type ios-types:ipv6-prefix;
          }
          leaf vrf {
            type string;
          }
        }
        leaf group {
          description
            "Group name";
          type string;
        }
        container host {
          description
            "match a hostname/domain";
          container domain-name {
            leaf name {
              type string;
            }
            leaf vrf {
              type string;
            }
          }
          container domain-match {
            leaf domain {
              description
                "match domain instead of exact";
              type string;
            }
            leaf vrf {
              type string;
            }
          }
        }
        container user-fqdn {
          description
            "match a hostname/domain";
          container domain-name {
            leaf name {
              type string;
            }
            leaf vrf {
              type string;
            }
          }
          container domain-match {
            leaf domain {
              description
                "match domain instead of exact";
              type string;
            }
            leaf vrf {
              type string;
            }
          }
        }
      }
    }
    leaf qos-group {
      description
        "Apply a Qos policy class map for this profile";
      type empty;
    }
    container self-identity {
      description
        "Specify Identity to use";
      presence "true";
    }
    leaf virtual-template {
      description
        "Specify the virtual-template for dynamic interface creation.";
      type empty;
    }
    leaf vrf {
      description
        "Specify the VRF it is related to";
      type empty;
    }
  }

  grouping crypto-isakmp-client-configuration-group-grouping {
    container access-restrict-option {
      description
        "Restrict clients in this group to an interface";
      uses ios-ifc:interface-grouping;
    }
    leaf access-restrict {
      description
        "Restrict clients in this group to an interface";
      status obsolete;
      type string;
    }
    leaf acl {
      description
        "Specify split tunneling inclusion access-list number";
      type union {
        type uint16 {
          range "100..199";
        }
        type string {
          pattern '[a-zA-Z].*';
        }
      }
    }
    container auto-update {
      description
        "Configure auto-upgrade";
      leaf client {
        description
          "Configure client";
        type string;
      }
      leaf url {
        description
          "Configure URL to download from";
        type string;
      }
      leaf rev {
        description
          "Use comma delimited list of revision strings only";
        type string;
      }
    }
    leaf backup-gateway {
      description
        "Specify backup gateway";
      type string;
    }
    leaf browser-proxy {
      description
        "Configure browser-proxy";
      must '/ios:native/ios:crypto/isakmp/client/configuration/browser-proxy-option[name=current()]' {
        error-message "It seems browser proxy name doesn't exist or attempting to remove when referred by ISAKMP Client configuration";
      }
      type string;
    }
    container configuration {
      description
        "Push configuration to the client";
      leaf url {
        description
          "URL for the client to fetch configuration";
        type string {
          pattern '(((bootflash:)|(cns:)|(flash:)|(ftp:)|(http:)|(https:)|(null:)|(nvram:)|(pram:)|(rcp:)|(scp:)|(tftp:)|(system:)|(tmpsys:)|(tar:)).*)';
        }
      }
      leaf version {
        description
          "version of the configuration available at the URL";
        type uint32 {
          range "1..32767";
        }
      }
    }
    container crypto {
      description
        "Client group crypto aaa attribute list";
      container aaa {
        description
          "AAA directive";
        container attribute {
          description
            "AAA attribute directive";
          leaf list {
            description
              "AAA attribute list";
            type string;
          }
        }
      }
    }
    container dhcp {
      description
        "Configure DHCP parameters";
      leaf giaddr {
        description
          "Specify giaddr for dhcp scope";
        type inet:ipv4-address;
      }
      list server-option {
        description
          "Specify dhcp server";
        key "dhcp-server";
        leaf dhcp-server {
          description
            "DHCP server IP address/Hostname";
          type union {
            type inet:ipv4-address;
            type string;
          }
        }
      }
      leaf server {
        description
          "Specify dhcp server";
        status obsolete;
        type union {
          type inet:ipv4-address;
          type string;
        }
      }
      leaf timeout {
        description
          "Configure DHCP response timeout in seconds";
        type uint8 {
          range "4..30";
        }
      }
    }
    container dns {
      description
        "Specify DNS Addresses";
      leaf primary {
        type inet:ipv4-address;
      }
      leaf secondary {
        type inet:ipv4-address;
      }
    }
    leaf domain {
      description
        "Set default domain name to send to client";
      type string;
    }
    container firewall {
      description
        "Enforce group firewall feature";
      leaf are-u-there {
        description
          "firewall attribute, are-u-there";
        type empty;
      }
      leaf policy {
        description
          "Specify firewall policy";
        type string;
      }
    }
    leaf group-lock {
      description
        "Enforce group lock feature";
      type empty;
    }
    leaf include-local-lan {
      description
        "Enable Local LAN Access with no split tunnel";
      type empty;
    }
    container key {
      description
        "pre-shared key/IKE password";
      leaf encryption {
        type enumeration {
          enum 0;
          enum 6;
        }
      }
      leaf key {
        type string;
      }
    }
    leaf max-logins {
      description
        "Set maximum simultaneous logins for users in this group";
      type uint8 {
        range "1..10";
      }
    }
    leaf max-users {
      description
        "Set maximum number of users for this group";
      type uint32 {
        range "1..5000";
      }
    }
    leaf netmask {
      description
        "netmask used by the client for local connectivity";
      type inet:ipv4-address;
    }
    leaf pfs {
      description
        "The client should propose PFS";
      type empty;
    }
    leaf pool {
      description
        "Set name of address pool";
      type string;
    }
    leaf route-metric {
      description
        "EZVPN VI route metric option";
      type uint8 {
        range "1..255";
      }
    }
    leaf save-password {
      description
        "Allows remote client to save XAUTH password";
      type empty;
    }
    leaf smartcard-removal-disconnect {
      description
        "Enables smartcard-removal-disconnect";
      type empty;
    }
    leaf split-dns {
      description
        "DNS name to append for resolution";
      type string;
    }
    container wins {
      description
        "Specify WINS Addresses";
      leaf primary {
        type inet:ipv4-address;
      }
      leaf secondary-address {
        when '../primary';
        type inet:ipv4-address;
      }
      leaf secondary {
        status obsolete;
        type inet:ipv4-address;
      }
    }
  }

  grouping crypto-isakmp-peer-grouping {
    leaf description {
      description
        "IKE peer specific description";
      type string {
        length "1..80";
      }
    }
    container set {
      description
        "set peer policy attributes";
      container aggressive-mode {
        description
          "aggressive mode attributes";
        container client-endpoint {
          description
            "specify a tunnel-client-endpoint attribute";
          leaf fqdn {
            description
              "Use the fqdn as tunnel-client-endpoint";
            type string;
          }
          leaf ipv4-address {
            description
              "Use the IP address as tunnel-client-endpoint";
            type inet:ipv4-address;
          }
          leaf ipv6-address {
            description
              "Use the IPv6 address as tunnel-client-endpoint";
            type inet:ipv6-address;
          }
          leaf user-fqdn {
            description
              "Use the user-fqdn as tunnel-client-endpoint";
            type string;
          }
        }
        container password {
          description
            "specify a tunnel-password attribute";
          leaf encryption {
            type enumeration {
              enum 0;
              enum 6;
            }
          }
          leaf key {
            type string;
          }
        }
      }
    }
  }

  grouping crypto-isakmp-grouping {
    leaf aggressive-mode {
      description
        "Disable ISAKMP aggressive mode";
      type enumeration {
        enum disable;
      }
    }
    container client {
      description
        "Set client configuration policy";
      container configuration {
        description
          "Set client configuration policy";
        container address-pool {
          description
            "Set network address for client";
          leaf local {
            description
              "Set a local address pool for clients";
            type string;
          }
        }
        list browser-proxy-option {
          description
            "Set browser proxy attributes for client";
          key "name";
          leaf name {
            description
              "browser-proxy name";
            type string;
          }
          container proxy {
            description
              "Proxy Server Settings";
            choice proxy-settings-choice {
              case auto-detect-case {
                leaf auto-detect {
                  description
                    "Auto-detect proxy settings";
                  type empty;
                }
              }
              case bypass-local-case {
                leaf bypass-local {
                  description
                    "Bypass proxy settings for local";
                  type empty;
                }
              }
              case none-case {
                leaf none {
                  description
                    "Don't use any proxy server";
                  type empty;
                }
              }
              case server-case {
                leaf server {
                  description
                    "Configure proxy server";
                  type string;
                }
                leaf exception-list {
                  description
                    "Configure exception list";
                  type string;
                }
              }
            }
          }
        }
        leaf browser-proxy {
          description
            "Set browser proxy attributes for client";
          status obsolete;
          type string;
        }
        list group {
          description
            "Set group profile attributes for client";
          key "name";
          leaf name {
            type string;
          }
          uses crypto-isakmp-client-configuration-group-grouping;
        }
      }
      list firewall {
        description
          "Define client firewall";
        key "policy-name";
        leaf policy-name {
          type string;
        }
        leaf optional {
          description
            "firewall policy is optional";
          type enumeration {
            enum cisco-integrated-client-firewall;
            enum cisco-security-agent;
            enum zonelabs-zonealarm;
            enum zonelabs-zonealarmpro;
          }
        }
        leaf required {
          description
            "firewall policy is mandatory";
          type enumeration {
            enum cisco-integrated-client-firewall;
            enum cisco-security-agent;
            enum zonelabs-zonealarm;
            enum zonelabs-zonealarmpro;
          }
        }
        container policy {
          description
            "Define Cisco firewall Policy";
          container central-policy-push {
            description
              "Define Cisco Protection Policy";
            when "../../optional = 'cisco-integrated-client-firewall' or ../../required = 'cisco-integrated-client-firewall' or ../../optional = 'zonelabs-zonealarm' or ../../required = 'zonelabs-zonealarm' or ../../optional = 'zonelabs-zonealarmpro' or ../../required = 'zonelabs-zonealarmpro'";
            container access-list {
              description
                "Specify access list";
              leaf direction {
                type enumeration {
                  enum in;
                  enum out;
                }
              }
              leaf acl {
                type union {
                  type uint16 {
                    range "100..199";
                  }
                  type string {
                    pattern '[a-zA-Z].*';
                  }
                }
              }
            }
          }
          leaf check-presence {
            description
              "Define firewall are-you-there policy";
            when "../../optional = 'cisco-security-agent' or ../../required = 'cisco-security-agent' or ../../optional = 'zonelabs-zonealarm' or ../../required = 'zonelabs-zonealarm' or ../../optional = 'zonelabs-zonealarmpro' or ../../required = 'zonelabs-zonealarmpro'";
            type empty;
          }
        }
      }
    }
    container default {
      description
        "ISAKMP default policy";
      leaf policy {
        description
          "Enable default policies for ISAKMP protection suite";
        type empty;
      }
    }
    container diagnose {
      description
        "Diagnostic configuration";
      leaf error {
        description
          "Enable diagnose error";
        type uint16 {
          range "0..1000";
        }
        default "50";
      }
    }
    leaf disconnect-revoked-peers {
      description
        "Disconnect Crypto Session with Revoked Peer";
      type empty;
    }
    leaf enable {
      description
        "Enable ISAKMP";
      type empty;
    }
    leaf fragmentation {
      description
        "IKE Fragmentation enabled if required";
      type empty;
    }
    leaf identity {
      description
        "Set the identity which ISAKMP will use";
      type enumeration {
        enum address;
        enum dn;
        enum hostname;
      }
    }
    leaf invalid-spi-recovery {
      description
        "Initiate IKE and send Invalid SPI Notify";
      type empty;
    }
    container keepalive {
      description
        "Set a keepalive interval for use with IOS peers";
      leaf number {
        type uint16 {
          range "10..3600";
        }
      }
      leaf retry-number {
        type uint8 {
          range "2..60";
        }
        default "2";
      }
      leaf send {
        type enumeration {
          enum on-demand;
          enum periodic;
        }
        default "on-demand";
      }
    }
    container key {
      description
        "Set pre-shared key for remote peer";
      list key-address-host {
        key "key";
        leaf key {
          description
            "The UNENCRYPTED (cleartext) user password";
          type string;
        }
        leaf encryption {
          description
            "Specifies an ENCRYPTED/UNENCRYPTED password will follow";
          type enumeration {
            enum 0;
            enum 6;
          }
        }
        container address {
          description
            "define shared key with IP address";
          list address-v4 {
            description
              "define shared key with IPv4 address";
            key "address";
            leaf address {
              description
                "Peer IP address";
              type inet:ipv4-address;
            }
            leaf mask {
              description
                "Peer IP subnet mask";
              type inet:ipv4-address;
            }
            leaf no-xauth {
              description
                "Bypasses XAuth for this peer";
              type empty;
            }
          }
          list address-v6 {
            description
              "define shared key with IPv6 address";
            key "ipv6";
            leaf ipv6 {
              description
                "Peer IPv6 prefix";
              type ios-types:ipv6-prefix;
            }
            leaf no-xauth {
              description
                "Bypasses XAuth for this peer";
              type empty;
            }
          }
        }
        list hostname {
          description
            "define shared key with hostname";
          key "name";
          leaf name {
            description
              "hostname of peer with whom the key is shared";
            type string;
          }
          leaf no-xauth {
            description
              "Bypasses XAuth for this peer";
            type empty;
          }
        }
      }
      container key-address {
        status deprecated;
        leaf encryption {
          status deprecated;
          type enumeration {
            enum 0;
            enum 6;
          }
        }
        leaf key {
          status deprecated;
          type string;
        }
        choice ipv4-ipv6 {
          status deprecated;
          case ipv4 {
            status deprecated;
            container addr4-container {
              status deprecated;
              leaf address {
                status deprecated;
                description
                  "define shared key with IP address";
                type inet:ipv4-address;
              }
              leaf mask {
                status deprecated;
                type inet:ipv4-address;
              }
              leaf no-xauth {
                status deprecated;
                description
                  "Bypasses XAuth for this peer";
                type empty;
              }
            }
          }
          case ipv6 {
            status deprecated;
            container addr6-container {
              status deprecated;
              container address {
                status deprecated;
                description
                  "define shared key with IP address";
                leaf ipv6 {
                  status deprecated;
                  description
                    "define shared key with IPv6 address";
                  type ios-types:ipv6-prefix;
                }
                leaf no-xauth {
                  status deprecated;
                  description
                    "Bypasses XAuth for this peer";
                  type empty;
                }
              }
            }
          }
        }
      }
      container key-host {
        status deprecated;
        leaf encryption {
          status deprecated;
          type enumeration {
            enum 0;
            enum 6;
          }
        }
        leaf key {
          status deprecated;
          type string;
        }
        container host-container {
          status deprecated;
          leaf hostname {
            status deprecated;
            description
              "define shared key with hostname";
            type string;
          }
          leaf no-xauth {
            status deprecated;
            description
              "Bypasses XAuth for this peer";
            type empty;
          }
        }
      }
    }
    container nat {
      description
        "Set a nat  keepalive interval for use with IOS peers";
      leaf keepalive {
        description
          "Set a nat keepalive interval for use with IOS peers";
        type uint16 {
          range "5..3600";
        }
      }
    }
    container peer {
      description
        "Set Peer Policy";
      container ipv4-addr {
        list address {
          description
            "define peer policy for IP address";
          key "ipv4";
          leaf ipv4 {
            type inet:ipv4-address;
          }
          leaf vrf {
            description
              "specify front door vrf of the peer";
            type string;
          }
          uses crypto-isakmp-peer-grouping;
        }
      }
      container ipv6-addr {
        list address {
          description
            "define peer policy for IP address";
          key "ipv6";
          leaf ipv6 {
            description
              "define peer policy for IPv6 address";
            type inet:ipv6-address;
          }
          leaf vrf {
            description
              "specify front door vrf of the peer";
            type string;
          }
          uses crypto-isakmp-peer-grouping;
        }
      }
      list hostname {
        description
          "hostname  define peer policy for hostname";
        key "name";
        leaf name {
          type string;
        }
        leaf vrf {
          description
            "specify front door vrf of the peer";
          type string;
        }
        uses crypto-isakmp-peer-grouping;
      }
    }
    leaf performance {
      description
        "Enable performance statistics collection";
      type empty;
    }
    list policy {
      description
        "Set policy for an ISAKMP protection suite";
      key "number";
      leaf number {
        type uint32 {
          range "1..10000";
        }
      }
      container default {
        description
          "Set a command to its defaults";
        uses crypto-isakmp-policy-grouping;
        leaf lifetime {
          description
            "Set lifetime for ISAKMP security association";
          type empty;
        }
      }
      uses crypto-isakmp-policy-grouping;
      leaf lifetime {
        description
          "Set lifetime for ISAKMP security association";
        type uint32 {
          range "60..86400";
        }
      }
    }
    list profile {
      description
        "Define ISAKMP Profiles";
      key "name";
      leaf name {
        type string;
      }
      container default {
        description
          "Set a command to its defaults";
        uses crypto-isakmp-profile-default-grouping;
      }
      uses crypto-isakmp-profile-grouping;
    }
    container xauth {
      description
        "Set Extended Authentication values";
      leaf timeout {
        description
          "Set Extended Authentication timeout";
        type uint8 {
          range "5..90";
        }
      }
    }
  }

  grouping crypto-key-decrypt-rc-rsa-np-grouping {
    leaf name {
      description
        "Name of keypair to decrypt.";
      type string;
    }
    leaf passphrase {
      description
        "decryption key.";
      type string;
    }
  }

  grouping crypto-key-decrypt-rc-rsa-grouping {
    container ec {
      description
        "EC keys";
      presence "true";
      uses crypto-key-decrypt-rc-rsa-np-grouping;
    }
    container rsa {
      description
        "RSA keys";
      presence "true";
      uses crypto-key-decrypt-rc-rsa-np-grouping;
    }
  }

  grouping crypto-key-encrypt-rc-rsa-np-grouping {
    leaf name {
      description
        "Name of keypair to encrypt.";
      type string;
    }
    leaf passphrase {
      description
        "encryption key.";
      type string;
    }
  }

  grouping crypto-key-encrypt-rc-rsa-grouping {
    container ec {
      description
        "EC keys";
      presence "true";
      uses crypto-key-encrypt-rc-rsa-np-grouping;
    }
    container rsa {
      description
        "RSA keys";
      presence "true";
      uses crypto-key-encrypt-rc-rsa-np-grouping;
    }
  }

  grouping crypto-key-url-file-ex-grouping {
    leaf file {
      type string {
        pattern '(((bootflash:)|(crashinfo:)|(flash:)|(ftp:)|(http:)|(https:)|(null:)|(nvram:)|(pram:)|(rcp:)|(scp:)|(system:)|(tar:)|(tftp:)|(tmpfs:)|(webui:)).*)';
      }
    }
  }

  grouping crypto-key-url-file-im-grouping {
    leaf file {
      type string {
        pattern '(((bootflash:)|(cns:)|(crashinfo:)|(flash:)|(ftp:)|(http:)|(https:)|(null:)|(nvram:)|(pram:)|(rcp:)|(scp:)|(system:)|(tar:)|(tftp:)|(tmpfs:)|(webui:)).*)';
      }
    }
  }

  grouping crypto-key-export-pem-grouping {
    container pem {
      description
        "File type to export";
      choice terminal-url {
        case terminal-case {
          container terminal {
            description
              "Export via the terminal (cut-and-paste)";
            choice des-3des {
              case pk-3des-case {
                leaf pk-3des {
                  description
                    "Encrypt the private key with 3DES";
                  type string;
                }
              }
              case des-case {
                leaf des {
                  description
                    "Encrypt the private key with DES";
                  type string;
                }
              }
            }
          }
        }
        case url-case {
          container url {
            description
              "Export via the file systems";
            uses crypto-key-url-file-ex-grouping;
            choice des-3des {
              case url-3des-case {
                leaf url-3des {
                  description
                    "Encrypt the private key with 3DES";
                  type string;
                }
              }
              case des-case {
                leaf des {
                  description
                    "Encrypt the private key with DES";
                  type string;
                }
              }
            }
          }
        }
      }
    }
  }

  grouping crypto-key-pubkey-key-grouping {
    leaf address {
      description
        "Assign an address to the key";
      type inet:ipv4-address;
    }
    container key-string {
      description
        "Key data";
      leaf hex-data {
        type string;
      }
      leaf quit {
        description
          "Exit data entry mode";
        type empty;
      }
    }
    leaf serial-number {
      description
        "Serial number of the device";
      type string;
    }
  }

  grouping crypto-key-pubkey-key-default-grouping {
    leaf address {
      description
        "Assign an address to the key";
      type empty;
    }
    container key-string {
      description
        "Key data";
      presence "true";
    }
    leaf serial-number {
      description
        "Serial number of the device";
      type empty;
    }
  }

  grouping crypto-key-pubkey-chain-grouping {
    list addressed-key {
      description
        "Public key associated with an address";
      key "ip";
      leaf ip {
        type inet:ipv4-address;
      }
      leaf use {
        type enumeration {
          enum encryption;
          enum signature;
        }
      }
      uses crypto-key-pubkey-key-grouping;
      container default {
        description
          "Set a command to its defaults";
        uses crypto-key-pubkey-key-default-grouping;
      }
    }
    list named-key {
      description
        "Public key associated with a name";
      key "name";
      leaf name {
        type string;
      }
      leaf use {
        type enumeration {
          enum encryption;
          enum signature;
        }
      }
      uses crypto-key-pubkey-key-grouping;
      container default {
        description
          "Set a command to its defaults";
        uses crypto-key-pubkey-key-default-grouping;
      }
    }
  }

  grouping crypto-key-pubkey-chain-default-grouping {
    list addressed-key {
      description
        "Public key associated with an address";
      key "ip";
      leaf ip {
        type inet:ipv4-address;
      }
      leaf use {
        type enumeration {
          enum encryption;
          enum signature;
        }
      }
    }
    list named-key {
      description
        "Public key associated with a name";
      key "name";
      leaf name {
        type string;
      }
      leaf use {
        type enumeration {
          enum encryption;
          enum signature;
        }
      }
    }
  }

  grouping crypto-key-grouping {
    container decrypt {
      description
        "Decrypt a keypair.";
      uses crypto-key-decrypt-rc-rsa-grouping;
      container write {
        description
          "Will write the configuration to startup-config.";
        uses crypto-key-decrypt-rc-rsa-grouping;
      }
    }
    container encrypt {
      description
        "Encrypt a keypair.";
      uses crypto-key-encrypt-rc-rsa-grouping;
      container write {
        description
          "Will write the configuration to startup-config.";
        uses crypto-key-encrypt-rc-rsa-grouping;
      }
    }
    container export {
      status obsolete;
      description
        "Export keys";
      list ec {
        description
          "Export EC keys";
        key "label";
        leaf label {
          type string;
        }
        uses crypto-key-export-pem-grouping;
      }
      list rsa {
        description
          "Export RSRA keys";
        key "label";
        leaf label {
          type string;
        }
        uses crypto-key-export-pem-grouping;
      }
    }
    container generate {
      status obsolete;
      description
        "Generate new keys";
      container ec {
        description
          "Generate EC keys for ECDSA";
        leaf keysize {
          description
            "Number of bits";
          type enumeration {
            enum 256;
            enum 384;
          }
        }
        leaf exportable {
          description
            "Allow key to be exported";
          type empty;
        }
        leaf label {
          description
            "Provide a label";
          type string;
        }
      }
      container rsa {
        description
          "Generate RSA keys";
        presence "true";
        leaf encryption {
          description
            "Generate a general purpose RSA key pair for signing and encryption";
          type empty;
        }
        leaf exportable {
          description
            "Allow the key to be exported";
          type empty;
        }
        leaf general-keys {
          description
            "Generate a general purpose RSA key pair for signing and encryption";
          type empty;
        }
        leaf label {
          description
            "Provide a label";
          type string;
        }
        leaf modulus {
          description
            "Provide number of modulus bits on the command line";
          type uint16 {
            range "360..4096";
          }
        }
        leaf on {
          description
            "create key on specified device.";
          type string;
        }
        leaf redundancy {
          description
            "Allow the key to be synced to high-availability peer";
          type empty;
        }
        leaf signature {
          description
            "Generate a general purpose RSA key pair for signing and encryption";
          type empty;
        }
        leaf storage {
          description
            "Store key on specified device";
          type string;
        }
        leaf usage-keys {
          description
            "Generate separate RSA key pairs for signing and encryption";
          type empty;
        }
      }
    }
    container import {
      status obsolete;
      description
        "Import keys";
      list ec {
        description
          "Import EC keys";
        key "name";
        leaf name {
          type string;
        }
        leaf exportable {
          description
            "Allow key to be exported";
          type empty;
        }
        choice terminal-url {
          case terminal-case {
            leaf terminal {
              description
                "Import via the terminal (cut-and-paste)";
              type string;
            }
          }
          case url-case {
            container url {
              description
                "Export via the file systems";
              uses crypto-key-url-file-im-grouping;
              leaf key {
                type string;
              }
            }
          }
        }
      }
      list rsa {
        description
          "Import RSA keys";
        key "label";
        leaf label {
          type string;
        }
        leaf encryption {
          description
            "Encryption key";
          type empty;
        }
        leaf exportable {
          description
            "Allow the key to be exported";
          type empty;
        }
        leaf general-purpose {
          description
            "General Purpose key";
          type empty;
        }
        leaf on {
          description
            "Make this an on-token key";
          type string;
        }
        leaf pem {
          description
            "File type to import";
          type empty;
        }
        leaf redundancy {
          description
            "Sync this key to the standby";
          type empty;
        }
        leaf signature {
          description
            "Signature key";
          type empty;
        }
        leaf storage {
          description
            "Store key on specified device";
          type string;
        }
        leaf usage-keys {
          description
            "Usage key pairs";
          type empty;
        }
        choice terminal-url {
          case terminal-case {
            leaf terminal {
              description
                "Import via the terminal (cut-and-paste)";
              type string;
            }
          }
          case url-case {
            container url {
              description
                "Export via the file systems";
              uses crypto-key-url-file-im-grouping;
              leaf key {
                type string;
              }
            }
          }
        }
      }
    }
    container move {
      status obsolete;
      description
        "Move keys";
      container rsa {
        description
          "Move RSA keys";
        leaf label {
          type string;
        }
        leaf non-exportable {
          description
            "Do Not allow the key to be exported";
          type empty;
        }
        leaf on {
          description
            "Make this an on-token key";
          type string;
        }
        leaf redundancy {
          description
            "Sync this key to the standby";
          type empty;
        }
        leaf storage {
          description
            "Store key on specified device";
          type string;
        }
      }
    }
    container pubkey-chain {
      description
        "Peer public key chain management";
      container rsa {
        description
          "Peer RSA public key chain management";
        uses crypto-key-pubkey-chain-grouping;
        container default {
          description
            "Set a command to its defaults";
          uses crypto-key-pubkey-chain-default-grouping;
        }
      }
    }
    leaf storage {
      description
        "default storage location for keypairs";
      type string;
    }
    container zeroize {
      status obsolete;
      description
        "Remove keys";
      container ec {
        description
          "Remove EC keys";
        presence "true";
        leaf label {
          type string;
        }
      }
      container pubkey-chain {
        description
          "Remove peer's cached public key";
        presence "true";
        leaf index {
          type uint16;
        }
      }
      container rsa {
        description
          "Remove RSA keys";
        presence "true";
        leaf label {
          type string;
        }
      }
    }
  }

  grouping crypto-keyring-key-grouping {
    leaf key {
      description
        "specify the key";
      type empty;
    }
    leaf encryption {
      type enumeration {
        enum 0;
        enum 6;
      }
    }
    leaf unencryt-key {
      type string;
    }
  }

  grouping crypto-map-grouping {
    uses crypto-map-common-grouping;
    container set {
      description
        "Set values for encryption/decryption";
      uses crypto-map-common-set-grouping;
      container security-association {
        description
          "Security association parameters";
        uses crypto-map-common-set-security-association-grouping;
        leaf level {
          description
            "specify a security association granularity level for identities";
          type enumeration {
            enum per-host;
          }
        }
      }
    }
  }

  grouping obsolete-crypto-map-grouping {
    uses obsolete-crypto-map-common-grouping;
    container set {
      description
        "Set values for encryption/decryption";
      status obsolete;
      uses obsolete-crypto-map-common-set-grouping;
      container security-association {
        description
          "Security association parameters";
        status obsolete;
        uses obsolete-crypto-map-common-set-security-association-grouping;
        leaf level {
          description
            "specify a security association granularity level for identities";
          status obsolete;
          type enumeration {
            enum per-host;
          }
        }
      }
    }
  }

  grouping crypto-map-default-grouping {
    leaf description {
      description
        "Description of the crypto map statement policy";
      type empty;
    }
    container dialer {
      description
        "Dialer related commands";
      leaf pre-classify {
        description
          "Enable dialer list classification before initiating IKE";
        type empty;
      }
    }
    container match {
      description
        "Match values";
      leaf address {
        description
          "Match address of packets to encrypt";
        type empty;
      }
    }
    container qos {
      description
        "Quality of Service related commands";
      leaf pre-classify {
        description
          "Enable QOS classification before packets are tunnel encapsulated";
        type empty;
      }
    }
    container reverse-route {
      description
        "Reverse Route Injection.";
      presence "true";
    }
    container set {
      description
        "Set values for encryption/decryption";
      leaf group {
        description
          "Set the san group parameters";
        type empty;
      }
      leaf identity {
        description
          "Identity restriction";
        type empty;
      }
      leaf ikev2-profile {
        description
          "Specify ikev2 Profile";
        type string;
      }
      leaf isakmp-profile {
        description
          "Specify isakmp Profile";
        type empty;
      }
      container pfs {
        description
          "Specify pfs settings";
        presence "true";
      }
      container reverse-route {
        description
          "Reverse Route Injection";
        presence "true";
      }
      container security-association {
        description
          "Security association parameters";
        leaf dfbit {
          description
            "Handling of encapsulated DF bit.";
          type empty;
        }
        container dummy {
          description
            "Enable transmitting dummy packets";
          presence "true";
        }
        leaf ecn {
          description
            "Handling of ECN bit";
          type empty;
        }
        container idle-time-container {
          leaf idle-time {
            description
              "Automatically delete IPSec SAs after a given idle period.";
            type empty;
          }
          leaf default {
            description
              "All SAs idle-out reset to default peer";
            type empty;
          }
        }
        leaf level {
          description
            "specify a security association granularity level for identities";
          type enumeration {
            enum per-host;
          }
        }
        container lifetime {
          description
            "security association lifetime";
          leaf days {
            description
              "Time-based key duration in days";
            type empty;
          }
          leaf kilobytes {
            description
              "Volume-based key duration";
            type empty;
          }
          leaf seconds {
            description
              "Time-based key duration in seconds";
            type empty;
          }
        }
        container replay {
          description
            "Set replay checking.";
          leaf disable {
            description
              "Disable replay checking";
            type empty;
          }
          leaf window-size {
            description
              "Set replay window size.";
            type empty;
          }
        }
      }
      leaf transform-set {
        description
          "Specify list of transform sets in priority order";
        type empty;
      }
    }
  }

  grouping obsolete-crypto-map-default-grouping {
    leaf description {
      description
        "Description of the crypto map statement policy";
      status obsolete;
      type empty;
    }
    container dialer {
      description
        "Dialer related commands";
      status obsolete;
      leaf pre-classify {
        description
          "Enable dialer list classification before initiating IKE";
        status obsolete;
        type empty;
      }
    }
    container match {
      description
        "Match values";
      status obsolete;
      leaf address {
        description
          "Match address of packets to encrypt";
        status obsolete;
        type empty;
      }
    }
    container qos {
      description
        "Quality of Service related commands";
      status obsolete;
      leaf pre-classify {
        description
          "Enable QOS classification before packets are tunnel encapsulated";
        status obsolete;
        type empty;
      }
    }
    container reverse-route {
      description
        "Reverse Route Injection.";
      status obsolete;
      presence "true";
    }
    container set {
      description
        "Set values for encryption/decryption";
      status obsolete;
      leaf group {
        description
          "Set the san group parameters";
        status obsolete;
        type empty;
      }
      leaf identity {
        description
          "Identity restriction";
        status obsolete;
        type empty;
      }
      leaf ikev2-profile {
        description
          "Specify ikev2 Profile";
        status obsolete;
        type string;
      }
      leaf isakmp-profile {
        description
          "Specify isakmp Profile";
        status obsolete;
        type empty;
      }
      container pfs {
        description
          "Specify pfs settings";
        status obsolete;
        presence "true";
      }
      container reverse-route {
        description
          "Reverse Route Injection";
        status obsolete;
        presence "true";
      }
      container security-association {
        description
          "Security association parameters";
        status obsolete;
        leaf dfbit {
          description
            "Handling of encapsulated DF bit.";
          status obsolete;
          type empty;
        }
        container dummy {
          description
            "Enable transmitting dummy packets";
          status obsolete;
          presence "true";
        }
        leaf ecn {
          description
            "Handling of ECN bit";
          status obsolete;
          type empty;
        }
        container idle-time-container {
          status obsolete;
          leaf idle-time {
            description
              "Automatically delete IPSec SAs after a given idle period.";
            status obsolete;
            type empty;
          }
          leaf default {
            description
              "All SAs idle-out reset to default peer";
            status obsolete;
            type empty;
          }
        }
        leaf level {
          description
            "specify a security association granularity level for identities";
          status obsolete;
          type enumeration {
            enum per-host;
          }
        }
        container lifetime {
          description
            "security association lifetime";
          status obsolete;
          leaf days {
            description
              "Time-based key duration in days";
            status obsolete;
            type empty;
          }
          leaf kilobytes {
            description
              "Volume-based key duration";
            status obsolete;
            type empty;
          }
          leaf seconds {
            description
              "Time-based key duration in seconds";
            status obsolete;
            type empty;
          }
        }
        container replay {
          description
            "Set replay checking.";
          status obsolete;
          leaf disable {
            description
              "Disable replay checking";
            status obsolete;
            type empty;
          }
          leaf window-size {
            description
              "Set replay window size.";
            status obsolete;
            type empty;
          }
        }
      }
      leaf transform-set {
        description
          "Specify list of transform sets in priority order";
        status obsolete;
        type empty;
      }
    }
  }

  grouping crypto-map-gdoi-mapping-grouping {
    leaf activate {
      description
        "Activate the crypto map to work in fail-close mode";
      type empty;
    }
    container match {
      description
        "Match address of packets for fail-close";
      leaf address {
        description
          "Match address of packets for fail-close.";
        type ios-types:ext-acl-type;
      }
    }
  }

  grouping obsolete-crypto-map-gdoi-mapping-grouping {
    leaf activate {
      description
        "Activate the crypto map to work in fail-close mode";
      status obsolete;
      type empty;
    }
    container match {
      description
        "Match address of packets for fail-close";
      status obsolete;
      leaf address {
        description
          "Match address of packets for fail-close.";
        status obsolete;
        type ios-types:ext-acl-type;
      }
    }
  }

  grouping crypto-map-gdoi-default-mapping-grouping {
    leaf activate {
      description
        "Activate the crypto map to work in fail-close mode";
      type empty;
    }
    container match {
      description
        "Match address of packets for fail-close";
      leaf address {
        description
          "Match address of packets for fail-close.";
        type empty;
      }
    }
  }

  grouping obsolete-crypto-map-gdoi-default-mapping-grouping {
    leaf activate {
      description
        "Activate the crypto map to work in fail-close mode";
      status obsolete;
      type empty;
    }
    container match {
      description
        "Match address of packets for fail-close";
      status obsolete;
      leaf address {
        description
          "Match address of packets for fail-close.";
        status obsolete;
        type empty;
      }
    }
  }

  grouping time-grouping-v2 {
    list time-string {
      description
        "This input is case sensitive. Example Input : Jan 03 2000 23:59:59 UTC Month : Jan|Feb|Mar|Apr|May|Jun|Jul|Aug|Sep|Oct|Nov|Dec Date : 01-31 Year : 1993-2035 Time : 24 hour format UTC time UTC keyword is Mandatory";
      key "datetime";
      leaf datetime {
        type string {
          pattern '(Jan|Feb|Mar|Apr|May|Jun|Jul|Aug|Sep|Oct|Nov|Dec)\s(0[1-9]|[12][0-9]|3[01])\s((199[3-9]|20([0-2][0-9]|3[0-4])))\s((([0-1]?[0-9])|(2[0-3])):[0-5][0-9]:[0-5][0-9])\sUTC';
        }
      }
    }
  }

  grouping compare-time-grouping-v2 {
    container eq {
      description
        "Equal";
      uses time-grouping-v2;
    }
    container ge {
      description
        "Greater than or equal";
      uses time-grouping-v2;
    }
    container lt {
      description
        "Less Than";
      uses time-grouping-v2;
    }
    container ne {
      description
        "Not Equal";
      uses time-grouping-v2;
    }
  }

  grouping compare-string-grouping-v2 {
    list co {
      description
        "Contains";
      key "name";
      leaf name {
        type string;
      }
    }
    list eq {
      description
        "Equal";
      key "name";
      leaf name {
        type string;
      }
    }
    list nc {
      description
        "Does not contain";
      key "name";
      leaf name {
        type string;
      }
    }
    list ne {
      description
        "Not Equal";
      key "name";
      leaf name {
        type string;
      }
    }
  }

  grouping compare-hex-string-grouping {
    list co {
      description
        "Contains";
      key "hex-data";
      leaf hex-data {
        type string {
          pattern '([0-9a-fA-F]+)';
        }
      }
    }
    list eq {
      description
        "Equal";
      key "hex-data";
      leaf hex-data {
        type string {
          pattern '([0-9a-fA-F]+)';
        }
      }
    }
    list nc {
      description
        "Does not contain";
      key "hex-data";
      leaf hex-data {
        type string {
          pattern '([0-9a-fA-F]+)';
        }
      }
    }
    list ne {
      description
        "Not Equal";
      key "hex-data";
      leaf hex-data {
        type string {
          pattern '([0-9a-fA-F]+)';
        }
      }
    }
  }

  grouping compare-string-grouping-deprecated {
    leaf co {
      status deprecated;
      description
        "Contains";
      type string;
    }
    leaf eq {
      status deprecated;
      description
        "Equal";
      type string;
    }
    leaf nc {
      status deprecated;
      description
        "Does not contain";
      type string;
    }
    leaf ne {
      status deprecated;
      description
        "Not Equal";
      type string;
    }
  }

  grouping crypto-pki-certificate-map-grouping-v2 {
    container alt-subject-name {
      description
        "Alternate subject name";
      uses compare-string-grouping-v2;
    }
    container expires-on {
      description
        "Expiration date/time";
      uses compare-time-grouping-v2;
    }
    container issuer-name {
      description
        "Certificate issuer name";
      uses compare-string-grouping-v2;
    }
    container name {
      description
        "Any subject name field";
      uses compare-string-grouping-v2;
    }
    container serial-number {
      description
        "Certificate serial number (hexadecimal)";
      uses compare-hex-string-grouping;
    }
    container subject-name {
      description
        "Certificate subject name";
      uses compare-string-grouping-v2;
    }
    container unstructured-subject-name {
      description
        "Unstructured subject name";
      uses compare-string-grouping-v2;
    }
    container valid-start {
      description
        "Valid after date/time";
      uses compare-time-grouping-v2;
    }
  }

  grouping crypto-pki-certificate-map-grouping-deprecated {
    container alt-subject-name {
      status deprecated;
      description
        "Alternate subject name";
      uses compare-string-grouping-deprecated;
    }
    container expires-on {
      status obsolete;
      description
        "Expiration date/time";
      uses compare-time-grouping-obsolete;
    }
    container issuer-name {
      status deprecated;
      description
        "Certificate issuer name";
      uses compare-string-grouping-deprecated;
    }
    container name {
      status deprecated;
      description
        "Any subject name field";
      uses compare-string-grouping-deprecated;
    }
    container serial-number {
      status deprecated;
      description
        "Certificate serial number (hexadecimal)";
      uses compare-string-grouping-deprecated;
    }
    container subject-name {
      status deprecated;
      description
        "Certificate subject name";
      uses compare-string-grouping-deprecated;
    }
    container unstructured-subject-name {
      status deprecated;
      description
        "Unstructured subject name";
      uses compare-string-grouping-deprecated;
    }
    container valid-start {
      status obsolete;
      description
        "Valid after date/time";
      uses compare-time-grouping-obsolete;
    }
  }

  grouping crypto-pki-profile-enrollment-auth-grouping {
    leaf command {
      description
        "command to authenticate or enroll";
      type string;
    }
    leaf terminal {
      description
        "authenticate or enroll using terminal";
      type empty;
    }
    container url {
      description
        "url to authenticate/enroll";
      leaf name {
        type string;
      }
      leaf vrf {
        description
          "VRF to use for certificate enrollment ";
        type string;
      }
    }
  }

  grouping crypto-pki-profile-enrollment-grouping {
    container authentication {
      description
        "Retrieve CA certificate(s)";
      uses crypto-pki-profile-enrollment-auth-grouping;
    }
    container enrollment {
      description
        "Enroll router with a CA";
      uses crypto-pki-profile-enrollment-auth-grouping;
      leaf credential {
        description
          "Use existing router cert for new enrollment";
        type string;
      }
      container http {
        description
          "HTTP credentials";
        leaf username {
          description
            "username";
          type string;
        }
        container password {
          description
            "Specify the HTTP password";
          leaf encryption {
            type enumeration {
              enum 0;
              enum 6;
            }
          }
          leaf key {
            type string {
              length "1..214";
            }
          }
        }
      }
    }
    leaf method-est {
      description
        "Use EST for this profile";
      type empty;
    }
    list parameter {
      description
        "Define a parameter value or prompt";
      key "number";
      leaf number {
        type uint8 {
          range "1..8";
        }
      }
      choice prompt-value {
        case prompt-case {
          leaf prompt {
            description
              "Define a parameter prompt";
            type string;
          }
        }
        case value-case {
          leaf value {
            description
              "Define a parameter value";
            type string;
          }
        }
      }
    }
    container reenrollment {
      description
        "Re-enroll router with a CA";
      uses crypto-pki-profile-enrollment-auth-grouping;
    }
    leaf source-interface {
      description
        "Interface used as source address";
      type string;
    }
  }

  grouping crypto-pki-trustpoint-ip-extension-grouping {
    container range {
      description
        "IP address range";
      choice ipv4-ipv6 {
        case ipv4-range {
          leaf start {
            description
              "Starting IP address";
            type inet:ipv4-address;
          }
          leaf end {
            description
              "Ending IP address";
            type inet:ipv4-address;
          }
        }
        case ipv6-range {
          leaf start-v6 {
            description
              "Starting IPv6 address";
            type inet:ipv6-address;
          }
          leaf end-v6 {
            description
              "Ending IPv6 address";
            type inet:ipv6-address;
          }
        }
      }
    }
    leaf prefix {
      description
        "Prefix or IP address";
      type union {
        type inet:ipv4-address;
        type inet:ipv4-prefix;
        type inet:ipv6-address;
        type ios-types:ipv6-prefix;
      }
    }
    container inherit {
      description
        "Inherit address from issuer";
      leaf ipv4 {
        description
          "Apply to ipv4 address";
        type empty;
      }
      leaf ipv6 {
        description
          "Apply to ipv6 address";
        type empty;
      }
    }
  }

  grouping crypto-pki-eku-grouping {
    leaf client-auth {
      description
        "Client Auth";
      type empty;
    }
    leaf code-signing {
      description
        "Code signing";
      type empty;
    }
    leaf email-protection {
      description
        "Email protection";
      type empty;
    }
    leaf ipsec-end-system {
      description
        "IPSEC end system";
      type empty;
    }
    leaf ipsec-tunnel {
      description
        "IPSEC Tunnel";
      type empty;
    }
    leaf ipsec-user {
      description
        "IPSEC User";
      type empty;
    }
    leaf ocsp-signing {
      description
        "OCSP Signing";
      type empty;
    }
    leaf server-auth {
      description
        "Server Auth";
      type empty;
    }
    leaf ssh-client {
      description
        "SSH Client";
      type empty;
    }
    leaf ssh-server {
      description
        "SSH Server";
      type empty;
    }
    leaf time-stamping {
      description
        "Time Stamping";
      type empty;
    }
  }

  grouping crypto-pki-trustpoint-grouping {
    container authorization {
      description
        "Authorization parameters.";
      leaf list {
        description
          "AAA authorization list to use";
        type string;
      }
      leaf password {
        description
          "password used for authorization request";
        type string;
      }
      container username {
        description
          "specify how AAA username is generated";
        container alt-subjectname {
          description
            "aaa username generated from certificate alt-subjectname";
          leaf userprinciplename {
            description
              "cert upn field as aaa username";
            type empty;
          }
          container userprinciplename-conf {
            container userprinciplename {
              description
                "cert upn field as aaa username";
              leaf secondary {
                description
                  "secondary username";
                when '../../../../../username';
                type empty;
              }
            }
          }
        }
        container subjectname {
          description
            "aaa username generated from certificate subjectname";
          leaf all {
            description
              "complete subject name as aaa username";
            type empty;
          }
          container all-conf {
            container all {
              description
                "complete subject name field as aaa username";
              leaf secondary {
                description
                  "secondary username";
                when '../../../../../username';
                type empty;
              }
            }
          }
          leaf commonname {
            description
              "common name as aaa username";
            type empty;
          }
          container commonname-conf {
            container commonname {
              description
                "Common name field as aaa username";
              leaf secondary {
                description
                  "secondary username";
                when '../../../../../username';
                type empty;
              }
            }
          }
          leaf country {
            description
              "country as aaa username";
            type empty;
          }
          container country-conf {
            container country {
              description
                "country field as aaa username";
              leaf secondary {
                description
                  "secondary username";
                when '../../../../../username';
                type empty;
              }
            }
          }
          leaf email {
            description
              "email as aaa username";
            type empty;
          }
          container email-conf {
            container email {
              description
                "email field as aaa username";
              leaf secondary {
                description
                  "secondary username";
                when '../../../../../username';
                type empty;
              }
            }
          }
          leaf ipaddress {
            description
              "IP address as aaa username";
            type empty;
          }
          container ipaddress-conf {
            container ipaddress {
              description
                "IP address field as aaa username";
              leaf secondary {
                description
                  "secondary username";
                when '../../../../../username';
                type empty;
              }
            }
          }
          leaf locality {
            description
              "locality as aaa username";
            type empty;
          }
          container locality-conf {
            container locality {
              description
                "locality field as aaa username";
              leaf secondary {
                description
                  "secondary username";
                when '../../../../../username';
                type empty;
              }
            }
          }
          leaf organization {
            description
              "organization as aaa username";
            type empty;
          }
          container organization-conf {
            container organization {
              description
                "organization field as aaa username";
              leaf secondary {
                description
                  "secondary username";
                when '../../../../../username';
                type empty;
              }
            }
          }
          leaf organizationalunit {
            description
              "organizational unit as aaa username";
            type empty;
          }
          container organizationalunit-conf {
            container organizationalunit {
              description
                "organizational unit field as aaa username";
              leaf secondary {
                description
                  "secondary username";
                when '../../../../../username';
                type empty;
              }
            }
          }
          leaf postalcode {
            description
              "postal code as aaa username";
            type empty;
          }
          container postalcode-conf {
            container postalcode {
              description
                "postal code field as aaa username";
              leaf secondary {
                description
                  "secondary username";
                when '../../../../../username';
                type empty;
              }
            }
          }
          leaf serialnumber {
            description
              "serial number as aaa username";
            type empty;
          }
          container serialnumber-conf {
            container serialnumber {
              description
                "serial number field as aaa username";
              leaf secondary {
                description
                  "secondary username";
                when '../../../../../username';
                type empty;
              }
            }
          }
          leaf state {
            description
              "state as aaa username";
            type empty;
          }
          container state-conf {
            container state {
              description
                "state field as aaa username";
              leaf secondary {
                description
                  "secondary username";
                when '../../../../../username';
                type empty;
              }
            }
          }
          leaf streetaddress {
            description
              "street address as aaa username";
            type empty;
          }
          container streetaddress-conf {
            container streetaddress {
              description
                "street address field as aaa username";
              leaf secondary {
                description
                  "secondary username";
                when '../../../../../username';
                type empty;
              }
            }
          }
          leaf title {
            description
              "title name as aaa username";
            type empty;
          }
          container title-conf {
            container title {
              description
                "title name field as aaa username";
              leaf secondary {
                description
                  "secondary username";
                when '../../../../../username';
                type empty;
              }
            }
          }
          leaf unstructuredname {
            description
              "unstructured name as aaa username";
            type empty;
          }
          container unstructuredname-conf {
            container unstructuredname {
              description
                "unstructured name field as aaa username";
              leaf secondary {
                description
                  "secondary username";
                when '../../../../../username';
                type empty;
              }
            }
          }
        }
      }
    }
    container certificate {
      description
        "certificate options";
      leaf chain {
        description
          "certificate chain configuration file";
        type string;
      }
    }
    container chain-validation {
      description
        "Validation parameters";
      leaf stop {
        description
          "Halt chain validation";
        type empty;
      }
      leaf continue {
        description
          "Validate this trustpoint's (sub)CA certificate";
        type string;
      }
    }
    container crl {
      description
        "CRL options";
      leaf query {
        description
          "Query CRL URL";
        type string;
      }
      container cache {
        description
          "CRL cache options";
        choice cache-choice {
          case none {
            leaf none {
              description
                "Do not cache CRLs";
              type empty;
            }
          }
          case extend {
            leaf extend {
              description
                "Extend CRL cache time";
              type uint16 {
                range "1..1440";
              }
            }
          }
          case delete-after {
            leaf delete-after {
              description
                "Remove CRL from cache after a timeout (in minutes)";
              type uint16 {
                range "1..43200";
              }
            }
          }
        }
      }
    }
    leaf disable-scep {
      description
        "Disable scep to enroll via http: file system";
      type empty;
    }
    leaf exit {
      description
        "Exit from certificate authority trustpoint entry mode";
      type empty;
    }
    container auto-enroll {
      description
        "Automatically enroll this router identity";
      presence "true";
      leaf percent {
        description
          "renewal percentage";
        type ios-types:percentage;
      }
      leaf regenerate {
        description
          "Regenerate keys on re-enrollment";
        type empty;
      }
    }
    leaf eckeypair {
      description
        "eckeypair for this identity";
      type string;
    }
    container eku {
      description
        "EKU parameters";
      container request {
        description
          "EKU requested attribute";
        uses crypto-pki-eku-grouping;
      }
    }
    container enrollment {
      description
        "Enrollment parameters";
      container http-proxy {
        description
          "HTTP proxy server for enrollment";
        leaf hostname {
          description
            "host-name";
          type string;
        }
        leaf port {
          description
            "port number";
          type uint16 {
            range "1..10000";
          }
        }
      }
      container mode {
        description
          "Mode supported by the Certificate Authority";
        leaf ra {
          description
            "Registration Authority mode";
          type empty;
        }
      }
      container enrollment-method {
        choice method {
          case pkcs12-case {
            leaf pkcs12 {
              description
                "Enroll via pkcs12";
              type empty;
            }
          }
          case profile-case {
            leaf profile {
              description
                "Specify an profile for enrollment";
              type leafref {
                path "/ios:native/ios:crypto/ios-crypto:pki/ios-crypto:profile/ios-crypto:enrollment/ios-crypto:tag";
              }
            }
          }
          case selfsigned-case {
            leaf selfsigned {
              description
                "Generate a Self Signed Certificate";
              type empty;
            }
          }
          case terminal-case {
            container terminal {
              description
                "Enroll via the terminal (cut-and-paste)";
              presence "true";
              leaf pem {
                description
                  "Include PEM encapsulation boundaries";
                type empty;
              }
            }
          }
          case url-case {
            leaf url {
              description
                "CA server enrollment URL";
              type string;
            }
          }
        }
      }
      leaf pkcs12 {
        status deprecated;
        type empty;
      }
      leaf profile {
        description
          "Specify an profile for enrollment";
        status deprecated;
        type leafref {
          path "/ios:native/ios:crypto/ios-crypto:pki/ios-crypto:profile/ios-crypto:enrollment/ios-crypto:tag";
        }
      }
      leaf selfsigned {
        description
          "Generate a Self Signed Certificate";
        status deprecated;
        type empty;
      }
      container terminal {
        description
          "Enroll via the terminal (cut-and-paste)";
        status deprecated;
        presence "true";
        leaf pem {
          description
            "Include PEM encapsulation boundaries";
          status deprecated;
          type empty;
        }
      }
      leaf url {
        description
          "CA server enrollment URL";
        status deprecated;
        type string;
      }
      container retry {
        description
          "Polling parameters";
        leaf count {
          description
            "How many times to poll CA for our certificate";
          type uint8 {
            range "1..100";
          }
        }
        leaf period {
          description
            "How long to wait between requests to CA for our certificate";
          type uint8 {
            range "1..60";
          }
        }
      }
    }
    leaf fqdn {
      description
        "include fully-qualified domain name";
      type string;
    }
    container password {
      description
        "revocation password";
      presence "true";
      leaf encryption-type {
        description
          "Encryption type";
        type uint8 {
          range "0..9";
        }
      }
      leaf clear-password {
        description
          "revocation password";
        type string;
      }
    }
    leaf fingerprint {
      description
        "CA Certificate Fingerprint";
      type string {
        pattern '([0-9a-fA-F]+)';
      }
    }
    leaf hash {
      description
        "Hash algorithm";
      default "sha512";
      type enumeration {
        enum md5;
        enum sha1;
        enum sha256;
        enum sha384;
        enum sha512;
      }
    }
    container http-proxy {
      description
        "HTTP proxy server for enrollment";
      leaf hostname {
        description
          "host-name";
        type string;
      }
      leaf port {
        description
          "port number";
        type uint16 {
          range "1..10000";
        }
      }
    }
    container ip-extension {
      description
        "RFC3779 IP extension for certificate request";
      container unicast {
        description
          "Apply to unicast traffic only";
        uses crypto-pki-trustpoint-ip-extension-grouping;
      }
      container multicast {
        description
          "Apply to multicast traffic only";
        uses crypto-pki-trustpoint-ip-extension-grouping;
      }
      uses crypto-pki-trustpoint-ip-extension-grouping;
    }
    container match {
      description
        "Match a certificate attributes/maps";
      container key-usage {
        description
          "key-usage attributes to validate";
        leaf cRLSign {
          type empty;
        }
      }
      container eku {
        description
          "EKU attributes to validate";
        uses crypto-pki-eku-grouping;
      }
      list certificate {
        description
          "Certificate map name";
        key "name";
        leaf name {
          type string;
        }
        container allow {
          description
            "Allow expired certificates to be accepted";
          leaf expired-certificate {
            type empty;
          }
        }
        leaf skip {
          description
            "Skip a certificate validity  check";
          type enumeration {
            enum authorization-check;
            enum revocation-check;
          }
        }
        container override {
          description
            "Over-ride fields in a certificate";
          container cdp {
            leaf directory {
              type string;
            }
            leaf url {
              type string;
            }
          }
          container ocsp {
            description
              "Over-ride the OCSP URL in a certificate";
            leaf trustpoint {
              description
                "Over-ride the trustpoint for verifying the OCSP certificate";
              type string;
            }
            leaf sequence-num {
              type uint16 {
                range "1..10000";
              }
            }
            leaf url {
              type string;
            }
          }
          container sia {
            description
              "Over-ride the SIA URL in a certificate";
            leaf sequence-num {
              type uint16 {
                range "1..10000";
              }
            }
            leaf url {
              type string;
            }
          }
        }
      }
    }
    container ocsp {
      description
        "OCSP parameters";
      leaf disable-nonce {
        description
          " Disable OCSP Nonce Extension";
        type empty;
      }
      leaf url {
        type string;
      }
    }
    leaf on {
      description
        "create keypair on device";
      type string;
    }
    leaf primary {
      description
        "Specify trustpoint as primary";
      type empty;
    }
    leaf regenerate {
      description
        "Regenerate keys on re-enrollment";
      type empty;
    }
    leaf-list revocation-check {
      description
        "Revocation checking options";
      ordered-by user;
      type enumeration {
        enum crl;
        enum none;
        enum ocsp;
      }
    }
    container root {
      description
        "Protocol to get CA certificate";
      leaf proxy {
        description
          "HTTP proxy server for getting CA cert";
        type string;
      }
      container tftp {
        description
          "Get CA certificate using tftp";
        leaf hostname {
          type string;
        }
        leaf filename {
          type string;
        }
      }
    }
    container source {
      description
        "Specify source interface";
      leaf interface {
        description
          "Interface used as source address";
        type string;
      }
    }
    leaf storage {
      description
        "key and certificate storage location";
      type string;
    }
    container rsakeypair {
      description
        "Specify rsakeypair for this identity";
      leaf key-label {
        description
          "RSA keypair label";
        type string;
      }
      leaf gen-key {
        description
          "General Purpose or Signature Key length";
        type uint16 {
          range "512..4096";
        }
      }
      leaf encrypt-key {
        description
          "Encryption Key length";
        type uint16 {
          range "512..4096";
        }
      }
    }
    container serial-number {
      description
        "Include serial number";
      presence "true";
      leaf none {
        description
          "do not include serial number";
        type empty;
      }
    }
    container ip-address {
      description
        "include ip address";
      leaf address-line {
        description
          "interface name or ip address";
        type string;
      }
      leaf none {
        description
          "do not include ip address";
        type empty;
      }
    }
    leaf subject-name {
      description
        "Subject Name";
      type string;
    }
    leaf subject-alt-name {
      description
        "Subject Alternate Name";
      type string;
    }
    leaf usage {
      description
        "Certificate Usage";
      type enumeration {
        enum ike;
        enum ssl-client;
        enum ssl-server;
      }
    }
    leaf vrf {
      description
        "Name of VRF to use with trustpoint";
      type string;
    }
    leaf auto-trigger {
      description
        "Trigger authentication automatically";
      type empty;
    }
  }

  grouping crypto-pki-trustpool-policy-grouping {
    container ca-bundle {
      description
        "CA bundle download parameters";
      leaf url {
        description
          "CA server bundle URL";
        type string;
      }
      choice source-vrf {
        case source {
          container source {
            description
              "Interface used as source address";
            leaf interface {
              type string;
            }
          }
        }
        case vrf {
          leaf vrf {
            description
              "Name of VRF to use with bundle";
            type string;
          }
        }
      }
    }
    leaf vrf {
      description
        "Name of VRF to use with trustpoint";
      type string;
    }
    container source {
      description
        "Specify source interface";
      leaf interface {
        description
          "Interface used as source address";
        type string;
      }
    }
    leaf storage {
      description
        "key and certificate storage location";
      type string;
    }
    leaf revocation-check {
      description
        "Revocation checking options";
      type enumeration {
        enum crl;
        enum none;
        enum ocsp;
      }
    }
    container ocsp {
      description
        "OCSP parameters";
      leaf disable-nonce {
        description
          " Disable OCSP Nonce Extension";
        type empty;
      }
      leaf url {
        type string;
      }
    }
    leaf chain-validation {
      description
        "Validation parameters";
      type empty;
    }
    leaf exit {
      type empty;
    }
    container match {
      description
        "Match a certificate attributes/maps";
      list certificate {
        description
          "Certificate map name";
        key "name";
        leaf name {
          type string;
        }
        container allow {
          description
            "Allow expired certificates to be accepted";
          leaf expired-certificate {
            type empty;
          }
        }
        leaf skip {
          description
            "Skip a certificate validity  check";
          type enumeration {
            enum authorization-check;
            enum revocation-check;
          }
        }
        container override {
          description
            "Over-ride fields in a certificate";
          container cdp {
            choice dir-url {
              case directory {
                leaf directory {
                  type string;
                }
              }
              case url {
                leaf url {
                  type string;
                }
              }
            }
          }
          container ocsp {
            description
              "Over-ride the OCSP URL in a certificate";
            leaf trustpool {
              description
                "Over-ride the trustpoint for verifying the OCSP certificate";
              type string;
            }
            leaf sequence-num {
              type uint16 {
                range "1..10000";
              }
            }
            leaf url {
              type string;
            }
          }
          container sia {
            description
              "Over-ride the SIA URL in a certificate";
            leaf sequence-num {
              type uint16 {
                range "1..10000";
              }
            }
            leaf url {
              type string;
            }
          }
        }
      }
    }
    container crl {
      description
        "CRL options";
      leaf query {
        description
          "Query CRL URL";
        type string;
      }
      container cache {
        description
          "CRL cache options";
        choice cache-choice {
          case none {
            leaf none {
              description
                "Do not cache CRLs";
              type empty;
            }
          }
          case delete-after {
            leaf delete-after {
              description
                "Remove CRL from cache after a timeout (in minutes)";
              type uint16 {
                range "1..43200";
              }
            }
          }
        }
      }
    }
  }

  grouping crypto-pki-certificate-chain-grouping {
    list certificate {
      description
        "Certificate issued by the CA";
      key "serial";
      leaf serial {
        type string;
      }
      leaf certtype {
        type enumeration {
          enum ca;
          enum ra-encrypt;
          enum ra-general;
          enum ra-sign;
          enum rollover;
          enum self-signed;
          enum "ca rollover";
        }
      }
    }
    container crl {
      description
        "Revocation list issued by the CA";
      leaf cdp-hexdata {
        description
          "Revocation distribution point";
        type string {
          pattern '([0-9a-fA-F]+)';
        }
      }
    }
  }

  grouping crypto-pki-server-grouping {
    container auto-rollover {
      description
        "Rollover the CA key and certificate";
      leaf days {
        description
          "Overlap time in days";
        type uint16 {
          range "0..1825";
        }
      }
      leaf hours {
        description
          "Overlap time in hours";
        type uint8 {
          range "0..23";
        }
      }
      leaf minutes {
        description
          "Overlap time in minutes";
        type uint8 {
          range "0..59";
        }
      }
    }
    leaf cdp-url {
      description
        "CDP to be included in the issued certificates";
      type string;
    }
    container database {
      description
        "Certificate Server database config parameters";
      leaf level {
        description
          "Level of data stored in database";
        type enumeration {
          enum complete;
          enum minimum;
          enum names;
        }
      }
      uses database-username-password-grouping;
      container url {
        description
          "database URL";
        leaf url-only {
          type string;
        }
        leaf file-type {
          description
            "type of file";
          type enumeration {
            enum cnm;
            enum crl;
            enum crt;
            enum ser;
            enum pem;
            enum p12;
          }
        }
        leaf publish {
          description
            "Store a copy at a storage location";
          type empty;
        }
        choice url-combination {
          case location-alone {
            leaf location {
              description
                "url value";
              type string;
            }
          }
          case url-with-username {
            container url-with-username {
              leaf location {
                description
                  "url value";
                type string;
              }
              uses database-username-password-grouping;
            }
          }
        }
      }
      container archive {
        description
          "Backup Certificate Server Signing Certificate and Keys";
        choice format {
          container pem {
            description
              "PEM format";
            presence "true";
            uses database-password-grouping;
          }
          container pkcs12 {
            description
              "PKCS12 format";
            presence "true";
            uses database-password-grouping;
          }
        }
      }
    }
    leaf serial-number {
      description
        "Serial number of last certificate issued";
      type string;
    }
    leaf revoke {
      description
        "Revoke a certificate";
      type string;
    }
    container mode {
      description
        "Mode";
      choice ra-or-subcs {
        case ra {
          leaf ra {
            type empty;
          }
          leaf transparent {
            type empty;
          }
        }
        case subca {
          leaf sub-cs {
            type empty;
          }
        }
      }
    }
    container lifetime {
      description
        "lifetime of the certificate";
      leaf certificate {
        type enumeration {
          enum ca-certificate;
          enum certificate;
          enum crl;
          enum enrollment-request;
        }
      }
      leaf days {
        type uint16 {
          range "0..7305";
        }
      }
      leaf hours {
        type uint8 {
          range "0..23";
        }
        default "0";
      }
      leaf minutes {
        type uint16 {
          range "0..59";
        }
        default "0";
      }
    }
    leaf hash {
      description
        "Hash algorithm";
      type enumeration {
        enum md5;
        enum sha1;
        enum sha256;
        enum sha384;
        enum sha512;
      }
    }
    container eku {
      description
        "EKU parameters";
      uses crypto-pki-eku-grouping;
    }
    leaf issuer-name {
      description
        "Issuer name";
      type string;
    }
    container grant {
      description
        "Certificate granting options";
      leaf type {
        type enumeration {
          enum none;
          enum ra-auto;
        }
      }
      container auto {
        leaf auto-alone {
          type empty;
        }
        leaf trustpoint {
          type string;
        }
        leaf tp-list {
          type string;
        }
        leaf rollover {
          type enumeration {
            enum ra-cert;
            enum ca-cert;
          }
        }
      }
    }
    leaf shutdown-config {
      description
        "Shutdown the certificate server";
      type boolean;
      default "true";
    }
    leaf shutdown {
      description
        "Shutdown the certificate server";
      status obsolete;
      type empty;
    }
  }

  grouping crypto-ssl-profile-aaa-auth-passwd-grouping {
    container password {
      description
        "Specify the AAA password";
      leaf encryption {
        type enumeration {
          enum 0;
          enum 6;
        }
      }
      leaf key {
        type string {
          length "1..214";
        }
      }
    }
  }

  grouping crypto-ssl-profile-aaa-auth-passwd-grouping-deprecated {
    container password {
      description
        "DEPRECATED Specify the AAA password";
      status deprecated;
      leaf encryption {
        status deprecated;
        type enumeration {
          enum 0;
          enum 6;
        }
      }
      leaf key {
        status deprecated;
        type string {
          length "1..214";
        }
      }
    }
  }

  grouping config-crypto-grouping {
    container call {
      description
        "Configure Crypto Call Admission Control";
      container admission {
        description
          "Configure Crypto Call Admission Control";
        container limit {
          description
            "Configure Crypto Call Admission Control limits";
          container all {
            description
              "Configure Crypto Call Admission Control total in-negotiation SA limit";
            leaf in-negotiation-sa {
              description
                "Maximum number of in-negotiation SAs allowed";
              type uint32 {
                range "10..99999";
              }
            }
          }
          container ike {
            description
              "Configure Crypto Call Admission Control active IKE SA limit";
            leaf in-negotiation-sa {
              description
                "Maximum number of in-negotiation IKE SAs allowed";
              type uint32 {
                range "10..99999";
              }
              default "1000";
            }
            leaf sa {
              description
                "Maximum active IKE SAs allowed";
              type uint32 {
                range "0..99999";
              }
              default "0";
            }
          }
          container ipsec {
            description
              "Configure Crypto Call Admission Control active IPSec SA limit";
            leaf sa {
              description
                "Maximum active IPSec SAs allowed";
              type uint32 {
                range "0..99999";
              }
              default "0";
            }
          }
        }
      }
    }
    list dynamic-map {
      description
        "Specify a dynamic crypto map template";
      key "name sequence";
      leaf name {
        type string;
      }
      leaf sequence {
        type uint16 {
          range "1..65535";
        }
      }
      container default {
        description
          "Set a command to its defaults";
        uses crypto-dynamic-map-default-grouping;
      }
      uses crypto-dynamic-map-grouping;
    }
    container engine {
      description
        "Enter a crypto engine configurable menu";
      leaf software {
        description
          "Software crypto engine";
        type enumeration {
          enum ipsec;
          enum isakmp;
        }
      }
      container compliance {
        description
          "Crypto engine compliance value";
        container shield {
          description
            "Compliance shield";
          leaf disable {
            description
              "Allow weak crypto to be configured";
            type empty;
          }
        }
      }
    }
    container gdoi {
      description
        "Configure GKM (Group Key Management, GDOI or G-IKEv2) Policy";
      list group {
        description
          "Configure a GKM (Group Key Management, GDOI or G-IKEv2) Group";
        key "name";
        leaf name {
          type string;
        }
        leaf ipv6 {
          description
            "IPv6 GKM (Group Key Management) Group";
          type empty;
        }
        uses crypto-gdio-grouping;
        container default {
          description
            "Set a command to its defaults";
          uses crypto-gdio-default-grouping;
        }
      }
    }
    container ikev2 {
      description
        "Configure IKEv2 Options";
      uses crypto-ikev2-grouping;
    }
    container gkm {
      description
        "Configure GKM (Group Key Management, GDOI or G-IKEv2) Policy";
      list group {
        description
          "Configure a GKM (Group Key Management, GDOI or G-IKEv2) Group";
        key "name";
        leaf name {
          type string;
        }
        leaf ipv6 {
          description
            "IPv6 GKM (Group Key Management) Group";
          type empty;
        }
        uses crypto-gdio-grouping;
        container default {
          description
            "Set a command to its defaults";
          uses crypto-gdio-default-grouping;
        }
      }
    }
    list identity {
      description
        "Enter a crypto identity list";
      key "name";
      leaf name {
        type string;
      }
      container default {
        description
          "Set a command to its defaults";
        uses crypto-identity-default-grouping;
      }
      uses crypto-identity-grouping;
    }
    container ipsec {
      description
        "Configure IPSEC policy";
      uses crypto-ipsec-grouping;
    }
    container key {
      description
        "Long term key operations";
      uses crypto-key-grouping;
    }
    list keyring {
      description
        "Key ring commands";
      key "name";
      leaf name {
        type string;
      }
      leaf vrf {
        description
          "Mention a vrf it belongs to";
        type string;
      }
      container default {
        description
          "Set a command to its defaults";
        uses crypto-keyring-grouping;
      }
      uses crypto-keyring-grouping;
    }
    container isakmp {
      description
        "Configure ISAKMP policy";
      uses crypto-isakmp-grouping;
    }
    container logging {
      description
        "logging messages";
      container ezvpn {
        description
          "ezvpn logging enable/disable";
        presence "true";
        leaf group {
          description
            "ezvpn group";
          type string;
        }
      }
      leaf ikev2 {
        description
          "logging IKEv2 sessions";
        type empty;
      }
      leaf session {
        description
          "logging up/down session";
        type empty;
      }
    }
    grouping map-sequence-ipv4-ipv6-grouping {
      list map {
        key "name seq";
        leaf name {
          type string;
        }
        leaf seq {
          description
            "sequence number";
          type uint32 {
            range "1..65535";
          }
        }
        choice ipsec-isakmp-gdoi-ipsec-manual {
          case ipsec-isakmp-case {
            container ipsec-isakmp {
              description
                "IPSEC w/ISAKMP";
              presence "true";
              choice dynamic-profile {
                case dynamic-case {
                  container dynamic {
                    description
                      "Enable dynamic crypto map support";
                    leaf mode {
                      description
                        "Name of dynamic-map template";
                      type string;
                    }
                    leaf discover {
                      description
                        "Enable dynamic peer discovery";
                      type empty;
                    }
                  }
                }
                case profile-case {
                  leaf profile {
                    description
                      "Enable crypto map as a crypto-profile";
                    type string;
                  }
                }
              }
            }
          }
          case gdoi {
            leaf gdoi {
              description
                "configure GDOI map";
              type empty;
            }
          }
          case ipsec-manual {
            leaf ipsec-manual {
              description
                "IPSEC w/manual keying";
              type empty;
            }
          }
        }
        uses crypto-map-grouping;
      }
    }

    grouping map-client-grouping {
      list accounting {
        key "name";
        leaf name {
          type string;
        }
        leaf client {
          description
            "Specify client configuration settings";
          mandatory true;
          type empty;
        }
        leaf accounting {
          description
            "Accounting parameters.";
          mandatory true;
          type empty;
        }
        leaf list {
          description
            "AAA accounting list to use";
          type string;
        }
      }
      list authentication-list {
        key "name";
        leaf name {
          type string;
        }
        leaf client {
          description
            "Specify client configuration settings";
          mandatory true;
          type empty;
        }
        leaf authentication {
          description
            "Use Extended Authentication";
          mandatory true;
          type empty;
        }
        leaf list {
          description
            "AAA authentication list to use";
          type string;
        }
      }
      list authentication-password {
        key "name";
        leaf name {
          type string;
        }
        leaf client {
          description
            "Specify client configuration settings";
          mandatory true;
          type empty;
        }
        leaf authentication {
          description
            "Use Extended Authentication";
          mandatory true;
          type empty;
        }
        leaf password {
          description
            "Password to use for authentication";
          type string;
        }
      }
      list authentication-username {
        key "name";
        leaf name {
          type string;
        }
        leaf client {
          description
            "Specify client configuration settings";
          mandatory true;
          type empty;
        }
        leaf authentication {
          description
            "Use Extended Authentication";
          mandatory true;
          type empty;
        }
        leaf username {
          description
            "Username to use for authentication";
          type string;
        }
      }
    }

    grouping map-gdoi-ipv4-ipv6-grouping {
      list map {
        key "name";
        leaf name {
          type string;
        }
        leaf gdoi {
          description
            "Configure crypto map gdoi features";
          type empty;
        }
        leaf fail-close {
          description
            "Configure crypto map on Fail Close mode";
          type empty;
        }
        leaf activate {
          description
            "Activate the crypto map to work in fail-close mode";
          type empty;
        }
        container match {
          description
            "acl";
          leaf address {
            description
              "address";
            type ios-types:access-list-standard-id-type;
          }
        }
      }
    }

    grouping map-local-ipv4-ipv6-grouping {
      list map {
        key "name";
        leaf name {
          type string;
        }
        container local-address {
          description
            "Interface to use for local address for this crypto map";
          uses ios-ifc:interface-grouping;
        }
      }
    }

    container map {
      description
        "Enter a crypto map";
      choice name-ipv6 {
        case name-case {
          container map-seq {
            uses map-sequence-ipv4-ipv6-grouping;
          }
          container map-client {
            uses map-client-grouping;
            list autorization {
              status obsolete;
              key "name";
              leaf name {
                status obsolete;
                type string;
              }
              leaf client {
                description
                  "Specify client configuration settings";
                status obsolete;
                type empty;
              }
              leaf autorization {
                status obsolete;
                description
                  "parameters.";
                mandatory true;
                type empty;
              }
              leaf list {
                status obsolete;
                description
                  "AAA accounting list to use";
                type string;
              }
            }
            list configuration-intiate {
              key "name";
              leaf name {
                type string;
              }
              leaf client {
                description
                  "Specify client configuration settings";
                type empty;
              }
              leaf configuration {
                description
                  "Specify client configuration settings";
                mandatory true;
                type empty;
              }
              leaf address {
                description
                  "Specify client network address configuration";
                mandatory true;
                type empty;
              }
              leaf initiate {
                description
                  "Push the network address to the client";
                type empty;
              }
            }
            list configuration-respond {
              status obsolete;
              key "name";
              leaf name {
                status obsolete;
                type string;
              }
              leaf client {
                status obsolete;
                description
                  "Specify client configuration settings";
                type empty;
              }
              leaf configuration {
                status obsolete;
                description
                  "Specify client configuration settings";
                mandatory true;
                type empty;
              }
              leaf address {
                status obsolete;
                description
                  "Specify client network address configuration";
                mandatory true;
                type empty;
              }
              leaf respond {
                status obsolete;
                description
                  "Respond to network address requests from the client";
                type empty;
              }
            }
          }
          container map-gdoi {
            uses map-gdoi-ipv4-ipv6-grouping;
          }
          container map-isakmp {
            list map {
              key "name";
              leaf name {
                type string;
              }
              leaf isakmp-profile {
                description
                  "Specify isakmp profile to use";
                must '/ios:native/ios:crypto/isakmp/profile[name=current()]' {
                  error-message "It seems ISAKMP profile doesn't exist or attempted to delete when actively referred";
                }
                type string;
              }
            }
          }
          container map-local {
            uses map-local-ipv4-ipv6-grouping;
          }
          container map-redundancy {
            list map {
              key "name";
              leaf name {
                type string;
              }
              container redundancy {
                description
                  "High availability options for this map";
                container replay-interval {
                  description
                    "HA replay counter interval";
                  leaf inbound {
                    description
                      "HA inbound replay counter interval";
                    type uint32 {
                      range "0..1000";
                    }
                  }
                  leaf outbound {
                    description
                      "HA outbound replay counter interval";
                    type uint32 {
                      range "1000..10000";
                    }
                  }
                }
              }
            }
          }
          container ipv6-map {
            description
              "Enter a ipv6 crypto map";
            container map-seq {
              uses map-sequence-ipv4-ipv6-grouping;
            }
            container map-client {
              uses map-client-grouping;
            }
            container map-gdoi {
              uses map-gdoi-ipv4-ipv6-grouping;
            }
            container map-local {
              uses map-local-ipv4-ipv6-grouping;
            }
          }
        }
        case ipv6-case {
          container ipv6 {
            description
              "Enter a ipv6 crypto map";
            container map-seq {
              uses map-sequence-ipv4-ipv6-grouping;
            }
            container map-client {
              uses map-client-grouping;
            }
            container map-gdoi {
              uses map-gdoi-ipv4-ipv6-grouping;
            }
            container map-local {
              uses map-local-ipv4-ipv6-grouping;
            }
          }
        }
      }
    }
    container crypto-map {
      status obsolete;
      list map {
        description
          "Enter a crypto map";
        status obsolete;
        key "name sequence-number";
        leaf name {
          status obsolete;
          type string;
        }
        leaf sequence-number {
          status obsolete;
          type uint16;
        }
        leaf ipv6 {
          description
            "IPv6 crypto map";
          status obsolete;
          type empty;
        }
        leaf keying {
          status obsolete;
          type enumeration {
            enum ipsec-isakmp;
            enum ipsec-manual;
            enum gdoi;
            enum ckm;
          }
        }
        choice dynamic-profile {
          status obsolete;
          case dynamic-case {
            status obsolete;
            leaf dynamic {
              description
                "Enable dynamic crypto map support";
              status obsolete;
              when "../keying = 'ipsec-isakmp'";
              type string;
            }
          }
          case profile-case {
            status obsolete;
            leaf profile {
              description
                "Enable crypto map as a crypto-profile";
              status obsolete;
              when "../keying = 'ipsec-isakmp'";
              type string;
            }
          }
        }
        container default {
          description
            "Set a command to its defaults";
          status obsolete;
          uses obsolete-crypto-map-default-grouping;
        }
        uses obsolete-crypto-map-grouping;
      }
    }
    container map-ipv6-gdoi {
      status obsolete;
      list map {
        description
          "Enter a crypto map";
        status obsolete;
        key "name";
        leaf name {
          status obsolete;
          type string;
        }
        leaf ipv6 {
          description
            "IPv6 crypto map";
          status obsolete;
          type empty;
        }
        leaf gdoi {
          description
            "Configure crypto map gdoi features";
          status obsolete;
          type enumeration {
            enum fail-close;
          }
        }
        container default {
          description
            "Set a command to its defaults";
          status obsolete;
          uses obsolete-crypto-map-gdoi-default-mapping-grouping;
        }
        uses obsolete-crypto-map-gdoi-mapping-grouping;
      }
    }
    container map-client {
      status obsolete;
      list map {
        description
          "Enter a crypto map";
        status obsolete;
        key "name";
        leaf name {
          status obsolete;
          type string;
        }
        leaf ipv6 {
          description
            "IPv6 crypto map";
          status obsolete;
          type empty;
        }
        container client {
          description
            "Specify client configuration settings";
          status obsolete;
          container accounting {
            description
              "Accounting parameters.";
            status obsolete;
            leaf list {
              description
                "AAA accounting list to use";
              status obsolete;
              type string;
            }
          }
          container authentication {
            description
              "Use Extended Authentication";
            status obsolete;
            leaf list {
              description
                "AAA authentication list to use";
              status obsolete;
              type string;
            }
          }
          container configuration {
            description
              "Specify client configuration settings";
            status obsolete;
            container address {
              description
                "Specify client network address configuration";
              status obsolete;
              leaf initiate {
                description
                  "Push the network address to the client";
                status obsolete;
                type empty;
              }
              leaf respond {
                description
                  "Respond to network address requests from the client";
                status obsolete;
                type empty;
              }
            }
          }
        }
        container isakmp {
          description
            "Specify isakmp configuration settings";
          status obsolete;
          leaf authorization {
            description
              "Authorization parameters.";
            status obsolete;
            type empty;
          }
          leaf list {
            description
              "AAA Authorization list to use";
            status obsolete;
            type string;
          }
        }
        leaf isakmp-profile {
          description
            "Specify isakmp profile to use";
          status obsolete;
          type string;
        }
        leaf local-address {
          description
            "Interface to use for local address for this crypto map";
          status obsolete;
          type string;
        }
        container redundancy {
          description
            "High availability options for this map";
          status obsolete;
          container replay-interval {
            description
              "HA replay counter interval";
            status obsolete;
            leaf inbound {
              description
                "HA inbound replay counter interval";
              status obsolete;
              type uint32 {
                range "0..1000";
              }
            }
            leaf outbound {
              description
                "HA outbound replay counter interval";
              status obsolete;
              type uint32 {
                range "1000..10000";
              }
            }
          }
        }
      }
    }
    container mib {
      description
        "Configure Crypto-related MIB Parameters";
      container ipsec {
        description
          "Configure MIB Parameters";
        container flowmib {
          description
            "Configure IPSec Flow-MIB Parameters";
          container history {
            description
              "Configure IPSEC Flow MIB History Parameters";
            container failure {
              description
                "Configure IPSEC Flow MIB Failure History Parameters";
              leaf size {
                description
                  "Configure IPSEC Flow MIB Tunnel Failure History Window Size";
                type uint8 {
                  range "2..200";
                }
                default "200";
              }
            }
            container tunnel {
              description
                "Configure IPSEC Flow MIB Tunnel History Parameters";
              leaf size {
                description
                  "Configure IPSEC Flow MIB Tunnel Failure History Window Size";
                type uint8 {
                  range "2..200";
                }
                default "200";
              }
            }
          }
        }
      }
    }
    container pki {
      description
        "Public Key components";
      leaf authenticate {
        description
          "Get the CA certificate";
        type string;
      }
      container certificate {
        description
          "Actions on certificates";
        list chain {
          status obsolete;
          description
            "Identify certificates";
          key "name";
          leaf name {
            status obsolete;
            type string;
          }
          container default {
            status obsolete;
            description
              "Set a command to its default";
            uses crypto-pki-certificate-chain-grouping-obsolete;
          }
          uses crypto-pki-certificate-chain-grouping-obsolete;
        }
        container pki-map {
          list map {
            description
              "Define certificate attributes map";
            key "tag sequence";
            leaf tag {
              type string;
            }
            leaf sequence {
              type uint16 {
                range "1..65535";
              }
            }
            uses crypto-pki-certificate-map-grouping-v2;
          }
        }
        list map {
          status deprecated;
          description
            "Define certificate attributes map";
          key "tag";
          leaf tag {
            status deprecated;
            type string;
          }
          leaf sequence {
            status deprecated;
            type uint16;
          }
          container default {
            status obsolete;
            uses crypto-pki-certificate-map-grouping-obsolete;
          }
          uses crypto-pki-certificate-map-grouping-deprecated;
        }
        container pool {
          description
            "Identify CA certificates in pool";
          presence "true";
          leaf cabundle {
            description
              "save the bundle file";
            type string;
          }
        }
        leaf query {
          description
            "Get certificates from the CA after reboot";
          type empty;
        }
        container self-signed {
          description
            "Self signed certificate hash algorithm";
          leaf hash {
            description
              "Hash algorithm";
            type enumeration {
              enum md5;
              enum sha1;
              enum sha256;
              enum sha384;
              enum sha512;
            }
          }
        }
        container storage {
          description
            "specify where to store certificates";
          leaf with-keypair {
            description
              "Store certificates with keypair";
            type empty;
          }
          leaf on {
            description
              "Create keypairs on device";
            type empty;
          }
          leaf path {
            type union {
              type enumeration {
                enum bootflash:;
                enum flash:;
                enum nvram:;
              }
              type string;
            }
          }
        }
        leaf validate {
          description
            "Validate a certificate chain";
          type string;
        }
      }
      container crl {
        description
          "Actions on certificate revocation lists";
        container cache {
          description
            "Cache which holds recently parsed CRLs";
          leaf size {
            description
              "Size of the recently parsed CRL cache";
            type uint32 {
              range "0..131072";
            }
            default "64";
          }
        }
        container download {
          description
            "auto-download CRL";
          container schedule {
            description
              "Schedule time to auto-download CRL";
            leaf prepublish {
              description
                "Requests CRL at prepublish time";
              type uint16;
              default "0";
            }
            container retries {
              description
                "Retry request for failed CDP locations";
              leaf number {
                type uint8 {
                  range "1..15";
                }
                default "5";
              }
              leaf interval {
                description
                  "retry time interval for each attempt";
                type uint16 {
                  range "15..600";
                }
                default "30";
              }
            }
            container time {
              description
                "Request auto-download CRL at this time";
              leaf date {
                type enumeration {
                  enum Friday;
                  enum Monday;
                  enum Saturday;
                  enum Sunday;
                  enum Thursday;
                  enum Tuesday;
                  enum Wednesday;
                }
              }
              leaf clock {
                type string;
              }
            }
          }
          leaf trustpoint {
            description
              "Trustpoint to auto-download CRL";
            type string;
          }
          container url {
            description
              "URL to auto-download CRL";
            leaf name {
              type string;
            }
            leaf source-interface {
              description
                "Interface used as source address";
              type string;
            }
            leaf vrf {
              description
                "VRF to use for CRL download";
              type string;
            }
          }
        }
        leaf request {
          description
            "Requests a current CRL";
          type string;
        }
      }
      leaf enroll {
        description
          "Request a certificate from a CA";
        type string;
      }
      list export {
        description
          "Export certificate or PKCS12 file";
        key "name";
        leaf name {
          type string;
        }
        container pem {
          description
            "Export to PEM files";
          container terminal {
            description
              "Export via the terminal (cut-and-paste)";
            presence "true";
            container pem-3des {
              description
                "Encrypt the private key with 3DES";
              leaf password {
                description
                  "Passphrase";
                type string;
              }
            }
            container des {
              description
                "Encrypt the private key with DES";
              leaf password {
                description
                  "Passphrase";
                type string;
              }
            }
            leaf rollover {
              description
                "Export the rollover CA certificate";
              type empty;
            }
          }
          container url {
            description
              "Export via the file systems";
            uses crypto-key-url-file-ex-grouping;
            leaf encrypt {
              type enumeration {
                enum 3des;
                enum des;
              }
            }
            leaf password {
              description
                "Passphrase";
              when '../encrypt';
              type string;
            }
          }
        }
        container pkcs12 {
          description
            "Export to PKCS12 file";
          uses crypto-key-url-file-ex-grouping;
          leaf password {
            description
              "Passphrase";
            type string;
          }
        }
      }
      list import {
        description
          "Import certificate or PKCS12 file";
        key "name";
        leaf name {
          type string;
        }
        leaf certificate {
          description
            "Import a certificate from a TFTP server or the terminal";
          type empty;
        }
        container pem {
          description
            "Import from PEM files";
          leaf check {
            description
              "Validate certificate on input";
            type empty;
          }
          leaf exportable {
            description
              "Allow the key as to be exported";
            type empty;
          }
          container terminal {
            description
              "Import via the terminal (cut-and-paste)";
            leaf password {
              description
                "Passphrase";
              type string;
            }
          }
          container url {
            description
              "Export via the file systems";
            uses crypto-key-url-file-ex-grouping;
            leaf password {
              description
                "Passphrase";
              type string;
            }
          }
          leaf usage-keys {
            description
              "Usage key pairs";
            type empty;
          }
        }
        container pkcs12 {
          description
            "Import from PKCS12 file";
          leaf check {
            type empty;
          }
          uses crypto-key-url-file-ex-grouping;
          leaf password {
            description
              "Passphrase";
            type string;
          }
        }
      }
      container profile {
        description
          "Define a certificate profile";
        list enrollment {
          description
            "Define an enrollment profile";
          key "tag";
          leaf tag {
            type string;
          }
          uses crypto-pki-profile-enrollment-grouping;
          container default {
            status obsolete;
            description
              "Set a command to its defaults";
            uses crypto-pki-profile-enrollment-grouping-obsolete;
          }
        }
      }
      list server {
        description
          "Enable IOS Certificate server";
        key "name";
        max-elements 1;
        leaf name {
          type string;
        }
        container default {
          status obsolete;
          description
            "Set a default value";
          uses crypto-pki-server-grouping-obsolete;
        }
        uses crypto-pki-server-grouping;
      }
      container pki-server-no-submode {
        container server {
          description
            "Enable IOS Certificate server";
          leaf name {
            type string;
          }
          leaf rollover {
            description
              "Rollover the server's key and certificate";
            type empty;
          }
          leaf cancel {
            description
              "Cancel a pending rollover";
            type empty;
          }
        }
      }
      list trustpoint {
        description
          "Define a CA trustpoint";
        key "id";
        leaf id {
          type string;
        }
        container default {
          status obsolete;
          description
            "Set a command to its defaults";
          uses crypto-pki-trustpoint-grouping-obsolete;
        }
        uses crypto-pki-trustpoint-grouping;
      }
      container token {
        description
          "Configure cryptographic token";
        list token-name {
          key "name";
          leaf name {
            type string;
          }
          uses crypto-pki-token-grouping;
        }
      }
      container trustpool {
        description
          "Define CA trustpool";
        leaf clean {
          description
            "Remove all downloaded trustpool certificates";
          type empty;
        }
        container import {
          description
            "Import a trustpool bundle";
          presence "true";
          leaf clean {
            description
              "Remove all downloaded trustpool certificates prior to import";
            type empty;
          }
          leaf terminal {
            description
              "Import bundle via the terminal (cut-and-paste) in PEM format";
            type empty;
          }
          leaf url {
            description
              "Import via the file systems";
            type string {
              pattern '(((bootflash:)|(harddisk:)|(flash:)|(nvram:)|(ftp:)|(http:)|(https:)|(scp:)|(tftp:)|(webui:)).*)';
            }
          }
          leaf ca-bundle {
            description
              "Import from ca-bundles configured in trustpool policy";
            type empty;
          }
        }
        container policy {
          description
            "Define trustpool policy";
          presence "true";
          container default {
            status obsolete;
            description
              "Set a command to its defaults";
            uses crypto-pki-trustpool-policy-grouping-obsolete;
          }
          uses crypto-pki-trustpool-policy-grouping;
        }
      }
      container default {
        status obsolete;
        description
          "set default values for tokens";
        uses crypto-pki-token-grouping-obsolete;
      }
    }
    container tls-tunnel {
      list tls-tunnel-list {
        description
          "Configure Crypto TLS-Tunnel Options";
        key "tunnel-name";
        leaf tunnel-name {
          description
            "Name of TLS-Tunnel";
          type string;
        }
        leaf cc-mode {
          description
            "Enable CC-Mode";
          type empty;
        }
        leaf device-id {
          description
            "Device Identifier";
          type string;
        }
        list tls-local-interface {
          description
            "Specify the WAN interfaces";
          key "priority";
          unique "interface-name";
          leaf interface-name {
            type string;
          }
          leaf priority {
            description
              "priority level";
            type uint8 {
              range "1..3";
            }
          }
        }
        list local-interface {
          status deprecated;
          description
            "Specify the WAN interfaces";
          key "interface-name";
          unique "priority";
          leaf interface-name {
            status deprecated;
            type string;
          }
          leaf priority {
            status deprecated;
            description
              "priority level";
            type uint8 {
              range "1..3";
            }
          }
        }
        leaf mode {
          description
            "Server Mode";
          type enumeration {
            enum dtls {
              value 1;
            }
            enum tls {
              value 2;
            }
          }
        }
        container overlay {
          description
            "Specify the Overlay type";
          choice overlay-case {
            case overlay-address-case {
              leaf address {
                description
                  "Specify the Overlay address";
                type inet:ip-address;
              }
              leaf vrf {
                description
                  "VRF name";
                must '/ios:native/ios:vrf/ios:definition[ios:name=current()] or /ios:native/ios:ip/ios:vrf[ios:name=current()]' {
                  error-message "VRF must be created 1st, deleted last";
                }
                type string;
              }
            }
            case overlay-intf-case {
              leaf interface {
                description
                  "Specify the Overlay interface";
                type string;
              }
            }
          }
        }
        container overlay-address {
          status obsolete;
          description
            "Specify the Overlay Address";
          leaf addresses {
            status obsolete;
            type inet:ip-address;
          }
          leaf vrf {
            status obsolete;
            description
              "VRF name";
            must '/ios:native/ios:vrf/ios:definition[ios:name=current()] or /ios:native/ios:ip/ios:vrf[ios:name=current()]' {
              error-message "VRF must be created 1st, deleted last";
            }
            type string;
          }
        }
        container pki {
          description
            "Specify the pki trustpoint for auth";
          list trustpoint {
            description
              "Specify the pki trustpoint";
            key "trustpoint-name";
            leaf trustpoint-name {
              type string;
            }
            leaf use {
              type enumeration {
                enum sign {
                  value 1;
                }
                enum verify {
                  value 2;
                }
              }
            }
          }
        }
        container protection {
          description
            "Cipher-Suite";
          leaf protection {
            type enumeration {
              enum dhe-psk-aes128-cbc-sha1;
              enum dhe-psk-aes256-cbc-sha1;
              enum psk-aes128-cbc-sha1;
              enum psk-aes256-cbc-sha1;
            }
          }
        }
        container psk {
          description
            "Specify the Pre-Shared Key";
          list id {
            key "id";
            leaf id {
              type string;
            }
            container key {
              uses crypto-keyring-key-grouping;
            }
          }
        }
        container server {
          description
            "Specify the Server Address";
          list ipv4 {
            key "ipv4";
            leaf ipv4 {
              type inet:ipv4-address;
            }
            leaf port {
              default "443";
              type uint32;
            }
          }
          list ipv6 {
            key "ipv6";
            leaf ipv6 {
              type inet:ipv6-address;
            }
            leaf port {
              type uint32;
            }
          }
          list url {
            key "url";
            leaf url {
              type string;
            }
            leaf port {
              type uint32;
            }
          }
        }
        leaf shutdown {
          description
            "Shut/No shut the crypto tls-tunnel";
          must "((../pki/trustpoint/trustpoint-name) and ((../local-interface/interface-name) or
                 (../tls-local-interface/interface-name)) and
                ((../overlay/address) or (../overlay/interface)) and
                ((../server/ipv4/ipv4) or (../server/ipv6/ipv6) or
                 (../server/url/url))) or .='true'" {
            error-message
              "Cannot activate the tls-tunnel until the pki trustpoint and
               overlay address/interface and  local-interface and server ip is configured or
               cannot delete the pki trustpoint and overlay address/interface and
               local-interface and server ip  while the tls-tunnel is active";
          }
          type boolean;
          default "true";
        }
      }
    }
    container ssl {
      description
        "Configure Crypto SSL Options";
      container ssl-authorization {
        description
          "ssl authorization";
        list policy {
          description
            "Crypto SSL authorization policy";
          key "name";
          leaf name {
            type string;
          }
          leaf banner {
            description
              "Specify banner";
            type string;
          }
          container client {
            description
              "Specify the client profile";
            leaf profile {
              description
                "Specify profile";
              type string;
            }
          }
          leaf def-domain {
            description
              "Specify def-domain";
            type string;
          }
          leaf disable-always-on {
            description
              "disable-always-on";
            type empty;
          }
          container dns {
            description
              "Specify DNS addresses";
            leaf primary-address {
              description
                "Primary DNS IP address";
              type inet:ipv4-address;
            }
            leaf secondary-address {
              description
                "Secondary DNS IP address";
              type inet:ipv4-address;
            }
          }
          container dpd-interval {
            description
              "Specify dead peer detection interval";
            leaf client {
              description
                "Client mode";
              type uint16 {
                range "5..3600";
              }
            }
            leaf server {
              description
                "Server mode";
              type uint16 {
                range "5..3600";
              }
            }
          }
          leaf homepage {
            description
              "Specify home page";
            type string {
              pattern '(((http:)|(https:)).*)';
            }
          }
          leaf include-local-lan {
            description
              "Include local lan";
            type empty;
          }
          container ipv6 {
            description
              "Specify the ipv6 attributes";
            container dns {
              description
                "Specify IPv6 dns";
              leaf primary-address {
                description
                  "Primary DNS IPv6 address";
                type inet:ipv6-address;
              }
              leaf secondary-address {
                description
                  "Secondary DNS IPv6 address";
                type inet:ipv6-address;
              }
            }
            container pool {
              description
                "Specify local IPv6 address pool";
              leaf WORD {
                description
                  "ipv6 address pool name";
                type string;
              }
            }
            leaf prefix {
              description
                "Specify ipv6 prefix length of the config address";
              type uint8 {
                range "1..128";
              }
            }
            container route {
              description
                "Specify ipv6 route set parameter";
              container set {
                description
                  "Specify the route access-list";
                leaf access-list {
                  description
                    "Specify access-list";
                  type string;
                }
              }
            }
          }
          leaf keepalive {
            description
              "Specify keepalive time";
            type uint32 {
              range "10..600";
            }
          }
          leaf module {
            description
              "Specify module";
            type enumeration {
              enum gina;
              enum dart;
            }
          }
          container msie-proxy {
            description
              "Proxy option";
            container exception {
              description
                "Specify exception";
              leaf WORD {
                description
                  "IP Address / DNS Name";
                type string;
              }
            }
            leaf option {
              description
                "Specify option";
              type enumeration {
                enum auto;
                enum bypass;
                enum none;
              }
            }
            container server {
              description
                "Proxy server to use";
              leaf WORD {
                description
                  "IP Address / DNS Name : Port";
                type string;
              }
            }
          }
          leaf mtu {
            description
              "Specify MTU in bytes";
            type uint32 {
              range "576..1406";
            }
          }
          leaf netmask {
            description
              "Specify netmask of the config address";
            type inet:ipv4-address;
          }
          leaf pool {
            description
              "Specify pool";
            type string;
          }
          container rekey {
            description
              "Specify the rekey parameters";
            leaf time {
              type uint16 {
                range "240..43200";
              }
            }
          }
          container route {
            description
              "Specify route parameters";
            container set {
              description
                "Specify route set parameters";
              leaf access-list {
                description
                  "Specify the route access-list";
                type string;
              }
              container interface {
                description
                  "Specify route interface";
                uses ios-ifc:interface-grouping;
              }
            }
          }
          leaf smartcard-removal-disconnect {
            description
              "smartcard-removal-disconnect";
            type empty;
          }
          leaf split-dns {
            description
              "Specify split-dns";
            type string;
          }
          container timeout {
            description
              "Specify timeout in seconds";
            leaf disconnect {
              description
                "Specify disconnect timeout in seconds";
              type int32 {
                range "60..86400";
              }
            }
            leaf idle {
              description
                "Specify idle timeout in seconds";
              type uint32 {
                range "60..86400";
              }
            }
            leaf session {
              description
                "Specify session timeout in seconds";
              type uint32 {
                range "1..1209600";
              }
            }
          }
          container wins {
            description
              "Specify WINS Addresses";
            leaf primary-ip {
              description
                "Primary WINS IP address";
              type inet:ipv4-address;
            }
            leaf secondary-ip {
              description
                "Secondary WINS IP address";
              type inet:ipv4-address;
            }
          }
        }
      }
      container authorization {
        status deprecated;
        description
          "ssl authorization";
        leaf policy {
          status deprecated;
          description
            "Crypto SSL authorization policy";
          type string;
        }
      }
      container diagnose {
        description
          "SSLVPN diagnose";
        leaf error {
          description
            "Start error trace debug";
          type uint16 {
            range "1..1000";
          }
        }
      }
      list ssl-policy {
        description
          "List of Crypto SSL policies";
        key "name";
        leaf name {
          type string;
          must 'string-length(.) <= 128';
        }
        container pki {
          description
            "Trustpoint options";
          container trustpoint {
            description
              "Certificate Trustpoint to authenticate clients";
            leaf name {
              type string;
            }
            leaf sign {
              description
                "Sign";
              type empty;
            }
          }
        }
        container ip {
          description
            "IP Options";
          choice ip-choice {
            case address-case {
              container address-container {
                description
                  "IP Address";
                container local {
                  description
                    "Local IP Address";
                  leaf ip-address {
                    description
                      "Specify an IP address to bind to";
                    type inet:ipv4-address;
                  }
                  leaf port {
                    description
                      "Specify the port number";
                    default "443";
                    type uint16 {
                      range "443|1025..65535";
                    }
                  }
                  leaf vrf {
                    description
                      "VRF name";
                    must "(/ios:native/ios:vrf/ios:definition[ios:name=current()] and
                          /ios:native/ios:vrf/ios:definition[ios:name=current()]/ios:address-family/ios:ipv4) or
                          /ios:native/ios:ip/ios:vrf[ios:name=current()]" {
                      error-message "It seems IP routing table VRF doesn't exist or attempted to delete when actively it's referred";
                    }
                    type string;
                  }
                  leaf standby {
                    description
                      "the gateway is standby";
                    type string;
                  }
                }
              }
            }
            case interface-case {
              container interface-container {
                description
                  "IP Interface";
                container interface-name {
                  uses ios:interface-with-dependency-grouping;
                  leaf port {
                    description
                      "Specify the port number";
                    default "443";
                    type uint16 {
                      range "443|1025..65535";
                    }
                  }
                  leaf vrf {
                    description
                      "VRF name";
                    must "(/ios:native/ios:vrf/ios:definition[ios:name=current()] and
                          /ios:native/ios:vrf/ios:definition[ios:name=current()]/ios:address-family/ios:ipv4) or
                          /ios:native/ios:ip/ios:vrf[ios:name=current()]" {
                      error-message "It seems IP routing table VRF doesn't exist or attempted to delete when actively it's referred";
                    }
                    type string;
                  }
                  leaf standby {
                    description
                      "the gateway is standby ";
                    type string;
                  }
                }
              }
            }
          }
          container address {
            status deprecated;
            description
              "This node is deprecated and replaced by address-container";
            container local {
              status deprecated;
              description
                "This node is deprecated and replaced under address-container";
              leaf ip-address {
                status deprecated;
                description
                  "This node is deprecated and replaced under address-container";
                type inet:ip-address;
              }
              leaf port {
                status deprecated;
                description
                  "This node is deprecated and replaced under address-container";
                default "443";
                type uint16 {
                  range "443|1025..65535";
                }
              }
              leaf vrf {
                status deprecated;
                description
                  "This node is deprecated and replaced under address-container";
                must '(/ios:native/ios:ip/ios:vrf[ios:name=current()])' {
                  error-message "It seems IP routing table VRF doesn't exist or attempted to delete when actively it's referred";
                }
                type string;
              }
              leaf standby {
                status deprecated;
                description
                  "This node is deprecated and replaced under address-container";
                type string;
              }
            }
          }
          container interface {
            status deprecated;
            description
              "This node is deprecated and replaced as interface-container";
            container interface-name-list {
              status deprecated;
              description
                "This node is deprecated and replaced under interface-container";
              uses ios-ifc:interface-deprecated-grouping;
              leaf port {
                status deprecated;
                description
                  "This node is deprecated and replaced under interface-container";
                default "443";
                type uint16 {
                  range "443|1025..65535";
                }
              }
              leaf vrf {
                status deprecated;
                description
                  "This node is deprecated and replaced under interface-container";
                must '(/ios:native/ios:ip/ios:vrf[ios:name=current()])' {
                  error-message "It seems IP routing table VRF doesn't exist or attempted to delete when actively it's referred";
                }
                type string;
              }
              leaf standby {
                status deprecated;
                description
                  "This node is deprecated and replaced under interface-container";
                type string;
              }
            }
          }
        }
        container ssl {
          description
            "Specify ssl proposal";
          leaf proposal {
            description
              "Configure Crypto SSL Options";
            must '/ios:native/ios:crypto/ssl/ssl-proposal[name=current()]' {
              error-message "%ERROR%: There is no proposal by the name";
            }
            type string;
            must 'string-length(.) <= 128';
          }
        }
        leaf shutdown {
          description
            "Shut/No shut the crypto ssl policy";
          must "((../pki/trustpoint/name) and ((../ip/address-container/local/ip-address) or
                 (../ip/interface-container/interface-name/port))) or .='true'" {
            error-message
              "Cannot activate the policy until the pki trustpoint and ip address/interface
               is configured or cannot delete the trustpoint or ip address/interface while the policy is active";
          }
          type boolean;
          default "true";
        }
      }
      leaf policy {
        status deprecated;
        description
          "Define SSL policies";
        type string;
      }
      list ssl-profile {
        description
          "Define SSL profiles";
        key "name";
        leaf name {
          type string;
        }
        container aaa {
          description
            "aaa";
          container accounting {
            description
              "aaa accounting";
            container user-pass {
              description
                "user-password based accounting";
              leaf list {
                description
                  "aaa accounting list";
                type empty;
              }
              leaf name {
                description
                  "aaa accounting list name";
                type string;
              }
            }
          }
          container authentication {
            description
              "aaa authentication";
            container user-pass {
              description
                "user-password based authentication";
              leaf list {
                description
                  "aaa authentication list";
                type empty;
              }
              leaf name {
                description
                  "aaa authentication list name";
                type string;
              }
            }
          }
          container authorization {
            description
              "aaa authorization";
            container group {
              description
                "AAA group authorization";
              choice override-userpass {
                case override-auth {
                  container override-auth {
                    description
                      "Override user authorization with group authorization. By default,
                       group authorization is overridden with user authorization";
                    container user-pass {
                      description
                        "user-password based authorization";
                      container list {
                        description
                          "AAA method list";
                        leaf list-name {
                          description
                            "AAA list name";
                          type string;
                        }
                        leaf user-name {
                          description
                            "AAA user name";
                          type string;
                        }
                        uses crypto-ssl-profile-aaa-auth-passwd-grouping;
                      }
                    }
                  }
                }
                case user-pass-auth {
                  container user-pass-auth {
                    description
                      "user-password based authorization";
                    container list {
                      description
                        "AAA method list";
                      leaf list-name {
                        description
                          "AAA list name";
                        type string;
                      }
                      leaf user-name {
                        description
                          "AAA user name";
                        type string;
                      }
                      uses crypto-ssl-profile-aaa-auth-passwd-grouping;
                    }
                  }
                }
              }
              container override {
                description
                  "DEPRECATED Override user authorization with group authorization. By default,
                   group authorization is overridden with user authorization";
                status deprecated;
                container user-pass {
                  description
                    "DEPRECATED user-password based authorization";
                  status deprecated;
                  container list {
                    description
                      "DEPRECATED AAA method list";
                    status deprecated;
                    leaf list-name {
                      description
                        "DEPRECATED AAA list name";
                      status deprecated;
                      type string;
                    }
                    leaf user-name {
                      description
                        "DEPRECATED AAA user name";
                      status deprecated;
                      type string;
                    }
                    uses crypto-ssl-profile-aaa-auth-passwd-grouping-deprecated;
                  }
                }
              }
              container user-pass {
                description
                  "DEPRECATED user-password based authorization";
                status deprecated;
                container list {
                  description
                    "DEPRECATED AAA method list";
                  status deprecated;
                  leaf list-name {
                    description
                      "DEPRECATED AAA list name";
                    status deprecated;
                    type string;
                  }
                  leaf user-name {
                    description
                      "DEPRECATED AAA user name";
                    status deprecated;
                    type string;
                  }
                  uses crypto-ssl-profile-aaa-auth-passwd-grouping-deprecated;
                }
              }
            }
            container user {
              description
                "AAA user authorization";
              container user-pass {
                description
                  "user-password based authorization";
                leaf cached {
                  description
                    "Use cached attributes from EAP authentication or AAA pre-shared key fetch";
                  type empty;
                }
                container list {
                  description
                    "AAA method list";
                  leaf list-name {
                    description
                      "AAA list name";
                    type string;
                  }
                  leaf user-name {
                    description
                      "AAA user name";
                    type string;
                  }
                  uses crypto-ssl-profile-aaa-auth-passwd-grouping;
                }
              }
            }
          }
        }
        container authentication {
          description
            "Specify authentication mode";
          container remote {
            description
              "Remote server";
            leaf user-pass {
              description
                "User credential mode";
              type empty;
            }
          }
        }
        container match {
          description
            "Specify the type to match";
          leaf policy {
            description
              "Specify Policy";
            must '/ios:native/ios:crypto/ssl/ssl-policy[name=current()]' {
              error-message "%ERROR%: There is no policy by the name";
            }
            type string;
          }
          leaf url {
            description
              "Specify URL";
            type string {
              pattern '((https:).*)';
              length "6..255";
            }
          }
        }
        leaf max-users {
          description
            "Specify number of maximum users";
          type uint16 {
            range "1..10000";
          }
        }
        leaf shutdown {
          description
            "Shutdown the  SSLVPN Profile";
          type empty;
        }
        leaf virtual-template {
          description
            "Specify the virtual-template for dynamic interface creation";
          type uint8 {
            range "1..200";
          }
        }
      }
      leaf profile {
        status deprecated;
        description
          "Define SSL profiles";
        type string;
      }
      list ssl-proposal {
        description
          "Define ssl Proposal";
        key "name";
        leaf name {
          type string;
        }
        container protection {
          description
            "Specify the protection algorithms";
          leaf rsa-3des-ede-sha1 {
            description
              "RSA, 3DES and SHA1";
            type empty;
          }
          leaf rsa-aes128-sha1 {
            description
              "RSA, AES128 and SHA1";
            type empty;
          }
          leaf rsa-aes256-sha1 {
            description
              "RSA, AES256 and SHA1";
            type empty;
          }
          leaf rsa-rc4128-md5 {
            description
              "RSA, RC4 and MD5";
            type empty;
          }
        }
      }
      container proposal {
        status deprecated;
        description
          "Define ssl Proposal";
        leaf name {
          status deprecated;
          type string;
        }
        container protection {
          status obsolete;
          description
            "Specify the protection algorithms";
          leaf rsa-3des-ede-sha1 {
            status obsolete;
            description
              "RSA, 3DES and SHA1";
            type empty;
          }
          leaf rsa-aes128-sha1 {
            status obsolete;
            description
              "RSA, AES128 and SHA1";
            type empty;
          }
          leaf rsa-aes256-sha1 {
            status obsolete;
            description
              "RSA, AES256 and SHA1";
            type empty;
          }
          leaf rsa-rc4128-md5 {
            status obsolete;
            description
              "RSA, RC4 and MD5";
            type empty;
          }
        }
      }
    }
    container vpn {
      description
        "Configure crypto vpn commands";
      container anyconnect {
        description
          "Configure anyconnect client package";
        list file-list {
          description
            "Configure filename of installing package";
          key "filename";
          unique "sequence";
          leaf filename {
            type string {
              pattern '\w+:.*.pkg';
            }
          }
          leaf sequence {
            description
              "client-side download sequence num (priority) of this package";
            type uint8 {
              range "1..9";
            }
          }
        }
        container file {
          status deprecated;
          description
            "This node is deprecated and replaced by list file";
          leaf filename {
            status deprecated;
            description
              "This node is deprecated and replaced by leaf filename";
            type string;
          }
          leaf sequence {
            status deprecated;
            description
              "This node is deprecated and replaced by leaf sequence";
            type uint8;
          }
        }
        list profile {
          description
            "Configure anyconnect profile and filename";
          key "profile-name";
          leaf profile-name {
            description
              "Configure anyconnect client profile";
            type string;
          }
          leaf file {
            description
              "Configure anyconnect client filename for profile";
            mandatory true;
            type string {
              pattern '\w+:.*';
            }
          }
        }
        container profile-container {
          status deprecated;
          description
            "This node is deprecated and replaced by list profile";
          leaf profile {
            status deprecated;
            description
              "This node is deprecated and replaced by leaf profile-name";
            must '(../filename)';
            type string;
          }
          leaf filename {
            status deprecated;
            description
              "This node is deprecated and replaced by leaf file";
            must '(../profile)';
            type string;
          }
        }
      }
      leaf csd {
        description
          "Configure Secure Desktop package";
        type string;
      }
    }
    leaf xauth {
      description
        "X-Auth parameters";
      type string;
    }
  }

  grouping config-interface-crypto-grouping {
    container crypto {
      description
        "Encryption/Decryption commands";
      container map {
        description
          "Assign a Crypto Map";
        leaf tag {
          type string;
        }
        leaf redundancy {
          description
            "enable redundancy";
          type string;
        }
        leaf stateful {
          description
            "enable stateful failover";
          type empty;
        }
      }
      container ipsec {
        description
          "Set IPSec parameters";
        leaf df-bit {
          description
            "Handling of encapsulated DF bit.";
          type enumeration {
            enum clear;
            enum copy;
            enum set;
          }
        }
        leaf fragmentation {
          description
            "Handling of fragmentation of near-MTU sized packets";
          type enumeration {
            enum after-encryption;
            enum before-encryption;
          }
        }
      }
    }
  }

  grouping config-interface-ipv6-crypto-grouping {
    container crypto {
      description
        "Encryption/Decryption commands";
      leaf map {
        description
          "Assign an IPv6  Crypto Map";
        type string;
      }
    }
  }

  grouping config-key-grouping {
    list chain {
      description
        "Key-chain management";
      key "name";
      leaf name {
        type string;
      }
      leaf macsec {
        type empty;
      }
      leaf tcp {
        type empty;
        must 'string-length(../name) <= 236' {
          error-message "TCP keychain name should not exceed 236 characters";
        }
      }
      list key {
        description
          "Configure a key";
        key "id";
        leaf id {
          description
            "Key identifier - (0-2147483674) for regular
             key chain and hex number with even number digits
             for macsec key chain";
          type string;
        }
        container cryptographic-algorithm-choice {
          description
            "Cryptographic authentication algorithm";
          leaf tcp {
            when '(../../../tcp)';
            type enumeration {
              enum aes-128-cmac;
              enum hmac-sha-1;
              enum hmac-sha-256;
            }
          }
          leaf default {
            when '(not(../../../macsec) and not(../../../tcp))';
            type enumeration {
              enum hmac-sha-1;
              enum hmac-sha-256;
              enum hmac-sha-384;
              enum hmac-sha-512;
              enum md5;
            }
          }
          leaf macsec {
            when '(../../../macsec)';
            type enumeration {
              enum aes-128-cmac;
              enum aes-256-cmac;
            }
            default "aes-128-cmac";
          }
        }
        leaf cryptographic-algorithm {
          status deprecated;
          description
            "Cryptographic authentication algorithm";
          type enumeration {
            enum aes-128-cmac;
            enum aes-256-cmac;
            enum hmac-sha-1;
            enum hmac-sha-256;
            enum hmac-sha-384;
            enum hmac-sha-512;
            enum md5;
          }
        }
        container key-string {
          description
            "Key string";
          leaf encryption {
            description
              "Key encryption method";
            type enumeration {
              enum 0;
              enum 6;
              enum 7;
            }
          }
          leaf key {
            type string;
            must '((not(../encryption) or ../encryption = 0) and string-length(.) <= 80) or (../encryption = 6 and string-length(.) <= 141) or (../encryption = 7)' {
              error-message "Clear-text should not be greater than 80";
            }
          }
        }
        container accept-lifetime {
          when 'not(../../macsec)';
          description
            "Time interval during which key is accepted";
          uses lifetime-grouping-v1;
        }
        container send-lifetime {
          when 'not(../../macsec)';
          description
            "Time interval during which key is sent";
          uses lifetime-grouping-v1;
        }
        choice lifetime-choice {
          status obsolete;
          case lifetime-only {
            status obsolete;
            container lifetime {
              status obsolete;
              description
                "Set lifetime of MACsec key";
              uses lifetime-grouping;
            }
          }
          case lifetime-local {
            status obsolete;
            container lifetime-local {
              status obsolete;
              container local {
                status obsolete;
                description
                  "Specify time in local timezone";
                uses lifetime-grouping;
              }
            }
          }
        }
        container macsec-lifetime {
          container lifetime {
            when '../../../macsec';
            description
              "Set lifetime of MACsec key";
            uses lifetime-grouping-v1;
          }
        }
        leaf send-id {
          when '(../../tcp)';
          description
            "configure a send id";
          type uint8 {
            range "0..255";
          }
        }
        leaf recv-id {
          when '(../../tcp)';
          description
            "configure a receive id";
          type uint8 {
            range "0..255";
          }
        }
        leaf include-tcp-options {
          when '(../../tcp)';
          description
            "Include tcp options in HMAC calculation";
          type boolean;
          default "false";
        }
        leaf accept-ao-mismatch {
          when '(../../tcp)';
          description
            "Accept packets with HMAC mismatch";
          type boolean;
          default "false";
        }
      }
    }
    container config-key {
      status obsolete;
      description
        "Set a private configuration key for general use";
      leaf newpass {
        status obsolete;
        description
          "Enter new password without space/tabs, space/tabs are not allowed";
        type string;
      }
      leaf oldpass {
        status obsolete;
        description
          "Enter old password without space/tabs, space/tabs are not allowed";
        type string;
      }
    }
  }

  grouping config-interface-tunnel-ipsec-grouping {
    container dike {
      description
        "Use IKEv2 to protect this tunnel interface";
      container profile {
        description
          "Determine the IKEv2 profile to use";
        leaf ikev2-profile {
          description
            "ikev2 policy profile";
          must '/ios:native/ios:crypto/ikev2/profile[name=current()]' {
            error-message "It seems IKEv2 profile doesn't exist or attempting to remove when referred by tunnel config";
          }
          type string;
        }
        choice local-remote {
          case local-case {
            leaf local {
              type uint32 {
                range "1..65535";
              }
            }
            container remote1 {
              leaf remote {
                type uint32 {
                  range "1..65535";
                }
              }
            }
          }
          case remote-case {
            leaf remote {
              type uint32 {
                range "1..65535";
              }
            }
          }
        }
      }
    }
    container ipsec {
      description
        "Use ipsec to protect this tunnel interface";
      leaf intiate {
        description
          "Initiate the IPsec tunnel right away";
        type empty;
      }
      container local-address {
        description
          "Specify an interface to be used as local address";
        uses ios-ifc:interface-grouping;
      }
      container policy {
        description
          "ACL config";
        choice ipv4-ipv6 {
          case ipv4-case {
            leaf ipv4 {
              description
                "IPv4 ACL";
              type ios-types:ext-acl-type;
            }
          }
          case ipv6-case {
            leaf ipv6 {
              description
                "IPv6 ACL";
              type string;
            }
          }
        }
      }
      container profile-option {
        description
          "Determine the ipsec policy profile to use.";
        leaf name {
          description
            "IPSec policy profile";
          type string;
        }
        choice isakmp_profile-ikev2_profile-shared {
          case ikev2-profile-case {
            leaf ikev2-profile {
              description
                "Specify ikev2 Profile";
              must '/ios:native/ios:crypto/ikev2/profile[name=current()]' {
                error-message "It seems IKEv2 profile doesn't exist or attempted to delete when actively referred by IPSec profile";
              }
              type string;
            }
          }
          case isakmp-profile-case {
            leaf isakmp-profile {
              description
                "Specify isakmp Profile";
              must '/ios:native/ios:crypto/isakmp/profile[name=current()]' {
                error-message "It seems ISAKMP profile doesn't exist or attempted to delete when actively referred by IPSec profile";
              }
              type string;
            }
          }
          case shared-case {
            leaf shared {
              description
                "Use a shared socket for the crypto connection";
              type empty;
            }
          }
        }
        leaf psk {
          description
            "Use key value for default tunnel protection";
          type string;
        }
      }
      leaf profile {
        description
          "Obsolete, use the other option profile-option to set ipsec policy profile";
        status obsolete;
        must '/ios:native/ios:crypto/ipsec/profile[name=current()]' {
          error-message "It seems IPSec profile doesn't exist or attempting to remove when referred by tunnel config";
        }
        type string;
      }
      leaf ikev2-profile {
        description
          "Obsolete, use the other option ikev2-profile to set ikev2 policy profile";
        status obsolete;
        must '/ios:native/ios:crypto/ikev2/profile[name=current()]' {
          error-message "It seems IKEv2 profile doesn't exist or attempting to remove when referred by tunnel config";
        }
        type string;
      }
    }
  }

  grouping compare-string-grouping-obsolete {
    leaf co {
      status obsolete;
      description
        "Contains";
      type string;
    }
    leaf eq {
      status obsolete;
      description
        "Equal";
      type string;
    }
    leaf nc {
      status obsolete;
      description
        "Does not contain";
      type string;
    }
    leaf ne {
      status obsolete;
      description
        "Not Equal";
      type string;
    }
  }

  grouping crypto-pki-certificate-map-grouping-obsolete {
    container alt-subject-name {
      status obsolete;
      description
        "Alternate subject name";
      uses compare-string-grouping-obsolete;
    }
    container expires-on {
      status obsolete;
      description
        "Expiration date/time";
      uses compare-time-grouping-obsolete;
    }
    container issuer-name {
      status obsolete;
      description
        "Certificate issuer name";
      uses compare-string-grouping-obsolete;
    }
    container name {
      status obsolete;
      description
        "Any subject name field";
      uses compare-string-grouping-obsolete;
    }
    container serial-number {
      status obsolete;
      description
        "Certificate serial number (hexadecimal)";
      uses compare-string-grouping-obsolete;
    }
    container subject-name {
      status obsolete;
      description
        "Certificate subject name";
      uses compare-string-grouping-obsolete;
    }
    container unstructured-subject-name {
      status obsolete;
      description
        "Unstructured subject name";
      uses compare-string-grouping-obsolete;
    }
    container valid-start {
      status obsolete;
      description
        "Valid after date/time";
      uses compare-time-grouping-obsolete;
    }
  }

  grouping time-grouping-obsolete {
    container time {
      status obsolete;
      choice date-month {
        status obsolete;
        case date1 {
          status obsolete;
          leaf date1 {
            status obsolete;
            type uint8 {
              range "1..31";
            }
          }
        }
        case month1 {
          status obsolete;
          leaf month1 {
            status obsolete;
            type string;
          }
        }
      }
      choice month-date {
        status obsolete;
        case date2 {
          status obsolete;
          leaf date2 {
            status obsolete;
            when '../month1';
            type uint8 {
              range "1..31";
            }
          }
        }
        case month2 {
          status obsolete;
          leaf month2 {
            status obsolete;
            when '../date1';
            type string;
          }
        }
      }
      leaf year {
        status obsolete;
        type uint16 {
          range "1993..2035";
        }
      }
      leaf clock {
        status obsolete;
        type string;
      }
      leaf utc {
        status obsolete;
        description
          "Time is in UTC (not local Time Zone)";
        type empty;
      }
    }
  }

  grouping compare-time-grouping-obsolete {
    container eq {
      status obsolete;
      description
        "Equal";
      uses time-grouping-obsolete;
    }
    container ge {
      status obsolete;
      description
        "Greater than or equal";
      uses time-grouping-obsolete;
    }
    container lt {
      status obsolete;
      description
        "Less Than";
      uses time-grouping-obsolete;
    }
    container ne {
      status obsolete;
      description
        "Not Equal";
      uses time-grouping-obsolete;
    }
  }

  grouping crypto-pki-certificate-chain-grouping-obsolete {
    list certificate {
      status obsolete;
      description
        "Certificate issued by the CA";
      key "serial";
      leaf serial {
        status obsolete;
        type string;
      }
      leaf certtype {
        status obsolete;
        type enumeration {
          enum ca;
          enum ra-encrypt;
          enum ra-general;
          enum ra-sign;
          enum rollover;
          enum self-signed;
          enum "ca rollover";
        }
      }
    }
    container crl {
      status obsolete;
      description
        "Revocation list issued by the CA";
      leaf cdp-hexdata {
        status obsolete;
        description
          "Revocation distribution point";
        type string {
          pattern '([0-9a-fA-F]+)';
        }
      }
    }
  }

  grouping crypto-pki-profile-enrollment-auth-grouping-obsolete {
    leaf command {
      status obsolete;
      description
        "command to authenticate or enroll";
      type string;
    }
    leaf terminal {
      status obsolete;
      description
        "authenticate or enroll using terminal";
      type empty;
    }
    container url {
      status obsolete;
      description
        "url to authenticate/enroll";
      leaf name {
        status obsolete;
        type string;
      }
      leaf vrf {
        status obsolete;
        description
          "VRF to use for certificate enrollment ";
        type string;
      }
    }
  }

  grouping crypto-pki-profile-enrollment-grouping-obsolete {
    container authentication {
      status obsolete;
      description
        "Retrieve CA certificate(s)";
      uses crypto-pki-profile-enrollment-auth-grouping-obsolete;
    }
    container enrollment {
      status obsolete;
      description
        "Enroll router with a CA";
      uses crypto-pki-profile-enrollment-auth-grouping-obsolete;
      leaf credential {
        description
          "Use existing router cert for new enrollment";
        type string;
      }
    }
    leaf method-est {
      status obsolete;
      description
        "Use EST for this profile";
      type empty;
    }
    list parameter {
      status obsolete;
      description
        "Define a parameter value or prompt";
      key "number";
      leaf number {
        status obsolete;
        type uint8 {
          range "1..8";
        }
      }
      choice prompt-value {
        status obsolete;
        case prompt-case {
          status obsolete;
          leaf prompt {
            status obsolete;
            description
              "Define a parameter prompt";
            type string;
          }
        }
        case value-case {
          status obsolete;
          leaf value {
            status obsolete;
            description
              "Define a parameter value";
            type string;
          }
        }
      }
    }
    container reenrollment {
      status obsolete;
      description
        "Re-enroll router with a CA";
      uses crypto-pki-profile-enrollment-auth-grouping-obsolete;
    }
    leaf source-interface {
      status obsolete;
      description
        "Interface used as source address";
      type string;
    }
  }

  grouping crypto-pki-eku-grouping-obsolete {
    leaf client-auth {
      status obsolete;
      description
        "Client Auth";
      type empty;
    }
    leaf code-signing {
      status obsolete;
      description
        "Code signing";
      type empty;
    }
    leaf email-protection {
      status obsolete;
      description
        "Email protection";
      type empty;
    }
    leaf ipsec-end-system {
      status obsolete;
      description
        "IPSEC end system";
      type empty;
    }
    leaf ipsec-tunnel {
      status obsolete;
      description
        "IPSEC Tunnel";
      type empty;
    }
    leaf ipsec-user {
      status obsolete;
      description
        "IPSEC User";
      type empty;
    }
    leaf ocsp-signing {
      status obsolete;
      description
        "OCSP Signing";
      type empty;
    }
    leaf server-auth {
      status obsolete;
      description
        "Server Auth";
      type empty;
    }
    leaf ssh-client {
      status obsolete;
      description
        "SSH Client";
      type empty;
    }
    leaf ssh-server {
      status obsolete;
      description
        "SSH Server";
      type empty;
    }
    leaf time-stamping {
      status obsolete;
      description
        "Time Stamping";
      type empty;
    }
  }

  grouping database-password-grouping-obsolete {
    container password {
      status obsolete;
      description
        "Passphrase to protect the private key archive";
      leaf encryption-type {
        status obsolete;
        type uint8 {
          range "0..9";
        }
      }
      leaf passphrase {
        status obsolete;
        type string {
          length "8..200";
        }
      }
    }
  }

  grouping database-username-password-grouping-obsolete {
    container username {
      status obsolete;
      description
        "username";
      leaf username-value {
        status obsolete;
        type string;
      }
      container password-ext {
        status obsolete;
        uses database-password-grouping-obsolete;
      }
    }
  }

  grouping crypto-pki-server-grouping-obsolete {
    container auto-rollover {
      status obsolete;
      description
        "Rollover the CA key and certificate";
      leaf days {
        status obsolete;
        description
          "Overlap time in days";
        type uint16 {
          range "0..1825";
        }
      }
      leaf hours {
        status obsolete;
        description
          "Overlap time in hours";
        type uint8 {
          range "0..23";
        }
      }
      leaf minutes {
        status obsolete;
        description
          "Overlap time in minutes";
        type uint8 {
          range "0..59";
        }
      }
    }
    leaf cdp-url {
      status obsolete;
      description
        "CDP to be included in the issued certificates";
      type string;
    }
    container database {
      status obsolete;
      description
        "Certificate Server database config parameters";
      leaf level {
        status obsolete;
        description
          "Level of data stored in database";
        type enumeration {
          enum complete;
          enum minimum;
          enum names;
        }
      }
      uses database-username-password-grouping-obsolete;
      container url {
        status obsolete;
        description
          "database URL";
        leaf url-only {
          status obsolete;
          type string;
        }
        leaf file-type {
          status obsolete;
          description
            "type of file";
          type enumeration {
            enum cnm;
            enum crl;
            enum crt;
            enum ser;
            enum pem;
            enum p12;
          }
        }
        leaf publish {
          status obsolete;
          description
            "Store a copy at a storage location";
          type empty;
        }
        choice url-combination {
          status obsolete;
          case location-alone {
            status obsolete;
            leaf location {
              status obsolete;
              description
                "url value";
              type string;
            }
          }
          case url-with-username {
            status obsolete;
            container url-with-username {
              status obsolete;
              leaf location {
                status obsolete;
                description
                  "url value";
                type string;
              }
              uses database-username-password-grouping-obsolete;
            }
          }
        }
      }
      container archive {
        status obsolete;
        description
          "Backup Certificate Server Signing Certificate and Keys";
        choice format {
          container pem {
            status obsolete;
            description
              "PEM format";
            presence "true";
            uses database-password-grouping-obsolete;
          }
          container pkcs12 {
            status obsolete;
            description
              "PKCS12 format";
            presence "true";
            uses database-password-grouping-obsolete;
          }
        }
      }
    }
    leaf serial-number {
      status obsolete;
      description
        "Serial number of last certificate issued";
      type string;
    }
    leaf revoke {
      status obsolete;
      description
        "Revoke a certificate";
      type string;
    }
    container mode {
      status obsolete;
      description
        "Mode";
      choice ra-or-subcs {
        status obsolete;
        case ra {
          status obsolete;
          leaf ra {
            status obsolete;
            type empty;
          }
          leaf transparent {
            status obsolete;
            type empty;
          }
        }
        case subca {
          status obsolete;
          leaf sub-cs {
            status obsolete;
            type empty;
          }
        }
      }
    }
    container lifetime {
      status obsolete;
      description
        "lifetime of the certificate";
      leaf certificate {
        status obsolete;
        type enumeration {
          enum ca-certificate;
          enum certificate;
          enum crl;
          enum enrollment-request;
        }
      }
      leaf days {
        status obsolete;
        type uint16 {
          range "0..7305";
        }
      }
      leaf hours {
        status obsolete;
        type uint8 {
          range "0..23";
        }
        default "0";
      }
      leaf minutes {
        status obsolete;
        type uint16 {
          range "0..59";
        }
        default "0";
      }
    }
    leaf hash {
      status obsolete;
      description
        "Hash algorithm";
      type enumeration {
        enum md5;
        enum sha1;
        enum sha256;
        enum sha384;
        enum sha512;
      }
    }
    container eku {
      status obsolete;
      description
        "EKU parameters";
      uses crypto-pki-eku-grouping-obsolete;
    }
    leaf issuer-name {
      status obsolete;
      description
        "Issuer name";
      type string;
    }
    container grant {
      status obsolete;
      description
        "Certificate granting options";
      leaf type {
        status obsolete;
        type enumeration {
          enum none;
          enum ra-auto;
        }
      }
      container auto {
        status obsolete;
        leaf auto-alone {
          status obsolete;
          type empty;
        }
        leaf trustpoint {
          status obsolete;
          type string;
        }
        leaf tp-list {
          status obsolete;
          type string;
        }
        leaf rollover {
          status obsolete;
          type enumeration {
            enum ra-cert;
            enum ca-cert;
          }
        }
      }
    }
    leaf shutdown-config {
      status obsolete;
      description
        "Shutdown the certificate server";
      type boolean;
      default "true";
    }
    leaf shutdown {
      description
        "Shutdown the certificate server";
      status obsolete;
      type empty;
    }
  }

  grouping crypto-pki-trustpoint-ip-extension-grouping-obsolete {
    container range {
      status obsolete;
      description
        "IP address range";
      choice ipv4-ipv6 {
        status obsolete;
        case ipv4-range {
          status obsolete;
          leaf start {
            status obsolete;
            description
              "Starting IP address";
            type inet:ipv4-address;
          }
          leaf end {
            status obsolete;
            description
              "Ending IP address";
            type inet:ipv4-address;
          }
        }
        case ipv6-range {
          status obsolete;
          leaf start-v6 {
            status obsolete;
            description
              "Starting IPv6 address";
            type inet:ipv6-address;
          }
          leaf end-v6 {
            status obsolete;
            description
              "Ending IPv6 address";
            type inet:ipv6-address;
          }
        }
      }
    }
    leaf prefix {
      status obsolete;
      description
        "Prefix or IP address";
      type union {
        type inet:ipv4-address;
        type inet:ipv4-prefix;
        type inet:ipv6-address;
        type ios-types:ipv6-prefix;
      }
    }
    container inherit {
      status obsolete;
      description
        "Inherit address from issuer";
      leaf ipv4 {
        status obsolete;
        description
          "Apply to ipv4 address";
        type empty;
      }
      leaf ipv6 {
        status obsolete;
        description
          "Apply to ipv6 address";
        type empty;
      }
    }
  }

  grouping crypto-pki-trustpoint-grouping-obsolete {
    container authorization {
      status obsolete;
      description
        "Authorization parameters.";
      leaf list {
        status obsolete;
        description
          "AAA authorization list to use";
        type string;
      }
      leaf password {
        status obsolete;
        description
          "password used for authorization request";
        type string;
      }
      container username {
        status obsolete;
        description
          "specify how AAA username is generated";
        container alt-subjectname {
          status obsolete;
          description
            "aaa username generated from certificate alt-subjectname";
          leaf userprinciplename {
            status obsolete;
            description
              "cert upn field as aaa username";
            type empty;
          }
          container userprinciplename-conf {
            status obsolete;
            container userprinciplename {
              status obsolete;
              description
                "cert upn field as aaa username";
              leaf secondary {
                status obsolete;
                description
                  "secondary username";
                when '../../../../../username';
                type empty;
              }
            }
          }
        }
        container subjectname {
          status obsolete;
          description
            "aaa username generated from certificate subjectname";
          leaf all {
            status obsolete;
            description
              "complete subject name as aaa username";
            type empty;
          }
          container all-conf {
            status obsolete;
            container all {
              status obsolete;
              description
                "complete subject name field as aaa username";
              leaf secondary {
                status obsolete;
                description
                  "secondary username";
                when '../../../../../username';
                type empty;
              }
            }
          }
          leaf commonname {
            status obsolete;
            description
              "common name as aaa username";
            type empty;
          }
          container commonname-conf {
            status obsolete;
            container commonname {
              status obsolete;
              description
                "Common name field as aaa username";
              leaf secondary {
                status obsolete;
                description
                  "secondary username";
                when '../../../../../username';
                type empty;
              }
            }
          }
          leaf country {
            status obsolete;
            description
              "country as aaa username";
            type empty;
          }
          container country-conf {
            status obsolete;
            container country {
              status obsolete;
              description
                "country field as aaa username";
              leaf secondary {
                status obsolete;
                description
                  "secondary username";
                when '../../../../../username';
                type empty;
              }
            }
          }
          leaf email {
            status obsolete;
            description
              "email as aaa username";
            type empty;
          }
          container email-conf {
            status obsolete;
            container email {
              status obsolete;
              description
                "email field as aaa username";
              leaf secondary {
                status obsolete;
                description
                  "secondary username";
                when '../../../../../username';
                type empty;
              }
            }
          }
          leaf ipaddress {
            status obsolete;
            description
              "IP address as aaa username";
            type empty;
          }
          container ipaddress-conf {
            status obsolete;
            container ipaddress {
              status obsolete;
              description
                "IP address field as aaa username";
              leaf secondary {
                status obsolete;
                description
                  "secondary username";
                when '../../../../../username';
                type empty;
              }
            }
          }
          leaf locality {
            status obsolete;
            description
              "locality as aaa username";
            type empty;
          }
          container locality-conf {
            status obsolete;
            container locality {
              status obsolete;
              description
                "locality field as aaa username";
              leaf secondary {
                status obsolete;
                description
                  "secondary username";
                when '../../../../../username';
                type empty;
              }
            }
          }
          leaf organization {
            status obsolete;
            description
              "organization as aaa username";
            type empty;
          }
          container organization-conf {
            status obsolete;
            container organization {
              description
                "organization field as aaa username";
              leaf secondary {
                status obsolete;
                description
                  "secondary username";
                when '../../../../../username';
                type empty;
              }
            }
          }
          leaf organizationalunit {
            status obsolete;
            description
              "organizational unit as aaa username";
            type empty;
          }
          container organizationalunit-conf {
            status obsolete;
            container organizationalunit {
              status obsolete;
              description
                "organizational unit field as aaa username";
              leaf secondary {
                status obsolete;
                description
                  "secondary username";
                when '../../../../../username';
                type empty;
              }
            }
          }
          leaf postalcode {
            status obsolete;
            description
              "postal code as aaa username";
            type empty;
          }
          container postalcode-conf {
            status obsolete;
            container postalcode {
              status obsolete;
              description
                "postal code field as aaa username";
              leaf secondary {
                status obsolete;
                description
                  "secondary username";
                when '../../../../../username';
                type empty;
              }
            }
          }
          leaf serialnumber {
            status obsolete;
            description
              "serial number as aaa username";
            type empty;
          }
          container serialnumber-conf {
            status obsolete;
            container serialnumber {
              status obsolete;
              description
                "serial number field as aaa username";
              leaf secondary {
                status obsolete;
                description
                  "secondary username";
                when '../../../../../username';
                type empty;
              }
            }
          }
          leaf state {
            status obsolete;
            description
              "state as aaa username";
            type empty;
          }
          container state-conf {
            status obsolete;
            container state {
              status obsolete;
              description
                "state field as aaa username";
              leaf secondary {
                status obsolete;
                description
                  "secondary username";
                when '../../../../../username';
                type empty;
              }
            }
          }
          leaf streetaddress {
            status obsolete;
            description
              "street address as aaa username";
            type empty;
          }
          container streetaddress-conf {
            status obsolete;
            container streetaddress {
              status obsolete;
              description
                "street address field as aaa username";
              leaf secondary {
                status obsolete;
                description
                  "secondary username";
                when '../../../../../username';
                type empty;
              }
            }
          }
          leaf title {
            status obsolete;
            description
              "title name as aaa username";
            type empty;
          }
          container title-conf {
            status obsolete;
            container title {
              status obsolete;
              description
                "title name field as aaa username";
              leaf secondary {
                status obsolete;
                description
                  "secondary username";
                when '../../../../../username';
                type empty;
              }
            }
          }
          leaf unstructuredname {
            status obsolete;
            description
              "unstructured name as aaa username";
            type empty;
          }
          container unstructuredname-conf {
            status obsolete;
            container unstructuredname {
              status obsolete;
              description
                "unstructured name field as aaa username";
              leaf secondary {
                status obsolete;
                description
                  "secondary username";
                when '../../../../../username';
                type empty;
              }
            }
          }
        }
      }
    }
    container certificate {
      status obsolete;
      description
        "certificate options";
      leaf chain {
        status obsolete;
        description
          "certificate chain configuration file";
        type string;
      }
    }
    container chain-validation {
      status obsolete;
      description
        "Validation parameters";
      leaf stop {
        status obsolete;
        description
          "Halt chain validation";
        type empty;
      }
      leaf continue {
        status obsolete;
        description
          "Validate this trustpoint's (sub)CA certificate";
        type string;
      }
    }
    container crl {
      status obsolete;
      description
        "CRL options";
      leaf query {
        status obsolete;
        description
          "Query CRL URL";
        type string;
      }
      container cache {
        status obsolete;
        description
          "CRL cache options";
        choice cache-choice {
          status obsolete;
          case none {
            status obsolete;
            leaf none {
              status obsolete;
              description
                "Do not cache CRLs";
              type empty;
            }
          }
          case extend {
            status obsolete;
            leaf extend {
              status obsolete;
              description
                "Extend CRL cache time";
              type uint16 {
                range "1..1440";
              }
            }
          }
          case delete-after {
            status obsolete;
            leaf delete-after {
              status obsolete;
              description
                "Remove CRL from cache after a timeout (in minutes)";
              type uint16 {
                range "1..43200";
              }
            }
          }
        }
      }
    }
    leaf exit {
      status obsolete;
      description
        "Exit from certificate authority trustpoint entry mode";
      type empty;
    }
    container auto-enroll {
      status obsolete;
      description
        "Automatically enroll this router identity";
      leaf percent {
        status obsolete;
        description
          "renewal percentage";
        type ios-types:percentage;
      }
      leaf regenerate {
        status obsolete;
        description
          "Regenerate keys on re-enrollment";
        type empty;
      }
    }
    leaf eckeypair {
      status obsolete;
      description
        "eckeypair for this identity";
      type string;
    }
    container eku {
      status obsolete;
      description
        "EKU parameters";
      container request {
        status obsolete;
        description
          "EKU requested attribute";
        uses crypto-pki-eku-grouping-obsolete;
      }
    }
    container enrollment {
      status obsolete;
      description
        "Enrollment parameters";
      container http-proxy {
        status obsolete;
        description
          "HTTP proxy server for enrollment";
        leaf hostname {
          status obsolete;
          description
            "host-name";
          type string;
        }
        leaf port {
          status obsolete;
          description
            "port number";
          type uint16 {
            range "1..10000";
          }
        }
      }
      container mode {
        status obsolete;
        description
          "Mode supported by the Certificate Authority";
        leaf ra {
          status obsolete;
          description
            "Registration Authority mode";
          type empty;
        }
      }
      container enrollment-method {
        status obsolete;
        choice method {
          status obsolete;
          case pkcs12-case {
            status obsolete;
            leaf pkcs12 {
              status obsolete;
              description
                "Enroll via pkcs12";
              type empty;
            }
          }
          case profile-case {
            status obsolete;
            leaf profile {
              status obsolete;
              description
                "Specify an profile for enrollment";
              type leafref {
                path "/ios:native/ios:crypto/ios-crypto:pki/ios-crypto:profile/ios-crypto:enrollment/ios-crypto:tag";
              }
            }
          }
          case selfsigned-case {
            status obsolete;
            leaf selfsigned {
              status obsolete;
              description
                "Generate a Self Signed Certificate";
              type empty;
            }
          }
          case terminal-case {
            status obsolete;
            container terminal {
              status obsolete;
              description
                "Enroll via the terminal (cut-and-paste)";
              presence "true";
              leaf pem {
                status obsolete;
                description
                  "Include PEM encapsulation boundaries";
                type empty;
              }
            }
          }
          case url-case {
            status obsolete;
            leaf url {
              status obsolete;
              description
                "CA server enrollment URL";
              type string;
            }
          }
        }
      }
      leaf pkcs12 {
        status obsolete;
        type empty;
      }
      leaf profile {
        status obsolete;
        description
          "Specify an profile for enrollment";
        type leafref {
          path "/ios:native/ios:crypto/ios-crypto:pki/ios-crypto:profile/ios-crypto:enrollment/ios-crypto:tag";
        }
      }
      container retry {
        status obsolete;
        description
          "Polling parameters";
        leaf count {
          status obsolete;
          description
            "How many times to poll CA for our certificate";
          type uint8 {
            range "1..100";
          }
        }
        leaf period {
          status obsolete;
          description
            "How long to wait between requests to CA for our certificate";
          type uint8 {
            range "1..60";
          }
        }
      }
      leaf selfsigned {
        status obsolete;
        description
          "Generate a Self Signed Certificate";
        type empty;
      }
      container terminal {
        status obsolete;
        description
          "Enroll via the terminal (cut-and-paste)";
        presence "true";
        leaf pem {
          status obsolete;
          description
            "Include PEM encapsulation boundaries";
          type empty;
        }
      }
      leaf url {
        status obsolete;
        description
          "CA server enrollment URL";
        type string;
      }
    }
    leaf fqdn {
      status obsolete;
      description
        "include fully-qualified domain name";
      type string;
    }
    container password {
      status obsolete;
      description
        "revocation password";
      presence "true";
      leaf encryption-type {
        status obsolete;
        description
          "Encryption type";
        type uint8 {
          range "0..9";
        }
      }
      leaf clear-password {
        status obsolete;
        description
          "revocation password";
        type string;
      }
    }
    leaf fingerprint {
      status obsolete;
      description
        "CA Certificate Fingerprint";
      type string {
        pattern '([0-9a-fA-F]+)';
      }
    }
    leaf hash {
      status obsolete;
      description
        "Hash algorithm";
      type enumeration {
        enum md5;
        enum sha1;
        enum sha256;
        enum sha384;
        enum sha512;
      }
    }
    container http-proxy {
      status obsolete;
      description
        "HTTP proxy server for enrollment";
      leaf hostname {
        status obsolete;
        description
          "host-name";
        type string;
      }
      leaf port {
        status obsolete;
        description
          "port number";
        type uint16 {
          range "1..10000";
        }
      }
    }
    container ip-extension {
      status obsolete;
      description
        "RFC3779 IP extension for certificate request";
      container unicast {
        status obsolete;
        description
          "Apply to unicast traffic only";
        uses crypto-pki-trustpoint-ip-extension-grouping-obsolete;
      }
      container multicast {
        status obsolete;
        description
          "Apply to multicast traffic only";
        uses crypto-pki-trustpoint-ip-extension-grouping-obsolete;
      }
      uses crypto-pki-trustpoint-ip-extension-grouping-obsolete;
    }
    container match {
      status obsolete;
      description
        "Match a certificate attributes/maps";
      container key-usage {
        status obsolete;
        description
          "key-usage attributes to validate";
        leaf cRLSign {
          status obsolete;
          type empty;
        }
      }
      container eku {
        status obsolete;
        description
          "EKU attributes to validate";
        uses crypto-pki-eku-grouping-obsolete;
      }
      list certificate {
        status obsolete;
        description
          "Certificate map name";
        key "name";
        leaf name {
          status obsolete;
          type string;
        }
        container allow {
          status obsolete;
          description
            "Allow expired certificates to be accepted";
          leaf expired-certificate {
            status obsolete;
            type empty;
          }
        }
        leaf skip {
          status obsolete;
          description
            "Skip a certificate validity  check";
          type enumeration {
            enum authorization-check;
            enum revocation-check;
          }
        }
        container override {
          status obsolete;
          description
            "Over-ride fields in a certificate";
          container cdp {
            status obsolete;
            leaf directory {
              status obsolete;
              type string;
            }
            leaf url {
              status obsolete;
              type string;
            }
          }
          container ocsp {
            status obsolete;
            description
              "Over-ride the OCSP URL in a certificate";
            leaf trustpoint {
              status obsolete;
              description
                "Over-ride the trustpoint for verifying the OCSP certificate";
              type string;
            }
            leaf sequence-num {
              status obsolete;
              type uint16 {
                range "1..10000";
              }
            }
            leaf url {
              status obsolete;
              type string;
            }
          }
          container sia {
            status obsolete;
            description
              "Over-ride the SIA URL in a certificate";
            leaf sequence-num {
              status obsolete;
              type uint16 {
                range "1..10000";
              }
            }
            leaf url {
              status obsolete;
              type string;
            }
          }
        }
      }
    }
    container ocsp {
      status obsolete;
      description
        "OCSP parameters";
      leaf disable-nonce {
        status obsolete;
        description
          " Disable OCSP Nonce Extension";
        type empty;
      }
      leaf url {
        status obsolete;
        type string;
      }
    }
    leaf on {
      status obsolete;
      description
        "create keypair on device";
      type string;
    }
    leaf primary {
      status obsolete;
      description
        "Specify trustpoint as primary";
      type empty;
    }
    leaf regenerate {
      status obsolete;
      description
        "Regenerate keys on re-enrollment";
      type empty;
    }
    leaf-list revocation-check {
      status obsolete;
      description
        "Revocation checking options";
      ordered-by user;
      type enumeration {
        enum crl;
        enum none;
        enum ocsp;
      }
    }
    container root {
      status obsolete;
      description
        "Protocol to get CA certificate";
      leaf proxy {
        status obsolete;
        description
          "HTTP proxy server for getting CA cert";
        type string;
      }
      container tftp {
        status obsolete;
        description
          "Get CA certificate using tftp";
        leaf hostname {
          status obsolete;
          type string;
        }
        leaf filename {
          status obsolete;
          type string;
        }
      }
    }
    container source {
      status obsolete;
      description
        "Specify source interface";
      leaf interface {
        status obsolete;
        description
          "Interface used as source address";
        type string;
      }
    }
    leaf storage {
      status obsolete;
      description
        "key and certificate storage location";
      type string;
    }
    leaf auto-trigger {
      status obsolete;
      description
        "Trigger authentication automatically";
      type empty;
    }
    container rsakeypair {
      status obsolete;
      description
        "Specify rsakeypair for this identity";
      leaf key-label {
        status obsolete;
        description
          "RSA keypair label";
        type string;
      }
      leaf gen-key {
        status obsolete;
        description
          "General Purpose or Signature Key length";
        type uint16 {
          range "360..4096";
        }
      }
      leaf encrypt-key {
        status obsolete;
        description
          "Encryption Key length";
        type uint16 {
          range "360..4096";
        }
      }
    }
    container serial-number {
      status obsolete;
      description
        "Include serial number";
      presence "true";
      leaf none {
        status obsolete;
        description
          "do not include serial number";
        type empty;
      }
    }
    container ip-address {
      status obsolete;
      description
        "include ip address";
      leaf address-line {
        status obsolete;
        description
          "interface name or ip address";
        type string;
      }
      leaf none {
        status obsolete;
        description
          "do not include ip address";
        type empty;
      }
    }
    leaf subject-name {
      status obsolete;
      description
        "Subject Name";
      type string;
    }
    leaf subject-alt-name {
      status obsolete;
      description
        "Subject Alternate Name";
      type string;
    }
    leaf usage {
      status obsolete;
      description
        "Certificate Usage";
      type enumeration {
        enum ike;
        enum ssl-client;
        enum ssl-server;
      }
    }
    leaf vrf {
      status obsolete;
      description
        "Name of VRF to use with trustpoint";
      type string;
    }
  }

  grouping crypto-pki-trustpool-policy-grouping-obsolete {
    container ca-bundle {
      status obsolete;
      description
        "CA bundle download parameters";
      leaf url {
        status obsolete;
        description
          "CA server bundle URL";
        type string;
      }
      choice source-vrf {
        status obsolete;
        case source {
          status obsolete;
          container source {
            status obsolete;
            description
              "Interface used as source address";
            leaf interface {
              status obsolete;
              type string;
            }
          }
        }
        case vrf {
          status obsolete;
          leaf vrf {
            status obsolete;
            description
              "Name of VRF to use with bundle";
            type string;
          }
        }
      }
    }
    leaf vrf {
      status obsolete;
      description
        "Name of VRF to use with trustpoint";
      type string;
    }
    container source {
      status obsolete;
      description
        "Specify source interface";
      leaf interface {
        status obsolete;
        description
          "Interface used as source address";
        type string;
      }
    }
    leaf storage {
      status obsolete;
      description
        "key and certificate storage location";
      type string;
    }
    leaf revocation-check {
      status obsolete;
      description
        "Revocation checking options";
      type enumeration {
        enum crl;
        enum none;
        enum ocsp;
      }
    }
    container ocsp {
      status obsolete;
      description
        "OCSP parameters";
      leaf disable-nonce {
        status obsolete;
        description
          " Disable OCSP Nonce Extension";
        type empty;
      }
      leaf url {
        status obsolete;
        type string;
      }
    }
    leaf chain-validation {
      status obsolete;
      description
        "Validation parameters";
      type empty;
    }
    leaf exit {
      status obsolete;
      type empty;
    }
    container match {
      status obsolete;
      description
        "Match a certificate attributes/maps";
      list certificate {
        status obsolete;
        description
          "Certificate map name";
        key "name";
        leaf name {
          status obsolete;
          type string;
        }
        container allow {
          status obsolete;
          description
            "Allow expired certificates to be accepted";
          leaf expired-certificate {
            status obsolete;
            type empty;
          }
        }
        leaf skip {
          status obsolete;
          description
            "Skip a certificate validity  check";
          type enumeration {
            enum authorization-check;
            enum revocation-check;
          }
        }
        container override {
          status obsolete;
          description
            "Over-ride fields in a certificate";
          container cdp {
            status obsolete;
            choice dir-url {
              status obsolete;
              case directory {
                status obsolete;
                leaf directory {
                  status obsolete;
                  type string;
                }
              }
              case url {
                status obsolete;
                leaf url {
                  status obsolete;
                  type string;
                }
              }
            }
          }
          container ocsp {
            status obsolete;
            description
              "Over-ride the OCSP URL in a certificate";
            leaf trustpool {
              status obsolete;
              description
                "Over-ride the trustpoint for verifying the OCSP certificate";
              type string;
            }
            leaf sequence-num {
              status obsolete;
              type uint16 {
                range "1..10000";
              }
            }
            leaf url {
              status obsolete;
              type string;
            }
          }
          container sia {
            status obsolete;
            description
              "Over-ride the SIA URL in a certificate";
            leaf sequence-num {
              status obsolete;
              type uint16 {
                range "1..10000";
              }
            }
            leaf url {
              status obsolete;
              type string;
            }
          }
        }
      }
    }
    container crl {
      status obsolete;
      description
        "CRL options";
      leaf query {
        status obsolete;
        description
          "Query CRL URL";
        type string;
      }
      container cache {
        status obsolete;
        description
          "CRL cache options";
        choice cache-choice {
          status obsolete;
          case none {
            status obsolete;
            leaf none {
              status obsolete;
              description
                "Do not cache CRLs";
              type empty;
            }
          }
          case delete-after {
            status obsolete;
            leaf delete-after {
              status obsolete;
              description
                "Remove CRL from cache after a timeout (in minutes)";
              type uint16 {
                range "1..43200";
              }
            }
          }
        }
      }
    }
  }

  grouping crypto-pki-token-grouping-obsolete {
    container removal {
      status obsolete;
      description
        "actions to take after token removal";
      leaf timeout {
        status obsolete;
        description
          "seconds after token removal at which keys from the token are cleared";
        type uint16 {
          range "0..480";
        }
      }
    }
  }

  grouping snmp-server-trap-gdoi-grouping {
    container gdoi {
      description
        "Enable GDOI traps";
      presence "true";
      leaf gm-incomplete-cfg {
        description
          "Enable SNMP GDOI GM Incomplete Config trap";
        type empty;
      }
      leaf gm-re-register {
        description
          "Enable SNMP GDOI GM Re-Register trap";
        type empty;
      }
      leaf gm-registration-complete {
        description
          "Enable SNMP GDOI GM Registration Complete trap";
        type empty;
      }
      leaf gm-rekey-fail {
        description
          "Enable SNMP GDOI GM Rekey Failure trap";
        type empty;
      }
      leaf gm-rekey-rcvd {
        description
          "Enable SNMP GDOI GM Rekey Received trap";
        type empty;
      }
      leaf gm-start-registration {
        description
          "Enable SNMP GDOI GM Start Registration trap";
        type empty;
      }
      leaf ks-gm-deleted {
        description
          "Enable SNMP GDOI KS GM Deleted Trap";
        type empty;
      }
      leaf ks-new-registration {
        description
          "Enable SNMP GDOI KS New Registration Trap";
        type empty;
      }
      leaf ks-no-rsa-keys {
        description
          "Enable SNMP GDOI KS trap for missing RSA keys";
        type empty;
      }
      leaf ks-peer-reachable {
        description
          "Enable SNMP GDOI KS Peer Reachable Trap";
        type empty;
      }
      leaf ks-peer-unreachable {
        description
          "Enable SNMP GDOI KS Peer Unreachable Trap";
        type empty;
      }
      leaf ks-reg-complete {
        description
          "Enable SNMP GDOI KS Registration Complete Trap";
        type empty;
      }
      leaf ks-rekey-pushed {
        description
          "Enable SNMP GDOI KS Rekey Pushed trap";
        type empty;
      }
      leaf ks-role-change {
        description
          "Enable SNMP GDOI KS Role Change Trap";
        type empty;
      }
    }
  }

  grouping monitor-event-trace-common {
    leaf dump-file {
      description
        "Set name of trace dump file";
      type string {
        length "1..100";
      }
    }
    leaf size {
      description
        "Number of entries in trace";
      type uint32 {
        range "1..1000000";
      }
    }
    container stacktrace {
      description
        "Enables the stack trace at tracepoints";
      presence "true";
      leaf depth {
        description
          "The number of stack frame details that are stored";
        type uint8 {
          range "1..16";
        }
        default "8";
      }
    }
  }

  grouping monitor-event-trace-crypto-grouping {
    container crypto {
      container ikev2 {
        container error {
          description
            "Enable IKEv2 Errors";
          presence "true";
          uses monitor-event-trace-common;
        }
        container event {
          description
            "Enable IKEv2 Events";
          presence "true";
          uses monitor-event-trace-common;
        }
        container exception {
          description
            "Enable IKEv2 Exception";
          presence "true";
          uses monitor-event-trace-common;
        }
      }
      container ipsec {
        container error {
          description
            "Enable ipsec Errors";
          presence "true";
          uses monitor-event-trace-common;
        }
        container event {
          description
            "Enable ipsec Events";
          presence "true";
          uses monitor-event-trace-common;
        }
        container exception {
          description
            "Enable ipsec Exception";
          presence "true";
          uses monitor-event-trace-common;
        }
      }
    }
  }

  grouping monitor-event-trace-nhrp-common {
    container error-enable {
      description
        "NHRP error enable";
      leaf error {
        description
          "NHRP error";
        type empty;
      }
    }
    container error-options {
      description
        "NHRP error options";
      container error {
        description
          "NHRP error";
        uses monitor-event-trace-common;
      }
    }
    container event-enable {
      description
        "NHRP event enable";
      leaf event {
        description
          "NHRP event";
        type empty;
      }
    }
    container event-options {
      description
        "NHRP event options";
      container event {
        description
          "NHRP event";
        uses monitor-event-trace-common;
      }
    }
    container exception-enable {
      description
        "NHRP exception enable";
      leaf exception {
        description
          "NHRP exception";
        type empty;
      }
    }
    container exception-options {
      description
        "NHRP exception options";
      container exception {
        description
          "NHRP exception";
        uses monitor-event-trace-common;
      }
    }
  }

  grouping monitor-event-trace-tunnel-common {
    leaf dump-file {
      description
        "Set name of dump file containing merged traces";
      type string {
        length "1..100";
      }
    }
    container nhrp {
      description
        "NHRP Trace";
      uses monitor-event-trace-nhrp-common;
    }
  }

  grouping monitor-event-trace-gdoi-grouping {
    container gdoi {
      description
        "gdoi event-trace";
      container coop {
        description
          "Enable GDOI coop";
        presence "true";
        uses monitor-event-trace-common;
      }
      container infra {
        description
          "Enable GDOI infra";
        presence "true";
        uses monitor-event-trace-common;
      }
      container registration {
        description
          "Enable GDOI registration";
        presence "true";
        uses monitor-event-trace-common;
      }
      container rekey {
        description
          "Enable GDOI rekey";
        presence "true";
        uses monitor-event-trace-common;
      }
    }
  }

  grouping monitor-event-trace-dmvpn-grouping {
    container dmvpn {
      container crypto-enable {
        description
          "Enable Dynamic Multipoint VPN Crypto events";
        leaf crypto {
          description
            "All DMVPN crypto events";
          type boolean;
          default "false";
        }
      }
      container crypto-options {
        description
          "DMVPN crypto options";
        container crypto {
          description
            "DMVPN crypto";
          uses monitor-event-trace-common;
        }
      }
      container tunnel-enable {
        description
          "Enable Dynamic Multipoint VPN on tunnel";
        leaf tunnel {
          description
            "All DMVPN tunnel events";
          type boolean;
          default "false";
        }
      }
      container tunnel-options {
        description
          "DMVPN tunnel options";
        container tunnel {
          description
            "DMVPN tunnel";
          uses monitor-event-trace-common;
        }
      }
      uses monitor-event-trace-tunnel-common;
    }
  }

  grouping monitor-event-trace-flexvpn-grouping {
    container flexvpn {
      container crypto-enable {
        description
          "Enable FlexVPN Crypto events";
        leaf crypto {
          description
            "All FlexVPN crypto events";
          type boolean;
          default "false";
        }
      }
      container crypto-options {
        description
          "FlexVPN crypto options";
        container crypto {
          description
            "FlexVPN crypto";
          uses monitor-event-trace-common;
        }
      }
      container tunnel-enable {
        description
          "Enable FlexVPN tunnel";
        leaf tunnel {
          description
            "All FlexVPN tunnel events";
          type boolean;
          default "false";
        }
      }
      container tunnel-options {
        description
          "FlexVPN tunnel options";
        container tunnel {
          description
            "FlexVPN tunnel";
          uses monitor-event-trace-common;
        }
      }
      uses monitor-event-trace-tunnel-common;
    }
  }

  augment "/ios:native/ios:key" {
    uses config-key-grouping;
  }

  augment "/ios:native/ios:crypto" {
    uses config-crypto-grouping;
  }

  augment "/ios:native/ios:interface/ios:Tunnel/ios-tun:tunnel/ios-tun:protection" {
    uses config-interface-tunnel-ipsec-grouping {
      if-feature "ios-features:crypto";
    }
  }

  augment "/ios:native/ios:interface/ios:Virtual-Template/ios-tun:tunnel/ios-tun:protection" {
    uses config-interface-tunnel-ipsec-grouping {
      if-feature "ios-features:crypto";
    }
  }

  augment "/ios:native/ios:interface/ios:FastEthernet" {
    uses config-interface-crypto-grouping {
      if-feature "ios-features:crypto";
    }
  }

  augment "/ios:native/ios:interface/ios:GigabitEthernet" {
    uses config-interface-crypto-grouping {
      if-feature "ios-features:crypto";
    }
  }

  augment "/ios:native/ios:interface/ios:TenGigabitEthernet" {
    uses config-interface-crypto-grouping {
      if-feature "ios-features:crypto";
    }
  }

  augment "/ios:native/ios:interface/ios:FiveGigabitEthernet" {
    uses config-interface-crypto-grouping {
      if-feature "ios-features:crypto";
    }
  }

  augment "/ios:native/ios:interface/ios:AppGigabitEthernet" {
    uses config-interface-crypto-grouping {
      if-feature "ios-features:crypto";
    }
  }

  augment "/ios:native/ios:interface/ios:TwentyFiveGigE" {
    uses config-interface-crypto-grouping {
      if-feature "ios-features:crypto";
    }
  }

  augment "/ios:native/ios:interface/ios:TwoGigabitEthernet" {
    uses config-interface-crypto-grouping {
      if-feature "ios-features:crypto";
    }
  }

  augment "/ios:native/ios:interface/ios:FortyGigabitEthernet" {
    uses config-interface-crypto-grouping {
      if-feature "ios-features:crypto";
    }
  }

  augment "/ios:native/ios:interface/ios:HundredGigE" {
    uses config-interface-crypto-grouping {
      if-feature "ios-features:crypto";
    }
  }

  augment "/ios:native/ios:interface/ios:Loopback" {
    uses config-interface-crypto-grouping {
      if-feature "ios-features:crypto";
    }
  }

  augment "/ios:native/ios:interface/ios:LISP" {
    uses config-interface-crypto-grouping {
      if-feature "ios-features:crypto";
    }
  }

  augment "/ios:native/ios:interface/ios:Ethernet" {
    uses config-interface-crypto-grouping {
      if-feature "ios-features:crypto";
    }
  }

  augment "/ios:native/ios:interface/ios:Tunnel" {
    uses config-interface-crypto-grouping {
      if-feature "ios-features:crypto";
    }
  }

  augment "/ios:native/ios:interface/ios:Port-channel" {
    uses config-interface-crypto-grouping {
      if-feature "ios-features:crypto";
    }
  }

  augment "/ios:native/ios:interface/ios:Virtual-Template" {
    uses config-interface-crypto-grouping {
      if-feature "ios-features:crypto";
    }
  }

  augment "/ios:native/ios:interface/ios:Vlan" {
    uses config-interface-crypto-grouping {
      if-feature "ios-features:crypto";
    }
  }

  augment "/ios:native/ios:interface/ios:Virtual-PPP" {
    uses config-interface-crypto-grouping {
      if-feature "ios-features:crypto";
    }
  }

  augment "/ios:native/ios:interface/ios:FastEthernet/ios:ipv6" {
    uses config-interface-ipv6-crypto-grouping {
      if-feature "ios-features:crypto";
    }
  }

  augment "/ios:native/ios:interface/ios:GigabitEthernet/ios:ipv6" {
    uses config-interface-ipv6-crypto-grouping {
      if-feature "ios-features:crypto";
    }
  }

  augment "/ios:native/ios:interface/ios:TenGigabitEthernet/ios:ipv6" {
    uses config-interface-ipv6-crypto-grouping {
      if-feature "ios-features:crypto";
    }
  }

  augment "/ios:native/ios:interface/ios:FiveGigabitEthernet/ios:ipv6" {
    uses config-interface-ipv6-crypto-grouping {
      if-feature "ios-features:crypto";
    }
  }

  augment "/ios:native/ios:interface/ios:AppGigabitEthernet/ios:ipv6" {
    uses config-interface-ipv6-crypto-grouping {
      if-feature "ios-features:crypto";
    }
  }

  augment "/ios:native/ios:interface/ios:TwentyFiveGigE/ios:ipv6" {
    uses config-interface-ipv6-crypto-grouping {
      if-feature "ios-features:crypto";
    }
  }

  augment "/ios:native/ios:interface/ios:TwoGigabitEthernet/ios:ipv6" {
    uses config-interface-ipv6-crypto-grouping {
      if-feature "ios-features:crypto";
    }
  }

  augment "/ios:native/ios:interface/ios:FortyGigabitEthernet/ios:ipv6" {
    uses config-interface-ipv6-crypto-grouping {
      if-feature "ios-features:crypto";
    }
  }

  augment "/ios:native/ios:interface/ios:HundredGigE/ios:ipv6" {
    uses config-interface-ipv6-crypto-grouping {
      if-feature "ios-features:crypto";
    }
  }

  augment "/ios:native/ios:interface/ios:Loopback/ios:ipv6" {
    uses config-interface-ipv6-crypto-grouping {
      if-feature "ios-features:crypto";
    }
  }

  augment "/ios:native/ios:interface/ios:Tunnel/ios:ipv6" {
    uses config-interface-ipv6-crypto-grouping {
      if-feature "ios-features:crypto";
    }
  }

  augment "/ios:native/ios:interface/ios:Port-channel/ios:ipv6" {
    uses config-interface-ipv6-crypto-grouping {
      if-feature "ios-features:crypto";
    }
  }

  augment "/ios:native/ios:interface/ios:Virtual-Template/ios:ipv6" {
    uses config-interface-ipv6-crypto-grouping {
      if-feature "ios-features:crypto";
    }
  }

  augment "/ios:native/ios:interface/ios:Vlan/ios:ipv6" {
    uses config-interface-ipv6-crypto-grouping {
      if-feature "ios-features:crypto";
    }
  }

  augment "/ios:native/ios:interface/ios:Virtual-PPP/ios:ipv6" {
    uses config-interface-ipv6-crypto-grouping {
      if-feature "ios-features:crypto";
    }
  }

  augment "/ios:native/ios:snmp-server/ios-snmp:enable/ios-snmp:enable-choice/ios-snmp:traps" {
    uses snmp-server-trap-gdoi-grouping;
  }

  augment "/ios:native/ios:monitor/ios:event-trace" {
    uses monitor-event-trace-crypto-grouping;
  }

  augment "/ios:native/ios:monitor/ios:event-trace" {
    uses monitor-event-trace-gdoi-grouping;
  }

  augment "/ios:native/ios:monitor/ios:event-trace" {
    uses monitor-event-trace-dmvpn-grouping;
  }

  augment "/ios:native/ios:monitor/ios:event-trace" {
    uses monitor-event-trace-flexvpn-grouping;
  }
}
