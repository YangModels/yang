module Cisco-IOS-XE-install-oper {
  yang-version 1.1;
  namespace "http://cisco.com/ns/yang/Cisco-IOS-XE-install-oper";
  prefix install-ios-xe-oper;

  import Cisco-IOS-XE-common-types {
    prefix common-types-ios-xe;
  }
  import Cisco-IOS-XE-install-event-types {
    prefix install-event-types-ios-xe;
  }
  import Cisco-IOS-XE-install-oper-types {
    prefix install-oper-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for install manager operational data.
     Copyright (c) 2020-2023 by Cisco Systems, Inc.
     All rights reserved.";

  revision 2024-03-01 {
    description
      "- Added install package action parameter to capture package decision.";
    reference
      "2.0.0";
    cisco-semver:module-version "2.0.0";
  }
  revision 2023-07-01 {
    description
      "- Fixed invalid 'when' constraint";
    reference
      "1.8.0";
    cisco-semver:module-version "1.8.0";
  }
  revision 2023-03-01 {
    description
      "- Added detailed summary for ongoing as well as completed install operations.";
    reference
      "1.7.0";
    cisco-semver:module-version "1.7.0";
  }
  revision 2022-11-01 {
    description
      "- Update yang-version to 1.1
       - Added cisco image name field to indicate the package name when published
       - Added parameter definition for install download operation.
       - Added scheduled start and end time parameters for install add, activate operations.";
    reference
      "1.6.0";
    cisco-semver:module-version "1.6.0";
  }
  revision 2022-07-01 {
    description
      "- Added support fot set default install operation.";
    reference
      "1.5.0";
    cisco-semver:module-version "1.5.0";
  }
  revision 2022-03-01 {
    description
      "- Added install-version-state-installed to indicate installed versions on device.
       - Description change to install-version-state-in-progress for clarity.
       - Added commit-type to indicate version commit trigger
       - Added timestamp to version
       - Added compatible controller version info for the package
       - Added controller mode to oper state
       - Added rollback label parameter
       - Added parameter definitions for install operations
       - Added install operation and operation history";
    reference
      "1.4.0";
    cisco-semver:module-version "1.4.0";
  }
  revision 2021-11-01 {
    description
      "Added installer version and timestamp for the packages";
    reference
      "1.3.0";
    cisco-semver:module-version "1.3.0";
  }
  revision 2021-07-01 {
    description
      "Added controller version corresponding to the install package in the version record";
    reference
      "1.2.0";
    cisco-semver:module-version "1.2.0";
  }
  revision 2021-03-01 {
    description
      " - Added support for install rollback points and install profiles.
        - New YANG definitions for install manager to provide ISSU specific
       operational data";
    reference
      "1.1.0";
    cisco-semver:module-version "1.1.0";
  }
  revision 2020-07-01 {
    description
      "Initial revision";
    reference
      "1.0.0";
    cisco-semver:module-version "1.0.0";
  }

  typedef install-package-type {
    type enumeration {
      enum install-pkg-unknown {
        value 0;
        description
          "Install package type unknown";
      }
      enum install-pkg-img {
        value 1;
        description
          "Install package of type Super Image";
      }
      enum install-pkg-smu {
        value 2;
        description
          "Install package of type Software Maintenance Upgrade";
      }
      enum install-pkg-subpkg {
        value 3;
        description
          "Install package of type sub-package";
      }
      enum install-pkg-dmp {
        value 4;
        description
          "Install package of type Data Model Package";
      }
      enum install-pkg-apsp {
        value 5;
        description
          "Install package of type Access Point Service Pack";
      }
      enum install-pkg-apdp {
        value 6;
        description
          "Install package of type Access Point Device Pack";
      }
      enum install-pkg-pkg {
        value 7;
        description
          "Install basic package type";
      }
    }
    description
      "Install package type";
  }

  typedef install-package-state {
    type enumeration {
      enum install-state-new {
        value 0;
        description
          "Install state for file is new";
      }
      enum install-state-added {
        value 1;
        description
          "Image has been added";
      }
      enum install-state-act-uncommitted {
        value 2;
        description
          "Install state is activated but not committed";
      }
      enum install-state-dact-uncommitted {
        value 3;
        description
          "Install state is deactivated and uncommitted";
      }
      enum install-state-committed {
        value 4;
        description
          "Install image is in committed state";
      }
      enum install-state-unknown {
        value 5;
        description
          "Install state is not known";
      }
    }
    description
      "Install package state";
  }

  typedef install-package-verify-status {
    type enumeration {
      enum install-package-verify-unknown {
        value 0;
        description
          "Install package verification status is unknown";
      }
      enum install-package-verify-ok {
        value 1;
        description
          "Install package is verified";
      }
      enum install-package-verify-fail {
        value 2;
        description
          "Install package verification failed";
      }
      enum install-package-verify-deferred {
        value 3;
        description
          "Install package verification is deferred";
      }
      enum install-package-verify-not-done {
        value 4;
        description
          "Install package verification is not done";
      }
    }
    description
      "Install package verification status";
  }

  typedef install-package-info-action {
    type enumeration {
      enum install-package-action-none {
        value 0;
        description
          "No install package action to be performed";
      }
      enum install-package-action-defer-delete {
        value 1;
        description
          "Defer deletion of package table record";
      }
    }
    description
      "Install package action to be performed";
  }

  typedef install-pkg-reload-condition {
    type enumeration {
      enum install-reload-cond-device-reload {
        value 0;
        description
          "Install restart condition is restart required";
      }
      enum install-reload-cond-non-reload {
        value 1;
        description
          "Install restart condition is no restart required";
      }
      enum install-reload-cond-restart {
        value 2;
        description
          "Install restart condition is restart";
      }
      enum install-reload-cond-issu {
        value 3;
        description
          "Install restart condition is ISSU dependent";
      }
      enum install-reload-cond-unknown {
        value 4;
        description
          "Reload condition is not known";
      }
    }
    description
      "Install package restart condition";
  }

  typedef install-smu-subcategory {
    type enumeration {
      enum install-smu-subcategory-apsp {
        value 0;
        description
          "Install Software Maintenance Upgrade sub-category is Access Point Service Pack";
      }
      enum install-smu-subcategory-apdp {
        value 1;
        description
          "Install Software Maintenance Upgrade sub-category is Access Point Device Pack";
      }
      enum install-smu-subcategory-unknown {
        value 2;
        description
          "Install Software Maintenance Upgrade sub-category is unknown";
      }
    }
    description
      "Install Software Maintenance Upgrade sub-category";
  }

  typedef install-mode {
    type enumeration {
      enum install-mode-bundle {
        value 0;
        description
          "install mode is bundle";
      }
      enum install-mode-install {
        value 1;
        description
          "Install boot mode is install";
      }
      enum install-mode-install-bundle {
        value 2;
        description
          "Install boot mode is bundle";
      }
      enum install-mode-unknown {
        value 3;
        description
          "Install boot mode is not known";
      }
    }
    description
      "Install mode type";
  }

  typedef install-smu-class {
    type enumeration {
      enum install-smu-class-recommended {
        value 0;
        description
          "Install Software Maintenance Upgrade class is recommended";
      }
      enum install-smu-class-optional {
        value 1;
        description
          "Install Software Maintenance Upgrade class is optional";
      }
      enum install-smu-class-unknown {
        value 2;
        description
          "Install Software Maintenance Upgrade class is unknown";
      }
    }
    description
      "Install Software Maintenance Upgrade class type";
  }

  typedef install-crdu-attr {
    type enumeration {
      enum install-crdu-attr-unrevertable {
        value 0;
        description
          "Install hot patch type is not reversible";
      }
      enum install-crdu-attr-revertable {
        value 1;
        description
          "Install hot patch type is reversible";
      }
      enum install-crdu-attr-unknown {
        value 2;
        description
          "Install hot patch attribute is unknown";
      }
    }
    description
      "Install hot patch attributes";
  }

  typedef install-version-state {
    type enumeration {
      enum install-version-state-provisioned-committed {
        value 0;
        description
          "Install version state is provisioned and committed";
      }
      enum install-version-state-provisioned-uncommitted {
        value 1;
        description
          "Install version state is provisioned and uncommitted";
      }
      enum install-version-state-in-progress {
        value 2;
        description
          "Install version state is in-progress, marked for activation";
      }
      enum install-version-state-invalid {
        value 3;
        description
          "Complete image is not available for this version";
      }
      enum install-version-state-present {
        value 4;
        description
          "Install version state is present but not used";
      }
      enum install-version-state-unknown {
        value 5;
        description
          "Install version state is not configured";
      }
      enum install-version-state-installed {
        value 6;
        description
          "Install version is installed on device and available for activation";
      }
    }
    description
      "Install version state";
  }

  typedef install-smu-license-level {
    type enumeration {
      enum install-smu-lic-name-base-network-essentials {
        value 0;
        description
          "Install Software Maintenance Upgrade license level is base-network-essentials";
      }
      enum install-smu-lic-name-base-network-advantage {
        value 1;
        description
          "Install Software Maintenance Upgrade license level is base-network-advantage";
      }
      enum install-smu-lic-name-dna-essentials {
        value 2;
        description
          "Install Software Maintenance Upgrade license level is dna-essentials";
      }
      enum install-smu-lic-name-dna-advantage {
        value 3;
        description
          "Install Software Maintenance Upgrade license level is dna-advantage";
      }
      enum install-smu-lic-name-unknown {
        value 4;
        description
          "Install Software Maintenance Upgrade license level is not known";
      }
    }
    description
      "Install Software Maintenance Upgrade license level";
  }

  typedef install-smu-impact-type {
    type enumeration {
      enum install-smu-impact-ap-images {
        value 0;
        description
          "Install Software Maintenance Upgrade impacts AP images";
      }
      enum install-smu-impact-unknown {
        value 1;
        description
          "Install Software Maintenance Upgrade impact is unknown";
      }
    }
    description
      "Install Software Maintenance Upgrade impact type";
  }

  typedef install-header-package-type {
    type enumeration {
      enum install-header-package-type-invalid {
        value 0;
        description
          "Install header package type is invalid";
      }
      enum install-header-package-type-rommon {
        value 1;
        description
          "Install header package is for ROMMON";
      }
      enum install-header-package-type-cc-base {
        value 2;
        description
          "Install header package is for CC Base";
      }
      enum install-header-package-type-cc-spa {
        value 3;
        description
          "Install header package is for CC supervisor card";
      }
      enum install-header-package-type-cc-srdriver {
        value 4;
        description
          "Install header package is for CC SR driver";
      }
      enum install-header-package-type-cc-spawma {
        value 5;
        description
          "Install header package is for CC shared port adaptor";
      }
      enum install-header-package-type-cc-iomd-sup {
        value 6;
        description
          "Install header package is for CC supervisor card daemon";
      }
      enum install-header-package-type-cc-mips-base {
        value 7;
        description
          "Install header package is for MIPS";
      }
      enum install-header-package-type-elc-base {
        value 8;
        description
          "Install header package is for line card base";
      }
      enum install-header-package-type-elc-spa {
        value 9;
        description
          "Install header package is for shared port adaptor card";
      }
      enum install-header-package-type-fp-base {
        value 10;
        description
          "Install header package is for FP base";
      }
      enum install-header-package-type-rp-super {
        value 11;
        description
          "Install header package is for RP super";
      }
      enum install-header-package-type-rp-base {
        value 12;
        description
          "Install header package is for RP base";
      }
      enum install-header-package-type-rp-daemons {
        value 13;
        description
          "Install header package is for RP daemons";
      }
      enum install-header-package-type-rp-iosd {
        value 14;
        description
          "Install header package is for RP IOS daemon";
      }
      enum install-header-package-type-rp-security {
        value 15;
        description
          "Install header package is for RP security";
      }
      enum install-header-package-type-firmware {
        value 16;
        description
          "Install header package is for firmware";
      }
    }
    description
      "Install header package type";
  }

  typedef install-timer-state {
    type enumeration {
      enum install-timer-state-unknown {
        value 0;
        description
          "Install timer state is not known";
      }
      enum install-timer-state-active {
        value 1;
        description
          "Install timer is running";
      }
      enum install-timer-state-inactive {
        value 2;
        description
          "Install timer is not running";
      }
    }
    description
      "Install timer state";
  }

  typedef install-system-activity {
    type enumeration {
      enum install-no-activity {
        value 0;
        description
          "Install or ISSU operation is not in progress";
      }
      enum install-install-in-progress {
        value 1;
        description
          "Install operation is in progress";
      }
      enum install-issu-in-progress {
        value 2;
        description
          "ISSU operation is in progress";
      }
    }
    description
      "System level install activity status";
  }

  typedef install-issu-capability {
    type enumeration {
      enum install-issu-disabled {
        value 0;
        description
          "ISSU is supported on a given platform but user can
           not perform ISSU. System do not satisfy one or many
           ISSU specific criteria";
      }
      enum install-issu-enabled {
        value 1;
        description
          "All ISSU specific system criteria are met.
           ISSU can be started";
      }
      enum install-issu-not-supported {
        value 2;
        description
          "Platform does not support issu feature";
      }
    }
    description
      "Capability of a system to start ISSU operation";
  }

  typedef install-boot-mode {
    type enumeration {
      enum install-boot-mode-unknown {
        value 0;
        description
          "System booted in unknown mode";
      }
      enum install-boot-mode-install {
        value 1;
        description
          "System booted in install mode";
      }
      enum install-boot-mode-bundle {
        value 2;
        description
          "System booted in bundle mode, ISSU not
           supported in bundle mode";
      }
    }
    description
      "System boot mode type";
  }

  typedef install-profile-type {
    type enumeration {
      enum install-profile-rollback {
        value 0;
        description
          "Install rollback profile type";
      }
    }
    description
      "Install profile types";
  }

  typedef install-commit-type {
    type enumeration {
      enum install-commit-pend {
        value 0;
        description
          "Install version is pending commit ";
      }
      enum install-commit-auto {
        value 1;
        description
          "Install version was auto-committed ";
      }
      enum install-commit-user {
        value 2;
        description
          "Install version was committed by user trigger";
      }
    }
    description
      "Install commit type";
  }

  grouping install-generic-pkg-info {
    description
      "Install common package generic info";
    leaf name {
      type string;
      description
        "Internal package name";
    }
    leaf build-time {
      type yang:date-and-time;
      description
        "Package build time";
    }
    leaf release-date {
      type yang:date-and-time;
      description
        "Package release date";
    }
    leaf user-name {
      type string;
      description
        "Name of the user that built the package";
    }
    leaf package-name {
      type string;
      description
        "Extended internal package name info for variants";
    }
    leaf build-name {
      type string;
      description
        "Release Name tag used for Package Build";
    }
    leaf installer-ver {
      type string;
      description
        "Installer version supported by the package";
    }
    leaf ctrl-ver {
      when "(/install-oper-data/install-location-information/oper-state/ctrl-mode = 'true')";
      type string;
      description
        "Compatible controller version for the package";
    }
  }

  grouping install-common-pkg-info {
    description
      "Install package info applicable to all package types";
    container generic-info {
      description
        "Install package generic information applicable to all package types";
      uses install-ios-xe-oper:install-generic-pkg-info;
    }
  }

  grouping install-common-smu-pkg-info {
    description
      "Software Maintenance Upgrade package information";
    leaf smu-id {
      type uint32;
      description
        "Software Maintenance Upgrade identifier";
    }
    leaf smu-mode {
      type install-ios-xe-oper:install-mode;
      description
        "Software Maintenance Upgrade mode";
    }
    leaf-list smu-supersedes-list {
      type uint32;
      max-elements 64;
      ordered-by user;
      description
        "Software Maintenance Upgrade supersede list";
    }
    leaf smu-subcategory {
      type install-ios-xe-oper:install-smu-subcategory;
      description
        "Software Maintenance Upgrade sub-category";
    }
    leaf smu-compatible-with {
      type string;
      description
        "Software Maintenance Upgrade compatible with";
    }
    leaf smu-type {
      type install-ios-xe-oper:install-pkg-reload-condition;
      description
        "Software Maintenance Upgrade type";
    }
    leaf activation-type {
      type install-ios-xe-oper:install-pkg-reload-condition;
      description
        "Activation type";
    }
    leaf deactivation-type {
      type install-ios-xe-oper:install-pkg-reload-condition;
      description
        "De-activation type";
    }
    leaf smu-impact {
      type install-ios-xe-oper:install-smu-impact-type;
      description
        "Software Maintenance Upgrade impact type";
    }
    leaf smu-class {
      type install-ios-xe-oper:install-smu-class;
      description
        "Software Maintenance Upgrade class";
    }
    leaf-list smu-fixes-list {
      type string;
      max-elements 64;
      ordered-by user;
      description
        "Software Maintenance Upgrade fixes";
    }
    leaf smu-license-level {
      type install-ios-xe-oper:install-smu-license-level;
      description
        "Software Maintenance Upgrade license level";
    }
    leaf crdu-attr {
      type install-ios-xe-oper:install-crdu-attr;
      description
        "Hot patch attribute";
    }
  }

  grouping install-smu-pkg-info {
    description
      "Install Software Maintenance Upgrade package information";
    container common-data {
      description
        "Common package data which is applicable to all types of packages";
      uses install-ios-xe-oper:install-common-pkg-info;
    }
    leaf defect {
      type string;
      description
        "Defect identifier fixed by this package";
    }
    container smu-data {
      description
        "Software Maintenance Upgrade data";
      uses install-ios-xe-oper:install-common-smu-pkg-info;
    }
  }

  grouping install-smu-attr {
    description
      "Software Maintenance Upgrade package attributes";
    leaf package-state {
      type install-ios-xe-oper:install-package-state;
      description
        "Package state";
    }
    container pkg-info-data {
      description
        "Package info data";
      uses install-ios-xe-oper:install-smu-pkg-info;
    }
  }

  grouping install-subpkg-pkg-info {
    description
      "Sub-package information";
    container common-data {
      description
        "Common package data which is applicable to all types of packages";
      uses install-ios-xe-oper:install-common-pkg-info;
    }
    leaf subpkg-type {
      type string;
      description
        "Sub-package type";
    }
    container smu-data {
      description
        "Software Maintenance Upgrade data";
      uses install-ios-xe-oper:install-common-smu-pkg-info;
    }
  }

  grouping install-subpkg-attr {
    description
      "Sub-package attribute";
    leaf package-state {
      type install-ios-xe-oper:install-package-state;
      description
        "Package state";
    }
    container pkg-info-data {
      description
        "Package information data";
      uses install-ios-xe-oper:install-subpkg-pkg-info;
    }
  }

  grouping install-img-pkg-info {
    description
      "Package information for image";
    container common-data {
      description
        "Common package data which is applicable to all types of packages";
      uses install-ios-xe-oper:install-common-pkg-info;
    }
  }

  grouping install-img-attr {
    description
      "Install image attributes";
    leaf timestamp {
      type yang:date-and-time;
      description
        "Timestamp of the package file";
    }
    leaf header-size {
      type uint32;
      units "bytes";
      description
        "Header size in bytes";
    }
    leaf header-package-type {
      type install-ios-xe-oper:install-header-package-type;
      description
        "Package header type";
    }
    container pkg-info-data {
      description
        "Package info data";
      uses install-ios-xe-oper:install-img-pkg-info;
    }
  }

  grouping install-auto-abort-timer {
    description
      "Install auto abort timer information";
    leaf state {
      type install-ios-xe-oper:install-timer-state;
      description
        "Install auto abort timer state";
    }
    leaf end-time {
      when "(../state = 'install-timer-state-active')";
      type yang:date-and-time;
      description
        "Install auto abort timer end time";
    }
  }

  grouping install-oper-state {
    description
      "Install operational state information";
    container auto-abort-timer {
      description
        "Install auto abort timer information";
      uses install-ios-xe-oper:install-auto-abort-timer;
    }
    leaf added-profile {
      type string;
      description
        "Install added profile information";
    }
    leaf sys-activity {
      type install-ios-xe-oper:install-system-activity;
      description
        "System level install activity status";
    }
    leaf sso-state {
      type boolean;
      description
        "System redundancy state";
    }
    leaf boot-mode {
      type install-ios-xe-oper:install-boot-mode;
      description
        "System boot mode";
    }
    leaf ctrl-mode {
      type boolean;
      description
        "Indicates if device is controller managed";
    }
  }

  grouping install-issu-oper-state {
    description
      "ISSU operational state information";
    leaf issu-cap {
      type install-ios-xe-oper:install-issu-capability;
      description
        "Capability of a system to start ISSU operation";
    }
  }

  grouping install-op-add-param {
    description
      "Install add operation parameters";
    leaf src-filename {
      type string;
      description
        "Install package source path, can be local or remote";
    }
    leaf dest-dir {
      type string;
      description
        "Directory on local media on device where install package will be downloaded";
    }
    leaf dest-filename {
      type string;
      description
        "Name of the package to be added";
    }
    leaf scheduled-start {
      type yang:date-and-time;
      description
        "Scheduled start time for operation";
    }
    leaf scheduled-end {
      type yang:date-and-time;
      description
        "Scheduled end time for operation";
    }
  }

  grouping install-op-rollback-param {
    description
      "Install rollback operation parameters";
    leaf rollback-id {
      type uint32;
      description
        "Id identifying commit point to rollback to";
    }
    leaf rollback-label {
      type string;
      description
        "Label identifying commit point to rollback to";
    }
    leaf reload-reqd {
      type boolean;
      description
        "Indicates if operation requires device reload";
    }
  }

  grouping install-op-activate-param {
    description
      "Install activate operation parameters";
    leaf abort-timer {
      type uint32;
      description
        "Install activate auto-abort timer value";
    }
    leaf scheduled-start {
      type yang:date-and-time;
      description
        "Scheduled start time for operation";
    }
    leaf scheduled-end {
      type yang:date-and-time;
      description
        "Scheduled end time for operation";
    }
  }

  grouping install-op-deactivate-param {
    description
      "Install deactivate operation parameters";
    leaf abort-timer {
      type uint32;
      description
        "Install deactivate auto-abort timer value";
    }
  }

  grouping install-op-commit-param {
    description
      "Install commit operation parameters";
    leaf create-chkpt {
      type boolean;
      description
        "parameter controlling commit point creation for future use";
    }
  }

  grouping install-op-set-default-param {
    description
      "Install set default operation parameters";
    leaf version {
      type string;
      description
        "Software image version to set as default";
    }
  }

  grouping install-op-download-param {
    description
      "Install download operation parameters";
    leaf src-path {
      type string;
      description
        "Copy image/SMU source path, can be local or remote";
    }
    leaf dest-dir {
      type string;
      description
        "Destination directory for download";
    }
    leaf dest-filename {
      type string;
      description
        "Target filename on download";
    }
    leaf username {
      type string;
      description
        "Username of remote server";
    }
    leaf password {
      type string;
      description
        "Password of remote server";
    }
    leaf password-type {
      type common-types-ios-xe:password-encryption-type;
      description
        "Encryption method used for password encryption";
    }
    leaf vrf {
      type string;
      description
        "VRF/VPN identifier to be used for download";
    }
    leaf timeout {
      type uint32;
      units "minutes";
      description
        "Timeout after which download expires";
    }
    leaf scheduled-start {
      type yang:date-and-time;
      description
        "Scheduled start time for operation";
    }
    leaf scheduled-end {
      type yang:date-and-time;
      description
        "Scheduled end time for operation";
    }
  }

  grouping install-op-remove-param {
    description
      "Install remove operation parameters";
    leaf dest-dir {
      type string;
      description
        "Directory from where package needs to be removed";
    }
    leaf dest-filename {
      type string;
      description
        "Name of the package to be removed";
    }
    leaf version {
      type string;
      description
        "Version corresponding to packages to be deleted";
    }
    leaf inactive {
      type boolean;
      description
        "Parameter indicating removal of all inactive packages on device";
    }
  }

  grouping install-op-cancel-param {
    description
      "Install abort operation parameters";
    leaf reload-reqd {
      type boolean;
      description
        "Indicates if operation requires device reload";
    }
  }

  grouping install-op-key {
    description
      "Install operation key to uniquely identify operation";
    leaf start-time {
      type yang:date-and-time;
      description
        "Operation Start time";
    }
    leaf op-uuid {
      type string;
      description
        "Operation uuid to identify operation uniquely externally";
    }
    leaf op-id {
      type uint32;
      description
        "Internal id to track operations on device";
    }
  }

  grouping install-operation {
    description
      "Install operation information";
    list install-txn-summary-op {
      when "(../op-done = 'op-not-complete')";
      key "fru slotnum baynum chassisnum txn-id";
      description
        "Install transaction summary";
      uses install-ios-xe-oper:install-transaction-summary-key;
      uses install-ios-xe-oper:install-transaction-summary;
    }
    list install-txn-sum-op-hist {
      when "(../op-done = 'op-complete')";
      key "fru slotnum baynum chassisnum txn-id";
      description
        "Install transaction summary history";
      uses install-ios-xe-oper:install-transaction-summary-key;
      uses install-ios-xe-oper:install-transaction-summary;
    }
    leaf end-time {
      type yang:date-and-time;
      description
        "Install operation end time";
    }
    leaf op-status {
      type install-oper-types-ios-xe:install-op-sts;
      description
        "Install operation granular status";
    }
    leaf op-done {
      type install-oper-types-ios-xe:install-op-finish-sts;
      description
        "Install operation finish status";
    }
    leaf pkg-type {
      type install-ios-xe-oper:install-package-type;
      description
        "Install package type used for operation";
    }
    leaf timeout {
      type uint32;
      description
        "Maximum time allowed for the operation completion";
    }
    leaf op-intf {
      type install-oper-types-ios-xe:install-op-intf;
      description
        "Device interface used to trigger install operation";
    }
    choice op-cmd-choice {
      description
        "Install operation command";
      case install-op-add {
        container add-param {
          description
            "Install add operation parameters";
          uses install-ios-xe-oper:install-op-add-param;
        }
      }
      case install-op-rollback {
        container rollback-param {
          description
            "Install rollback operation parameters";
          uses install-ios-xe-oper:install-op-rollback-param;
        }
      }
      case install-op-activate {
        container act-param {
          description
            "Install activate operation parameters";
          uses install-ios-xe-oper:install-op-activate-param;
        }
      }
      case install-op-commit {
        container commit-param {
          description
            "Install commit operation parameters";
          uses install-ios-xe-oper:install-op-commit-param;
        }
      }
      case install-op-deactivate {
        container deact-param {
          description
            "Install deactivate operation parameters";
          uses install-ios-xe-oper:install-op-deactivate-param;
        }
      }
      case install-op-remove {
        container remove-param {
          description
            "Install remove operation parameters";
          uses install-ios-xe-oper:install-op-remove-param;
        }
      }
      case install-op-cancel {
        container cancel-param {
          description
            "Install cancel operation parameters";
          uses install-ios-xe-oper:install-op-cancel-param;
        }
      }
      case install-op-set-default {
        container set-default-param {
          description
            "Install set-default operation parameters";
          uses install-ios-xe-oper:install-op-set-default-param;
        }
      }
      case install-op-download {
        container download-param {
          description
            "Install download operation parameters";
          uses install-ios-xe-oper:install-op-download-param;
        }
      }
    }
  }

  grouping txn-sub-sts-key {
    description
      "Time sequence for transaction status changes";
    leaf timestamp {
      type yang:date-and-time;
      description
        "Timestamp when particular status was reported";
    }
  }

  grouping txn-sub-sts-val {
    description
      "Install transaction sub-status value";
    leaf txn-sub-state {
      type install-event-types-ios-xe:install-sub-state;
      description
        "Install transaction sub-status reported for timestamp";
    }
  }

  grouping install-transaction-summary-key {
    description
      "Install location reporting sub status for install operation";
    leaf fru {
      type common-types-ios-xe:fru-type;
      description
        "Field replaceable unit type";
    }
    leaf slotnum {
      type uint16;
      description
        "Slot number";
    }
    leaf baynum {
      type uint16;
      description
        "Bay number";
    }
    leaf chassisnum {
      type uint16;
      description
        "Chassis number";
    }
    leaf txn-id {
      type uint32;
      description
        "Transaction id corresponding to status";
    }
  }

  grouping install-transaction-summary {
    description
      "Install transaction summary";
    leaf start-time {
      type yang:date-and-time;
      description
        "Start time for transaction";
    }
    leaf end-time {
      type yang:date-and-time;
      description
        "End time for transaction";
    }
    leaf txn-cmd {
      type install-oper-types-ios-xe:install-txn-cmd;
      description
        "Install transaction command";
    }
    leaf txn-status {
      type install-oper-types-ios-xe:install-txn-sts;
      description
        "Install transaction status";
    }
    leaf txn-sub-state {
      type install-event-types-ios-xe:install-sub-state;
      description
        "Install transaction sub-status";
    }
    list install-txn-sub-sts-log {
      key "timestamp";
      description
        "Install transaction sub state update details";
      uses install-ios-xe-oper:txn-sub-sts-key;
      uses install-ios-xe-oper:txn-sub-sts-val;
    }
  }

  grouping install-location-info {
    description
      "Install operational information for install location";
    list install-packages {
      key "pkg-dir pkg-name";
      description
        "Install package information";
      uses install-ios-xe-oper:install-package-path;
      uses install-ios-xe-oper:install-package-info;
    }
    list install-version-info {
      key "version version-extension";
      description
        "Install version information";
      uses install-ios-xe-oper:install-version-key;
      uses install-ios-xe-oper:install-version-file;
    }
    list install-version-state-info {
      key "version-state";
      description
        "Install version state information";
      uses install-ios-xe-oper:install-version-state-key;
      uses install-ios-xe-oper:install-version-key;
    }
    container oper-state {
      description
        "Install operational state information";
      uses install-ios-xe-oper:install-oper-state;
    }
    list install-rbk-info {
      key "rbk-id";
      description
        "Install rollback points information";
      uses install-ios-xe-oper:install-rollback-point;
    }
    list install-rbk-label {
      key "rbk-label";
      description
        "Install rollback labels information";
      uses install-ios-xe-oper:install-rollback-label;
    }
    list install-profile {
      key "name";
      description
        "Install profiles information";
      uses install-ios-xe-oper:install-profile;
    }
    container issu-oper-state {
      description
        "ISSU operational state information";
      uses install-ios-xe-oper:install-issu-oper-state;
    }
  }

  grouping install-package-path {
    description
      "Install package path";
    leaf pkg-dir {
      type string;
      description
        "Package directory";
    }
    leaf pkg-name {
      type string;
      description
        "Package name";
    }
  }

  grouping install-package-data {
    description
      "Package data";
    leaf pkg-name {
      type string;
      description
        "Package name";
    }
    leaf version {
      type string;
      description
        "Version";
    }
    leaf checksum {
      type string;
      description
        "Checksum";
    }
    leaf pkg-size {
      type uint64;
      units "bytes";
      description
        "Package size in bytes";
    }
    leaf verify-status {
      type install-ios-xe-oper:install-package-verify-status;
      description
        "Package verification status";
    }
    leaf timestamp {
      when "(parent::node()/parent::node()[local-name() = 'install-packages'])";
      type yang:date-and-time;
      description
        "Timestamp reflecting when package was copied on device";
    }
    choice pkg-type-choice {
      description
        "Package type";
      case install-pkg-img {
        container img-attr {
          when "(../verify-status = 'install-package-verify-ok')";
          description
            "Image attributes";
          uses install-ios-xe-oper:install-img-attr;
        }
      }
      case install-pkg-smu {
        container smu-attr {
          when "(../verify-status = 'install-package-verify-ok')";
          description
            "Software Maintenance Upgrade attributes";
          uses install-ios-xe-oper:install-smu-attr;
        }
      }
      case install-pkg-subpkg {
        container subpkg-attr {
          when "(../verify-status = 'install-package-verify-ok')";
          description
            "Sub-package attributes";
          uses install-ios-xe-oper:install-subpkg-attr;
        }
      }
      case install-pkg-dmp {
        container dmp-attr {
          when "(../verify-status = 'install-package-verify-ok')";
          description
            "Data Model Package attributes";
          uses install-ios-xe-oper:install-smu-attr;
        }
      }
      case install-pkg-apsp {
        container apsp-attr {
          when "(../verify-status = 'install-package-verify-ok')";
          description
            "Access Point Service Pack attributes";
          uses install-ios-xe-oper:install-smu-attr;
        }
      }
      case install-pkg-apdp {
        container apdp-attr {
          when "(../verify-status = 'install-package-verify-ok')";
          description
            "Access Point Device Pack attributes";
          uses install-ios-xe-oper:install-smu-attr;
        }
      }
      case install-pkg-pkg {
        container pkg-attr {
          when "(../verify-status = 'install-package-verify-ok')";
          description
            "Package attributes";
          uses install-ios-xe-oper:install-img-attr;
        }
      }
    }
  }

  grouping install-packages {
    description
      "Install package info";
    container pkg-data {
      description
        "Package data";
      uses install-ios-xe-oper:install-package-data;
    }
    list install-included-packages {
      key "inc-version inc-pkg-name";
      description
        "Included package information";
      uses install-ios-xe-oper:install-include-pkg-key;
      uses install-ios-xe-oper:install-package-data;
    }
  }

  grouping install-package-data-key {
    description
      "Package data key";
    leaf version {
      type string;
      description
        "Version";
    }
    leaf pkg-name {
      type string;
      description
        "Package name";
    }
  }

  grouping install-include-pkg-key {
    description
      "Package data";
    leaf inc-version {
      type string;
      description
        "Version";
    }
    leaf inc-pkg-name {
      type string;
      description
        "Package name";
    }
  }

  grouping install-package-info {
    description
      "Install top package info";
    leaf ios-dir {
      type string;
      description
        "IOS directory path of package";
    }
    container pkg-data {
      when "(../pkg-action != 'install-package-action-defer-delete')";
      description
        "Package data";
      uses install-ios-xe-oper:install-package-data;
    }
    list install-related-packages {
      when "(../pkg-action != 'install-package-action-defer-delete')";
      key "version pkg-name";
      description
        "Included package information";
      uses install-ios-xe-oper:install-package-data-key;
      uses install-ios-xe-oper:install-packages;
    }
    leaf cisco-image-name {
      type string;
      description
        "Cisco provided name to package when published";
    }
    leaf pkg-action {
      type install-ios-xe-oper:install-package-info-action;
      description
        "Action to be performed on this package";
    }
  }

  grouping install-pkg-state-key {
    description
      "Install package state key";
    leaf package-type {
      type install-ios-xe-oper:install-package-type;
      description
        "Package type";
    }
    leaf pkg-dir {
      type string;
      description
        "Package directory";
    }
    leaf pkg-name {
      type string;
      description
        "Package name";
    }
  }

  grouping install-pkg-state-info {
    description
      "Install package state information";
    leaf package-state {
      type install-ios-xe-oper:install-package-state;
      description
        "Package state";
    }
  }

  grouping install-version-key {
    description
      "Install version key";
    leaf version {
      type string;
      description
        "Software image version";
    }
    leaf version-extension {
      type string;
      description
        "Extended version octet to differentiate base images with same release version";
    }
  }

  grouping install-version-file {
    description
      "Install version file information";
    leaf is-default {
      type boolean;
      description
        "Is this default version";
    }
    leaf previous {
      type install-ios-xe-oper:install-version-state;
      description
        "Is this previous version";
    }
    leaf current {
      type install-ios-xe-oper:install-version-state;
      description
        "Is this current version";
    }
    leaf src-filename {
      type string;
      description
        "Source file name";
    }
    leaf src-checksum {
      type string;
      description
        "Source file checksum";
    }
    list install-package-state-info {
      key "package-type pkg-dir pkg-name";
      description
        "Install package state information";
      uses install-ios-xe-oper:install-pkg-state-key;
      uses install-ios-xe-oper:install-pkg-state-info;
    }
    leaf ctrl-ver {
      type string;
      description
        "Compatible controller version";
    }
    leaf commit-type {
      type install-ios-xe-oper:install-commit-type;
      description
        "Commit trigger for version";
    }
    leaf timestamp {
      type yang:date-and-time;
      description
        "Timestamp for install version entry";
    }
    leaf cisco-image-name {
      type string;
      description
        "Cisco provided name to package when published";
    }
  }

  grouping install-version-state-key {
    description
      "Install version state key";
    leaf version-state {
      type install-ios-xe-oper:install-version-state;
      description
        "Version state";
    }
  }

  grouping install-rollback-point {
    description
      "Install rollback point information";
    leaf rbk-id {
      type uint32;
      description
        "Rollback identifier";
    }
    leaf date-created {
      type yang:date-and-time;
      description
        "Date of creation of rollback point";
    }
    leaf pkg-commit-type {
      type install-ios-xe-oper:install-package-type;
      description
        "Type of commit that created the rollback point";
    }
    leaf reload-required {
      type boolean;
      description
        "Is reload required to rollback to this point";
    }
    leaf is-valid {
      type boolean;
      description
        "Is rollback point valid";
    }
    leaf rbk-label {
      type string;
      description
        "Label for this rollback point";
    }
    leaf boot-mode {
      type install-ios-xe-oper:install-mode;
      description
        "Boot mode when rollback point was created";
    }
    container base-version {
      description
        "Base image version for the rollback point";
      uses install-ios-xe-oper:install-version-key;
    }
    list install-pkg-state {
      key "package-type pkg-dir pkg-name";
      description
        "Install package state information for this rollback point";
      uses install-ios-xe-oper:install-pkg-state-key;
      uses install-ios-xe-oper:install-pkg-state-info;
    }
  }

  grouping install-rollback-label {
    description
      "Install rollback label information";
    leaf rbk-label {
      type string;
      description
        "Rollback label information for the rollback point";
    }
    leaf descr {
      type string;
      description
        "Description for the rollback point";
    }
    leaf rbk-id {
      type uint32;
      description
        "Rollback identifier for the rollback point";
    }
  }

  grouping install-rollback-profile-info {
    description
      "Install rollback profile information";
    leaf rbk-id {
      type uint32;
      description
        "Rollback identifier for the given profile name";
    }
  }

  grouping install-profile {
    description
      "Install profile information";
    leaf name {
      type string;
      description
        "Name of the install profile";
    }
    leaf descr {
      type string;
      description
        "Description of the install profile";
    }
    choice profile-type-choice {
      description
        "Type of profile";
      case install-profile-rollback {
        container rbk-profile-info {
          description
            "Rollback profile information";
          uses install-ios-xe-oper:install-rollback-profile-info;
        }
      }
    }
  }

  container install-oper-data {
    config false;
    description
      "Install manager operational data";
    list install-oper {
      key "start-time op-uuid op-id";
      description
        "Install operations under execution on device";
      uses install-ios-xe-oper:install-op-key;
      uses install-ios-xe-oper:install-operation;
    }
    list install-oper-hist {
      key "start-time op-uuid op-id";
      description
        "Install operations history on device";
      uses install-ios-xe-oper:install-op-key;
      uses install-ios-xe-oper:install-operation;
    }
    list install-location-information {
      key "fru slot bay chassis";
      description
        "Install locations which contain install specific details";
      uses common-types-ios-xe:internal-location;
      uses install-ios-xe-oper:install-location-info;
    }
  }
}
