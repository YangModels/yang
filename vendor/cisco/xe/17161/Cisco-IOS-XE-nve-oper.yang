module Cisco-IOS-XE-nve-oper {
  yang-version 1.1;
  namespace "http://cisco.com/ns/yang/Cisco-IOS-XE-nve-oper";
  prefix nve-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Network Virtualization Element operational data.
     Copyright (c) 2024 by Cisco Systems, Inc.
     All rights reserved.";

  revision 2024-07-01 {
    description
      "Initial revision";
    reference
      "1.0.0";
    cisco-semver:module-version "1.0.0";
  }

  typedef nve-encap-type {
    type enumeration {
      enum nve-encap-none {
        value 0;
        description
          "No Network Virtualization Element encapsulation";
      }
      enum nve-encap-vxlan-ipv4 {
        value 1;
        description
          "VXLAN IPv4 encapsulation";
      }
      enum nve-encap-nvgre {
        value 2;
        description
          "Network Virtualization GRE encapsulation";
      }
      enum nve-encap-vxlan-ipv6 {
        value 3;
        description
          "VXLAN IPv6 encapsulation";
      }
      enum nve-encap-vxlan-dual {
        value 4;
        description
          "VXLAN dual encapsulation";
      }
      enum nve-encap-vxlan-dual-prefer-ipv4 {
        value 5;
        description
          "VXLAN dual encapsulation prefer IPv4";
      }
    }
    description
      "Network Virtualization Element Encapsulation type";
  }

  typedef nve-encap-mcast-type {
    type enumeration {
      enum nve-encap-mcast-none {
        value 0;
        description
          "No Network Virtualization Element Multicast";
      }
      enum nve-encap-mcast-ipv4 {
        value 1;
        description
          "Network Virtualization Element IPv4 Multicast";
      }
      enum nve-encap-mcast-ipv6 {
        value 2;
        description
          "Network Virtualization Element IPv6 Multicast";
      }
    }
    description
      "Network Virtualization Element Multicast type";
  }

  typedef nve-state-type {
    type enumeration {
      enum nve-state-invalid {
        value 0;
        description
          "Invalid Network Virtualization Element State";
      }
      enum nve-state-down {
        value 1;
        description
          "Network Virtualization Element down";
      }
      enum nve-state-up {
        value 2;
        description
          "Network Virtualization Element up";
      }
    }
    description
      "Network Virtualization Element State";
  }

  typedef nve-vni-state-type {
    type enumeration {
      enum nve-vni-state-invalid {
        value 0;
        description
          "Invalid Virtual Network Interface state";
      }
      enum nve-vni-state-create {
        value 1;
        description
          "Virtual Network Interface created";
      }
      enum nve-vni-state-up {
        value 2;
        description
          "Virtual Network Interface up";
      }
      enum nve-vni-state-down {
        value 3;
        description
          "Virtual Network Interface down";
      }
      enum nve-vni-state-delete {
        value 4;
        description
          "Virtual Network Interface deleted";
      }
      enum nve-vni-state-admindown {
        value 5;
        description
          "Virtual Network Interface admin down";
      }
      enum nve-vni-state-bd-admindn {
        value 6;
        description
          "Virtual Network Interface BD admin down";
      }
    }
    description
      "Virtual Network Interface State";
  }

  typedef nve-vni-svi-state-type {
    type enumeration {
      enum nve-vni-svi-state-invalid {
        value 0;
        description
          "Invalid Switch Virtual Interface State";
      }
      enum nve-vni-svi-state-down {
        value 1;
        description
          "Switch Virtual Interface down";
      }
      enum nve-vni-svi-state-up {
        value 2;
        description
          "Switch Virtual Interface up";
      }
    }
    description
      "Switch Virtual Interface operational state";
  }

  typedef nve-vni-type {
    type enumeration {
      enum nve-vni-type-l2 {
        value 0;
        description
          "L2 Virtual Network Interface";
      }
      enum nve-vni-type-l3 {
        value 1;
        description
          "L3 Virtual Network Interface";
      }
    }
    description
      "Virtual Network Interface type";
  }

  typedef nve-vni-learning-mode {
    type enumeration {
      enum nve-vni-cp-learning {
        value 0;
        description
          "Virtual Network Interface Control Plane Learning";
      }
      enum nve-vni-dp-learning {
        value 1;
        description
          "Virtual Network Interface Data Plane Learning";
      }
    }
    description
      "Virtual Network Interface Learning Mode";
  }

  typedef nve-peer-state {
    type enumeration {
      enum nve-peer-init {
        value 0;
        description
          "Peer initial state";
      }
      enum nve-peer-add-pending {
        value 1;
        description
          "Peer add pending";
      }
      enum nve-peer-add-complete {
        value 2;
        description
          "Peer added";
      }
      enum nve-peer-delete-pending {
        value 4;
        description
          "Peer delete pending";
      }
      enum nve-peer-delete-complete {
        value 16;
        description
          "Peer deleted";
      }
      enum nve-peer-add-rcvd {
        value 32;
        description
          "Peer add received";
      }
      enum nve-peer-delete-rcvd {
        value 64;
        description
          "Peer delete received";
      }
    }
    description
      "Network Virtualization Element peer state";
  }

  typedef nve-vni-replication-type {
    type enumeration {
      enum nve-vni-repl-mcast-ipv4 {
        value 0;
        description
          "Virtual Network Interface Multicast IPv4 Replication";
      }
      enum nve-vni-repl-mcast-ipv6 {
        value 1;
        description
          "Virtual Network Interface Multicast IPv6 Replication";
      }
      enum nve-vni-static-ingress-replication {
        value 2;
        description
          "Virtual Network Interface Static Ingress Replication";
      }
      enum nve-vni-bgp-ingress-replication {
        value 3;
        description
          "Virtual Network Interface BGP Ingress Replication";
      }
    }
    description
      "Virtual Network Interface Replication Type";
  }

  grouping nve-vni-oper-counters {
    description
      "Virtual Network Interfaces counters table";
    leaf vni-id {
      type uint32;
      description
        "Virtual Network Interface id";
    }
    leaf nve-id {
      type uint32;
      description
        "Network Virtualization Element id";
    }
    leaf uc-input-packets {
      type uint64;
      description
        "Unicast input packets";
    }
    leaf uc-input-bytes {
      type uint64;
      description
        "Unicast input bytes";
    }
    leaf mc-input-packets {
      type uint64;
      description
        "Multicast input packets";
    }
    leaf mc-input-bytes {
      type uint64;
      description
        "Multicast input bytes";
    }
    leaf uc-output-packets {
      type uint64;
      description
        "Unicast output packets";
    }
    leaf uc-output-bytes {
      type uint64;
      description
        "Unicast output bytes";
    }
    leaf mc-output-packets {
      type uint64;
      description
        "Multicast output packets";
    }
    leaf mc-output-bytes {
      type uint64;
      description
        "Multicast output bytes";
    }
  }

  grouping nve-vni-oper {
    description
      "Virtual Network Interface operational data";
    leaf vni-id {
      type uint32;
      description
        "Virtual Network Interface id";
    }
    leaf nve-id {
      type uint32;
      description
        "Network Virtualization Element id";
    }
    leaf vni-oper-state {
      type nve-ios-xe-oper:nve-vni-state-type;
      description
        "Virtual Network Interface operational state";
    }
    leaf vlan-id {
      type uint32;
      description
        "VLAN id";
    }
    leaf vni-type {
      type nve-ios-xe-oper:nve-vni-type;
      description
        "Virtual Network Interface type";
    }
    leaf vni-learning-mode {
      type nve-ios-xe-oper:nve-vni-learning-mode;
      description
        "VNI Learning mode";
    }
    leaf nve-vni-vrf {
      type string;
      description
        "Virtual Network Interface VRF";
    }
    leaf l3-vni-id {
      type uint32;
      description
        "L3 Virtual Network Interface id";
    }
    leaf svi-vlan-id {
      type uint32;
      description
        "VLAN id";
    }
    leaf svi-mac {
      type yang:mac-address;
      description
        "Switch Virtual Interface MAC address";
    }
    leaf local-routing {
      type boolean;
      description
        "Local routing enabled";
    }
    leaf mcast-v4-address {
      type inet:ip-address;
      description
        "Multicast IPv4 address";
    }
    leaf mcast-v6-address {
      type inet:ip-address;
      description
        "Multicast IPv6 address";
    }
    leaf trm-mdt-v4-address {
      type inet:ip-address;
      description
        "Tenant Routed Multicast Distribution Tree IPv4";
    }
    leaf trm-mdt-v6-address {
      type inet:ip-address;
      description
        "Tenant Routed Multicast Distribution Tree IPv6";
    }
    leaf repl-type {
      type nve-ios-xe-oper:nve-vni-replication-type;
      description
        "Virtual Network Interface replication type";
    }
    leaf svi-state {
      type nve-ios-xe-oper:nve-vni-svi-state-type;
      description
        "Switch Virtual Interface operational state";
    }
  }

  grouping nve-peer-oper {
    description
      "Network Virtualization Element Peer operational data";
    leaf peer-addr {
      type inet:ip-address;
      description
        "Peer IP address";
    }
    leaf nve-id {
      type uint32;
      description
        "Network Virtualization Element id";
    }
    leaf-list cp-vnis {
      type uint32;
      ordered-by user;
      description
        "Peer Virtual Network Interfaces";
    }
    leaf rmac {
      type yang:mac-address;
      description
        "Router MAC address";
    }
    leaf peer-up-time {
      type yang:date-and-time;
      description
        "Peer uptime";
    }
    leaf peer-state {
      type nve-ios-xe-oper:nve-peer-state;
      description
        "Peer state";
    }
  }

  grouping nve-oper-counters {
    description
      "Network Virtualization Element operational counters";
    leaf unit-number {
      type uint32;
      description
        "Network Virtualization Element id";
    }
    leaf uc-input-packets {
      type uint64;
      description
        "Unicast input packets";
    }
    leaf uc-input-bytes {
      type uint64;
      description
        "Unicast input bytes";
    }
    leaf mc-input-packets {
      type uint64;
      description
        "Multicast input packets";
    }
    leaf mc-input-bytes {
      type uint64;
      description
        "Multicast input bytes";
    }
    leaf uc-output-packets {
      type uint64;
      description
        "Unicast output packets";
    }
    leaf uc-output-bytes {
      type uint64;
      description
        "Unicast output bytes";
    }
    leaf mc-output-packets {
      type uint64;
      description
        "Multicast output packets";
    }
    leaf mc-output-bytes {
      type uint64;
      description
        "Multicast output bytes";
    }
    list nve-vni-oper-counters {
      key "vni-id";
      description
        "Virtual Network Interfaces counters table";
      uses nve-ios-xe-oper:nve-vni-oper-counters;
    }
  }

  grouping nve-oper {
    description
      "Network Virtualization Element Operational data";
    leaf unit-number {
      type uint32;
      description
        "Network Virtualization Element unit number";
    }
    leaf nve-if {
      type string;
      description
        "Network Virtualization Element interface";
    }
    leaf admin-state {
      type nve-ios-xe-oper:nve-state-type;
      description
        "Network Virtualization Element administrative state";
    }
    leaf oper-state {
      type nve-ios-xe-oper:nve-state-type;
      description
        "Network Virtualization Element operational state";
    }
    leaf nve-encap {
      type nve-ios-xe-oper:nve-encap-type;
      description
        "Network Virtualization Element encapsulation";
    }
    leaf nve-mcast-encap {
      type nve-ios-xe-oper:nve-encap-mcast-type;
      description
        "Network Virtualization Element multicast encapsulation";
    }
    leaf is-bgp-signal {
      type boolean;
      description
        "BGP signalling";
    }
    leaf vxlan-port {
      type uint16;
      description
        "Vxlan port";
    }
    leaf l2dp-vni-num {
      type uint32;
      description
        "Number of L2 Virtual Network Interfaces";
    }
    leaf l2cp-vni-num {
      type uint32;
      description
        "Number of CP L2 Virtual Network Interfaces";
    }
    leaf l3cp-vni-num {
      type uint32;
      description
        "Number of CP L3 Virtual Network Interfaces";
    }
    leaf src-if {
      type string;
      description
        "Network Virtualization Element source interface";
    }
    leaf src-ipv4-address {
      type inet:ipv4-address;
      description
        "IPv4 source address";
    }
    leaf src-ipv6-address {
      type inet:ipv6-address;
      description
        "IPv6 source address";
    }
    leaf src-vrf {
      type string;
      description
        "Source VRF";
    }
    leaf tunnel-if {
      type string;
      description
        "Network Virtualization Element tunnel interface";
    }
    leaf v6-tunnel-if {
      type string;
      description
        "Network Virtualization Element IPv6 tunnel interface";
    }
    list nve-vni-oper {
      key "vni-id";
      description
        "Virtual Network Interfaces table";
      uses nve-ios-xe-oper:nve-vni-oper;
    }
    list nve-peer-oper {
      key "peer-addr";
      description
        "Peers table";
      uses nve-ios-xe-oper:nve-peer-oper;
    }
  }

  container nve-oper-data {
    config false;
    description
      "Network Virtualization Element operational data";
    list nve-oper {
      key "unit-number";
      description
        "Network Virtualization Element operational data";
      uses nve-ios-xe-oper:nve-oper;
    }
    list nve-oper-counters {
      key "unit-number";
      description
        "Network Virtualization Element counters";
      uses nve-ios-xe-oper:nve-oper-counters;
    }
  }
}
