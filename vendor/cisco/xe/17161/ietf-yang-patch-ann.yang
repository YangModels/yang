module ietf-yang-patch-ann {
  namespace "urn:dummy";
  prefix dummy;

  import tailf-common {
    prefix tailf;
  }

  organization "Tail-f Systems";

  description
    "Annotation module for ietf-yang-patch.

     Copyright 2019 Cisco Systems, Inc.
     All rights reserved.
     Permission is hereby granted to redistribute this file without
     modification.";

  tailf:annotate-module 'ietf-yang-patch' {
    tailf:export rest;
    tailf:export netconf;
  }
}
