module Cisco-IOS-XE-vlan {
  yang-version 1.1;
  namespace "http://cisco.com/ns/yang/Cisco-IOS-XE-vlan";
  prefix ios-vlan;

  import cisco-semver {
    prefix cisco-semver;
  }
  import ietf-inet-types {
    prefix inet;
  }
  import Cisco-IOS-XE-native {
    prefix ios;
  }
  import Cisco-IOS-XE-l2vpn {
    prefix ios-l2vpn;
  }
  import Cisco-IOS-XE-vtp {
    prefix ios-vtp;
  }
  import Cisco-IOS-XE-features {
    prefix ios-features;
  }
  import Cisco-IOS-XE-device-tracking {
    prefix ios-dt;
  }
  import Cisco-IOS-XE-nd {
    prefix ios-nd;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Virtual LANs (VLAN) Yang Model.
     Copyright (c) 2016-2019, 2024 by Cisco Systems, Inc.
     All rights reserved.";

  revision 2024-11-01 {
    description
      "- Added support for ra-throttler policy
       - Added support for arp to configuration-entry
       - Update must constraint for vlan 1 to configure its name as 'default'";
    cisco-semver:module-version "8.1.0";
  }
  revision 2024-07-01 {
    description
      "- added must constraint for non-empty vlan-lists to vlan group
       - Change the description of vlan-lists and vlan-list id
       - Update must constraint for sisf features to allow 'default' policy
       - added must constraint to vlan id
       - removed must constraint from vlan id";
    cisco-semver:module-version "8.0.0";
  }
  revision 2024-03-01 {
    description
      "- obsolete the deprecated vlan-list";
    cisco-semver:module-version "7.0.0";
  }
  revision 2023-07-01 {
    description
      "- Added support for routing-proxy and dad-proxy
       - Added evi-member new container to support new evpn-instance CLI";
    cisco-semver:module-version "6.0.0";
  }
  revision 2022-11-01 {
    description
      "- Update yang-version to 1.1
       - Added if-feature statement to disable IPv6 DHCP Guard commands on platforms where this feature is not supported";
    cisco-semver:module-version "5.0.0";
  }
  revision 2022-07-01 {
    description
      "- Add limitation to forbid vlan 1 to configure name
       - Add dependency between vlan name and vlan id";
    cisco-semver:module-version "4.1.0";
  }
  revision 2022-03-01 {
    description
      "- Added protected leaf for member vni
       - Added if-features around the raguard to selective enable/disable";
    cisco-semver:module-version "4.0.0";
  }
  revision 2021-11-01 {
    description
      "- Added configuration-entry list to vlan so that vlan-id accepts a range string
       - Deprecated configuration list";
    cisco-semver:module-version "3.2.0";
  }
  revision 2021-03-01 {
    description
      "- Added the missing commands to fill the gap between CLI and Yang for SISF";
    cisco-semver:module-version "3.1.0";
  }
  revision 2020-11-01 {
    description
      "- Added status obsolete for the 'container lldp' node under vlan-list";
    cisco-semver:module-version "3.0.1";
  }
  revision 2020-03-01 {
    description
      "- added some tailf for deprecated leafs
       - VACL access-map list key changes with 'name' and 'value'";
    cisco-semver:module-version "2.0.0";
  }
  revision 2019-07-01 {
    description
      "- Establish semantic version baseline
       - Added 'member access-vfi' to 'vlan configuration'
       - Added support for 'ipv6 nd raguard' under 'vlan configuration *'
       - Support for service policy in VLAN and fixed VLAN filter as range-list
       - Add support for device-tracking";
    cisco-semver:module-version "1.0.0";
  }
  revision 2018-11-07 {
    description
      "Cleanup spelling errors in description statements";
  }
  revision 2018-10-27 {
    description
      "Remove type string for vlan id";
  }
  revision 2018-04-23 {
    description
      "Delete the extra call to interface-common-grouping";
  }
  revision 2018-03-13 {
    description
      "Add support for Evpn";
  }
  revision 2017-10-02 {
    description
      "Add support for 'ipv6 nd suppress' and 'vlan group *'";
  }
  revision 2017-05-31 {
    description
      "Add vtp-version and vlan name dependency, and service-routing dependency support";
  }
  revision 2017-04-13 {
    description
      "Add service-routing/redistribute support";
  }
  revision 2017-02-07 {
    description
      "Initial revision";
  }

  grouping config-interface-vlan-grouping {
    container private-vlan {
      if-feature "ios-features:private-vlan";
      description
        "Configure private VLAN SVI interface settings";
      leaf mapping {
        description
          "Set the private VLAN SVI interface mapping";
        type string;
      }
    }
    container service-routing {
      description
        "Service Routing in Interface Mode";
      container mdns-sd {
        description
          "Service-Routing mdns-sd configuration in interface mode";
        presence "true";
        list service-policy {
          description
            "Configure CPL Service Policy";
          key "dir";
          leaf dir {
            description
              "Bound Filtering Interface";
            type enumeration {
              enum IN;
              enum OUT;
            }
          }
          leaf name {
            description
              "service policy Name in Interface";
            type string;
          }
        }
        container redistribute {
          description
            "Redistribution of services";
          leaf mdns-sd {
            description
              "Redistribution of services";
            type empty;
          }
          leaf withdraw-only {
            description
              "Enable redistribution only for service withdraw";
            type empty;
          }
        }
      }
    }
    container glbp {
      description
        "Gateway Load Balancing Protocol interface commands";
      list range {
        key "range";
        leaf range {
          description
            "Group number";
          type uint16 {
            range "0..1023";
          }
        }
        container forwarder {
          description
            "Forwarder configuration";
          container preempt {
            description
              "Overthrow lower priority active forwarders";
            presence "true";
            container delay {
              description
                "Wait before preempting";
              leaf minimum {
                description
                  "Number of seconds for minimum delay";
                type uint16 {
                  range "0..3600";
                }
              }
            }
          }
        }
        container ip {
          description
            "Enable group and set virtual IP address";
          presence "true";
          list ipv4 {
            key "ipv4";
            leaf ipv4 {
              description
                "Virtual IP address";
              type inet:ipv4-address;
            }
          }
        }
        container preempt {
          description
            "Overthrow lower priority designated routers";
          presence "true";
          container delay {
            description
              "Wait before preempting";
            leaf minimum {
              description
                "Number of seconds for minimum delay";
              type uint16 {
                range "0..3600";
              }
            }
          }
        }
        leaf priority {
          description
            "Priority value";
          type uint8 {
            range "1..255";
          }
        }
        container weighting {
          description
            "Gateway weighting and tracking";
          list value {
            description
              "Weighting maximum value";
            key "value";
            leaf value {
              type int8;
            }
            leaf upper {
              type int8;
            }
            leaf lower {
              type int8;
            }
          }
          container track {
            description
              "Interface tracking";
            list range {
              key "range";
              leaf range {
                description
                  "Tracked object";
                type uint16 {
                  range "1..1000";
                }
              }
              leaf decrement {
                description
                  "Decrement value";
                type uint8 {
                  range "1..255";
                }
              }
            }
          }
        }
        container timers {
          description
            "Adjust GLBP timers";
          container msec {
            description
              "Specify hello interval in milliseconds";
            list range {
              key "range";
              leaf range {
                description
                  "Hello interval in milliseconds";
                type uint16 {
                  range "50..60000";
                }
              }
              leaf range0 {
                description
                  "Hold time in seconds";
                type uint8 {
                  range "1..180";
                }
              }
            }
          }
        }
        leaf name {
          description
            "Redundancy name";
          type string;
        }
      }
    }
  }

  grouping config-vlan-grouping {
    list access-map {
      description
        "Create vlan access-map or enter vlan access-map command mode";
      key "name value";
      leaf name {
        description
          "Vlan access map tag";
        type string;
      }
      leaf value {
        description
          "Sequence to insert to/delete from existing vlan access-map entry";
        type uint16 {
          range "0..65535";
        }
      }
      container match {
        description
          "Match values.";
        container ipv6 {
          description
            "IPv6 based match";
          leaf-list address {
            description
              "Match IPv6 address to access control.";
            ordered-by user;
            type string;
          }
        }
        container ip {
          description
            "IP based match";
          leaf-list address {
            type string;
          }
        }
      }
      leaf action {
        description
          "Take the action";
        type enumeration {
          enum drop;
          enum forward;
        }
        default "forward";
      }
    }
    list configuration-entry {
      description
        "vlan feature configuration mode";
      key "vlan-id";
      leaf vlan-id {
        description
          "VLAN ID List Eg. 1-10,15";
        type string {
          pattern '(((409[0-4]|40[0-8][0-9]|[1-3][0-9]{3}|[1-9][0-9]{1,2}|[1-9])(\-(409[0-4]|40[0-8][0-9]|[1-3][0-9]{3}|[1-9][0-9]{1,2}|[1-9]))?)(,((409[0-4]|40[0-8][0-9]|[1-3][0-9]{3}|[1-9][0-9]{1,2}|[1-9])(\-(409[0-4]|40[0-8][0-9]|[1-3][0-9]{3}|[1-9][0-9]{1,2}|[1-9]))?))*)';
        }
      }
      container ip {
        description
          "ip root chain";
        container flow {
          description
            "vlan NetFlow configuration commands";
          list monitor {
            description
              "Apply a Flow Monitor";
            key "flow-monitor";
            leaf flow-monitor {
              description
                "User defined";
              type string;
            }
            leaf input {
              type empty;
            }
            leaf output {
              type empty;
            }
          }
        }
      }
      container device-tracking {
        description
          "Configure device-tracking on the VLAN";
        presence "Attach default device-tracking policy on vlan";
        leaf attach-policy {
          description
            "Apply a policy for feature device-tracking";
          type string;
          must "/ios:native/ios:device-tracking/ios-dt:policy[ios-dt:word = current()] or .='default'" {
            error-message "Create policy first, then attach policy; Detach policy first then remove policy";
          }
        }
      }
      container ipv6 {
        description
          "ipv6 root chain";
        container nd {
          description
            "IPv6 nd configuration commands";
          container suppress {
            description
              "Configure ND suppress on the vlan";
            presence "true";
            leaf attach-policy {
              description
                "Apply a policy for feature ND suppress";
              type string;
            }
          }
          container raguard {
            if-feature "ios-features:raguard";
            description
              "Configure ipv6 raguard on the vlan";
            leaf raguard {
              type empty;
            }
            leaf attach-policy {
              description
                "Apply a policy for feature ipv6 raguard";
              type string;
              must "/ios:native/ios:ipv6/ios:nd/ios-nd:raguard/ios-nd:policy[ios-nd:raguard-policy-name=current()] or .='default'" {
                error-message "Global ipv6 nd raguard policy, must be created first and deleted last";
              }
            }
          }
          container ra-throttler {
            if-feature "ios-features:ra-throttler";
            description
              "Configure ipv6 ra-throttler on the vlan";
            leaf ra-throttler {
              type empty;
            }
            leaf attach-policy {
              description
                "Apply a policy for feature ipv6 ra-throttler";
              type string;
              must "(/ios:native/ios:ipv6/ios:nd/ios-nd:ra-throttler/ios-nd:policy[ios-nd:policy-name=current()]) or .='default'" {
                error-message "Create RA throttler policy first, then attach policy; Detach policy from interface before removing the policy";
              }
            }
          }
          leaf routing-proxy {
            if-feature "ios-features:routing-proxy";
            description
              "Configure Routing Proxy on the interface";
            type empty;
          }
          leaf dad-proxy {
            if-feature "ios-features:dad-proxy";
            description
              "Configure DAD proxy on the interface";
            type empty;
          }
        }
        container dhcp {
          description
            "IPv6 dhcp configuration commands";
          container guard {
            if-feature "ios-features:dhcp-guard";
            description
              "Configure IPv6 DHCP guard on the vlan";
            presence "true";
            leaf attach-policy {
              description
                "Apply a policy for feature DHCP Guard";
              type string;
            }
          }
        }
        container destination-guard {
          description
            "Configure destination guard on the vlan";
          presence "true";
          leaf attach-policy {
            description
              "Apply a policy for feature Destination Guard";
            type string;
          }
        }
      }
      container member {
        container evi-member {
          if-feature "ios-features:l2vpn";
          description
            "Ethernet Virtual Private Network (EVPN) instance member";
          container evpn-instance {
            description
              "Ethernet Virtual Private Network (EVPN) instance";
            presence "true";
            choice evi-type-choice {
              case auto-evi-case {
                container auto-evi-config {
                  description
                    "Auto EVPN instance member";
                  leaf profile {
                    description
                      "The profile which auto EVPN instance member created from";
                    must '/ios:native/ios:l2vpn/ios-l2vpn:evpn_cont/ios-l2vpn:l2-profile/ios-l2vpn:evpn/ios-l2vpn:profile/ios-l2vpn:profile-name-list[ios-l2vpn:name = current()]' {
                      error-message "EVPN L2 Profile does not exist";
                    }
                    type string;
                  }
                  leaf protected {
                    description
                      "Enable local peer to peer blocking";
                    when "(not(../profile) and /ios:native/ios:l2vpn/ios-l2vpn:evpn_cont/ios-l2vpn:l2-profile/ios-l2vpn:evpn/ios-l2vpn:profile/ios-l2vpn:default/ios-l2vpn:encapsulation = 'vxlan')or ((../profile) and /ios:native/ios:l2vpn/ios-l2vpn:evpn_cont/ios-l2vpn:l2-profile/ios-l2vpn:evpn/ios-l2vpn:profile/ios-l2vpn:profile-name-list[ios-l2vpn:name = current()/../profile]/ios-l2vpn:encapsulation = 'vxlan')";
                    type empty;
                  }
                }
              }
              case manual-evi-case {
                container manual-evi-config {
                  description
                    "Manual EVPN instance member";
                  leaf evi {
                    description
                      "EVPN instance number";
                    type uint16 {
                      range "1..65535";
                    }
                  }
                  leaf vni {
                    description
                      "VxLAN VNI value";
                    must '../evi' {
                      error-message "Member evi must be specifed before specifying vni value";
                    }
                    type uint32 {
                      range "4096..16777215";
                    }
                  }
                  leaf protected {
                    description
                      "Enable local peer to peer blocking";
                    must '../vni' {
                      error-message "The protected option is only available for Vxlan encapsulation when VNI value is specified";
                    }
                    type empty;
                  }
                }
              }
            }
          }
        }
        container evpn-instance {
          status deprecated;
          description
            "Ethernet Virtual Private Network (EVPN)";
          leaf evpn-instance {
            status deprecated;
            type uint16 {
              range "1..65535";
            }
          }
          leaf vni {
            status deprecated;
            description
              "VxLAN VNI value";
            type uint32 {
              range "4096..16777215";
            }
          }
          leaf protected {
            status deprecated;
            description
              "Enable local peer to peer blocking";
            type empty;
          }
        }
        leaf vni {
          description
            "VxLAN VNI value";
          type uint32 {
            range "4096..16777215";
          }
        }
        leaf access-vfi {
          description
            "Enter VFI name";
          type string;
        }
      }
      leaf arp {
        if-feature "ios-features:ewlc-platform";
        description
          "ARP settings on VLAN";
        type enumeration {
          enum broadcast;
        }
      }
    }
    list configuration {
      status deprecated;
      description
        "vlan feature configuration mode (DEPRECATED, use configuration-entry)";
      key "vlan-id";
      leaf vlan-id {
        status deprecated;
        description
          "VLAN ID List Eg. 1-10,15";
        type uint16 {
          range "1..4094";
        }
      }
      container ip {
        description
          "ip root chain";
        container flow {
          description
            "vlan NetFlow configuration commands";
          list monitor {
            status deprecated;
            description
              "Apply a Flow Monitor";
            key "flow-monitor";
            leaf flow-monitor {
              status deprecated;
              description
                "User defined";
              type string;
            }
            leaf input {
              status deprecated;
              type empty;
            }
            leaf output {
              status deprecated;
              type empty;
            }
          }
        }
      }
      container device-tracking {
        status deprecated;
        description
          "Configure device-tracking on the VLAN";
        presence "Attach default device-tracking policy on vlan";
        leaf attach-policy {
          status deprecated;
          description
            "Apply a policy for feature device-tracking";
          type string;
          must '/ios:native/ios:device-tracking/ios-dt:policy[ios-dt:word = current()]' {
            error-message "Create policy first, then attach policy; Detach policy first then remove policy";
          }
        }
      }
      container ipv6 {
        description
          "ipv6 root chain";
        container nd {
          description
            "IPv6 nd configuration commands";
          container suppress {
            status deprecated;
            description
              "Configure ND suppress on the vlan";
            presence "true";
            leaf attach-policy {
              status deprecated;
              description
                "Apply a policy for feature ND suppress";
              type string;
            }
          }
          container raguard {
            if-feature "ios-features:raguard";
            description
              "Configure ipv6 raguard on the vlan";
            leaf raguard {
              status deprecated;
              type empty;
            }
            leaf attach-policy {
              status deprecated;
              description
                "Apply a policy for feature ipv6 raguard";
              must '/ios:native/ios:ipv6/ios:nd/ios-nd:raguard/ios-nd:policy[ios-nd:raguard-policy-name=current()]' {
                error-message "Global ipv6 nd raguard policy, must be created first and deleted last";
              }
              type string;
            }
          }
        }
        container dhcp {
          description
            "IPv6 dhcp configuration commands";
          container guard {
            if-feature "ios-features:dhcp-guard";
            status deprecated;
            description
              "Configure IPv6 DHCP guard on the vlan";
            presence "true";
            leaf attach-policy {
              status deprecated;
              description
                "Apply a policy for feature DHCP Guard";
              type string;
            }
          }
        }
        container destination-guard {
          status deprecated;
          description
            "Configure destination guard on the vlan";
          presence "true";
          leaf attach-policy {
            status deprecated;
            description
              "Apply a policy for feature Destination Guard";
            type string;
          }
        }
      }
      container member {
        container evpn-instance {
          status deprecated;
          description
            "Ethernet Virtual Private Network (EVPN)";
          leaf evpn-instance {
            status deprecated;
            type uint16 {
              range "1..65535";
            }
          }
          leaf vni {
            status deprecated;
            description
              "VxLAN VNI value";
            type uint32 {
              range "4096..16777215";
            }
          }
        }
        leaf vni {
          status deprecated;
          description
            "VxLAN VNI value";
          type uint32 {
            range "4096..16777215";
          }
        }
        leaf access-vfi {
          status deprecated;
          description
            "Enter VFI name";
          type string;
        }
      }
    }
    list filter {
      description
        "Apply a VLAN Map";
      key "word";
      leaf word {
        type string;
      }
      leaf-list vlan-lists {
        description
          "VLANs to apply filter to";
        type uint16 {
          range "1..4094";
        }
      }
      leaf vlan-list {
        status obsolete;
        description
          "VLANs to apply filter to (OBSOLETE)";
        type union {
          type uint16 {
            range "1..4094";
          }
          type string;
        }
      }
    }
    container accounting {
      description
        "VLAN accounting configuration";
      presence "true";
      leaf input {
        description
          "Input accounting";
        type empty;
      }
      leaf output {
        description
          "Output accounting";
        type empty;
      }
    }
    container internal {
      description
        "internal VLAN";
      container allocation {
        description
          "internal VLAN allocation";
        leaf policy {
          type enumeration {
            enum ascending;
            enum descending;
          }
        }
      }
    }
    container dot1q {
      description
        "dot1q parameters";
      container tag {
        description
          "tag parameters";
        leaf native {
          description
            "tag native vlan";
          type empty;
        }
      }
    }
    container access-log {
      description
        "Configure VACL logging";
      leaf maxflow {
        description
          "Set vacl logging maximum flow number";
        type uint16 {
          range "0..2048";
        }
      }
      leaf ratelimit {
        description
          "Set vacl logging rate limiter";
        type uint16 {
          range "10..5000";
        }
      }
      leaf threshold {
        description
          "Set vacl log-update threshold";
        type uint32 {
          range "0..2147483647";
        }
      }
    }
    list group {
      description
        "Create a vlan group";
      key "name";
      must 'vlan-lists/.' {
        error-message "A VLAN group must have at least one VLAN in the VLAN list";
      }
      leaf name {
        description
          "Group name starts with alphabet";
        type string;
      }
      leaf-list vlan-lists {
        description
          "VLANs in the vlan group";
        type uint16 {
          range "1..4094";
        }
      }
      list vlan-list {
        status obsolete;
        description
          "List of vlans in this group (OBSOLETE)";
        key "vlan-id";
        leaf vlan-id {
          status obsolete;
          description
            "a single VLAN id (allowed value range 1-4094)or Comma-separated VLAN id range.e.g. 99 or 1-30 or  1-20,30,40-50 (OBSOLETE)";
          type union {
            type uint16 {
              range "1..4094";
            }
            type ios-types:range-string;
          }
        }
      }
    }
    list vlan-list {
      key "id";
      leaf id {
        description
          "VLAN ID";
        type uint16 {
          range "1..4094";
        }
      }
      leaf remote-span {
        description
          "Configure as Remote SPAN VLAN";
        type empty;
      }
      container private-vlan {
        if-feature "ios-features:private-vlan";
        description
          "Configure a private VLAN";
        leaf primary {
          description
            "Configure the VLAN as a primary private VLAN";
          type empty;
        }
        leaf association {
          description
            "Configure association between private VLANs";
          type string;
        }
        leaf community {
          description
            "Configure the VLAN as a community private VLAN";
          type empty;
        }
        leaf isolated {
          description
            "Configure the VLAN as an isolated private VLAN";
          type empty;
        }
      }
      leaf name {
        description
          "Ascii name of the VLAN";
        type string {
          length "1..128";
        }
        must "((/ios:native/ios:vtp/ios-vtp:version = 3 and string-length(.) <= 128) or (/ios:native/ios:vtp/ios-vtp:version <= 2 and string-length(.) <= 32)) and (not ((../id = 1) and (current() != 'default'))) and (count(/ios:native/ios:vlan/ios-vlan:vlan-list[ios-vlan:name = current()])<=1)" {
          error-message "You must disable VTPv1 and VTPv2 or switch to VTPv3 before configuring a VLAN name longer than 32 characters or default VLAN 1 may not have its name changed or different VLANs have an identical name";
        }
      }
      leaf state {
        description
          "Operational state of the VLAN";
        type enumeration {
          enum active;
          enum suspend;
        }
      }
      container lldp {
        status obsolete;
        leaf run {
          status obsolete;
          type empty;
        }
      }
      leaf uni-vlan {
        description
          "Configure a UNI VLAN";
        type enumeration {
          enum community;
          enum isolated;
        }
      }
      leaf shutdown {
        description
          "Shutdown VLAN switching";
        type empty;
      }
    }
  }

  augment "/ios:native/ios:vlan" {
    uses config-vlan-grouping;
    uses ios-dt:config-vlan-device-tracking-grouping;
  }

  augment "/ios:native/ios:interface/ios:Vlan" {
    uses config-interface-vlan-grouping {
      if-feature "ios-features:vlan";
    }
  }
}
