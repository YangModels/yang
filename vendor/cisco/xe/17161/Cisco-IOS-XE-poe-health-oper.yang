module Cisco-IOS-XE-poe-health-oper {
  yang-version 1.1;
  namespace "http://cisco.com/ns/yang/Cisco-IOS-XE-poe-health-oper";
  prefix poe-health-xe;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring power over ethernet feature in a Network Element.
     Copyright (c) 2022 by Cisco Systems, Inc.
     All rights reserved.";

  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  typedef poe-state-type {
    type enumeration {
      enum poe-state-none {
        value 0;
        description
          "None indicates the initial state of the port";
      }
      enum poe-state-shut {
        value 1;
        description
          "Port is in shut down state";
      }
      enum poe-state-detecting {
        value 2;
        description
          "Port is trying to detect a PD";
      }
      enum poe-state-detected {
        value 3;
        description
          "Port has detected PD";
      }
      enum poe-state-powering {
        value 4;
        description
          "Port is trying to power up the PD";
      }
      enum poe-state-powered {
        value 5;
        description
          "Port has powered up the PD";
      }
      enum poe-state-fault {
        value 6;
        description
          "Port has encountered a fault";
      }
      enum poe-state-sleep {
        value 7;
        description
          "PoE state is sleep";
      }
      enum poe-state-spare-detecting {
        value 8;
        description
          "Port is trying to detect PD on spare pair";
      }
      enum poe-state-spare-powering {
        value 9;
        description
          "Port is powering up the spare pair";
      }
      enum poe-state-spare-powered {
        value 10;
        description
          "Port has powered up the spare pair";
      }
    }
    description
      "State of the PoE port";
  }

  typedef poe-class-type {
    type enumeration {
      enum poe-class-none {
        value 0;
        description
          "PoE initial class value";
      }
      enum poe-class-1 {
        value 1;
        description
          "PoE class type is 1";
      }
      enum poe-class-2 {
        value 2;
        description
          "PoE class type is 2";
      }
      enum poe-class-3 {
        value 3;
        description
          "PoE class type is 3";
      }
      enum poe-class-4 {
        value 4;
        description
          "PoE class type is 4";
      }
      enum poe-class-undefined {
        value 5;
        description
          "PoE class type is undefined";
      }
      enum poe-class-0 {
        value 6;
        description
          "PoE class type is 0";
      }
      enum poe-class-current-limit {
        value 7;
        description
          "Error condition indicating invalid class";
      }
      enum poe-class-5 {
        value 8;
        description
          "PoE class type is 5 ";
      }
      enum poe-class-6 {
        value 9;
        description
          "PoE class type is 6";
      }
      enum poe-class-7 {
        value 10;
        description
          "PoE class type is 7";
      }
      enum poe-class-8 {
        value 11;
        description
          "PoE class type is 8";
      }
      enum poe-class-4p {
        value 12;
        description
          "PoE class type is class 4 type 1";
      }
      enum poe-class-5ds {
        value 13;
        description
          "PoE class 5 dual signature";
      }
      enum poe-class-rsv {
        value 14;
        description
          "PoE class type is reserved";
      }
      enum poe-class-mismatch {
        value 15;
        description
          "PoE class type is mismatch";
      }
      enum poe-class-null {
        value 16;
        description
          "PoE class type is NULL";
      }
      enum poe-class-ds {
        value 17;
        description
          "PoE class type is dual signature";
      }
    }
    description
      "Type of PoE class";
  }

  typedef poe-port-event-type {
    type enumeration {
      enum poe-event-port-none {
        value 0;
        description
          "PoE event is none";
      }
      enum poe-event-port-shut {
        value 1;
        description
          "PoE event is port shut";
      }
      enum poe-event-port-auto {
        value 2;
        description
          "PoE event is port auto";
      }
      enum poe-event-pd-detected {
        value 3;
        description
          "PoE event is PD detected";
      }
      enum poe-event-pwr-on {
        value 4;
        description
          "PoE event is power on";
      }
      enum poe-event-pwr-good {
        value 5;
        description
          "PoE event is power good";
      }
      enum poe-event-pcut-icut {
        value 6;
        description
          "PoE event is power cutoff threshold ";
      }
      enum poe-event-pd-removal {
        value 7;
        description
          "PoE event is PD removal";
      }
      enum poe-event-tstart-fault {
        value 8;
        description
          "PoE event is start fault";
      }
      enum poe-event-class-over {
        value 9;
        description
          "PoE event is class over current";
      }
      enum poe-class-pgood-timeout {
        value 10;
        description
          "PoE event is power good timeout";
      }
      enum poe-event-imax-fault {
        value 11;
        description
          "PoE event is over current fault";
      }
      enum poe-event-periodic-poll {
        value 12;
        description
          "PoE event is periodic poll";
      }
      enum poe-event-pwr-police-overdrawn {
        value 13;
        description
          "PoE event is power police current overdrawn";
      }
      enum poe-event-pwr-police-enable {
        value 14;
        description
          "PoE event is power police enable";
      }
      enum poe-event-pwr-police-disable {
        value 15;
        description
          "PoE event is power police disable";
      }
      enum poe-event-pwr-police {
        value 16;
        description
          "PoE event is power police";
      }
      enum poe-event-mosfet-fault {
        value 17;
        description
          "PoE event is MOSFET fault";
      }
      enum poe-event-oss {
        value 18;
        description
          "PoE event is OSS";
      }
      enum poe-event-spare-pair-pwr-on {
        value 19;
        description
          "PoE event is spare pair power on";
      }
      enum poe-event-spare-pair-pwr-good {
        value 20;
        description
          "PoE event is spare pair power good";
      }
      enum poe-event-spare-pair-pwr-off {
        value 21;
        description
          "PoE event is spare pair power off";
      }
      enum poe-event-spare-pair-tstart {
        value 22;
        description
          "PoE event is spare pair fault";
      }
      enum poe-event-spare-pair-imax-fault {
        value 23;
        description
          "PoE event is spare pair max fault";
      }
      enum poe-event-spare-pair-pd-removal {
        value 24;
        description
          "PoE event is spare pair PD removal";
      }
      enum poe-event-spare-pair-pwr-gd-timeout {
        value 25;
        description
          "PoE event is spare pair power good timeout";
      }
      enum poe-event-spare-pair-det-short {
        value 26;
        description
          "PoE event is spare pair detected short circuit";
      }
      enum poe-event-spare-pair-det-timeout {
        value 27;
        description
          "PoE event is spare pair detection timeout";
      }
      enum poe-event-det-short {
        value 28;
        description
          "PoE event is detected short circuit";
      }
      enum poe-event-both-shut {
        value 29;
        description
          "PoE event is both pair shut";
      }
      enum poe-event-spare-pair-shut {
        value 30;
        description
          "PoE event is spare pair shut";
      }
      enum poe-event-spare-pair-auto {
        value 31;
        description
          "PoE event is spare pair auto";
      }
      enum poe-event-spare-pair-pd-detected {
        value 32;
        description
          "PoE event is spare pair PD detected";
      }
      enum poe-event-spare-pair-pcut-icut {
        value 33;
        description
          "PoE event is spare pair power cutoff threshold";
      }
      enum poe-event-spare-pair-class-over {
        value 34;
        description
          "PoE event is spare pair class over";
      }
      enum poe-event-spare-pair-mosfet-fault {
        value 35;
        description
          "PoE event is spare pair MOSFET fault";
      }
      enum poe-event-priority-fault {
        value 36;
        description
          "PoE event is priority fault";
      }
      enum poe-event-spare-pair-priority-fault {
        value 37;
        description
          "PoE event is spare pair priority fault";
      }
      enum poe-event-port-intrnl-cmd {
        value 38;
        description
          "PoE event is port internal command";
      }
      enum poe-event-port-intrnl-intr {
        value 39;
        description
          "PoE event is port internal interrupt";
      }
      enum poe-event-port-intrnl-intr-cls {
        value 40;
        description
          "PoE event is port internal interrupt class";
      }
      enum poe-event-spare-pair-intrnl-cmd {
        value 41;
        description
          "PoE event is spare pair internal command";
      }
      enum poe-event-spare-pair-intrnl-intr {
        value 42;
        description
          "PoE event is spare pair internal interrupt";
      }
      enum poe-event-spare-pair-intrnl-intr-cls {
        value 43;
        description
          "PoE event is spare pair internal interrupt class";
      }
      enum poe-event-spare-pair-pwr-plc-ovrdrn {
        value 44;
        description
          "PoE event is spare pair power police overdrawn";
      }
      enum poe-event-update-cls-det {
        value 45;
        description
          "PoE event is update class detection";
      }
      enum poe-event-update-cfg {
        value 46;
        description
          "PoE event is update configuration";
      }
    }
    description
      "PoE event type of the device";
  }

  typedef poe-detect-status {
    type enumeration {
      enum poe-detect-status-unknown {
        value 0;
        description
          "PoE detected status is unknown";
      }
      enum poe-detect-status-short-circuit {
        value 1;
        description
          "PoE detected status is short circuit";
      }
      enum poe-detect-status-reserved {
        value 2;
        description
          "PoE detected status is reserved";
      }
      enum poe-detect-status-too-low {
        value 3;
        description
          "PoE detected status is too low";
      }
      enum poe-detect-status-valid {
        value 4;
        description
          "PoE detected status is valid";
      }
      enum poe-detect-status-too-high {
        value 5;
        description
          "PoE detected status is too high";
      }
      enum poe-detect-status-open-circuit {
        value 6;
        description
          "PoE detected status is open circuit";
      }
      enum poe-detect-status-detected {
        value 7;
        description
          "PoE detected status is detected";
      }
      enum poe-detect-status-mosfet-fault {
        value 8;
        description
          "PoE detected status is MOSFET fault";
      }
    }
    description
      "PoE detected status";
  }

  typedef poe-port-priority {
    type enumeration {
      enum poe-priority-0 {
        value 0;
        description
          "PoE port priority is 0";
      }
      enum poe-priority-1 {
        value 1;
        description
          "PoE port priority is 1";
      }
      enum poe-priority-2 {
        value 2;
        description
          "PoE port priority is 2";
      }
      enum poe-priority-3 {
        value 3;
        description
          "PoE port priority is 3";
      }
      enum poe-priority-4 {
        value 4;
        description
          "PoE port priority is 4";
      }
      enum poe-priority-5 {
        value 5;
        description
          "PoE port priority is 5";
      }
      enum poe-priority-6 {
        value 6;
        description
          "PoE port priority is 6";
      }
      enum poe-priority-7 {
        value 7;
        description
          "PoE port priority is 7";
      }
    }
    description
      "Priority of the port";
  }

  grouping pair-info {
    description
      "PoE per pair information ";
    leaf consumed-power {
      type uint32;
      description
        "Power device consumed power ";
    }
    leaf pcut-icut {
      type uint32;
      description
        "Power cutoff threshold information";
    }
    leaf capacitance {
      type uint8;
      description
        "Capacitance measured on the pair-set";
    }
    leaf resistance {
      type uint8;
      description
        "Resistance measured on the pair-set";
    }
    leaf detect-status {
      type uint8;
      description
        "Detect status on the pair-set";
    }
    leaf class {
      type poe-health-xe:poe-class-type;
      description
        "Class on the pair-set";
    }
    leaf assigned-class {
      type poe-health-xe:poe-class-type;
      description
        "Assigned class on the pair-set";
    }
    leaf high-power {
      type uint8;
      description
        "High power config on the pair-set";
    }
    leaf pd-detect-status {
      type poe-health-xe:poe-detect-status;
      description
        "Pair-set detect status";
    }
  }

  grouping poe-meta {
    description
      "PoE meta information of the port";
    leaf min-current {
      type uint32;
      description
        "Minimum current drawn by the port";
    }
    leaf max-current {
      type uint32;
      description
        "Maximum current drawn by the port";
    }
    leaf poe-ha-cfg {
      type uint8;
      description
        "Fast PoE configuration";
    }
    leaf perpatul-poe-cfg {
      type uint8;
      description
        "Perpetual PoE configuration";
    }
    leaf four-pair-force {
      type uint8;
      description
        "Four pair force configuration";
    }
    leaf police-cfg {
      type uint8;
      description
        "Police configuration";
    }
    leaf police-action {
      type uint8;
      description
        "Police action type";
    }
    leaf port-shutdown-cnt {
      type uint16;
      description
        "Port shutdown count";
    }
    leaf mosfet-fault-cnt {
      type uint16;
      description
        "MOSFET fault count";
    }
    leaf over-tmp-cnt {
      type uint16;
      description
        "Over temperature count";
    }
    leaf internal-err-cnt {
      type uint16;
      description
        "Internal error count";
    }
    leaf poe-shutdown-cnt {
      type uint16;
      description
        "PoE shutdown count";
    }
    leaf poe-detected-cnt {
      type uint16;
      description
        "PoE detected count";
    }
    leaf tstart-fault-cnt {
      type uint16;
      description
        "Start fault count";
    }
    leaf imax-fault-cnt {
      type uint16;
      description
        "Over current fault count";
    }
    leaf spare-internal-err-cnt {
      type uint16;
      description
        "Spare pair internal error count";
    }
    leaf spare-poe-shutdown-cnt {
      type uint16;
      description
        "Spare pair PoE shutdown count";
    }
    leaf spare-poe-detected-cnt {
      type uint16;
      description
        "Spare pair PoE detected count";
    }
    leaf spare-tstart-fault-cnt {
      type uint16;
      description
        "Spare pair start fault count";
    }
    leaf spare-imax-fault-cnt {
      type uint16;
      description
        "Spare pair over current fault";
    }
  }

  grouping port-health {
    description
      " PoE port operational data ";
    leaf index {
      type uint8;
      description
        "Index of the device";
    }
    leaf time-sec {
      type uint64;
      description
        "Time in seconds";
    }
    leaf time-usec {
      type uint32;
      description
        "Time in micro seconds";
    }
    leaf port-state {
      type poe-health-xe:poe-state-type;
      description
        "Port state of the device";
    }
    leaf port-event {
      type poe-health-xe:poe-port-event-type;
      description
        "Port events of the device";
    }
    leaf is-cisco-pd {
      type uint8;
      description
        "The device connected is a cisco PD or not";
    }
    leaf conn-chk {
      type uint8;
      description
        "Connection check of the device";
    }
    leaf port-priority {
      type uint8;
      description
        "Port priority of the device";
    }
    leaf port-voltage {
      type uint64;
      description
        "Port voltage of the device";
    }
    leaf four-pair-pcut {
      type uint32;
      description
        "Four pair cut";
    }
    container signal-pair-info {
      description
        "Signal pair information of the device";
      uses poe-health-xe:pair-info;
    }
    container spare-pair-info {
      description
        "Spare pair information of the device";
      uses poe-health-xe:pair-info;
    }
    container poe-meta-data {
      description
        "PoE meta data information";
      uses poe-health-xe:poe-meta;
    }
    leaf event-time {
      type yang:date-and-time;
      description
        "Records the time when event occurs";
    }
    leaf is-a-cisco-pd {
      type boolean;
      description
        "The device connected is a cisco PD or not";
    }
    leaf pd-port-priority {
      type poe-health-xe:poe-port-priority;
      description
        "Port priority information of the PD connected";
    }
  }

  grouping health-history {
    description
      "Health history of port";
    leaf port-num {
      type uint32;
      description
        "PoE Port number";
    }
    leaf count {
      type uint8;
      description
        "Number of events tracked on the port";
    }
    leaf current-index {
      type uint8;
      description
        "Current index in the circular buffer";
    }
    list port-health {
      key "index";
      description
        "PoE port operational data";
      uses poe-health-xe:port-health;
    }
  }

  grouping poe-global-info {
    description
      "Global PoE related info table ";
    leaf switch-num {
      type uint8;
      description
        "Switch or linecard number";
    }
    leaf ieee-rev {
      type uint8;
      description
        "Ieee revision of switch or linecard";
    }
    leaf vendor-id {
      type uint8;
      description
        "PSE vendor ID ";
    }
    leaf pse-fw-ver {
      type uint8;
      description
        "Power source equipment firmware version";
    }
    leaf device-id {
      type uint8;
      description
        "PSE device ID";
    }
    leaf fpga-sw-ver {
      type uint16;
      description
        "Field programmable gate array software version";
    }
    leaf fpga-bootloader-ver {
      type uint16;
      description
        "Field programmable gate array boot loader version";
    }
  }

  container poe-health-oper-data {
    config false;
    description
      "PoE health status information";
    list location {
      key "fru slot bay chassis node";
      description
        "A list of data provider locations";
      uses common-types-ios-xe:extended-location;
      list poe-global {
        key "switch-num";
        description
          "PoE global data";
        uses poe-health-xe:poe-global-info;
      }
      list poe-port {
        key "port-num";
        description
          "PoE port details";
        uses poe-health-xe:health-history;
      }
    }
  }
}
