module Cisco-IOS-XE-service-insertion {
  yang-version 1.1;
  namespace "http://cisco.com/ns/yang/Cisco-IOS-XE-service-insertion";
  prefix ios-service-insertion;

  import cisco-semver {
    prefix cisco-semver;
  }
  import ietf-inet-types {
    prefix inet;
  }
  import Cisco-IOS-XE-native {
    prefix ios;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Service Insertion Yang model.
     Copyright (c) 2016, 2018-2021 by Cisco Systems, Inc.
     All rights reserved.";

  revision 2024-11-01 {
    description
      "- Moved leaf cluster-type to the beginning of container";
    cisco-semver:module-version "4.1.0";
  }
  revision 2024-03-01 {
    description
      "- Added IPV6 address in service-node and appnav-controller
       - Removed tailf hidden nodes";
    cisco-semver:module-version "4.0.0";
  }
  revision 2023-07-01 {
    description
      "- Moved service-insertion-oper to obsolete";
    cisco-semver:module-version "3.0.0";
  }
  revision 2022-11-01 {
    description
      "- Update yang-version to 1.1";
    cisco-semver:module-version "2.3.0";
  }
  revision 2021-07-01 {
    description
      "- Changed service-node-group from leaf to leaf-list";
    cisco-semver:module-version "2.2.0";
  }
  revision 2020-11-01 {
    description
      "- Added multi-sn device-role and appnav-controller oper model.";
    cisco-semver:module-version "2.1.0";
  }
  revision 2020-07-01 {
    description
      "
       - Corrected node-discovery enable command";
    cisco-semver:module-version "2.0.0";
  }
  revision 2020-03-01 {
    description
      "
       - Corrected sequence issue in appnav-controller-group";
    cisco-semver:module-version "1.2.0";
  }
  revision 2019-11-01 {
    description
      "
       - Added appnav controllers config";
    cisco-semver:module-version "1.1.0";
  }
  revision 2019-07-01 {
    description
      "- Establish semantic version baseline
       - Added service controller type appqoe: Application Quality Of Experience";
    cisco-semver:module-version "1.0.0";
  }
  revision 2017-02-07 {
    description
      "Initial revision";
  }

  grouping config-service-insertion-grouping {
    leaf acg-reload-delay {
      description
        "Reload delay timer for ACG";
      type uint16 {
        range "120..450";
      }
    }
    list appnav-controller-group {
      description
        "AppNav Controller Group";
      key "group-name";
      leaf group-name {
        type string;
      }
      leaf appqoe {
        description
          "appqoe AppNav Controller group";
        type empty;
      }
      leaf description {
        description
          "ACG description";
        type string;
      }
      list appnav-controllers {
        description
          "AppNav controller";
        key "address";
        leaf address {
          type union {
            type inet:ipv4-address;
            type inet:ipv6-address;
          }
        }
        leaf vrf {
          description
            "AppNav controller IP VRF";
          must '/ios:native/ios:vrf/ios:definition[ios:name=current()] or /ios:native/ios:ip/ios:vrf[ios:name=current()]' {
            error-message "VRF must be created 1st, deleted last";
          }
          type string {
            length "1..32";
          }
        }
      }
      leaf-list appnav-controller {
        status deprecated;
        description
          "AppNav controller";
        type inet:ipv4-address;
      }
    }
    list service-node-group {
      description
        "service node Group";
      key "name";
      leaf name {
        type string;
      }
      leaf appqoe {
        description
          "appqoe service node group";
        type empty;
      }
      leaf description {
        description
          "Group Description";
        type string;
      }
      leaf device-role {
        must 'not(../../service-context/appqoe/cluster-type)' {
          error-message "Service-Node device-role cannot be configured when cluster-type is configured";
        }
        description
          "Assign this device the role of Service-Node";
        type enumeration {
          enum service-node;
        }
      }
      leaf node-discovery {
        description
          "service node auto discovery";
        type enumeration {
          enum enable;
        }
      }
      leaf-list service-node {
        description
          "service node";
        type union {
          type inet:ipv4-address;
          type inet:ipv6-address;
        }
      }
    }
    container service-context {
      description
        "Service Context";
      list waas {
        description
          "Service controller waas";
        key "name";
        leaf name {
          type string;
        }
        leaf appnav-controller-group {
          description
            "AppNav Controller Group";
          type leafref {
            path "../../../appnav-controller-group/group-name";
          }
        }
        container authentication {
          description
            "Authentication key";
          leaf sha1 {
            description
              "Authentication type";
            type empty;
          }
          leaf key {
            description
              "Authentication Key";
            type empty;
          }
          leaf encrypt {
            type enumeration {
              enum 0;
              enum 7;
            }
          }
          leaf string {
            type string;
          }
        }
        leaf-list service-node-groups {
          description
            "service node Group";
          ordered-by user;
          type leafref {
            path "../../../service-node-group/name";
          }
        }
        leaf service-node-group {
          status deprecated;
          description
            "service node Group";
          type leafref {
            path "../../../service-node-group/name";
          }
        }
        leaf service-policy {
          description
            "Specify a service policy for the service context";
          type string;
        }
        container passthrough-flow {
          description
            "Passthrough flow update";
          leaf unsync {
            description
              "Disable passthrough flow update among AppNav Controllers";
            type empty;
          }
        }
        container vrf {
          description
            "Specify VRF where service would be applied";
          leaf default {
            description
              "default";
            type empty;
          }
          leaf global {
            description
              "global";
            type empty;
          }
          list name-config {
            description
              "vrf name";
            ordered-by user;
            key "name";
            leaf name {
              type string;
            }
          }
          leaf name {
            status deprecated;
            description
              "vrf name";
            type string;
          }
        }
        leaf enable {
          description
            "service context enable";
          type empty;
        }
      }
      list appqoe {
        description
          "Service controller appqoe";
        key "name";
        leaf name {
          type string;
        }
        leaf cluster-type {
          must 'not(../../../service-node-group/device-role)' {
            error-message "Cluster-Type cannot be configured when Service-Node device-role is configured";
          }
          description
            "Defines the AppQoE cluster type of this device";
          type enumeration {
            enum integrated-service-node;
            enum service-controller;
            enum hybrid;
          }
        }
        leaf appnav-controller-group {
          description
            "AppNav Controller Group";
          type leafref {
            path "../../../appnav-controller-group/group-name";
          }
        }
        leaf-list service-node-groups {
          ordered-by user;
          description
            "service node Group";
          type leafref {
            path "../../../service-node-group/name";
          }
        }
        leaf service-node-group {
          status deprecated;
          description
            "service node Group is deprecated";
          type leafref {
            path "../../../service-node-group/name";
          }
        }
        leaf enable {
          description
            "service context enable";
          type empty;
        }
        container vrf {
          description
            "Specify VRF where service would be applied";
          leaf default {
            description
              "default";
            type empty;
          }
          leaf global {
            description
              "global";
            type empty;
          }
          leaf name {
            description
              "vrf name";
            type string;
          }
        }
      }
    }
    container swap {
      description
        "Swap src-ip";
      leaf src-ip {
        description
          "Swap source-ip of service-insertion packets";
        type empty;
      }
    }
    container waas {
      description
        "enable waas on the interface";
      leaf-list interfaces {
        description
          "interface to enable waas";
        ordered-by user;
        type string;
      }
      container interface {
        status deprecated;
        description
          "interface to enable waas";
        uses ios-ifc:interface-grouping;
      }
    }
    container appqoe {
      description
        "enable appqoe on the interface";
      container interface {
        description
          "interface to enable appqoe";
        uses ios-ifc:interface-grouping;
      }
    }
  }

  container service-insertion-oper {
    status obsolete;
    container appqoe {
      config false;
      leaf device-mode {
        type enumeration {
          enum service-node;
          enum integrated-service-node;
          enum service-controller;
        }
      }
      list service-nodes {
        must "../device-mode = 'integrated-service-node' or
                     ../device-mode = 'service-controller'";
        key "address";
        leaf address {
          type inet:ipv4-address;
        }
        leaf system-ip {
          type inet:ipv4-address;
        }
        leaf site-id {
          type uint32;
        }
        leaf health-status {
          type enumeration {
            enum down;
            enum green;
            enum yellow;
            enum red;
          }
        }
        leaf error-message {
          type string;
        }
      }
    }
  }

  augment "/ios:native/ios:service-insertion" {
    uses config-service-insertion-grouping;
  }
}
