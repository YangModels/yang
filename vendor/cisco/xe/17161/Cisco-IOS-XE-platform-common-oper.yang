module Cisco-IOS-XE-platform-common-oper {
  yang-version 1.1;
  namespace "http://cisco.com/ns/yang/Cisco-IOS-XE-platform-common-oper";
  prefix platform-common-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     common to platform oper as well as platform events.
     Copyright (c) 2019, 2022 by Cisco Systems, Inc.
     All rights reserved.";

  revision 2022-11-01 {
    description
      "Update yang-version to 1.1";
    reference
      "1.1.0";
    cisco-semver:module-version "1.1.0";
  }
  revision 2019-11-01 {
    description
      "Initial revision";
    reference
      "1.0.0";
    cisco-semver:module-version "1.0.0";
  }

  typedef plat-comp-type {
    type enumeration {
      enum comp-chassis {
        value 0;
        description
          "Component type - chassis";
      }
      enum comp-backplane {
        value 1;
        description
          "Component type - backplane";
      }
      enum comp-power-supply {
        value 2;
        description
          "Component type - power supply";
      }
      enum comp-fan {
        value 3;
        description
          "Component type - fan or fan tray";
      }
      enum comp-sensor {
        value 4;
        description
          "Component type - sensor";
      }
      enum comp-module {
        value 5;
        description
          "Component type - module";
      }
      enum comp-linecard {
        value 6;
        description
          "Component type - linecard";
      }
      enum comp-port {
        value 7;
        description
          "Component type - port";
      }
      enum comp-cpu {
        value 8;
        description
          "Component type - cpu";
      }
      enum comp-operating-system {
        value 9;
        description
          "Component type - operating system";
      }
      enum comp-optical-channel {
        value 10;
        description
          "Component type - optical channel";
      }
      enum comp-container {
        value 11;
        description
          "Component type - container";
      }
      enum comp-fru {
        value 12;
        description
          "Component type - fru";
      }
      enum comp-controller-card {
        value 13;
        description
          "Component type - controller card";
      }
      enum comp-transceiver {
        value 14;
        description
          "Component type - transceiver";
      }
    }
    description
      "Component Type";
  }

  typedef plat-comp-status {
    type enumeration {
      enum status-active {
        value 0;
        description
          "Component status - active";
      }
      enum status-inactive {
        value 1;
        description
          "Component status - inactive";
      }
      enum status-disabled {
        value 2;
        description
          "Component status - disabled";
      }
    }
    description
      "Component status";
  }

  typedef plat-comp-status-desc {
    type enumeration {
      enum ok {
        value 0;
        description
          "Component status description - ok";
      }
      enum thermal-failure {
        value 1;
        description
          "Component status description - thermal failure";
      }
      enum fan-failure {
        value 2;
        description
          "Component status description - fan failure";
      }
      enum supply-failure {
        value 3;
        description
          "Component status description - supply failure";
      }
      enum no-response {
        value 4;
        description
          "Component status description - no response";
      }
      enum bad-power {
        value 5;
        description
          "Component status description - bad power or
           input is out of range";
      }
      enum overload {
        value 6;
        description
          "Component status description - overload";
      }
      enum no-input-power {
        value 7;
        description
          "Component status description - no input power";
      }
      enum disabled {
        value 8;
        description
          "Component status description - disabled";
      }
      enum not-present {
        value 9;
        description
          "Component status description - vacant";
      }
      enum standby {
        value 10;
        description
          "Component status description - standby";
      }
      enum bad-cookie {
        value 11;
        description
          "Component status description - bad cookie";
      }
      enum invalid {
        value 12;
        description
          "Component status description - invalid";
      }
    }
    description
      "Component status description";
  }

  typedef plat-sensor-alarm-severity {
    type enumeration {
      enum alarm-severity-unknown {
        value 0;
        description
          "Sensor alarm severity - unknown or normal";
      }
      enum alarm-severity-minor {
        value 1;
        description
          "Sensor alarm severity - minor";
      }
      enum alarm-severity-major {
        value 2;
        description
          "Sensor alarm severity - major";
      }
      enum alarm-severity-critical {
        value 3;
        description
          "Sensor alarm severity - critical";
      }
      enum alarm-severity-warning {
        value 4;
        description
          "Sensor alarm severity - warning";
      }
      enum alarm-severity-shutdown {
        value 5;
        description
          "Sensor alarm severity - shutdown";
      }
    }
    description
      "Temperature Alarm Severity";
  }

  typedef plat-sensor-type {
    type enumeration {
      enum sensor-unknown {
        value 0;
        description
          "Sensor type - unknown";
      }
      enum sensor-temp-cpu {
        value 1;
        description
          "Sensor type - temperature cpu";
      }
      enum sensor-temp-uadp {
        value 2;
        description
          "Sensor type - temperature asic";
      }
      enum sensor-temp-inlet {
        value 3;
        description
          "Sensor type - temperature inlet";
      }
      enum sensor-temp-outlet {
        value 4;
        description
          "Sensor type - temperature outlet";
      }
      enum sensor-temp-hotspot {
        value 5;
        description
          "Sensor type - temperature hotspot";
      }
      enum sensor-pfu-redundancy {
        value 6;
        description
          "Sensor type - power supply redundancy";
      }
    }
    description
      "Temperature sensor type";
  }

  typedef plat-sensor-state {
    type enumeration {
      enum green {
        value 0;
        description
          "Sensor state - green";
      }
      enum yellow {
        value 1;
        description
          "Sensor state - yellow";
      }
      enum red {
        value 2;
        description
          "Sensor state - red";
      }
    }
    description
      "Platform sensor state";
  }

  grouping plat-sensor-data {
    description
      "Sensor state data for device components";
    leaf value-instant {
      type decimal64 {
        fraction-digits 2;
      }
      description
        "Instantaneous sensor reading
         value of a component";
    }
    leaf value-avg {
      type decimal64 {
        fraction-digits 2;
      }
      description
        "Arithmetic mean value of the statistic over a
         sampling period";
    }
    leaf value-max {
      type decimal64 {
        fraction-digits 2;
      }
      description
        "High water mark value of the statistic over a
         sampling period";
    }
    leaf value-min {
      type decimal64 {
        fraction-digits 2;
      }
      description
        "Low water mark value of the statistic over a
         sampling period";
    }
    leaf sampling-period-sec {
      type uint32;
      description
        "Sampling period in seconds";
    }
  }

  grouping plat-sensor-alarm-data {
    description
      "Sensor alarm data of a component";
    leaf alarm-status {
      type boolean;
      description
        "Alarm status";
    }
    leaf alarm-threshold-high {
      type uint32;
      description
        "High threshold limit of a generated alarm";
    }
    leaf alarm-threshold-low {
      type uint32;
      description
        "Low threshold limit of a generated alarm";
    }
    leaf severity {
      type platform-common-ios-xe-oper:plat-sensor-alarm-severity;
      description
        "Alarm Severity";
    }
  }
}
