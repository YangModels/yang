module Cisco-IOS-XE-mmode {
  yang-version 1.1;
  namespace "http://cisco.com/ns/yang/Cisco-IOS-XE-mmode";
  prefix ios-mmode;

  import cisco-semver {
    prefix cisco-semver;
  }
  import Cisco-IOS-XE-native {
    prefix ios;
  }

  description
    "Cisco XE Maintenance Mode Yang Model.
     Copyright (c) 2016-2023, 2019 by Cisco Systems, Inc.
     All rights reserved.";

  revision 2023-07-01 {
    description
      "Adding  protocol range under maintenance-template";
    cisco-semver:module-version "2.0.0";
  }
  revision 2022-11-01 {
    description
      "- Update yang-version to 1.1";
    cisco-semver:module-version "1.1.0";
  }
  revision 2019-07-01 {
    description
      "Establish semantic version baseline";
    cisco-semver:module-version "1.0.0";
  }
  revision 2017-11-29 {
    description
      "Adding FHRP protocols under maintenance-template";
  }
  revision 2017-06-15 {
    description
      "Changing model to cover maintenance-template ipmulticast vrf change";
  }
  revision 2017-05-17 {
    description
      "Adding more commands under maintenance-template";
  }
  revision 2017-03-13 {
    description
      "Initial draft for GIR config commands";
  }

  augment "/ios:native/ios:system" {
    container mode {
      description
        "System mode";
      container maintenance {
        description
          "System maintenance";
        presence "true";
        container config-maintenance {
          leaf failsafe {
            description
              "Client ack timeout minutes (default is 30 mins)";
            type uint8 {
              range "15..180";
            }
          }
          container on-reload {
            description
              "On reload maintenance mode configuration";
            container reset-reason {
              description
                "Reset reason";
              leaf maintenance {
                description
                  "Maintenance mode";
                type empty;
              }
            }
          }
          leaf template {
            description
              "maintenance-template name";
            type string;
          }
          leaf timeout {
            description
              "maintenance duration minutes (default is 30 mins)";
            type uint8 {
              range "15..180";
            }
          }
        }
      }
    }
  }

  augment "/ios:native" {
    list maintenance-template {
      description
        "maintenance-template configuration";
      key "templ-name";
      leaf templ-name {
        description
          "maintenance-template name";
        type string;
      }
      container config-maintenance-templ {
        container router {
          description
            "routing protocol";
          list routing-protocol {
            ordered-by user;
            key "protocol instance";
            leaf protocol {
              description
                "isolate protocol";
              type enumeration {
                enum bgp;
                enum isis;
                enum ospf;
                enum ospfv3;
              }
            }
            leaf instance {
              description
                "instance/AS number";
              type uint32;
            }
            must "protocol != 'ospf' or (protocol = 'ospf' and instance <= 65535 and instance >=1 )" {
              error-message "Supported protocol range is (1..65535)";
            }
            must "protocol != 'ospfv3' or (protocol = 'ospfv3' and instance <= 65535 and instance >=1 )" {
              error-message "Supported protocol range is (1..65535)";
            }
          }
        }
        list hsrp {
          description
            "HSRP protocol instance";
          ordered-by user;
          key "interface group-number";
          leaf interface {
            description
              "full interface name and number (Note: the device will accept both full and short interface names, but the names in running config will be shown in full form)";
            type string;
          }
          leaf group-number {
            description
              "HSRP group number";
            type uint16 {
              range "0..255";
            }
          }
        }
        list vrrp {
          description
            "VRRP protocol instance";
          ordered-by user;
          key "interface group-number";
          leaf interface {
            description
              "full interface name and number (Note: the device will accept both full and short interface names, but the names in running config will be shown in full form)";
            type string;
          }
          leaf group-number {
            description
              "VRRP group number";
            type uint16 {
              range "0..255";
            }
          }
        }
        list vrrpv3 {
          description
            "VRRPv3 protocol";
          ordered-by user;
          key "interface group-number address-family";
          leaf interface {
            description
              "full interface name and number (Note: the device will accept both full and short interface names, but the names in running config will be shown in full form)";
            type string;
          }
          leaf group-number {
            description
              "VRRP group number";
            type uint16 {
              range "0..255";
            }
          }
          leaf address-family {
            description
              "address family";
            type enumeration {
              enum ipv4;
              enum ipv6;
            }
          }
        }
        container shutdown {
          description
            "shutdown";
          leaf l2 {
            description
              "shutdown all L2 interfaces";
            type empty;
          }
        }
        container ipmulticast {
          description
            "ipmulticast";
          leaf-list vrf {
            description
              "vrf instance name";
            type string;
          }
        }
      }
    }
  }
}
