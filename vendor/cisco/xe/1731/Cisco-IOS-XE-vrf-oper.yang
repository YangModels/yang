module Cisco-IOS-XE-vrf-oper {
  yang-version 1;
  namespace "http://cisco.com/ns/yang/Cisco-IOS-XE-vrf-oper";
  prefix vrf-ios-xe-oper;
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for IOS-XE VRF operational data.
     Copyright (c) 2018-2019 by Cisco Systems, Inc.
     All rights reserved.";

  revision 2019-05-01 {
    description
      "Added semantic version";
    reference "1.1.0";
    cisco-semver:module-version "1.1.0";
  }
  revision 2018-09-10 {
    description
      "Initial revision";
    reference "1.0.0";
    cisco-semver:module-version "1.0.0";
  }

  typedef vrf-af {
    type enumeration {
      enum "ipv4-unicast" {
        value 0;
        description
          "Address family ipv4 unicast";
        tailf:code-name "ENUM_vrf_af_VRF_AF_IPv4";
      }
      enum "ipv6-unicast" {
        value 1;
        description
          "Address family ipv6 unicast";
        tailf:code-name "ENUM_vrf_af_VRF_AF_IPv6";
      }
      enum "ipv4-multicast" {
        value 2;
        description
          "Address family ipv4 multicast";
        tailf:code-name "ENUM_vrf_af_VRF_AF_IPMCAST";
      }
      enum "ipv6-multicast" {
        value 3;
        description
          "Address family ipv6 multicast";
        tailf:code-name "ENUM_vrf_af_VRF_AF_IPv6MCAST";
      }
    }
    description
      "VRF address family types";
  }

  grouping vrf-af-entry {
    description
      "VRF address family operational data";
    leaf address-family {
      type vrf-ios-xe-oper:vrf-af;
      description
        "Address family enabled on this VRF";
    }
  }

  grouping vrf-entry {
    description
      "VRF entry to store operational data";
    leaf vrf-name {
      type string;
      description
        "Unique name of this VRF";
    }
    leaf-list interface {
      type string;
      ordered-by user;
      description
        "List of interfaces using this VRF";
    }
    list address-family-entry {
      description
        "List of address family data for this VRF";
      uses vrf-ios-xe-oper:vrf-af-entry;
    }
  }

  container vrf-oper-data {
    config false;
    description
      "VRF operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list vrf-entry {
      key "vrf-name";
      description
        "VRF entries";
      uses vrf-ios-xe-oper:vrf-entry;
    }
  }

  grouping __yangpp_metadata {
    description
      "Internal metadata for this module and imported modules";
    leaf json-metadata-leaf {
      type empty;
      description
        "Hidden internal leaf that holds this module's metadata";
      tailf:hidden "full";
      tailf:meta-data "jsonmetadata" {
        tailf:meta-value "{\"Cisco-IOS-XE-vrf-oper\":{\"__auto_internal_label_map__\":{\"VRF_AF_IPMCAST\":\"ipv4-multicast\",\"VRF_AF_IPv4\":\"ipv4-unicast\",\"VRF_AF_IPv6\":\"ipv6-unicast\",\"VRF_AF_IPv6MCAST\":\"ipv6-multicast\"},\"c\":{\"vrf-oper-data\":{\"m\":[{\"o\":\"Cisco_IOS_XE_vrf_oper\",\"t\":\"r\"}]}}}}";
      }
    }
  }

  container schema-metadata-Cisco-IOS-XE-vrf-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-vrf-oper";
    }
    tailf:meta-data "organization" {
      tailf:meta-value "Cisco Systems, Inc.";
    }
    tailf:meta-data "semver" {
      tailf:meta-value "2019-05-01";
    }
  }
}
