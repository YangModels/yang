module Cisco-IOS-XE-stack-mgr-events-oper {
  yang-version 1;
  namespace "http://cisco.com/ns/yang/Cisco-IOS-XE-stack-mgr-events-oper";
  prefix stack-mgr-events-oper;

  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for stack manager operations events generated from the Cisco Devices.
     These models may produce high volume of data.
     Copyright (c) 2019-2020 by Cisco Systems, Inc.
     All rights reserved";

  revision 2020-07-01 {
    description
      "- Remove unused empty container stack-mgr-events";
    reference "2.0.0";
    cisco-semver:module-version "2.0.0";
  }
  revision 2019-11-01 {
    description
      "- Added semantic version
       - Added version mismatch event";
    reference "1.1.0";
    cisco-semver:module-version "1.1.0";
  }
  revision 2019-01-24 {
    description
      "Initial revision";
    reference "1.0.0";
    cisco-semver:module-version "1.0.0";
  }

  typedef stack-mgr-notification-severity {
    type enumeration {
      enum "critical" {
        value 0;
      }
      enum "major" {
        value 1;
      }
      enum "minor" {
        value 2;
      }
    }
    description
      "Notification severity";
  }

  typedef stack-mgr-eventq-event-type {
    type enumeration {
      enum "node-added" {
        value 0;
        description
          "Node is added to the stack";
      }
      enum "node-removed" {
        value 1;
        description
          "Node is removed from the stack";
      }
      enum "node-new-master" {
        value 2;
        description
          "New Master or Active elected in the stack";
      }
      enum "node-version-mismatch" {
        value 3;
        description
          "Node version mismatch with other members in the stack";
      }
    }
    description
      "Stack Node Role";
  }

  grouping stack-mgr-eventq-db-elem {
    description
      "Stack manager client events data model";
    leaf severity {
      type stack-mgr-events-oper:stack-mgr-notification-severity;
      description
        "Event severity";
    }
    leaf host-name {
      type string;
      description
        "Host name";
    }
    leaf system-ip {
      type inet:ip-address;
      description
        "Mgmt IP address";
    }
    leaf event {
      type stack-mgr-events-oper:stack-mgr-eventq-event-type;
      description
        "Stack Manager event type";
    }
    leaf member-number {
      type uint8;
      description
        "Stack member number for the event";
    }
    leaf serial-number {
      type string;
      description
        "Stack member serial number for the event";
    }
    leaf pid {
      type string;
      description
        "Stack member model number for the event";
    }
  }

  notification stkmevent {
    description
      "Stack manager client operational events. Provides an event for each significant activity in stack. It may generate high volume of data, depending on scale";
    uses stack-mgr-events-oper:stack-mgr-eventq-db-elem;
  }
}
