module Cisco-IOS-XE-aaa-types {
  yang-version 1;
  namespace "http://cisco.com/ns/yang/Cisco-IOS-XE-aaa-types";
  prefix aaa-types;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains type definitions for AAA Types.
     Copyright (c) 2019 by Cisco Systems, Inc.
     All rights reserved.";

  revision 2020-03-01 {
    description
      "- Added Server list AAA attributes";
    reference "1.1.0";
    cisco-semver:module-version "1.1.0";
    cisco-semver-internal:os-version "17.2.1";
  }
  revision 2019-11-01 {
    description
      "Initial revision";
    reference "1.0.0";
    cisco-semver:module-version "1.0.0";
    cisco-semver-internal:os-version "17.1.1";
  }

  typedef protocol-type {
    type enumeration {
      enum "aaa-protocol-type-none" {
        value 0;
        description
          "AAA protocol type None";
        tailf:code-name "ENUM_protocol_type__AAA_PROTOCOL_TYPE_NONE";
      }
      enum "aaa-protocol-type-invalid" {
        value 1;
        description
          "AAA protocol type Invalid";
        tailf:code-name "ENUM_protocol_type__AAA_PROTOCOL_TYPE_INVALID";
      }
      enum "aaa-protocol-type-lcp" {
        value 2;
        description
          "AAA protocol type LCP";
        tailf:code-name "ENUM_protocol_type__AAA_PROTOCOL_TYPE_LCP";
      }
      enum "aaa-protocol-type-ip" {
        value 3;
        description
          "AAA protocol type IP";
        tailf:code-name "ENUM_protocol_type__AAA_PROTOCOL_TYPE_IP";
      }
      enum "aaa-protocol-type-ipsec" {
        value 4;
        description
          "AAA protocol IPSec";
        tailf:code-name "ENUM_protocol_type__AAA_PROTOCOL_TYPE_IPSEC";
      }
      enum "aaa-protocol-type-ipx" {
        value 5;
        description
          "AAA protocol type IPX";
        tailf:code-name "ENUM_protocol_type__AAA_PROTOCOL_TYPE_IPX";
      }
      enum "aaa-protocol-type-atalk" {
        value 6;
        description
          "AAA protocol type ATALK";
        tailf:code-name "ENUM_protocol_type__AAA_PROTOCOL_TYPE_ATALK";
      }
      enum "aaa-protocol-type-xremote" {
        value 7;
        description
          "AAA protocol type XRemote";
        tailf:code-name "ENUM_protocol_type__AAA_PROTOCOL_TYPE_XREMOTE";
      }
      enum "aaa-protocol-type-tn3270" {
        value 8;
        description
          "AAA protocol type TN3270";
        tailf:code-name "ENUM_protocol_type__AAA_PROTOCOL_TYPE_TN3270";
      }
      enum "aaa-protocol-type-telnet" {
        value 9;
        description
          "AAA protocol type Telnet";
        tailf:code-name "ENUM_protocol_type__AAA_PROTOCOL_TYPE_TELNET";
      }
      enum "aaa-protocol-type-tcp-clear" {
        value 10;
        description
          "AAA protocol type TCP Clear";
        tailf:code-name "ENUM_protocol_type__AAA_PROTOCOL_TYPE_TCP_CLEAR";
      }
      enum "aaa-protocol-type-rlogin" {
        value 11;
        description
          "AAA protocol type RLogin";
        tailf:code-name "ENUM_protocol_type__AAA_PROTOCOL_TYPE_RLOGIN";
      }
      enum "aaa-protocol-type-lat" {
        value 12;
        description
          "AAA protocol type LAT";
        tailf:code-name "ENUM_protocol_type__AAA_PROTOCOL_TYPE_LAT";
      }
      enum "aaa-protocol-type-pad" {
        value 13;
        description
          "AAA protocol type PAD";
        tailf:code-name "ENUM_protocol_type__AAA_PROTOCOL_TYPE_PAD";
      }
      enum "aaa-protocol-type-osicp" {
        value 14;
        description
          "AAA protocol type OSICP";
        tailf:code-name "ENUM_protocol_type__AAA_PROTOCOL_TYPE_OSICP";
      }
      enum "aaa-protocol-type-tagcp" {
        value 15;
        description
          "AAA protocol type TAGCP";
        tailf:code-name "ENUM_protocol_type__AAA_PROTOCOL_TYPE_TAGCP";
      }
      enum "aaa-protocol-type-bacp" {
        value 16;
        description
          "AAA protocol type BACP";
        tailf:code-name "ENUM_protocol_type__AAA_PROTOCOL_TYPE_BACP";
      }
      enum "aaa-protocol-type-decnet" {
        value 17;
        description
          "AAA protocol type Decnet";
        tailf:code-name "ENUM_protocol_type__AAA_PROTOCOL_TYPE_DECNET";
      }
      enum "aaa-protocol-type-ccp" {
        value 18;
        description
          "AAA protocol type CCP";
        tailf:code-name "ENUM_protocol_type__AAA_PROTOCOL_TYPE_CCP";
      }
      enum "aaa-protocol-type-cdp" {
        value 19;
        description
          "AAA protocol type CDP";
        tailf:code-name "ENUM_protocol_type__AAA_PROTOCOL_TYPE_CDP";
      }
      enum "aaa-protocol-type-bridging" {
        value 20;
        description
          "AAA protocol type Bridging";
        tailf:code-name "ENUM_protocol_type__AAA_PROTOCOL_TYPE_BRIDGING";
      }
      enum "aaa-protocol-type-nbf" {
        value 21;
        description
          "AAA protocol type NBF";
        tailf:code-name "ENUM_protocol_type__AAA_PROTOCOL_TYPE_NBF";
      }
      enum "aaa-protocol-type-bap" {
        value 22;
        description
          "AAA protocol type BAP";
        tailf:code-name "ENUM_protocol_type__AAA_PROTOCOL_TYPE_BAP";
      }
      enum "aaa-protocol-type-multilink" {
        value 23;
        description
          "AAA protocol type Multilink";
        tailf:code-name "ENUM_protocol_type__AAA_PROTOCOL_TYPE_MULTILINK";
      }
      enum "aaa-protocol-type-h323" {
        value 24;
        description
          "AAA protocol type H323";
        tailf:code-name "ENUM_protocol_type__AAA_PROTOCOL_TYPE_H323";
      }
      enum "aaa-protocol-type-unknown" {
        value 25;
        description
          "AAA protocol type Unknown";
        tailf:code-name "ENUM_protocol_type__AAA_PROTOCOL_TYPE_UNKNOWN";
      }
      enum "aaa-protocol-type-call-accept" {
        value 26;
        description
          "AAA protocol type Accept";
        tailf:code-name "ENUM_protocol_type__AAA_PROTOCOL_TYPE_CALL_ACCEPT";
      }
      enum "aaa-protocol-type-vpdn-session" {
        value 27;
        description
          "AAA protocol type VPDN Session";
        tailf:code-name "ENUM_protocol_type__AAA_PROTOCOL_TYPE_VPDN_SESSION";
      }
      enum "aaa-protocol-type-rm-call-status" {
        value 28;
        description
          "AAA protocol type RM Call Status";
        tailf:code-name "ENUM_protocol_type__AAA_PROTOCOL_TYPE_RM_CALL_STATUS";
      }
      enum "aaa-protocol-type-rm-nas-status" {
        value 29;
        description
          "AAA protocol type RM NAS status";
        tailf:code-name "ENUM_protocol_type__AAA_PROTOCOL_TYPE_RM_NAS_STATUS";
      }
      enum "aaa-protocol-type-dial-in" {
        value 30;
        description
          "AAA protocol type Dial-In";
        tailf:code-name "ENUM_protocol_type__AAA_PROTOCOL_TYPE_DIAL_IN";
      }
      enum "aaa-protocol-type-dial-out" {
        value 31;
        description
          "AAA protocol type Dial-Out";
        tailf:code-name "ENUM_protocol_type__AAA_PROTOCOL_TYPE_DIAL_OUT";
      }
      enum "aaa-protocol-type-ss7" {
        value 32;
        description
          "AAA protocol type SS7";
        tailf:code-name "ENUM_protocol_type__AAA_PROTOCOL_TYPE_SS7";
      }
      enum "aaa-protocol-type-rms-stop" {
        value 33;
        description
          "AAA protocol type RMS Stop";
        tailf:code-name "ENUM_protocol_type__AAA_PROTOCOL_TYPE_RMS_STOP";
      }
      enum "aaa-protocol-type-rms-start" {
        value 34;
        description
          "AAA protocol type RMS Start";
        tailf:code-name "ENUM_protocol_type__AAA_PROTOCOL_TYPE_RMS_START";
      }
      enum "aaa-protocol-type-vpdn" {
        value 35;
        description
          "AAA protocol type VPDN";
        tailf:code-name "ENUM_protocol_type__AAA_PROTOCOL_TYPE_VPDN";
      }
      enum "aaa-protocol-type-sss" {
        value 36;
        description
          "AAA protocol type SSS";
        tailf:code-name "ENUM_protocol_type__AAA_PROTOCOL_TYPE_SSS";
      }
      enum "aaa-protocol-type-subscriber" {
        value 37;
        description
          "AAA protocol type Subscriber";
        tailf:code-name "ENUM_protocol_type__AAA_PROTOCOL_TYPE_SUBSCRIBER";
      }
      enum "aaa-protocol-type-atm" {
        value 38;
        description
          "AAA protocol type ATM";
        tailf:code-name "ENUM_protocol_type__AAA_PROTOCOL_TYPE_ATM";
      }
      enum "aaa-protocol-type-ssh" {
        value 39;
        description
          "AAA protocol type SSH";
        tailf:code-name "ENUM_protocol_type__AAA_PROTOCOL_TYPE_SSH";
      }
      enum "aaa-protocol-type-ipv6" {
        value 40;
        description
          "AAA protocol type IPv6";
        tailf:code-name "ENUM_protocol_type__AAA_PROTOCOL_TYPE_IPV6";
      }
      enum "aaa-protocol-type-pppoe" {
        value 41;
        description
          "AAA protocol type PPPoE";
        tailf:code-name "ENUM_protocol_type__AAA_PROTOCOL_TYPE_PPPOE";
      }
      enum "aaa-protocol-type-cdma" {
        value 42;
        description
          "AAA protocol type CDMA";
        tailf:code-name "ENUM_protocol_type__AAA_PROTOCOL_TYPE_CDMA";
      }
      enum "aaa-protocol-type-crb" {
        value 43;
        description
          "AAA protocol type CRB";
        tailf:code-name "ENUM_protocol_type__AAA_PROTOCOL_TYPE_CRB";
      }
      enum "aaa-protocol-type-template" {
        value 44;
        description
          "AAA protocol type Template";
        tailf:code-name "ENUM_protocol_type__AAA_PROTOCOL_TYPE_TEMPLATE";
      }
      enum "aaa-protocol-type-aaa" {
        value 45;
        description
          "AAA protocol type AAA";
        tailf:code-name "ENUM_protocol_type__AAA_PROTOCOL_TYPE_AAA";
      }
      enum "aaa-protocol-type-mac" {
        value 46;
        description
          "AAA protocol type MAC";
        tailf:code-name "ENUM_protocol_type__AAA_PROTOCOL_TYPE_MAC";
      }
      enum "aaa-protocol-type-leap" {
        value 47;
        description
          "AAA protocol type LEAP";
        tailf:code-name "ENUM_protocol_type__AAA_PROTOCOL_TYPE_LEAP";
      }
      enum "aaa-protocol-type-aironet" {
        value 48;
        description
          "AAA protocol type Aironet";
        tailf:code-name "ENUM_protocol_type__AAA_PROTOCOL_TYPE_AIRONET";
      }
      enum "aaa-protocol-type-entity" {
        value 49;
        description
          "AAA protocol type Entity";
        tailf:code-name "ENUM_protocol_type__AAA_PROTOCOL_TYPE_ENTITY";
      }
      enum "aaa-protocol-type-epd" {
        value 50;
        description
          "AAA protocol type EPD";
        tailf:code-name "ENUM_protocol_type__AAA_PROTOCOL_TYPE_EPD";
      }
      enum "aaa-protocol-type-igmp" {
        value 51;
        description
          "AAA protocol type IGMP";
        tailf:code-name "ENUM_protocol_type__AAA_PROTOCOL_TYPE_IGMP";
      }
      enum "aaa-protocol-type-webvpn" {
        value 52;
        description
          "AAA protocol type WEBVPN";
        tailf:code-name "ENUM_protocol_type__AAA_PROTOCOL_TYPE_WEBVPN";
      }
      enum "aaa-protocol-type-cts" {
        value 53;
        description
          "AAA protocol type CTS";
        tailf:code-name "ENUM_protocol_type__AAA_PROTOCOL_TYPE_CTS";
      }
      enum "aaa-protocol-type-radius" {
        value 54;
        description
          "AAA protocol type RADIUS";
        tailf:code-name "ENUM_protocol_type__AAA_PROTOCOL_TYPE_RADIUS";
      }
      enum "aaa-protocol-type-evc" {
        value 55;
        description
          "AAA protocol type EVC";
        tailf:code-name "ENUM_protocol_type__AAA_PROTOCOL_TYPE_EVC";
      }
      enum "aaa-protocol-type-elmi" {
        value 56;
        description
          "AAA protocol type ELMI";
        tailf:code-name "ENUM_protocol_type__AAA_PROTOCOL_TYPE_ELMI";
      }
      enum "aaa-protocol-type-dot1x" {
        value 57;
        description
          "AAA protocol type 802.1x";
        tailf:code-name "ENUM_protocol_type__AAA_PROTOCOL_TYPE_DOT1X";
      }
      enum "aaa-protocol-type-dtp" {
        value 58;
        description
          "AAA protocol type DTP";
        tailf:code-name "ENUM_protocol_type__AAA_PROTOCOL_TYPE_DTP";
      }
      enum "aaa-protocol-type-lacp" {
        value 59;
        description
          "AAA protocol type LACP";
        tailf:code-name "ENUM_protocol_type__AAA_PROTOCOL_TYPE_LACP";
      }
      enum "aaa-protocol-type-pagp" {
        value 60;
        description
          "AAA protocol type PAGP";
        tailf:code-name "ENUM_protocol_type__AAA_PROTOCOL_TYPE_PAGP";
      }
      enum "aaa-protocol-type-stp" {
        value 61;
        description
          "AAA protocol type STP";
        tailf:code-name "ENUM_protocol_type__AAA_PROTOCOL_TYPE_STP";
      }
      enum "aaa-protocol-type-vtp" {
        value 62;
        description
          "AAA protocol type VTP";
        tailf:code-name "ENUM_protocol_type__AAA_PROTOCOL_TYPE_VTP";
      }
      enum "aaa-protocol-type-ethernet-mac-tunnel" {
        value 63;
        description
          "AAA protocol type Ethernet MAC Tunnel";
        tailf:code-name "ENUM_protocol_type__AAA_PROTOCOL_TYPE_ETHERNET_MAC_TUNNEL";
      }
      enum "aaa-protocol-type-bridge-domain" {
        value 64;
        description
          "AAA protocol type Bridge Domain";
        tailf:code-name "ENUM_protocol_type__AAA_PROTOCOL_TYPE_BRIDGE_DOMAIN";
      }
      enum "aaa-protocol-type-ethernet-cfm" {
        value 65;
        description
          "AAA protocol type Ethernet CFM";
        tailf:code-name "ENUM_protocol_type__AAA_PROTOCOL_TYPE_ETHERNET_CFM";
      }
      enum "aaa-protocol-type-ethernet-service-instance" {
        value 66;
        description
          "AAA protocol type Ethernet Service Instance";
        tailf:code-name "ENUM_protocol_type__AAA_PROTOCOL_TYPE_ETHERNET_SERVICE_INSTANCE";
      }
      enum "aaa-protocol-type-service-group" {
        value 67;
        description
          "AAA protocol type Service Group";
        tailf:code-name "ENUM_protocol_type__AAA_PROTOCOL_TYPE_SERVICE_GROUP";
      }
      enum "aaa-protocol-type-ip-dhcp-snooping" {
        value 68;
        description
          "AAA protocol type IP DHCP Snooping";
        tailf:code-name "ENUM_protocol_type__AAA_PROTOCOL_TYPE_IP_DHCP_SNOOPING";
      }
      enum "aaa-protocol-type-ip-source-guard" {
        value 69;
        description
          "AAA protocol type IP Source Guard";
        tailf:code-name "ENUM_protocol_type__AAA_PROTOCOL_TYPE_IP_SOURCE_GUARD";
      }
      enum "aaa-protocol-type-error-disable" {
        value 70;
        description
          "AAA protocol type Error Disable";
        tailf:code-name "ENUM_protocol_type__AAA_PROTOCOL_TYPE_ERROR_DISABLE";
      }
      enum "aaa-protocol-type-cmac-bridge-domain" {
        value 71;
        description
          "AAA protocol type CMAC Bridge Domain";
        tailf:code-name "ENUM_protocol_type__AAA_PROTOCOL_TYPE_CMAC_BRIDGE_DOMAIN";
      }
      enum "aaa-protocol-type-mac-in-mac-tunnel" {
        value 72;
        description
          "AAA protocol type MAC-IN-MAC Tunnel";
        tailf:code-name "ENUM_protocol_type__AAA_PROTOCOL_TYPE_MAC_IN_MAC_TUNNEL";
      }
      enum "aaa-protocol-type-l2vpn" {
        value 73;
        description
          "AAA protocol type L2VPN";
        tailf:code-name "ENUM_protocol_type__AAA_PROTOCOL_TYPE_L2VPN";
      }
      enum "aaa-protocol-type-snmp" {
        value 74;
        description
          "AAA protocol type SNMP";
        tailf:code-name "ENUM_protocol_type__AAA_PROTOCOL_TYPE_SNMP";
      }
      enum "aaa-protocol-type-vnid" {
        value 75;
        description
          "AAA protocol type VNID";
        tailf:code-name "ENUM_protocol_type__AAA_PROTOCOL_TYPE_VNID";
      }
    }
    description
      "Protocol Type";
  }

  typedef serv-type {
    type enumeration {
      enum "aaa-service-type-none" {
        value 0;
        description
          "AAA service type None";
        tailf:code-name "ENUM_serv_type__AAA_SERVICE_TYPE_NONE";
      }
      enum "aaa-service-type-invalid" {
        value 1;
        description
          "AAA service type Invalid";
        tailf:code-name "ENUM_serv_type__AAA_SERVICE_TYPE_INVALID";
      }
      enum "aaa-service-type-shell" {
        value 2;
        description
          "AAA service type Shell";
        tailf:code-name "ENUM_serv_type__AAA_SERVICE_TYPE_SHELL";
      }
      enum "aaa-service-type-arap" {
        value 3;
        description
          "AAA service type ARAP";
        tailf:code-name "ENUM_serv_type__AAA_SERVICE_TYPE_ARAP";
      }
      enum "aaa-service-type-ppp" {
        value 4;
        description
          "AAA service type PPP";
        tailf:code-name "ENUM_serv_type__AAA_SERVICE_TYPE_PPP";
      }
      enum "aaa-service-type-slip" {
        value 5;
        description
          "AAA service type Slip";
        tailf:code-name "ENUM_serv_type__AAA_SERVICE_TYPE_SLIP";
      }
      enum "aaa-service-type-system" {
        value 6;
        description
          "AAA service type System";
        tailf:code-name "ENUM_serv_type__AAA_SERVICE_TYPE_SYSTEM";
      }
      enum "aaa-service-type-resource" {
        value 7;
        description
          "AAA service type Resource";
        tailf:code-name "ENUM_serv_type__AAA_SERVICE_TYPE_RESOURCE";
      }
      enum "aaa-service-type-connection" {
        value 8;
        description
          "AAA service type Connection";
        tailf:code-name "ENUM_serv_type__AAA_SERVICE_TYPE_CONNECTION";
      }
      enum "aaa-service-type-tty-daemon" {
        value 9;
        description
          "AAA service type TTY Daemon";
        tailf:code-name "ENUM_serv_type__AAA_SERVICE_TYPE_TTY_DAEMON";
      }
      enum "aaa-service-type-vpdn" {
        value 10;
        description
          "AAA service type VPDN";
        tailf:code-name "ENUM_serv_type__AAA_SERVICE_TYPE_VPDN";
      }
      enum "aaa-service-type-vpdn-out" {
        value 11;
        description
          "AAA service type VPDN Out";
        tailf:code-name "ENUM_serv_type__AAA_SERVICE_TYPE_VPDN_OUT";
      }
      enum "aaa-service-type-raccess" {
        value 12;
        description
          "AAA service type Remote-Access";
        tailf:code-name "ENUM_serv_type__AAA_SERVICE_TYPE_RACCESS";
      }
      enum "aaa-service-type-h323" {
        value 13;
        description
          "AAA service type H323";
        tailf:code-name "ENUM_serv_type__AAA_SERVICE_TYPE_H323";
      }
      enum "aaa-service-type-outbound" {
        value 14;
        description
          "AAA service type Outbound";
        tailf:code-name "ENUM_serv_type__AAA_SERVICE_TYPE_OUTBOUND";
      }
      enum "aaa-service-type-mobile-ip" {
        value 15;
        description
          "AAA service type Mobile-IP";
        tailf:code-name "ENUM_serv_type__AAA_SERVICE_TYPE_MOBILE_IP";
      }
      enum "aaa-service-type-auth-proxy" {
        value 16;
        description
          "AAA service type Auth-Proxy";
        tailf:code-name "ENUM_serv_type__AAA_SERVICE_TYPE_AUTH_PROXY";
      }
      enum "aaa-service-type-eou" {
        value 17;
        description
          "AAA service type EOU";
        tailf:code-name "ENUM_serv_type__AAA_SERVICE_TYPE_EOU";
      }
      enum "aaa-service-type-ike" {
        value 18;
        description
          "AAA service type IKE";
        tailf:code-name "ENUM_serv_type__AAA_SERVICE_TYPE_IKE";
      }
      enum "aaa-service-type-resource-management" {
        value 19;
        description
          "AAA service type Resource Management";
        tailf:code-name "ENUM_serv_type__AAA_SERVICE_TYPE_RESOURCE_MANAGEMENT";
      }
      enum "aaa-service-type-callback" {
        value 20;
        description
          "AAA service type Callback";
        tailf:code-name "ENUM_serv_type__AAA_SERVICE_TYPE_CALLBACK";
      }
      enum "aaa-service-type-gprs" {
        value 21;
        description
          "AAA service type GPRS";
        tailf:code-name "ENUM_serv_type__AAA_SERVICE_TYPE_GPRS";
      }
      enum "aaa-service-type-gprs-pdp-context" {
        value 22;
        description
          "AAA service type GPRS PDP Context";
        tailf:code-name "ENUM_serv_type__AAA_SERVICE_TYPE_GPRS_PDP_CONTEXT";
      }
      enum "aaa-service-type-preauth" {
        value 23;
        description
          "AAA service type Pre-Auth";
        tailf:code-name "ENUM_serv_type__AAA_SERVICE_TYPE_PREAUTH";
      }
      enum "aaa-service-type-translate" {
        value 24;
        description
          "AAA service type Translate";
        tailf:code-name "ENUM_serv_type__AAA_SERVICE_TYPE_TRANSLATE";
      }
      enum "aaa-service-type-pki" {
        value 25;
        description
          "AAA service type PKI";
        tailf:code-name "ENUM_serv_type__AAA_SERVICE_TYPE_PKI";
      }
      enum "aaa-service-type-ca" {
        value 26;
        description
          "AAA service type CA";
        tailf:code-name "ENUM_serv_type__AAA_SERVICE_TYPE_CA";
      }
      enum "aaa-service-type-tti" {
        value 27;
        description
          "AAA service type Trusted Transitive Introduction";
        tailf:code-name "ENUM_serv_type__AAA_SERVICE_TYPE_TTI";
      }
      enum "aaa-service-type-multicast" {
        value 28;
        description
          "AAA service type Multicast";
        tailf:code-name "ENUM_serv_type__AAA_SERVICE_TYPE_MULTICAST";
      }
      enum "aaa-service-type-encryption" {
        value 29;
        description
          "AAA service type Encryption";
        tailf:code-name "ENUM_serv_type__AAA_SERVICE_TYPE_ENCRYPTION";
      }
    }
    description
      "Service Type";
  }

  typedef aaa-req-status {
    type enumeration {
      enum "aaa-req-status-begin" {
        value 0;
        description
          "AAA Request Status Begin";
        tailf:code-name "ENUM_aaa_req_status__AAA_REQ_STATUS_BEGIN";
      }
      enum "aaa-req-status-sent" {
        value 1;
        description
          "AAA Request Status Sent";
        tailf:code-name "ENUM_aaa_req_status__AAA_REQ_STATUS_SENT";
      }
      enum "aaa-req-status-pass" {
        value 2;
        description
          "AAA Request Status Pass";
        tailf:code-name "ENUM_aaa_req_status__AAA_REQ_STATUS_PASS";
      }
      enum "aaa-req-status-fail" {
        value 3;
        description
          "AAA Request Fail";
        tailf:code-name "ENUM_aaa_req_status__AAA_REQ_STATUS_FAIL";
      }
      enum "aaa-req-status-fail-no-retries" {
        value 4;
        description
          "AAA Request Status Fail No Retries";
        tailf:code-name "ENUM_aaa_req_status__AAA_REQ_STATUS_FAIL_NO_RETRIES";
      }
      enum "aaa-req-status-failover-retry" {
        value 5;
        description
          "AAA Request Status Failover Retry";
        tailf:code-name "ENUM_aaa_req_status__AAA_REQ_STATUS_FAILOVER_RETRY";
      }
      enum "aaa-req-status-user-nopassword" {
        value 6;
        description
          "AAA Request Status User Nopassword";
        tailf:code-name "ENUM_aaa_req_status__AAA_REQ_STATUS_USER_NOPASSWORD";
      }
      enum "aaa-req-status-get-user" {
        value 7;
        description
          "AAA Request Status Get User";
        tailf:code-name "ENUM_aaa_req_status__AAA_REQ_STATUS_GET_USER";
      }
      enum "aaa-req-status-get-password" {
        value 8;
        description
          "AAA Request Status Get Password";
        tailf:code-name "ENUM_aaa_req_status__AAA_REQ_STATUS_GET_PASSWORD";
      }
      enum "aaa-req-status-get-data" {
        value 9;
        description
          "AAA Request Status Get Data";
        tailf:code-name "ENUM_aaa_req_status__AAA_REQ_STATUS_GET_DATA";
      }
      enum "aaa-req-status-cancelled" {
        value 10;
        description
          "AAA Request Status Cancelled";
        tailf:code-name "ENUM_aaa_req_status__AAA_REQ_STATUS_CANCELLED";
      }
      enum "aaa-req-status-get-challenge-response" {
        value 11;
        description
          "AAA Request Status Get Challenge Response";
        tailf:code-name "ENUM_aaa_req_status__AAA_REQ_STATUS_GET_CHALLENGE_RESPONSE";
      }
      enum "aaa-req-status-get-new-password" {
        value 12;
        description
          "AAA Request Status Get New Password";
        tailf:code-name "ENUM_aaa_req_status__AAA_REQ_STATUS_GET_NEW_PASSWORD";
      }
      enum "aaa-req-status-get-challenge-resp-noecho" {
        value 13;
        description
          "AAA Request Status Get Challenge Response Noecho";
        tailf:code-name "ENUM_aaa_req_status__AAA_REQ_STATUS_GET_CHALLENGE_RESP_NOECHO";
      }
    }
    description
      "AAA Request Status";
  }

  typedef aaa-attribute-type-tdl {
    type enumeration {
      enum "aaa-at-invalid" {
        value 0;
        description
          "Invalid attribute";
        tailf:code-name "ENUM_aaa_attribute_type_tdl__AAA_AT_INVALID_TDL";
      }
      enum "aaa-at-abort-cause" {
        value 1;
        description
          "Extended disconnect cause reasons";
        tailf:code-name "ENUM_aaa_attribute_type_tdl__AAA_AT_ABORT_CAUSE_TDL";
      }
      enum "aaa-at-acct-status-type" {
        value 2;
        description
          "The type of accounting request";
        tailf:code-name "ENUM_aaa_attribute_type_tdl__AAA_AT_ACCT_STATUS_TYPE_TDL";
      }
      enum "aaa-at-acct-tunnel-packets-lost" {
        value 3;
        description
          "The number of packets lost on a given link";
        tailf:code-name "ENUM_aaa_attribute_type_tdl__AAA_AT_ACCT_TUNNEL_PACKETS_LOST_TDL";
      }
      enum "aaa-at-acl" {
        value 4;
        description
          "An access list";
        tailf:code-name "ENUM_aaa_attribute_type_tdl__AAA_AT_ACL_TDL";
      }
      enum "aaa-at-authorized-services" {
        value 5;
        description
          "Services authorized by server";
        tailf:code-name "ENUM_aaa_attribute_type_tdl__AAA_AT_AUTHORIZED_SERVICES_TDL";
      }
      enum "aaa-at-auto-logon-service" {
        value 6;
        description
          "SG replacement for Service Selection Gateway vsa";
        tailf:code-name "ENUM_aaa_attribute_type_tdl__AAA_AT_AUTO_LOGON_SERVICE_TDL";
      }
      enum "aaa-at-azn-tag" {
        value 7;
        description
          "Identifies the translate-tag";
        tailf:code-name "ENUM_aaa_attribute_type_tdl__AAA_AT_AZN_TAG_TDL";
      }
      enum "aaa-at-ipv4-address" {
        value 8;
        description
          "The IPv4 address for the user";
        tailf:code-name "ENUM_aaa_attribute_type_tdl__AAA_AT_IPV4_ADDRESS_TDL";
      }
      enum "aaa-at-svc-assigned-ipv4-address" {
        value 9;
        description
          "Service assigned IP address for the user";
        tailf:code-name "ENUM_aaa_attribute_type_tdl__AAA_AT_SVC_ASSIGNED_IPV4_ADDRESS_TDL";
      }
      enum "aaa-at-ipv6-address" {
        value 10;
        description
          "The IPv6 address for the user";
        tailf:code-name "ENUM_aaa_attribute_type_tdl__AAA_AT_IPV6_ADDRESS_TDL";
      }
      enum "aaa-at-address-pool" {
        value 11;
        description
          "The IP address pool to obtain address from";
        tailf:code-name "ENUM_aaa_attribute_type_tdl__AAA_AT_ADDRESS_POOL_TDL";
      }
      enum "aaa-at-ip-subscriber-route" {
        value 12;
        description
          "IP Subscriber routes configuration";
        tailf:code-name "ENUM_aaa_attribute_type_tdl__AAA_AT_IP_SUBSCRIBER_ROUTE_TDL";
      }
      enum "aaa-at-async-map" {
        value 13;
        description
          "Async control character map";
        tailf:code-name "ENUM_aaa_attribute_type_tdl__AAA_AT_ASYNC_MAP_TDL";
      }
      enum "aaa-at-authentic" {
        value 14;
        description
          "Method of authentication";
        tailf:code-name "ENUM_aaa_attribute_type_tdl__AAA_AT_AUTHENTIC_TDL";
      }
      enum "aaa-at-autocommand" {
        value 15;
        description
          "Automatic command to run at startup";
        tailf:code-name "ENUM_aaa_attribute_type_tdl__AAA_AT_AUTOCOMMAND_TDL";
      }
      enum "aaa-at-autocommand-ip-prompt" {
        value 16;
        description
          "Automatic command to run at IP prompt";
        tailf:code-name "ENUM_aaa_attribute_type_tdl__AAA_AT_AUTOCOMMAND_IP_PROMPT_TDL";
      }
      enum "aaa-at-authen-status" {
        value 17;
        description
          "Indicates the authenticated status";
        tailf:code-name "ENUM_aaa_attribute_type_tdl__AAA_AT_AUTHEN_STATUS_TDL";
      }
      enum "aaa-at-authen-method" {
        value 18;
        description
          "Indicates the negotiated authentication protocol";
        tailf:code-name "ENUM_aaa_attribute_type_tdl__AAA_AT_AUTHEN_METHOD_TDL";
      }
      enum "aaa-at-authen-strength" {
        value 19;
        description
          "Indicates strength of authentication protocol [128 bit | 40 bit..]";
        tailf:code-name "ENUM_aaa_attribute_type_tdl__AAA_AT_AUTHEN_STRENGTH_TDL";
      }
      enum "aaa-at-callback" {
        value 20;
        description
          "Callback dial string";
        tailf:code-name "ENUM_aaa_attribute_type_tdl__AAA_AT_CALLBACK_TDL";
      }
      enum "aaa-at-callback-line" {
        value 21;
        description
          "Per-username line for callback";
        tailf:code-name "ENUM_aaa_attribute_type_tdl__AAA_AT_CALLBACK_LINE_TDL";
      }
      enum "aaa-at-callback-no-verify" {
        value 22;
        description
          "Does not require authentication after callback";
        tailf:code-name "ENUM_aaa_attribute_type_tdl__AAA_AT_CALLBACK_NO_VERIFY_TDL";
      }
      enum "aaa-at-callback-rotary" {
        value 23;
        description
          "Per-username rotary group for callback";
        tailf:code-name "ENUM_aaa_attribute_type_tdl__AAA_AT_CALLBACK_ROTARY_TDL";
      }
      enum "aaa-at-call-drops" {
        value 24;
        description
          "Call drop rate";
        tailf:code-name "ENUM_aaa_attribute_type_tdl__AAA_AT_CALL_DROPS_TDL";
      }
      enum "aaa-at-call-type" {
        value 25;
        description
          "Call type";
        tailf:code-name "ENUM_aaa_attribute_type_tdl__AAA_AT_CALL_TYPE_TDL";
      }
      enum "aaa-at-force-local-chap" {
        value 26;
        description
          "Force local CHAP flag";
        tailf:code-name "ENUM_aaa_attribute_type_tdl__AAA_AT_FORCE_LOCAL_CHAP_TDL";
      }
      enum "aaa-at-call-origin-endpoint" {
        value 27;
        description
          "The leg-2 endpoint value";
        tailf:code-name "ENUM_aaa_attribute_type_tdl__AAA_AT_CALL_ORIGIN_ENDPOINT_TDL";
      }
      enum "aaa-at-call-origin-endpoint-type" {
        value 28;
        description
          "The leg-2 endpoint info type";
        tailf:code-name "ENUM_aaa_attribute_type_tdl__AAA_AT_CALL_ORIGIN_ENDPOINT_TYPE_TDL";
      }
      enum "aaa-at-chap-challenge" {
        value 29;
        description
          "CHAP challenge";
        tailf:code-name "ENUM_aaa_attribute_type_tdl__AAA_AT_CHAP_CHALLENGE_TDL";
      }
      enum "aaa-at-chap-id" {
        value 30;
        description
          "CHAP id";
        tailf:code-name "ENUM_aaa_attribute_type_tdl__AAA_AT_CHAP_ID_TDL";
      }
      enum "aaa-at-chap-response" {
        value 31;
        description
          "CHAP response";
        tailf:code-name "ENUM_aaa_attribute_type_tdl__AAA_AT_CHAP_RESPONSE_TDL";
      }
      enum "aaa-at-chap-authen-user" {
        value 32;
        description
          "CHAP authentication user key";
        tailf:code-name "ENUM_aaa_attribute_type_tdl__AAA_AT_CHAP_AUTHEN_USER_TDL";
      }
      enum "aaa-at-connect-info" {
        value 33;
        description
          "Nature of the connection";
        tailf:code-name "ENUM_aaa_attribute_type_tdl__AAA_AT_CONNECT_INFO_TDL";
      }
      enum "aaa-at-user-data" {
        value 34;
        description
          "User data";
        tailf:code-name "ENUM_aaa_attribute_type_tdl__AAA_AT_USER_DATA_TDL";
      }
      enum "aaa-at-server-data" {
        value 35;
        description
          "Server data";
        tailf:code-name "ENUM_aaa_attribute_type_tdl__AAA_AT_SERVER_DATA_TDL";
      }
      enum "aaa-at-clid" {
        value 36;
        description
          "Calling station identifier";
        tailf:code-name "ENUM_aaa_attribute_type_tdl__AAA_AT_CLID_TDL";
      }
      enum "aaa-at-formatted-clid" {
        value 37;
        description
          "Formatted calling station identifier";
        tailf:code-name "ENUM_aaa_attribute_type_tdl__AAA_AT_FORMATTED_CLID_TDL";
      }
      enum "aaa-at-circuit-id" {
        value 38;
        description
          "Circuit-Id Tag";
        tailf:code-name "ENUM_aaa_attribute_type_tdl__AAA_AT_CIRCUIT_ID_TDL";
      }
      enum "aaa-at-remote-id" {
        value 39;
        description
          "Remote-Id Tag";
        tailf:code-name "ENUM_aaa_attribute_type_tdl__AAA_AT_REMOTE_ID_TDL";
      }
      enum "aaa-at-vendor-class-id" {
        value 40;
        description
          "Vendor-Class-Id Tag";
        tailf:code-name "ENUM_aaa_attribute_type_tdl__AAA_AT_VENDOR_CLASS_ID_TDL";
      }
      enum "aaa-at-caller-type-of-num" {
        value 41;
        description
          "ISDN caller type of number";
        tailf:code-name "ENUM_aaa_attribute_type_tdl__AAA_AT_CALLER_TYPE_OF_NUM_TDL";
      }
      enum "aaa-at-clid-mac-addr" {
        value 42;
        description
          "The MAC address from where the call came";
        tailf:code-name "ENUM_aaa_attribute_type_tdl__AAA_AT_CLID_MAC_ADDR_TDL";
      }
      enum "aaa-at-session-limit" {
        value 43;
        description
          "Session limit per port";
        tailf:code-name "ENUM_aaa_attribute_type_tdl__AAA_AT_SESSION_LIMIT_TDL";
      }
      enum "aaa-at-mac-address" {
        value 44;
        description
          "MAC address of client";
        tailf:code-name "ENUM_aaa_attribute_type_tdl__AAA_AT_MAC_ADDRESS_TDL";
      }
      enum "aaa-at-epd-peer-version" {
        value 45;
        description
          "EPD peer version";
        tailf:code-name "ENUM_aaa_attribute_type_tdl__AAA_AT_EPD_PEER_VERSION_TDL";
      }
      enum "aaa-at-epd-peer-mode" {
        value 46;
        description
          "EPD peer mode";
        tailf:code-name "ENUM_aaa_attribute_type_tdl__AAA_AT_EPD_PEER_MODE_TDL";
      }
      enum "aaa-at-epd-peer-keepalive" {
        value 47;
        description
          "EPD peer keepalive";
        tailf:code-name "ENUM_aaa_attribute_type_tdl__AAA_AT_EPD_PEER_KEEPALIVE_TDL";
      }
      enum "aaa-at-epd-peer-inform-owner-on-pull" {
        value 48;
        description
          "EPD peer inform Owner On Pull";
        tailf:code-name "ENUM_aaa_attribute_type_tdl__AAA_AT_EPD_PEER_INFORM_OWNER_ON_PULL_TDL";
      }
      enum "aaa-at-epd-acct-flows" {
        value 49;
        description
          "Number of EPD accounting flows";
        tailf:code-name "ENUM_aaa_attribute_type_tdl__AAA_AT_EPD_ACCT_FLOWS_TDL";
      }
      enum "aaa-at-epd-acct-flows-duration" {
        value 50;
        description
          "EPD accounting flow duration";
        tailf:code-name "ENUM_aaa_attribute_type_tdl__AAA_AT_EPD_ACCT_FLOWS_DURATION_TDL";
      }
      enum "aaa-at-actual-rate-up" {
        value 51;
        description
          "Actual Data-Rate Upstream";
        tailf:code-name "ENUM_aaa_attribute_type_tdl__AAA_AT_ACTUAL_RATE_UP_TDL";
      }
      enum "aaa-at-actual-rate-down" {
        value 52;
        description
          "Actual Data-Rate Downstream";
        tailf:code-name "ENUM_aaa_attribute_type_tdl__AAA_AT_ACTUAL_RATE_DOWN_TDL";
      }
      enum "aaa-at-min-rate-up" {
        value 53;
        description
          "Minimum Data-Rate Upstream";
        tailf:code-name "ENUM_aaa_attribute_type_tdl__AAA_AT_MIN_RATE_UP_TDL";
      }
      enum "aaa-at-min-rate-down" {
        value 54;
        description
          "Minimum Data-Rate Downstream";
        tailf:code-name "ENUM_aaa_attribute_type_tdl__AAA_AT_MIN_RATE_DOWN_TDL";
      }
      enum "aaa-at-attainable-rate-up" {
        value 55;
        description
          "Attainable Data-Rate Upstream";
        tailf:code-name "ENUM_aaa_attribute_type_tdl__AAA_AT_ATTAINABLE_RATE_UP_TDL";
      }
      enum "aaa-at-attainable-rate-down" {
        value 56;
        description
          "Attainable Data-Rate Downstream";
        tailf:code-name "ENUM_aaa_attribute_type_tdl__AAA_AT_ATTAINABLE_RATE_DOWN_TDL";
      }
      enum "aaa-at-max-rate-up" {
        value 57;
        description
          "Maximum Data-Rate Upstream";
        tailf:code-name "ENUM_aaa_attribute_type_tdl__AAA_AT_MAX_RATE_UP_TDL";
      }
      enum "aaa-at-max-rate-down" {
        value 58;
        description
          "Maximum Data-Rate Downstream";
        tailf:code-name "ENUM_aaa_attribute_type_tdl__AAA_AT_MAX_RATE_DOWN_TDL";
      }
      enum "aaa-at-min-rate-up-lp" {
        value 59;
        description
          "Minimum Data-Rate Upstream-Low-Power";
        tailf:code-name "ENUM_aaa_attribute_type_tdl__AAA_AT_MIN_RATE_UP_LP_TDL";
      }
      enum "aaa-at-min-rate-down-lp" {
        value 60;
        description
          "Minimum Data-Rate Downstream Low Power";
        tailf:code-name "ENUM_aaa_attribute_type_tdl__AAA_AT_MIN_RATE_DOWN_LP_TDL";
      }
      enum "aaa-at-max-inter-delay-up" {
        value 61;
        description
          "Maximum Interleaving Delay Upstream";
        tailf:code-name "ENUM_aaa_attribute_type_tdl__AAA_AT_MAX_INTER_DELAY_UP_TDL";
      }
      enum "aaa-at-max-inter-delay-down" {
        value 62;
        description
          "Maximum Interleaving Delay Downstream";
        tailf:code-name "ENUM_aaa_attribute_type_tdl__AAA_AT_MAX_INTER_DELAY_DOWN_TDL";
      }
      enum "aaa-at-actual-inter-delay-up" {
        value 63;
        description
          "Actual Interleaving Delay Upstream";
        tailf:code-name "ENUM_aaa_attribute_type_tdl__AAA_AT_ACTUAL_INTER_DELAY_UP_TDL";
      }
      enum "aaa-at-actual-inter-delay-down" {
        value 64;
        description
          "Actual Interleaving Delay Downstream";
        tailf:code-name "ENUM_aaa_attribute_type_tdl__AAA_AT_ACTUAL_INTER_DELAY_DOWN_TDL";
      }
      enum "aaa-at-iwf-tag" {
        value 65;
        description
          "Interworking Functionality Tag";
        tailf:code-name "ENUM_aaa_attribute_type_tdl__AAA_AT_IWF_TAG_TDL";
      }
      enum "aaa-at-access-loop-encapsulation" {
        value 66;
        description
          "Access Loop Encapsulation";
        tailf:code-name "ENUM_aaa_attribute_type_tdl__AAA_AT_ACCESS_LOOP_ENCAPSULATION_TDL";
      }
      enum "aaa-at-epd-reporting-reason" {
        value 67;
        description
          "EPD reporting reason";
        tailf:code-name "ENUM_aaa_attribute_type_tdl__AAA_AT_EPD_REPORTING_REASON_TDL";
      }
      enum "aaa-at-dsl-type" {
        value 68;
        description
          "DSL type";
        tailf:code-name "ENUM_aaa_attribute_type_tdl__AAA_AT_DSL_TYPE_TDL";
      }
      enum "aaa-at-ancp-line-rate" {
        value 69;
        description
          "Line rate of Digital Subscriber Line Access Multiplex client";
        tailf:code-name "ENUM_aaa_attribute_type_tdl__AAA_AT_ANCP_LINE_RATE_TDL";
      }
      enum "aaa-at-data-rate-kbps" {
        value 70;
        description
          "Rate of data received in kbps";
        tailf:code-name "ENUM_aaa_attribute_type_tdl__AAA_AT_DATA_RATE_KBPS_TDL";
      }
      enum "aaa-at-xmit-rate-kbps" {
        value 71;
        description
          "The kbps rate which packets are being sent to the user";
        tailf:code-name "ENUM_aaa_attribute_type_tdl__AAA_AT_XMIT_RATE_KBPS_TDL";
      }
      enum "aaa-at-ancp-access-loop-cir-id" {
        value 72;
        description
          "Access Node Control Protocol access loop cir-id";
        tailf:code-name "ENUM_aaa_attribute_type_tdl__AAA_AT_ANCP_ACCESS_LOOP_CIR_ID_TDL";
      }
      enum "aaa-at-command" {
        value 73;
        description
          "Command";
        tailf:code-name "ENUM_aaa_attribute_type_tdl__AAA_AT_COMMAND_TDL";
      }
      enum "aaa-at-command-arg" {
        value 74;
        description
          "Command argument";
        tailf:code-name "ENUM_aaa_attribute_type_tdl__AAA_AT_COMMAND_ARG_TDL";
      }
      enum "aaa-at-conn-prog" {
        value 75;
        description
          "Connection progress";
        tailf:code-name "ENUM_aaa_attribute_type_tdl__AAA_AT_CONN_PROG_TDL";
      }
      enum "aaa-at-connect-rx-speed" {
        value 76;
        description
          "Connection RX speed";
        tailf:code-name "ENUM_aaa_attribute_type_tdl__AAA_AT_CONNECT_RX_SPEED_TDL";
      }
      enum "aaa-at-connect-tx-speed" {
        value 77;
        description
          "Connection TX speed";
        tailf:code-name "ENUM_aaa_attribute_type_tdl__AAA_AT_CONNECT_TX_SPEED_TDL";
      }
      enum "aaa-at-data-rate" {
        value 78;
        description
          "Rate of data received";
        tailf:code-name "ENUM_aaa_attribute_type_tdl__AAA_AT_DATA_RATE_TDL";
      }
      enum "aaa-at-data-service" {
        value 79;
        description
          "Type of data service for outgoing call";
        tailf:code-name "ENUM_aaa_attribute_type_tdl__AAA_AT_DATA_SERVICE_TDL";
      }
      enum "aaa-at-dial-number" {
        value 80;
        description
          "Number to dial for outgoing call";
        tailf:code-name "ENUM_aaa_attribute_type_tdl__AAA_AT_DIAL_NUMBER_TDL";
      }
      enum "aaa-at-trunkgroup" {
        value 81;
        description
          "The trunk-group to be used for the outgoing call";
        tailf:code-name "ENUM_aaa_attribute_type_tdl__AAA_AT_TRUNKGROUP_TDL";
      }
      enum "aaa-at-dnis" {
        value 82;
        description
          "Destination station identifier";
        tailf:code-name "ENUM_aaa_attribute_type_tdl__AAA_AT_DNIS_TDL";
      }
      enum "aaa-at-dns-server" {
        value 83;
        description
          "Primary and Secondary DNS Servers";
        tailf:code-name "ENUM_aaa_attribute_type_tdl__AAA_AT_DNS_SERVER_TDL";
      }
      enum "aaa-at-auto-update" {
        value 84;
        description
          "Client Url Revision";
        tailf:code-name "ENUM_aaa_attribute_type_tdl__AAA_AT_AUTO_UPDATE_TDL";
      }
      enum "aaa-at-dns-server-primary" {
        value 85;
        description
          "Primary DNS server address";
        tailf:code-name "ENUM_aaa_attribute_type_tdl__AAA_AT_DNS_SERVER_PRIMARY_TDL";
      }
      enum "aaa-at-dns-server-secondary" {
        value 86;
        description
          "Secondary DNS server address";
        tailf:code-name "ENUM_aaa_attribute_type_tdl__AAA_AT_DNS_SERVER_SECONDARY_TDL";
      }
      enum "aaa-at-eap-message" {
        value 87;
        description
          "Extended Access Protocol (EAP) packet encapsulation";
        tailf:code-name "ENUM_aaa_attribute_type_tdl__AAA_AT_EAP_MESSAGE_TDL";
      }
      enum "aaa-at-eap-session-id" {
        value 88;
        description
          "EAP Session ID for CAK name derivation";
        tailf:code-name "ENUM_aaa_attribute_type_tdl__AAA_AT_EAP_SESSION_ID_TDL";
      }
      enum "aaa-at-dns-client-assign" {
        value 89;
        description
          "Assign client with DNS attributes";
        tailf:code-name "ENUM_aaa_attribute_type_tdl__AAA_AT_DNS_CLIENT_ASSIGN_TDL";
      }
      enum "aaa-at-email-server-ack-flag" {
        value 90;
        description
          "Email server ack flag";
        tailf:code-name "ENUM_aaa_attribute_type_tdl__AAA_AT_EMAIL_SERVER_ACK_FLAG_TDL";
      }
      enum "aaa-at-event" {
        value 91;
        description
          "Specifies the event requested by the NAD";
        tailf:code-name "ENUM_aaa_attribute_type_tdl__AAA_AT_EVENT_TDL";
      }
      enum "aaa-at-reason" {
        value 92;
        description
          "Reason information";
        tailf:code-name "ENUM_aaa_attribute_type_tdl__AAA_AT_REASON_TDL";
      }
      enum "aaa-at-fax-account-id-origin" {
        value 93;
        description
          "Fax account id origin";
        tailf:code-name "ENUM_aaa_attribute_type_tdl__AAA_AT_FAX_ACCOUNT_ID_ORIGIN_TDL";
      }
      enum "aaa-at-fax-auth-status" {
        value 94;
        description
          "Fax authentication status";
        tailf:code-name "ENUM_aaa_attribute_type_tdl__AAA_AT_FAX_AUTH_STATUS_TDL";
      }
      enum "aaa-at-fax-connect-speed" {
        value 95;
        description
          "Fax connect speed";
        tailf:code-name "ENUM_aaa_attribute_type_tdl__AAA_AT_FAX_CONNECT_SPEED_TDL";
      }
      enum "aaa-at-fax-cover-page-flag" {
        value 96;
        description
          "Fax cover page flag";
        tailf:code-name "ENUM_aaa_attribute_type_tdl__AAA_AT_FAX_COVER_PAGE_FLAG_TDL";
      }
      enum "aaa-at-fax-dsn-address" {
        value 97;
        description
          "Fax Delivery Status Notification address";
        tailf:code-name "ENUM_aaa_attribute_type_tdl__AAA_AT_FAX_DSN_ADDRESS_TDL";
      }
      enum "aaa-at-fax-dsn-flag" {
        value 98;
        description
          "Flag for fax Delivery Status Notification";
        tailf:code-name "ENUM_aaa_attribute_type_tdl__AAA_AT_FAX_DSN_FLAG_TDL";
      }
      enum "aaa-at-fax-mdn-address" {
        value 99;
        description
          "Fax Message Disposition Notifications address";
        tailf:code-name "ENUM_aaa_attribute_type_tdl__AAA_AT_FAX_MDN_ADDRESS_TDL";
      }
      enum "aaa-at-fax-mdn-flag" {
        value 100;
        description
          "Fax Message Disposition Notifications flag";
        tailf:code-name "ENUM_aaa_attribute_type_tdl__AAA_AT_FAX_MDN_FLAG_TDL";
      }
      enum "aaa-at-fax-msg-id" {
        value 101;
        description
          "Fax message ID";
        tailf:code-name "ENUM_aaa_attribute_type_tdl__AAA_AT_FAX_MSG_ID_TDL";
      }
      enum "aaa-at-fax-modem-time" {
        value 102;
        description
          "Fax modem time";
        tailf:code-name "ENUM_aaa_attribute_type_tdl__AAA_AT_FAX_MODEM_TIME_TDL";
      }
      enum "aaa-at-fax-pages" {
        value 103;
        description
          "Fax pages";
        tailf:code-name "ENUM_aaa_attribute_type_tdl__AAA_AT_FAX_PAGES_TDL";
      }
      enum "aaa-at-fax-abort-cause" {
        value 104;
        description
          "Fax abort cause";
        tailf:code-name "ENUM_aaa_attribute_type_tdl__AAA_AT_FAX_ABORT_CAUSE_TDL";
      }
      enum "aaa-at-email-server-address" {
        value 105;
        description
          "Email server address";
        tailf:code-name "ENUM_aaa_attribute_type_tdl__AAA_AT_EMAIL_SERVER_ADDRESS_TDL";
      }
      enum "aaa-at-fax-process-abort-flag" {
        value 106;
        description
          "Fax process abort flag";
        tailf:code-name "ENUM_aaa_attribute_type_tdl__AAA_AT_FAX_PROCESS_ABORT_FLAG_TDL";
      }
      enum "aaa-at-fax-recipient-count" {
        value 107;
        description
          "Fax recipient count";
        tailf:code-name "ENUM_aaa_attribute_type_tdl__AAA_AT_FAX_RECIPIENT_COUNT_TDL";
      }
      enum "aaa-at-fltsv-cache-refresh" {
        value 108;
        description
          "Filter cache timer";
        tailf:code-name "ENUM_aaa_attribute_type_tdl__AAA_AT_FLTSV_CACHE_REFRESH_TDL";
      }
      enum "aaa-at-fltsv-cache-time" {
        value 109;
        description
          "Time which filter profile should remain cached";
        tailf:code-name "ENUM_aaa_attribute_type_tdl__AAA_AT_FLTSV_CACHE_TIME_TDL";
      }
      enum "aaa-at-fltsv-required" {
        value 110;
        description
          "Requires a filter profile";
        tailf:code-name "ENUM_aaa_attribute_type_tdl__AAA_AT_FLTSV_REQUIRED_TDL";
      }
      enum "aaa-at-framed-protocol" {
        value 111;
        description
          "The framed protocol";
        tailf:code-name "ENUM_aaa_attribute_type_tdl__AAA_AT_FRAMED_PROTOCOL_TDL";
      }
      enum "aaa-at-framed-mtu" {
        value 112;
        description
          "The MTU available on the link";
        tailf:code-name "ENUM_aaa_attribute_type_tdl__AAA_AT_FRAMED_MTU_TDL";
      }
      enum "aaa-at-force-56" {
        value 113;
        description
          "Whether the NAS should use only 56 KB";
        tailf:code-name "ENUM_aaa_attribute_type_tdl__AAA_AT_FORCE_56_TDL";
      }
      enum "aaa-at-gateway-id" {
        value 114;
        description
          "Gateway ID";
        tailf:code-name "ENUM_aaa_attribute_type_tdl__AAA_AT_GATEWAY_ID_TDL";
      }
      enum "aaa-at-ggsn-grouped" {
        value 115;
        description
          "Grouped Gateway GPRS Support Node Attributes";
        tailf:code-name "ENUM_aaa_attribute_type_tdl__AAA_AT_GGSN_GROUPED_TDL";
      }
      enum "aaa-at-h323-billing-model" {
        value 116;
        description
          "H323 billing model";
        tailf:code-name "ENUM_aaa_attribute_type_tdl__AAA_AT_H323_BILLING_MODEL_TDL";
      }
      enum "aaa-at-h323-call-origin" {
        value 117;
        description
          "H323 call origin";
        tailf:code-name "ENUM_aaa_attribute_type_tdl__AAA_AT_H323_CALL_ORIGIN_TDL";
      }
      enum "aaa-at-h323-call-type" {
        value 118;
        description
          "H323 call type";
        tailf:code-name "ENUM_aaa_attribute_type_tdl__AAA_AT_H323_CALL_TYPE_TDL";
      }
      enum "aaa-at-h323-conf-id" {
        value 119;
        description
          "H323 conference ID";
        tailf:code-name "ENUM_aaa_attribute_type_tdl__AAA_AT_H323_CONF_ID_TDL";
      }
      enum "aaa-at-h323-connect-time" {
        value 120;
        description
          "H323 connection time";
        tailf:code-name "ENUM_aaa_attribute_type_tdl__AAA_AT_H323_CONNECT_TIME_TDL";
      }
      enum "aaa-at-h323-credit-amount" {
        value 121;
        description
          "H323 credit amount";
        tailf:code-name "ENUM_aaa_attribute_type_tdl__AAA_AT_H323_CREDIT_AMOUNT_TDL";
      }
      enum "aaa-at-h323-credit-time" {
        value 122;
        description
          "H323 credit time";
        tailf:code-name "ENUM_aaa_attribute_type_tdl__AAA_AT_H323_CREDIT_TIME_TDL";
      }
      enum "aaa-at-h323-currency-type" {
        value 123;
        description
          "H323 currency type";
        tailf:code-name "ENUM_aaa_attribute_type_tdl__AAA_AT_H323_CURRENCY_TYPE_TDL";
      }
      enum "aaa-at-h323-disconnect-cause" {
        value 124;
        description
          "H323 disconnect cause";
        tailf:code-name "ENUM_aaa_attribute_type_tdl__AAA_AT_H323_DISCONNECT_CAUSE_TDL";
      }
      enum "aaa-at-h323-disconnect-time" {
        value 125;
        description
          "H323 disconnect time";
        tailf:code-name "ENUM_aaa_attribute_type_tdl__AAA_AT_H323_DISCONNECT_TIME_TDL";
      }
      enum "aaa-at-h323-gw-id" {
        value 126;
        description
          "H323 gateway ID";
        tailf:code-name "ENUM_aaa_attribute_type_tdl__AAA_AT_H323_GW_ID_TDL";
      }
      enum "aaa-at-h323-incoming-conf-id" {
        value 127;
        description
          "H323 incoming conference ID";
        tailf:code-name "ENUM_aaa_attribute_type_tdl__AAA_AT_H323_INCOMING_CONF_ID_TDL";
      }
      enum "aaa-at-h323-ivr-in" {
        value 128;
        description
          "H323 Interactive Voice Response in";
        tailf:code-name "ENUM_aaa_attribute_type_tdl__AAA_AT_H323_IVR_IN_TDL";
      }
      enum "aaa-at-h323-ivr-out" {
        value 129;
        description
          "H323 Interactive Voice Response out";
        tailf:code-name "ENUM_aaa_attribute_type_tdl__AAA_AT_H323_IVR_OUT_TDL";
      }
      enum "aaa-at-h323-preferred-lang" {
        value 130;
        description
          "H323 preferred language";
        tailf:code-name "ENUM_aaa_attribute_type_tdl__AAA_AT_H323_PREFERRED_LANG_TDL";
      }
      enum "aaa-at-h323-prompt-id" {
        value 131;
        description
          "H323 prompt ID";
        tailf:code-name "ENUM_aaa_attribute_type_tdl__AAA_AT_H323_PROMPT_ID_TDL";
      }
      enum "aaa-at-h323-redirect-ip-address" {
        value 132;
        description
          "H323 redirect ip address";
        tailf:code-name "ENUM_aaa_attribute_type_tdl__AAA_AT_H323_REDIRECT_IP_ADDRESS_TDL";
      }
      enum "aaa-at-h323-redirect-number" {
        value 133;
        description
          "H323 redirect number";
        tailf:code-name "ENUM_aaa_attribute_type_tdl__AAA_AT_H323_REDIRECT_NUMBER_TDL";
      }
      enum "aaa-at-h323-remote-address" {
        value 134;
        description
          "H323 remote address";
        tailf:code-name "ENUM_aaa_attribute_type_tdl__AAA_AT_H323_REMOTE_ADDRESS_TDL";
      }
      enum "aaa-at-h323-remote-id" {
        value 135;
        description
          "H323 remote ID";
        tailf:code-name "ENUM_aaa_attribute_type_tdl__AAA_AT_H323_REMOTE_ID_TDL";
      }
      enum "aaa-at-h323-return-code" {
        value 136;
        description
          "H323 return code";
        tailf:code-name "ENUM_aaa_attribute_type_tdl__AAA_AT_H323_RETURN_CODE_TDL";
      }
      enum "aaa-at-h323-setup-time" {
        value 137;
        description
          "H323 setup time";
        tailf:code-name "ENUM_aaa_attribute_type_tdl__AAA_AT_H323_SETUP_TIME_TDL";
      }
      enum "aaa-at-h323-time-and-day" {
        value 138;
        description
          "H323 time and day";
        tailf:code-name "ENUM_aaa_attribute_type_tdl__AAA_AT_H323_TIME_AND_DAY_TDL";
      }
      enum "aaa-at-h323-voice-quality" {
        value 139;
        description
          "H323 voice quality";
        tailf:code-name "ENUM_aaa_attribute_type_tdl__AAA_AT_H323_VOICE_QUALITY_TDL";
      }
      enum "aaa-at-h323-subscriber" {
        value 140;
        description
          "H323 subscriber";
        tailf:code-name "ENUM_aaa_attribute_type_tdl__AAA_AT_H323_SUBSCRIBER_TDL";
      }
      enum "aaa-at-release-source" {
        value 141;
        description
          "Originator of the call release";
        tailf:code-name "ENUM_aaa_attribute_type_tdl__AAA_AT_RELEASE_SOURCE_TDL";
      }
      enum "aaa-at-idle-timeout" {
        value 142;
        description
          "Idle seconds before disconnect";
        tailf:code-name "ENUM_aaa_attribute_type_tdl__AAA_AT_IDLE_TIMEOUT_TDL";
      }
      enum "aaa-at-call-in-acl" {
        value 143;
        description
          "A call ingress access list";
        tailf:code-name "ENUM_aaa_attribute_type_tdl__AAA_AT_CALL_IN_ACL_TDL";
      }
      enum "aaa-at-in-acl" {
        value 144;
        description
          "An ingress access list";
        tailf:code-name "ENUM_aaa_attribute_type_tdl__AAA_AT_IN_ACL_TDL";
      }
      enum "aaa-at-input-giga-words" {
        value 145;
        description
          "Number of times that Acct-Input-Octets has wrapped";
        tailf:code-name "ENUM_aaa_attribute_type_tdl__AAA_AT_INPUT_GIGA_WORDS_TDL";
      }
      enum "aaa-at-input-octets" {
        value 146;
        description
          "Bytes received from a port";
        tailf:code-name "ENUM_aaa_attribute_type_tdl__AAA_AT_INPUT_OCTETS_TDL";
      }
      enum "aaa-at-input-packets" {
        value 147;
        description
          "Packets received from a port";
        tailf:code-name "ENUM_aaa_attribute_type_tdl__AAA_AT_INPUT_PACKETS_TDL";
      }
      enum "aaa-at-input-giga-words-ipv6" {
        value 148;
        description
          "Number of times that Acct-Input-Octets-IPv6 has wrapped";
        tailf:code-name "ENUM_aaa_attribute_type_tdl__AAA_AT_INPUT_GIGA_WORDS_IPV6_TDL";
      }
      enum "aaa-at-input-octets-ipv6" {
        value 149;
        description
          "Bytes received from a port for IPv6 sessions";
        tailf:code-name "ENUM_aaa_attribute_type_tdl__AAA_AT_INPUT_OCTETS_IPV6_TDL";
      }
      enum "aaa-at-input-packets-ipv6" {
        value 150;
        description
          "IPv6 Packets received from a port";
        tailf:code-name "ENUM_aaa_attribute_type_tdl__AAA_AT_INPUT_PACKETS_IPV6_TDL";
      }
      enum "aaa-at-tariff-input-giga-words" {
        value 151;
        description
          "Number of times that tariff-input-octets has wrapped";
        tailf:code-name "ENUM_aaa_attribute_type_tdl__AAA_AT_TARIFF_INPUT_GIGA_WORDS_TDL";
      }
      enum "aaa-at-tariff-input-octets" {
        value 152;
        description
          "Per Tariff bytes received for a session";
        tailf:code-name "ENUM_aaa_attribute_type_tdl__AAA_AT_TARIFF_INPUT_OCTETS_TDL";
      }
      enum "aaa-at-tariff-input-packets" {
        value 153;
        description
          "Per Tariff Packets received for a session";
        tailf:code-name "ENUM_aaa_attribute_type_tdl__AAA_AT_TARIFF_INPUT_PACKETS_TDL";
      }
      enum "aaa-at-tariff-input-giga-words-ipv6" {
        value 154;
        description
          "Number of times that tariff-input-octets-ipv6 has wrapped";
        tailf:code-name "ENUM_aaa_attribute_type_tdl__AAA_AT_TARIFF_INPUT_GIGA_WORDS_IPV6_TDL";
      }
      enum "aaa-at-tariff-input-octets-ipv6" {
        value 155;
        description
          "Per tariff IPv6 bytes received for a session";
        tailf:code-name "ENUM_aaa_attribute_type_tdl__AAA_AT_TARIFF_INPUT_OCTETS_IPV6_TDL";
      }
      enum "aaa-at-tariff-input-packets-ipv6" {
        value 156;
        description
          "Per Tariff IPv6 Packets received for a session";
        tailf:code-name "ENUM_aaa_attribute_type_tdl__AAA_AT_TARIFF_INPUT_PACKETS_IPV6_TDL";
      }
      enum "aaa-at-tariff-output-giga-words" {
        value 157;
        description
          "Number of times that tariff-output-octets has wrapped";
        tailf:code-name "ENUM_aaa_attribute_type_tdl__AAA_AT_TARIFF_OUTPUT_GIGA_WORDS_TDL";
      }
      enum "aaa-at-tariff-output-octets" {
        value 158;
        description
          "Per Tariff bytes sent for a session";
        tailf:code-name "ENUM_aaa_attribute_type_tdl__AAA_AT_TARIFF_OUTPUT_OCTETS_TDL";
      }
      enum "aaa-at-tariff-output-packets" {
        value 159;
        description
          "Per Tariff Packets sent for a session";
        tailf:code-name "ENUM_aaa_attribute_type_tdl__AAA_AT_TARIFF_OUTPUT_PACKETS_TDL";
      }
      enum "aaa-at-tariff-output-giga-words-ipv6" {
        value 160;
        description
          "Number of times that tariff-output-octets-ipv6 has wrapped";
        tailf:code-name "ENUM_aaa_attribute_type_tdl__AAA_AT_TARIFF_OUTPUT_GIGA_WORDS_IPV6_TDL";
      }
      enum "aaa-at-tariff-output-octets-ipv6" {
        value 161;
        description
          "Per tariff IPv6 bytes sent for a session";
        tailf:code-name "ENUM_aaa_attribute_type_tdl__AAA_AT_TARIFF_OUTPUT_OCTETS_IPV6_TDL";
      }
      enum "aaa-at-tariff-output-packets-ipv6" {
        value 162;
        description
          "Per Tariff IPv6 Packets sent for a session";
        tailf:code-name "ENUM_aaa_attribute_type_tdl__AAA_AT_TARIFF_OUTPUT_PACKETS_IPV6_TDL";
      }
      enum "aaa-at-idmgr-data" {
        value 163;
        description
          "ID MGR data";
        tailf:code-name "ENUM_aaa_attribute_type_tdl__AAA_AT_IDMGR_DATA_TDL";
      }
      enum "aaa-at-idmgr-svc-key" {
        value 164;
        description
          "Key to identify a service; session-handle + service-name";
        tailf:code-name "ENUM_aaa_attribute_type_tdl__AAA_AT_IDMGR_SVC_KEY_TDL";
      }
      enum "aaa-at-pppoe-unique-key" {
        value 165;
        description
          "Unique key identifier for pppoe session";
        tailf:code-name "ENUM_aaa_attribute_type_tdl__AAA_AT_PPPOE_UNIQUE_KEY_TDL";
      }
      enum "aaa-at-session-guid" {
        value 166;
        description
          "Global identifier for a session";
        tailf:code-name "ENUM_aaa_attribute_type_tdl__AAA_AT_SESSION_GUID_TDL";
      }
      enum "aaa-at-nas-identifier" {
        value 167;
        description
          "A string identifying the NAS sending the Access-Request";
        tailf:code-name "ENUM_aaa_attribute_type_tdl__AAA_AT_NAS_IDENTIFIER_TDL";
      }
      enum "aaa-at-charged-units" {
        value 168;
        description
          "Charged units";
        tailf:code-name "ENUM_aaa_attribute_type_tdl__AAA_AT_CHARGED_UNITS_TDL";
      }
      enum "aaa-at-disconnect-text" {
        value 169;
        description
          "Disconnect text";
        tailf:code-name "ENUM_aaa_attribute_type_tdl__AAA_AT_DISCONNECT_TEXT_TDL";
      }
      enum "aaa-at-info-type" {
        value 170;
        description
          "Information type";
        tailf:code-name "ENUM_aaa_attribute_type_tdl__AAA_AT_INFO_TYPE_TDL";
      }
      enum "aaa-at-logical-if-index" {
        value 171;
        description
          "Interface from which call was made";
        tailf:code-name "ENUM_aaa_attribute_type_tdl__AAA_AT_LOGICAL_IF_INDEX_TDL";
      }
      enum "aaa-at-peer-address" {
        value 172;
        description
          "The number this call was connected to";
        tailf:code-name "ENUM_aaa_attribute_type_tdl__AAA_AT_PEER_ADDRESS_TDL";
      }
      enum "aaa-at-peer-id" {
        value 173;
        description
          "Id value of the peer table entry this call was made to";
        tailf:code-name "ENUM_aaa_attribute_type_tdl__AAA_AT_PEER_ID_TDL";
      }
      enum "aaa-at-peer-if-index" {
        value 174;
        description
          "Index value of peer table entry the call was made to";
        tailf:code-name "ENUM_aaa_attribute_type_tdl__AAA_AT_PEER_IF_INDEX_TDL";
      }
      enum "aaa-at-acom-level" {
        value 175;
        description
          "Telephony VSA level";
        tailf:code-name "ENUM_aaa_attribute_type_tdl__AAA_AT_ACOM_LEVEL_TDL";
      }
      enum "aaa-at-tx-duration" {
        value 176;
        description
          "Duration of transmit path open from this peer to gateway";
        tailf:code-name "ENUM_aaa_attribute_type_tdl__AAA_AT_TX_DURATION_TDL";
      }
      enum "aaa-at-voice-tx-duration" {
        value 177;
        description
          "Duration of voice packets transmitted";
        tailf:code-name "ENUM_aaa_attribute_type_tdl__AAA_AT_VOICE_TX_DURATION_TDL";
      }
      enum "aaa-at-noise-level" {
        value 178;
        description
          "The average noise level in dBm";
        tailf:code-name "ENUM_aaa_attribute_type_tdl__AAA_AT_NOISE_LEVEL_TDL";
      }
      enum "aaa-at-codec-bytes" {
        value 179;
        description
          "Codec bytes";
        tailf:code-name "ENUM_aaa_attribute_type_tdl__AAA_AT_CODEC_BYTES_TDL";
      }
      enum "aaa-at-coder-type-rate" {
        value 180;
        description
          "Coder type rate";
        tailf:code-name "ENUM_aaa_attribute_type_tdl__AAA_AT_CODER_TYPE_RATE_TDL";
      }
      enum "aaa-at-early-packets" {
        value 181;
        description
          "Packets received too early to store in jitter buffer";
        tailf:code-name "ENUM_aaa_attribute_type_tdl__AAA_AT_EARLY_PACKETS_TDL";
      }
      enum "aaa-at-late-packets" {
        value 182;
        description
          "Packets arrive too late for CODEC";
        tailf:code-name "ENUM_aaa_attribute_type_tdl__AAA_AT_LATE_PACKETS_TDL";
      }
      enum "aaa-at-lost-packets" {
        value 183;
        description
          "Number of packets lost";
        tailf:code-name "ENUM_aaa_attribute_type_tdl__AAA_AT_LOST_PACKETS_TDL";
      }
      enum "aaa-at-gapfill-w-itpol" {
        value 184;
        description
          "Gap fill with interpolation";
        tailf:code-name "ENUM_aaa_attribute_type_tdl__AAA_AT_GAPFILL_W_ITPOL_TDL";
      }
      enum "aaa-at-gapfill-w-predt" {
        value 185;
        description
          "Gap fill with prediction";
        tailf:code-name "ENUM_aaa_attribute_type_tdl__AAA_AT_GAPFILL_W_PREDT_TDL";
      }
      enum "aaa-at-gapfill-w-rdncy" {
        value 186;
        description
          "Gap fill with redundancy";
        tailf:code-name "ENUM_aaa_attribute_type_tdl__AAA_AT_GAPFILL_W_RDNCY_TDL";
      }
      enum "aaa-at-gapfill-w-silen" {
        value 187;
        description
          "Gap fill with silence";
        tailf:code-name "ENUM_aaa_attribute_type_tdl__AAA_AT_GAPFILL_W_SILEN_TDL";
      }
      enum "aaa-at-lowater-playout-delay" {
        value 188;
        description
          "Low-water play-out delay";
        tailf:code-name "ENUM_aaa_attribute_type_tdl__AAA_AT_LOWATER_PLAYOUT_DELAY_TDL";
      }
      enum "aaa-at-hiwater-playout-delay" {
        value 189;
        description
          "Hi-water play-out delay";
        tailf:code-name "ENUM_aaa_attribute_type_tdl__AAA_AT_HIWATER_PLAYOUT_DELAY_TDL";
      }
      enum "aaa-at-ontime-rv-playout" {
        value 190;
        description
          "Duration of a call play-out since data received on time";
        tailf:code-name "ENUM_aaa_attribute_type_tdl__AAA_AT_ONTIME_RV_PLAYOUT_TDL";
      }
      enum "aaa-at-receive-delay" {
        value 191;
        description
          "Average voice play-out FIFO-delay plus decoder-delay";
        tailf:code-name "ENUM_aaa_attribute_type_tdl__AAA_AT_RECEIVE_DELAY_TDL";
      }
      enum "aaa-at-round-trip-delay" {
        value 192;
        description
          "The voice packet round trip delay";
        tailf:code-name "ENUM_aaa_attribute_type_tdl__AAA_AT_ROUND_TRIP_DELAY_TDL";
      }
      enum "aaa-at-remote-udp-port" {
        value 193;
        description
          "Remote system UDP listener port";
        tailf:code-name "ENUM_aaa_attribute_type_tdl__AAA_AT_REMOTE_UDP_PORT_TDL";
      }
      enum "aaa-at-session-protocol" {
        value 194;
        description
          "Session protocol used for Internet call through IP";
        tailf:code-name "ENUM_aaa_attribute_type_tdl__AAA_AT_SESSION_PROTOCOL_TDL";
      }
      enum "aaa-at-vad-enable" {
        value 195;
        description
          "Whether or not Voice Activity Detection enabled";
        tailf:code-name "ENUM_aaa_attribute_type_tdl__AAA_AT_VAD_ENABLE_TDL";
      }
      enum "aaa-at-in-area" {
        value 196;
        description
          "Zone ID for H323 call or originating domain for SIP";
        tailf:code-name "ENUM_aaa_attribute_type_tdl__AAA_AT_IN_AREA_TDL";
      }
      enum "aaa-at-out-area" {
        value 197;
        description
          "Zone ID for H323 call or terminating domain for SIP";
        tailf:code-name "ENUM_aaa_attribute_type_tdl__AAA_AT_OUT_AREA_TDL";
      }
      enum "aaa-at-in-if-desc" {
        value 198;
        description
          "Description field of voice port for a incoming call";
        tailf:code-name "ENUM_aaa_attribute_type_tdl__AAA_AT_IN_IF_DESC_TDL";
      }
      enum "aaa-at-out-if-desc" {
        value 199;
        description
          "Description field of voice port for a outgoing call";
        tailf:code-name "ENUM_aaa_attribute_type_tdl__AAA_AT_OUT_IF_DESC_TDL";
      }
      enum "aaa-at-service-descriptor" {
        value 200;
        description
          "Routing and accounting information from the route server";
        tailf:code-name "ENUM_aaa_attribute_type_tdl__AAA_AT_SERVICE_DESCRIPTOR_TDL";
      }
      enum "aaa-at-in-carrier-id" {
        value 201;
        description
          "The incoming carrier identifier";
        tailf:code-name "ENUM_aaa_attribute_type_tdl__AAA_AT_IN_CARRIER_ID_TDL";
      }
      enum "aaa-at-out-carrier-id" {
        value 202;
        description
          "The outgoing carrier identifier";
        tailf:code-name "ENUM_aaa_attribute_type_tdl__AAA_AT_OUT_CARRIER_ID_TDL";
      }
      enum "aaa-at-in-tg-label" {
        value 203;
        description
          "The incoming trunk group label";
        tailf:code-name "ENUM_aaa_attribute_type_tdl__AAA_AT_IN_TG_LABEL_TDL";
      }
      enum "aaa-at-out-tg-label" {
        value 204;
        description
          "The outgoing trunk group label";
        tailf:code-name "ENUM_aaa_attribute_type_tdl__AAA_AT_OUT_TG_LABEL_TDL";
      }
      enum "aaa-at-alert-time" {
        value 205;
        description
          "Alert time point";
        tailf:code-name "ENUM_aaa_attribute_type_tdl__AAA_AT_ALERT_TIME_TDL";
      }
      enum "aaa-at-gw-rxd-cdn" {
        value 206;
        description
          "Gateway received called number";
        tailf:code-name "ENUM_aaa_attribute_type_tdl__AAA_AT_GW_RXD_CDN_TDL";
      }
      enum "aaa-at-gw-rxd-cgn" {
        value 207;
        description
          "Gateway received calling number";
        tailf:code-name "ENUM_aaa_attribute_type_tdl__AAA_AT_GW_RXD_CGN_TDL";
      }
      enum "aaa-at-gw-rxd-ocn" {
        value 208;
        description
          "Gateway received original called number";
        tailf:code-name "ENUM_aaa_attribute_type_tdl__AAA_AT_GW_RXD_OCN_TDL";
      }
      enum "aaa-at-gw-rxd-cnn" {
        value 209;
        description
          "Gateway received alias called number";
        tailf:code-name "ENUM_aaa_attribute_type_tdl__AAA_AT_GW_RXD_CNN_TDL";
      }
      enum "aaa-at-gw-rxd-rdn" {
        value 210;
        description
          "Gateway received redirecting number";
        tailf:code-name "ENUM_aaa_attribute_type_tdl__AAA_AT_GW_RXD_RDN_TDL";
      }
      enum "aaa-at-final-cdn" {
        value 211;
        description
          "Gateway sent final translated called number";
        tailf:code-name "ENUM_aaa_attribute_type_tdl__AAA_AT_FINAL_CDN_TDL";
      }
      enum "aaa-at-final-cgn" {
        value 212;
        description
          "Gateway sent final translated calling number";
        tailf:code-name "ENUM_aaa_attribute_type_tdl__AAA_AT_FINAL_CGN_TDL";
      }
      enum "aaa-at-final-rdn" {
        value 213;
        description
          "Gateway sent final translated redirecting number";
        tailf:code-name "ENUM_aaa_attribute_type_tdl__AAA_AT_FINAL_RDN_TDL";
      }
      enum "aaa-at-gk-xlated-cdn" {
        value 214;
        description
          "Gatekeeper sent e164 alias called number";
        tailf:code-name "ENUM_aaa_attribute_type_tdl__AAA_AT_GK_XLATED_CDN_TDL";
      }
      enum "aaa-at-gk-xlated-cgn" {
        value 215;
        description
          "Gatekeeper sent e164 alias calling number";
        tailf:code-name "ENUM_aaa_attribute_type_tdl__AAA_AT_GK_XLATED_CGN_TDL";
      }
      enum "aaa-at-gw-coll-cdn" {
        value 216;
        description
          "Gateway appl collected called number";
        tailf:code-name "ENUM_aaa_attribute_type_tdl__AAA_AT_GW_COLL_CDN_TDL";
      }
      enum "aaa-at-orig-cic" {
        value 217;
        description
          "Gateway sent final originating translated called number";
        tailf:code-name "ENUM_aaa_attribute_type_tdl__AAA_AT_ORIG_CIC_TDL";
      }
      enum "aaa-at-term-cic" {
        value 218;
        description
          "Gateway sent final terminating translated called number";
        tailf:code-name "ENUM_aaa_attribute_type_tdl__AAA_AT_TERM_CIC_TDL";
      }
      enum "aaa-at-termination-action" {
        value 219;
        description
          "An indication for termination";
        tailf:code-name "ENUM_aaa_attribute_type_tdl__AAA_AT_TERMINATION_ACTION_TDL";
      }
      enum "aaa-at-aaa-unique-id" {
        value 220;
        description
          "The AAA unique id";
        tailf:code-name "ENUM_aaa_attribute_type_tdl__AAA_AT_AAA_UNIQUE_ID_TDL";
      }
      enum "aaa-at-interface" {
        value 221;
        description
          "Name of the interface that is in use";
        tailf:code-name "ENUM_aaa_attribute_type_tdl__AAA_AT_INTERFACE_TDL";
      }
      enum "aaa-at-interface-config" {
        value 222;
        description
          "Configuration commands for an interface";
        tailf:code-name "ENUM_aaa_attribute_type_tdl__AAA_AT_INTERFACE_CONFIG_TDL";
      }
      enum "aaa-at-interface-parent" {
        value 223;
        description
          "Parent interface that is in use";
        tailf:code-name "ENUM_aaa_attribute_type_tdl__AAA_AT_INTERFACE_PARENT_TDL";
      }
      enum "aaa-at-interface-parent-type" {
        value 224;
        description
          "Type of the parent interface that is in use";
        tailf:code-name "ENUM_aaa_attribute_type_tdl__AAA_AT_INTERFACE_PARENT_TYPE_TDL";
      }
      enum "aaa-at-interface-type" {
        value 225;
        description
          "Type of the interface that is in use";
        tailf:code-name "ENUM_aaa_attribute_type_tdl__AAA_AT_INTERFACE_TYPE_TDL";
      }
      enum "aaa-at-interim-interval" {
        value 226;
        description
          "Accounting interim interval";
        tailf:code-name "ENUM_aaa_attribute_type_tdl__AAA_AT_INTERIM_INTERVAL_TDL";
      }
      enum "aaa-at-ip-addresses" {
        value 227;
        description
          "IP addresses of the home gateway";
        tailf:code-name "ENUM_aaa_attribute_type_tdl__AAA_AT_IP_ADDRESSES_TDL";
      }
      enum "aaa-at-ip-address-limits" {
        value 228;
        description
          "Session limits for IP addresses of the home gateway";
        tailf:code-name "ENUM_aaa_attribute_type_tdl__AAA_AT_IP_ADDRESS_LIMITS_TDL";
      }
      enum "aaa-at-key-exchange" {
        value 229;
        description
          "Key exchange";
        tailf:code-name "ENUM_aaa_attribute_type_tdl__AAA_AT_KEY_EXCHANGE_TDL";
      }
      enum "aaa-at-vpdn-template" {
        value 230;
        description
          "Name of vpdn-template to use";
        tailf:code-name "ENUM_aaa_attribute_type_tdl__AAA_AT_VPDN_TEMPLATE_TDL";
      }
      enum "aaa-at-l2f-cm-retransmit-retries" {
        value 231;
        description
          "Number of retries before tearing down a Layer-2 Forwarding tunnel";
        tailf:code-name "ENUM_aaa_attribute_type_tdl__AAA_AT_L2F_CM_RETRANSMIT_RETRIES_TDL";
      }
      enum "aaa-at-l2f-init-retransmit-retries" {
        value 232;
        description
          "Layer-2 Forwarding initial retries before placing HGW on busy list";
        tailf:code-name "ENUM_aaa_attribute_type_tdl__AAA_AT_L2F_INIT_RETRANSMIT_RETRIES_TDL";
      }
      enum "aaa-at-l2f-tunnel-timeout-setup" {
        value 233;
        description
          "Time permitted to setup a Layer-2 Forwarding tunnel";
        tailf:code-name "ENUM_aaa_attribute_type_tdl__AAA_AT_L2F_TUNNEL_TIMEOUT_SETUP_TDL";
      }
      enum "aaa-at-l2f-busy-list-timeout" {
        value 234;
        description
          "How long an address is on the Layer-2 Forwarding busy list";
        tailf:code-name "ENUM_aaa_attribute_type_tdl__AAA_AT_L2F_BUSY_LIST_TIMEOUT_TDL";
      }
      enum "aaa-at-l2tp-busy-disconnect" {
        value 235;
        description
          "L2TP busy disconnect";
        tailf:code-name "ENUM_aaa_attribute_type_tdl__AAA_AT_L2TP_BUSY_DISCONNECT_TDL";
      }
      enum "aaa-at-l2tp-framing-cap" {
        value 236;
        description
          "L2TP framing capabilities";
        tailf:code-name "ENUM_aaa_attribute_type_tdl__AAA_AT_L2TP_FRAMING_CAP_TDL";
      }
      enum "aaa-at-l2tp-bearer-cap" {
        value 237;
        description
          "L2TP bearer capabilities";
        tailf:code-name "ENUM_aaa_attribute_type_tdl__AAA_AT_L2TP_BEARER_CAP_TDL";
      }
      enum "aaa-at-l2tp-cm-local-window-size" {
        value 238;
        description
          "L2TP CM local window size";
        tailf:code-name "ENUM_aaa_attribute_type_tdl__AAA_AT_L2TP_CM_LOCAL_WINDOW_SIZE_TDL";
      }
      enum "aaa-at-l2tp-cm-max-timeout" {
        value 239;
        description
          "L2TP CM max timeout";
        tailf:code-name "ENUM_aaa_attribute_type_tdl__AAA_AT_L2TP_CM_MAX_TIMEOUT_TDL";
      }
      enum "aaa-at-l2tp-cm-min-timeout" {
        value 240;
        description
          "L2TP CM min timeout";
        tailf:code-name "ENUM_aaa_attribute_type_tdl__AAA_AT_L2TP_CM_MIN_TIMEOUT_TDL";
      }
      enum "aaa-at-l2tp-init-max-timeout" {
        value 241;
        description
          "Maximum Start Control Connection Request timeout";
        tailf:code-name "ENUM_aaa_attribute_type_tdl__AAA_AT_L2TP_INIT_MAX_TIMEOUT_TDL";
      }
      enum "aaa-at-l2tp-init-min-timeout" {
        value 242;
        description
          "Minimum Start Control Connection Request timeout";
        tailf:code-name "ENUM_aaa_attribute_type_tdl__AAA_AT_L2TP_INIT_MIN_TIMEOUT_TDL";
      }
      enum "aaa-at-l2tp-init-retransmit-retries" {
        value 243;
        description
          "Start Control Connection Request retries before placing L2TP Network Server on busy list";
        tailf:code-name "ENUM_aaa_attribute_type_tdl__AAA_AT_L2TP_INIT_RETRANSMIT_RETRIES_TDL";
      }
      enum "aaa-at-l2tp-busy-list-timeout" {
        value 244;
        description
          "How long an address is on the L2TP busy list";
        tailf:code-name "ENUM_aaa_attribute_type_tdl__AAA_AT_L2TP_BUSY_LIST_TIMEOUT_TDL";
      }
      enum "aaa-at-l2tp-drop-out-of-order" {
        value 245;
        description
          "L2TP drop out of order";
        tailf:code-name "ENUM_aaa_attribute_type_tdl__AAA_AT_L2TP_DROP_OUT_OF_ORDER_TDL";
      }
      enum "aaa-at-l2tp-hello-interval" {
        value 246;
        description
          "L2TP hello interval";
        tailf:code-name "ENUM_aaa_attribute_type_tdl__AAA_AT_L2TP_HELLO_INTERVAL_TDL";
      }
      enum "aaa-at-l2tp-hidden-avp" {
        value 247;
        description
          "L2TP hidden Attribute-Value Pair";
        tailf:code-name "ENUM_aaa_attribute_type_tdl__AAA_AT_L2TP_HIDDEN_AVP_TDL";
      }
      enum "aaa-at-l2tp-rx-speed" {
        value 248;
        description
          "L2TP configurable rx speed";
        tailf:code-name "ENUM_aaa_attribute_type_tdl__AAA_AT_L2TP_RX_SPEED_TDL";
      }
      enum "aaa-at-l2tp-tx-speed" {
        value 249;
        description
          "L2TP configurable tx speed";
        tailf:code-name "ENUM_aaa_attribute_type_tdl__AAA_AT_L2TP_TX_SPEED_TDL";
      }
      enum "aaa-at-l2tp-ignore-connect-speed" {
        value 250;
        description
          "L2TP ignore Attribute-Value Pair 24";
        tailf:code-name "ENUM_aaa_attribute_type_tdl__AAA_AT_L2TP_IGNORE_CONNECT_SPEED_TDL";
      }
      enum "aaa-at-l2tp-max-ato" {
        value 251;
        description
          "L2TP max Adaptive Time-Out";
        tailf:code-name "ENUM_aaa_attribute_type_tdl__AAA_AT_L2TP_MAX_ATO_TDL";
      }
      enum "aaa-at-l2tp-no-session-timeout" {
        value 252;
        description
          "L2TP no session timeout";
        tailf:code-name "ENUM_aaa_attribute_type_tdl__AAA_AT_L2TP_NO_SESSION_TIMEOUT_TDL";
      }
      enum "aaa-at-l2tp-relay-group-name" {
        value 253;
        description
          "PPPoE bba-group to be used for relay";
        tailf:code-name "ENUM_aaa_attribute_type_tdl__AAA_AT_L2TP_RELAY_GROUP_NAME_TDL";
      }
      enum "aaa-at-l2tp-queue-size" {
        value 254;
        description
          "L2TP queue size";
        tailf:code-name "ENUM_aaa_attribute_type_tdl__AAA_AT_L2TP_QUEUE_SIZE_TDL";
      }
      enum "aaa-at-l2tp-receive-window" {
        value 255;
        description
          "L2TP receive window";
        tailf:code-name "ENUM_aaa_attribute_type_tdl__AAA_AT_L2TP_RECEIVE_WINDOW_TDL";
      }
      enum "aaa-at-l2tp-cm-retransmit-retries" {
        value 256;
        description
          "L2TP CM retransmit retries";
        tailf:code-name "ENUM_aaa_attribute_type_tdl__AAA_AT_L2TP_CM_RETRANSMIT_RETRIES_TDL";
      }
      enum "aaa-at-l2tp-sequencing" {
        value 257;
        description
          "L2TP sequencing";
        tailf:code-name "ENUM_aaa_attribute_type_tdl__AAA_AT_L2TP_SEQUENCING_TDL";
      }
      enum "aaa-at-l2tp-static-rtt" {
        value 258;
        description
          "L2TP static RTT";
        tailf:code-name "ENUM_aaa_attribute_type_tdl__AAA_AT_L2TP_STATIC_RTT_TDL";
      }
      enum "aaa-at-l2tp-tunnel-authen" {
        value 259;
        description
          "L2TP tunnel authentication";
        tailf:code-name "ENUM_aaa_attribute_type_tdl__AAA_AT_L2TP_TUNNEL_AUTHEN_TDL";
      }
      enum "aaa-at-l2tp-tunnel-acct" {
        value 260;
        description
          "L2TP tunnel accounting";
        tailf:code-name "ENUM_aaa_attribute_type_tdl__AAA_AT_L2TP_TUNNEL_ACCT_TDL";
      }
      enum "aaa-at-l2tp-tunnel-password" {
        value 261;
        description
          "L2TP tunnel password";
        tailf:code-name "ENUM_aaa_attribute_type_tdl__AAA_AT_L2TP_TUNNEL_PASSWORD_TDL";
      }
      enum "aaa-at-l2tp-tunnel-timeout-setup" {
        value 262;
        description
          "L2TP tunnel timeout setup";
        tailf:code-name "ENUM_aaa_attribute_type_tdl__AAA_AT_L2TP_TUNNEL_TIMEOUT_SETUP_TDL";
      }
      enum "aaa-at-l2tp-clid-mask-method" {
        value 263;
        description
          "Method to mask CLID in L2TP Attribute-Value Pair 22 of Incoming Call Request";
        tailf:code-name "ENUM_aaa_attribute_type_tdl__AAA_AT_L2TP_CLID_MASK_METHOD_TDL";
      }
      enum "aaa-at-l2tp-udp-checksum" {
        value 264;
        description
          "L2TP UDP checksum";
        tailf:code-name "ENUM_aaa_attribute_type_tdl__AAA_AT_L2TP_UDP_CHECKSUM_TDL";
      }
      enum "aaa-at-l2tp-security-ip-address-check" {
        value 265;
        description
          "LAC to verify outgoing/incoming IP to/from L2TP Network Server";
        tailf:code-name "ENUM_aaa_attribute_type_tdl__AAA_AT_L2TP_SECURITY_IP_ADDRESS_CHECK_TDL";
      }
      enum "aaa-at-l2tp-security-required" {
        value 266;
        description
          "Security required for L2TP tunnel";
        tailf:code-name "ENUM_aaa_attribute_type_tdl__AAA_AT_L2TP_SECURITY_REQUIRED_TDL";
      }
      enum "aaa-at-l2tp-security-teardown-conn" {
        value 267;
        description
          "IKE phase 1 Security Association on L2TP tunnel teardown";
        tailf:code-name "ENUM_aaa_attribute_type_tdl__AAA_AT_L2TP_SECURITY_TEARDOWN_CONN_TDL";
      }
      enum "aaa-at-l2tp-resync-packets" {
        value 268;
        description
          "L2TP tunnel resync packets";
        tailf:code-name "ENUM_aaa_attribute_type_tdl__AAA_AT_L2TP_RESYNC_PACKETS_TDL";
      }
      enum "aaa-at-link-compression" {
        value 269;
        description
          "Link compression";
        tailf:code-name "ENUM_aaa_attribute_type_tdl__AAA_AT_LINK_COMPRESSION_TDL";
      }
      enum "aaa-at-map-class" {
        value 270;
        description
          "Map class for outgoing call";
        tailf:code-name "ENUM_aaa_attribute_type_tdl__AAA_AT_MAP_CLASS_TDL";
      }
      enum "aaa-at-epd-error-cause" {
        value 271;
        description
          "EPD error cause";
        tailf:code-name "ENUM_aaa_attribute_type_tdl__AAA_AT_EPD_ERROR_CAUSE_TDL";
      }
      enum "aaa-at-error-cause" {
        value 272;
        description
          "Dynamic-author error cause";
        tailf:code-name "ENUM_aaa_attribute_type_tdl__AAA_AT_ERROR_CAUSE_TDL";
      }
      enum "aaa-at-message" {
        value 273;
        description
          "A reply message for the user";
        tailf:code-name "ENUM_aaa_attribute_type_tdl__AAA_AT_MESSAGE_TDL";
      }
      enum "aaa-at-message-authenticator" {
        value 274;
        description
          "Used to sign Access-Requests to prevent spoof";
        tailf:code-name "ENUM_aaa_attribute_type_tdl__AAA_AT_MESSAGE_AUTHENTICATOR_TDL";
      }
      enum "aaa-at-mlp-links-current" {
        value 275;
        description
          "Current number of multilink links";
        tailf:code-name "ENUM_aaa_attribute_type_tdl__AAA_AT_MLP_LINKS_CURRENT_TDL";
      }
      enum "aaa-at-mlp-links-max" {
        value 276;
        description
          "Maximum allowable links in multilink call";
        tailf:code-name "ENUM_aaa_attribute_type_tdl__AAA_AT_MLP_LINKS_MAX_TDL";
      }
      enum "aaa-at-mlp-session-id" {
        value 277;
        description
          "Multilink session identifier";
        tailf:code-name "ENUM_aaa_attribute_type_tdl__AAA_AT_MLP_SESSION_ID_TDL";
      }
      enum "aaa-at-modem-on-hold" {
        value 278;
        description
          "Per-call configuration of V.92 modem on hold";
        tailf:code-name "ENUM_aaa_attribute_type_tdl__AAA_AT_MODEM_ON_HOLD_TDL";
      }
      enum "aaa-at-modem-script" {
        value 279;
        description
          "Chat scripts for session";
        tailf:code-name "ENUM_aaa_attribute_type_tdl__AAA_AT_MODEM_SCRIPT_TDL";
      }
      enum "aaa-at-mobile-ip-spi" {
        value 280;
        description
          "Mobile IP Security Association";
        tailf:code-name "ENUM_aaa_attribute_type_tdl__AAA_AT_MOBILE_IP_SPI_TDL";
      }
      enum "aaa-at-mobile-ip-stat-ip-pool" {
        value 281;
        description
          "Mobile IP static IP pool";
        tailf:code-name "ENUM_aaa_attribute_type_tdl__AAA_AT_MOBILE_IP_STAT_IP_POOL_TDL";
      }
      enum "aaa-at-mobile-ip-stat-adr" {
        value 282;
        description
          "Mobile IP static IP address";
        tailf:code-name "ENUM_aaa_attribute_type_tdl__AAA_AT_MOBILE_IP_STAT_ADR_TDL";
      }
      enum "aaa-at-mobile-ip-dyn-pool" {
        value 283;
        description
          "Mobile IP dynamic IP pool";
        tailf:code-name "ENUM_aaa_attribute_type_tdl__AAA_AT_MOBILE_IP_DYN_POOL_TDL";
      }
      enum "aaa-at-mobile-ip-dyn-adr" {
        value 284;
        description
          "Mobile IP dynamic address";
        tailf:code-name "ENUM_aaa_attribute_type_tdl__AAA_AT_MOBILE_IP_DYN_ADR_TDL";
      }
      enum "aaa-at-mobile-ip-stat-pool-defenition" {
        value 285;
        description
          "Mobile IP static address authorization";
        tailf:code-name "ENUM_aaa_attribute_type_tdl__AAA_AT_MOBILE_IP_STAT_POOL_DEFENITION_TDL";
      }
      enum "aaa-at-mobile-ip-stat-pool" {
        value 286;
        description
          "IP addresses for mobile-ip static address authorization";
        tailf:code-name "ENUM_aaa_attribute_type_tdl__AAA_AT_MOBILE_IP_STAT_POOL_TDL";
      }
      enum "aaa-at-mobileip-rf-swact" {
        value 287;
        description
          "Mobile IP RF Switch of Activity";
        tailf:code-name "ENUM_aaa_attribute_type_tdl__AAA_AT_MOBILEIP_RF_SWACT_TDL";
      }
      enum "aaa-at-dhcp-server" {
        value 288;
        description
          "DHCP server address";
        tailf:code-name "ENUM_aaa_attribute_type_tdl__AAA_AT_DHCP_SERVER_TDL";
      }
      enum "aaa-at-mobile-ip-dhcp-server" {
        value 289;
        description
          "Mobile IP DHCP server";
        tailf:code-name "ENUM_aaa_attribute_type_tdl__AAA_AT_MOBILE_IP_DHCP_SERVER_TDL";
      }
      enum "aaa-at-dhcp-class" {
        value 290;
        description
          "DHCP class name";
        tailf:code-name "ENUM_aaa_attribute_type_tdl__AAA_AT_DHCP_CLASS_TDL";
      }
      enum "aaa-at-config-source-dpm" {
        value 291;
        description
          "Configuration sourced by DHCP Policy Module";
        tailf:code-name "ENUM_aaa_attribute_type_tdl__AAA_AT_CONFIG_SOURCE_DPM_TDL";
      }
      enum "aaa-at-multicast-client" {
        value 292;
        description
          "Multicast client";
        tailf:code-name "ENUM_aaa_attribute_type_tdl__AAA_AT_MULTICAST_CLIENT_TDL";
      }
      enum "aaa-at-multicast-rlimit" {
        value 293;
        description
          "Multicast rate limit";
        tailf:code-name "ENUM_aaa_attribute_type_tdl__AAA_AT_MULTICAST_RLIMIT_TDL";
      }
      enum "aaa-at-multilink-idle" {
        value 294;
        description
          "Multilink idle threshold";
        tailf:code-name "ENUM_aaa_attribute_type_tdl__AAA_AT_MULTILINK_IDLE_TDL";
      }
      enum "aaa-at-multilink-load" {
        value 295;
        description
          "Multilink load threshold";
        tailf:code-name "ENUM_aaa_attribute_type_tdl__AAA_AT_MULTILINK_LOAD_TDL";
      }
      enum "aaa-at-multilink-max" {
        value 296;
        description
          "Multilink maximum links";
        tailf:code-name "ENUM_aaa_attribute_type_tdl__AAA_AT_MULTILINK_MAX_TDL";
      }
      enum "aaa-at-multilink-min" {
        value 297;
        description
          "Multilink minimum links";
        tailf:code-name "ENUM_aaa_attribute_type_tdl__AAA_AT_MULTILINK_MIN_TDL";
      }
      enum "aaa-at-multilink-negotiate" {
        value 298;
        description
          "Multilink negotiate";
        tailf:code-name "ENUM_aaa_attribute_type_tdl__AAA_AT_MULTILINK_NEGOTIATE_TDL";
      }
      enum "aaa-at-nas-description" {
        value 299;
        description
          "NAS description";
        tailf:code-name "ENUM_aaa_attribute_type_tdl__AAA_AT_NAS_DESCRIPTION_TDL";
      }
      enum "aaa-at-nbns-primary-server" {
        value 300;
        description
          "Primary NetBIOS Name Server";
        tailf:code-name "ENUM_aaa_attribute_type_tdl__AAA_AT_NBNS_PRIMARY_SERVER_TDL";
      }
      enum "aaa-at-nbns-secondary-server" {
        value 301;
        description
          "Secondary NetBIOS Name Server";
        tailf:code-name "ENUM_aaa_attribute_type_tdl__AAA_AT_NBNS_SECONDARY_SERVER_TDL";
      }
      enum "aaa-at-num-sessions" {
        value 302;
        description
          "Number of sessions";
        tailf:code-name "ENUM_aaa_attribute_type_tdl__AAA_AT_NUM_SESSIONS_TDL";
      }
      enum "aaa-at-ipv4-netmask" {
        value 303;
        description
          "The IP netmask for the user";
        tailf:code-name "ENUM_aaa_attribute_type_tdl__AAA_AT_IPV4_NETMASK_TDL";
      }
      enum "aaa-at-no-escape" {
        value 304;
        description
          "No escape";
        tailf:code-name "ENUM_aaa_attribute_type_tdl__AAA_AT_NO_ESCAPE_TDL";
      }
      enum "aaa-at-no-hangup" {
        value 305;
        description
          "No hangup";
        tailf:code-name "ENUM_aaa_attribute_type_tdl__AAA_AT_NO_HANGUP_TDL";
      }
      enum "aaa-at-old-password" {
        value 306;
        description
          "The old password for a change password protocol";
        tailf:code-name "ENUM_aaa_attribute_type_tdl__AAA_AT_OLD_PASSWORD_TDL";
      }
      enum "aaa-at-old-prompts" {
        value 307;
        description
          "The old prompt for a change password protocol";
        tailf:code-name "ENUM_aaa_attribute_type_tdl__AAA_AT_OLD_PROMPTS_TDL";
      }
      enum "aaa-at-call-out-acl" {
        value 308;
        description
          "A call egress access list";
        tailf:code-name "ENUM_aaa_attribute_type_tdl__AAA_AT_CALL_OUT_ACL_TDL";
      }
      enum "aaa-at-output-giga-words" {
        value 309;
        description
          "Number of times that Acct-Output-Octets has wrapped";
        tailf:code-name "ENUM_aaa_attribute_type_tdl__AAA_AT_OUTPUT_GIGA_WORDS_TDL";
      }
      enum "aaa-at-out-acl" {
        value 310;
        description
          "An egress access list";
        tailf:code-name "ENUM_aaa_attribute_type_tdl__AAA_AT_OUT_ACL_TDL";
      }
      enum "aaa-at-output-octets" {
        value 311;
        description
          "The number of bytes sent to a port";
        tailf:code-name "ENUM_aaa_attribute_type_tdl__AAA_AT_OUTPUT_OCTETS_TDL";
      }
      enum "aaa-at-output-packets" {
        value 312;
        description
          "The number of packets sent to a port";
        tailf:code-name "ENUM_aaa_attribute_type_tdl__AAA_AT_OUTPUT_PACKETS_TDL";
      }
      enum "aaa-at-output-giga-words-ipv6" {
        value 313;
        description
          "Number of times that Acct-Output-Octets-ipv6 has wrapped";
        tailf:code-name "ENUM_aaa_attribute_type_tdl__AAA_AT_OUTPUT_GIGA_WORDS_IPV6_TDL";
      }
      enum "aaa-at-output-octets-ipv6" {
        value 314;
        description
          "The number of bytes sent to a port in an IPv6 session";
        tailf:code-name "ENUM_aaa_attribute_type_tdl__AAA_AT_OUTPUT_OCTETS_IPV6_TDL";
      }
      enum "aaa-at-output-packets-ipv6" {
        value 315;
        description
          "The number of IPv6 packets sent to a port";
        tailf:code-name "ENUM_aaa_attribute_type_tdl__AAA_AT_OUTPUT_PACKETS_IPV6_TDL";
      }
      enum "aaa-at-ip-port-bundle-hdl" {
        value 316;
        description
          "Unique identifier for a L4 redirect session";
        tailf:code-name "ENUM_aaa_attribute_type_tdl__AAA_AT_IP_PORT_BUNDLE_HDL_TDL";
      }
      enum "aaa-at-nativeip-vrf" {
        value 317;
        description
          "combination of native IP address and VRF";
        tailf:code-name "ENUM_aaa_attribute_type_tdl__AAA_AT_NATIVEIP_VRF_TDL";
      }
      enum "aaa-at-domainip-vrf" {
        value 318;
        description
          "combination of domain IP address and VRF";
        tailf:code-name "ENUM_aaa_attribute_type_tdl__AAA_AT_DOMAINIP_VRF_TDL";
      }
      enum "aaa-at-system-script" {
        value 319;
        description
          "System script for a particular session";
        tailf:code-name "ENUM_aaa_attribute_type_tdl__AAA_AT_SYSTEM_SCRIPT_TDL";
      }
      enum "aaa-at-user-password" {
        value 320;
        description
          "The password of the user to be authenticated";
        tailf:code-name "ENUM_aaa_attribute_type_tdl__AAA_AT_USER_PASSWORD_TDL";
      }
      enum "aaa-at-pool-definition" {
        value 321;
        description
          "IP pool definition";
        tailf:code-name "ENUM_aaa_attribute_type_tdl__AAA_AT_POOL_DEFINITION_TDL";
      }
      enum "aaa-at-pool-addr" {
        value 322;
        description
          "Subnet from AR to be used by ODAP for DHCP leases";
        tailf:code-name "ENUM_aaa_attribute_type_tdl__AAA_AT_POOL_ADDR_TDL";
      }
      enum "aaa-at-pool-mask" {
        value 323;
        description
          "Subnet mask to/from AR to specify subnet size";
        tailf:code-name "ENUM_aaa_attribute_type_tdl__AAA_AT_POOL_MASK_TDL";
      }
      enum "aaa-at-pool-timeout" {
        value 324;
        description
          "IP Pool timeout";
        tailf:code-name "ENUM_aaa_attribute_type_tdl__AAA_AT_POOL_TIMEOUT_TDL";
      }
      enum "aaa-at-port" {
        value 325;
        description
          "The port for reverse-access authorization";
        tailf:code-name "ENUM_aaa_attribute_type_tdl__AAA_AT_PORT_TDL";
      }
      enum "aaa-at-port-limit" {
        value 326;
        description
          "Number of ports that can be allocated to this call";
        tailf:code-name "ENUM_aaa_attribute_type_tdl__AAA_AT_PORT_LIMIT_TDL";
      }
      enum "aaa-at-port-used" {
        value 327;
        description
          "Port used";
        tailf:code-name "ENUM_aaa_attribute_type_tdl__AAA_AT_PORT_USED_TDL";
      }
      enum "aaa-at-ppp-vj-slot" {
        value 328;
        description
          "PPP VJ slot compression";
        tailf:code-name "ENUM_aaa_attribute_type_tdl__AAA_AT_PPP_VJ_SLOT_TDL";
      }
      enum "aaa-at-ppp-disc-cause" {
        value 329;
        description
          "PPP disconnect cause";
        tailf:code-name "ENUM_aaa_attribute_type_tdl__AAA_AT_PPP_DISC_CAUSE_TDL";
      }
      enum "aaa-at-presession-octets-in" {
        value 330;
        description
          "The bytes sent from the station before authentication";
        tailf:code-name "ENUM_aaa_attribute_type_tdl__AAA_AT_PRESESSION_OCTETS_IN_TDL";
      }
      enum "aaa-at-presession-octets-out" {
        value 331;
        description
          "The bytes sent to the station before authentication";
        tailf:code-name "ENUM_aaa_attribute_type_tdl__AAA_AT_PRESESSION_OCTETS_OUT_TDL";
      }
      enum "aaa-at-presession-packets-in" {
        value 332;
        description
          "The packets sent from the station before authentication";
        tailf:code-name "ENUM_aaa_attribute_type_tdl__AAA_AT_PRESESSION_PACKETS_IN_TDL";
      }
      enum "aaa-at-presession-packets-out" {
        value 333;
        description
          "The packets sent to the station before authentication";
        tailf:code-name "ENUM_aaa_attribute_type_tdl__AAA_AT_PRESESSION_PACKETS_OUT_TDL";
      }
      enum "aaa-at-presession-time" {
        value 334;
        description
          "The seconds a user was connected before authentication";
        tailf:code-name "ENUM_aaa_attribute_type_tdl__AAA_AT_PRESESSION_TIME_TDL";
      }
      enum "aaa-at-privilege-level" {
        value 335;
        description
          "The privilege level the user has";
        tailf:code-name "ENUM_aaa_attribute_type_tdl__AAA_AT_PRIVILEGE_LEVEL_TDL";
      }
      enum "aaa-at-view" {
        value 336;
        description
          "The view the user has";
        tailf:code-name "ENUM_aaa_attribute_type_tdl__AAA_AT_VIEW_TDL";
      }
      enum "aaa-at-protocol" {
        value 337;
        description
          "AAA protocol";
        tailf:code-name "ENUM_aaa_attribute_type_tdl__AAA_AT_PROTOCOL_TDL";
      }
      enum "aaa-at-proxy-acl" {
        value 338;
        description
          "Proxy access list";
        tailf:code-name "ENUM_aaa_attribute_type_tdl__AAA_AT_PROXY_ACL_TDL";
      }
      enum "aaa-at-auth-required" {
        value 339;
        description
          "Further authentication required";
        tailf:code-name "ENUM_aaa_attribute_type_tdl__AAA_AT_AUTH_REQUIRED_TDL";
      }
      enum "aaa-at-auth-type" {
        value 340;
        description
          "Authentication protocol that will be applied to the peer";
        tailf:code-name "ENUM_aaa_attribute_type_tdl__AAA_AT_AUTH_TYPE_TDL";
      }
      enum "aaa-at-wlan-nas-location" {
        value 341;
        description
          "Dot11 NAS location";
        tailf:code-name "ENUM_aaa_attribute_type_tdl__AAA_AT_WLAN_NAS_LOCATION_TDL";
      }
      enum "aaa-at-wlan-algo-type" {
        value 342;
        description
          "Dot11 authentication algorithm type";
        tailf:code-name "ENUM_aaa_attribute_type_tdl__AAA_AT_WLAN_ALGO_TYPE_TDL";
      }
      enum "aaa-at-wlan-vlan-id" {
        value 343;
        description
          "Dot11 VLAN identifier";
        tailf:code-name "ENUM_aaa_attribute_type_tdl__AAA_AT_WLAN_VLAN_ID_TDL";
      }
      enum "aaa-at-service-type" {
        value 344;
        description
          "Authorization service type";
        tailf:code-name "ENUM_aaa_attribute_type_tdl__AAA_AT_SERVICE_TYPE_TDL";
      }
      enum "aaa-at-session-key" {
        value 345;
        description
          "Key to encrypt session";
        tailf:code-name "ENUM_aaa_attribute_type_tdl__AAA_AT_SESSION_KEY_TDL";
      }
      enum "aaa-at-service-set-id" {
        value 346;
        description
          "Dot11 Service Set ID";
        tailf:code-name "ENUM_aaa_attribute_type_tdl__AAA_AT_SERVICE_SET_ID_TDL";
      }
      enum "aaa-at-aironet-extention" {
        value 347;
        description
          "Dot11 Aironet Admin Capabilities";
        tailf:code-name "ENUM_aaa_attribute_type_tdl__AAA_AT_AIRONET_EXTENTION_TDL";
      }
      enum "aaa-at-modem-service" {
        value 348;
        description
          "Pre-auth modem service";
        tailf:code-name "ENUM_aaa_attribute_type_tdl__AAA_AT_MODEM_SERVICE_TDL";
      }
      enum "aaa-at-redirect-number" {
        value 349;
        description
          "The 800 number the user called";
        tailf:code-name "ENUM_aaa_attribute_type_tdl__AAA_AT_REDIRECT_NUMBER_TDL";
      }
      enum "aaa-at-reload-user" {
        value 350;
        description
          "The name of user issuing the reload command";
        tailf:code-name "ENUM_aaa_attribute_type_tdl__AAA_AT_RELOAD_USER_TDL";
      }
      enum "aaa-at-reload-reason" {
        value 351;
        description
          "The reason that the box was reloaded or restarted";
        tailf:code-name "ENUM_aaa_attribute_type_tdl__AAA_AT_RELOAD_REASON_TDL";
      }
      enum "aaa-at-ios-version" {
        value 352;
        description
          "The IOS version running on the box";
        tailf:code-name "ENUM_aaa_attribute_type_tdl__AAA_AT_IOS_VERSION_TDL";
      }
      enum "aaa-at-shared-profile-enable" {
        value 353;
        description
          "Sharing user profile";
        tailf:code-name "ENUM_aaa_attribute_type_tdl__AAA_AT_SHARED_PROFILE_ENABLE_TDL";
      }
      enum "aaa-at-resource-service" {
        value 354;
        description
          "Resource service requested from server";
        tailf:code-name "ENUM_aaa_attribute_type_tdl__AAA_AT_RESOURCE_SERVICE_TDL";
      }
      enum "aaa-at-rm-call-count" {
        value 355;
        description
          "Resource Manager call count";
        tailf:code-name "ENUM_aaa_attribute_type_tdl__AAA_AT_RM_CALL_COUNT_TDL";
      }
      enum "aaa-at-rm-call-handle" {
        value 356;
        description
          "Resource Manager call handle";
        tailf:code-name "ENUM_aaa_attribute_type_tdl__AAA_AT_RM_CALL_HANDLE_TDL";
      }
      enum "aaa-at-rm-call-treatment" {
        value 357;
        description
          "Resource Manager call treatment";
        tailf:code-name "ENUM_aaa_attribute_type_tdl__AAA_AT_RM_CALL_TREATMENT_TDL";
      }
      enum "aaa-at-rm-call-type" {
        value 358;
        description
          "Resource Manager call type";
        tailf:code-name "ENUM_aaa_attribute_type_tdl__AAA_AT_RM_CALL_TYPE_TDL";
      }
      enum "aaa-at-rm-cp-name" {
        value 359;
        description
          "Resource Manager CP name";
        tailf:code-name "ENUM_aaa_attribute_type_tdl__AAA_AT_RM_CP_NAME_TDL";
      }
      enum "aaa-at-rm-dnis-group-name" {
        value 360;
        description
          "Resource Manager DNIS group name";
        tailf:code-name "ENUM_aaa_attribute_type_tdl__AAA_AT_RM_DNIS_GROUP_NAME_TDL";
      }
      enum "aaa-at-rm-link-type" {
        value 361;
        description
          "Resource Manager link type";
        tailf:code-name "ENUM_aaa_attribute_type_tdl__AAA_AT_RM_LINK_TYPE_TDL";
      }
      enum "aaa-at-rm-mlp-id" {
        value 362;
        description
          "Resource Manager multilink id";
        tailf:code-name "ENUM_aaa_attribute_type_tdl__AAA_AT_RM_MLP_ID_TDL";
      }
      enum "aaa-at-rm-nas-state" {
        value 363;
        description
          "Resource Manager NAS state";
        tailf:code-name "ENUM_aaa_attribute_type_tdl__AAA_AT_RM_NAS_STATE_TDL";
      }
      enum "aaa-at-rm-port-descripiton" {
        value 364;
        description
          "Resource Manager port description";
        tailf:code-name "ENUM_aaa_attribute_type_tdl__AAA_AT_RM_PORT_DESCRIPITON_TDL";
      }
      enum "aaa-at-rm-request-type" {
        value 365;
        description
          "Resource Manager request type";
        tailf:code-name "ENUM_aaa_attribute_type_tdl__AAA_AT_RM_REQUEST_TYPE_TDL";
      }
      enum "aaa-at-rm-response-code" {
        value 366;
        description
          "Resource Manager response code";
        tailf:code-name "ENUM_aaa_attribute_type_tdl__AAA_AT_RM_RESPONSE_CODE_TDL";
      }
      enum "aaa-at-rm-rg-application" {
        value 367;
        description
          "Resource Manager application";
        tailf:code-name "ENUM_aaa_attribute_type_tdl__AAA_AT_RM_RG_APPLICATION_TDL";
      }
      enum "aaa-at-rm-rg-name" {
        value 368;
        description
          "Resource Manager RG name";
        tailf:code-name "ENUM_aaa_attribute_type_tdl__AAA_AT_RM_RG_NAME_TDL";
      }
      enum "aaa-at-rm-rg-service" {
        value 369;
        description
          "Resource Manager RG service";
        tailf:code-name "ENUM_aaa_attribute_type_tdl__AAA_AT_RM_RG_SERVICE_TDL";
      }
      enum "aaa-at-rm-rg-service-name" {
        value 370;
        description
          "Resource Manager RG service name";
        tailf:code-name "ENUM_aaa_attribute_type_tdl__AAA_AT_RM_RG_SERVICE_NAME_TDL";
      }
      enum "aaa-at-rm-server-state" {
        value 371;
        description
          "Resource Manager server state";
        tailf:code-name "ENUM_aaa_attribute_type_tdl__AAA_AT_RM_SERVER_STATE_TDL";
      }
      enum "aaa-at-rm-template-name" {
        value 372;
        description
          "Resource Manager template name";
        tailf:code-name "ENUM_aaa_attribute_type_tdl__AAA_AT_RM_TEMPLATE_NAME_TDL";
      }
      enum "aaa-at-rm-version" {
        value 373;
        description
          "Resource Manager protocol version";
        tailf:code-name "ENUM_aaa_attribute_type_tdl__AAA_AT_RM_VERSION_TDL";
      }
      enum "aaa-at-rm-vpdn-tunnel-status" {
        value 374;
        description
          "Resource Manager VPDN tunnel status";
        tailf:code-name "ENUM_aaa_attribute_type_tdl__AAA_AT_RM_VPDN_TUNNEL_STATUS_TDL";
      }
      enum "aaa-at-rm-overflow" {
        value 375;
        description
          "Resource Manager overflow flag";
        tailf:code-name "ENUM_aaa_attribute_type_tdl__AAA_AT_RM_OVERFLOW_TDL";
      }
      enum "aaa-at-negotiated-route" {
        value 376;
        description
          "Negotiated Routing information for a user session";
        tailf:code-name "ENUM_aaa_attribute_type_tdl__AAA_AT_NEGOTIATED_ROUTE_TDL";
      }
      enum "aaa-at-route" {
        value 377;
        description
          "Routing information for a user session";
        tailf:code-name "ENUM_aaa_attribute_type_tdl__AAA_AT_ROUTE_TDL";
      }
      enum "aaa-at-pw-lifetime" {
        value 378;
        description
          "Password lifetime";
        tailf:code-name "ENUM_aaa_attribute_type_tdl__AAA_AT_PW_LIFETIME_TDL";
      }
      enum "aaa-at-ppp-vj-slot-comp" {
        value 379;
        description
          "PPP VJ slot compression";
        tailf:code-name "ENUM_aaa_attribute_type_tdl__AAA_AT_PPP_VJ_SLOT_COMP_TDL";
      }
      enum "aaa-at-route-ip" {
        value 380;
        description
          "Route IP address";
        tailf:code-name "ENUM_aaa_attribute_type_tdl__AAA_AT_ROUTE_IP_TDL";
      }
      enum "aaa-at-tunnel-private-group-id" {
        value 381;
        description
          "Tunnel private group id";
        tailf:code-name "ENUM_aaa_attribute_type_tdl__AAA_AT_TUNNEL_PRIVATE_GROUP_ID_TDL";
      }
      enum "aaa-at-state" {
        value 382;
        description
          "State information";
        tailf:code-name "ENUM_aaa_attribute_type_tdl__AAA_AT_STATE_TDL";
      }
      enum "aaa-at-class" {
        value 383;
        description
          "Class information";
        tailf:code-name "ENUM_aaa_attribute_type_tdl__AAA_AT_CLASS_TDL";
      }
      enum "aaa-at-route-filter-in" {
        value 384;
        description
          "Route filter IN";
        tailf:code-name "ENUM_aaa_attribute_type_tdl__AAA_AT_ROUTE_FILTER_IN_TDL";
      }
      enum "aaa-at-route-filter-out" {
        value 385;
        description
          "Route filter OUT";
        tailf:code-name "ENUM_aaa_attribute_type_tdl__AAA_AT_ROUTE_FILTER_OUT_TDL";
      }
      enum "aaa-at-routing" {
        value 386;
        description
          "Framed routing";
        tailf:code-name "ENUM_aaa_attribute_type_tdl__AAA_AT_ROUTING_TDL";
      }
      enum "aaa-at-sap" {
        value 387;
        description
          "Service Access Point";
        tailf:code-name "ENUM_aaa_attribute_type_tdl__AAA_AT_SAP_TDL";
      }
      enum "aaa-at-sap-filter-in" {
        value 388;
        description
          "SAP filter IN";
        tailf:code-name "ENUM_aaa_attribute_type_tdl__AAA_AT_SAP_FILTER_IN_TDL";
      }
      enum "aaa-at-sap-filter-out" {
        value 389;
        description
          "SAP filter OUT";
        tailf:code-name "ENUM_aaa_attribute_type_tdl__AAA_AT_SAP_FILTER_OUT_TDL";
      }
      enum "aaa-at-send-auth" {
        value 390;
        description
          "Authentication protocol for peer";
        tailf:code-name "ENUM_aaa_attribute_type_tdl__AAA_AT_SEND_AUTH_TDL";
      }
      enum "aaa-at-send-name" {
        value 391;
        description
          "Name of local host dialing out";
        tailf:code-name "ENUM_aaa_attribute_type_tdl__AAA_AT_SEND_NAME_TDL";
      }
      enum "aaa-at-tunnel-tos-reflect" {
        value 392;
        description
          "Tunnel TOS reflect";
        tailf:code-name "ENUM_aaa_attribute_type_tdl__AAA_AT_TUNNEL_TOS_REFLECT_TDL";
      }
      enum "aaa-at-tunnel-tos-setting" {
        value 393;
        description
          "Tunnel TOS setting";
        tailf:code-name "ENUM_aaa_attribute_type_tdl__AAA_AT_TUNNEL_TOS_SETTING_TDL";
      }
      enum "aaa-at-tunnel-pmtu" {
        value 394;
        description
          "Tunnel Path MTU enabled";
        tailf:code-name "ENUM_aaa_attribute_type_tdl__AAA_AT_TUNNEL_PMTU_TDL";
      }
      enum "aaa-at-tunnel-renego-lcp" {
        value 395;
        description
          "LCP renegotiation option";
        tailf:code-name "ENUM_aaa_attribute_type_tdl__AAA_AT_TUNNEL_RENEGO_LCP_TDL";
      }
      enum "aaa-at-tunnel-ip-mtu-adjust" {
        value 396;
        description
          "IP MTU adjust flag";
        tailf:code-name "ENUM_aaa_attribute_type_tdl__AAA_AT_TUNNEL_IP_MTU_ADJUST_TDL";
      }
      enum "aaa-at-remote-name" {
        value 397;
        description
          "Name of remote host to dial-out and pre-auth dial-in to";
        tailf:code-name "ENUM_aaa_attribute_type_tdl__AAA_AT_REMOTE_NAME_TDL";
      }
      enum "aaa-at-send-secret" {
        value 398;
        description
          "Name of the secret to be used for authentication";
        tailf:code-name "ENUM_aaa_attribute_type_tdl__AAA_AT_SEND_SECRET_TDL";
      }
      enum "aaa-at-server-admin-msg" {
        value 399;
        description
          "Server admin message";
        tailf:code-name "ENUM_aaa_attribute_type_tdl__AAA_AT_SERVER_ADMIN_MSG_TDL";
      }
      enum "aaa-at-server-key" {
        value 400;
        description
          "Server key";
        tailf:code-name "ENUM_aaa_attribute_type_tdl__AAA_AT_SERVER_KEY_TDL";
      }
      enum "aaa-at-server-name" {
        value 401;
        description
          "Server name";
        tailf:code-name "ENUM_aaa_attribute_type_tdl__AAA_AT_SERVER_NAME_TDL";
      }
      enum "aaa-at-service" {
        value 402;
        description
          "AAA service";
        tailf:code-name "ENUM_aaa_attribute_type_tdl__AAA_AT_SERVICE_TDL";
      }
      enum "aaa-at-service-name" {
        value 403;
        description
          "Service name to be advertised to client";
        tailf:code-name "ENUM_aaa_attribute_type_tdl__AAA_AT_SERVICE_NAME_TDL";
      }
      enum "aaa-at-parent-session-id" {
        value 404;
        description
          "Session id of the parent session";
        tailf:code-name "ENUM_aaa_attribute_type_tdl__AAA_AT_PARENT_SESSION_ID_TDL";
      }
      enum "aaa-at-cisco-service-type" {
        value 405;
        description
          "Specifies the service requested by the NAD";
        tailf:code-name "ENUM_aaa_attribute_type_tdl__AAA_AT_CISCO_SERVICE_TYPE_TDL";
      }
      enum "aaa-at-cisco-event-type" {
        value 406;
        description
          "Specifies the event requested by the NAD";
        tailf:code-name "ENUM_aaa_attribute_type_tdl__AAA_AT_CISCO_EVENT_TYPE_TDL";
      }
      enum "aaa-at-cisco-auto-smart-port" {
        value 407;
        description
          "Specifies the smartport definition to applied";
        tailf:code-name "ENUM_aaa_attribute_type_tdl__AAA_AT_CISCO_AUTO_SMART_PORT_TDL";
      }
      enum "aaa-at-session-id" {
        value 408;
        description
          "The id that identifies a pair of start and stop records";
        tailf:code-name "ENUM_aaa_attribute_type_tdl__AAA_AT_SESSION_ID_TDL";
      }
      enum "aaa-at-session-handle" {
        value 409;
        description
          "Handle for session";
        tailf:code-name "ENUM_aaa_attribute_type_tdl__AAA_AT_SESSION_HANDLE_TDL";
      }
      enum "aaa-at-acct-record-number" {
        value 410;
        description
          "Unique number for every accounting record";
        tailf:code-name "ENUM_aaa_attribute_type_tdl__AAA_AT_ACCT_RECORD_NUMBER_TDL";
      }
      enum "aaa-at-acct-record-type" {
        value 411;
        description
          "Accounting record type";
        tailf:code-name "ENUM_aaa_attribute_type_tdl__AAA_AT_ACCT_RECORD_TYPE_TDL";
      }
      enum "aaa-at-string-session-id" {
        value 412;
        description
          "The string id that identifies a pair of start and stop records";
        tailf:code-name "ENUM_aaa_attribute_type_tdl__AAA_AT_STRING_SESSION_ID_TDL";
      }
      enum "aaa-at-subscriber-label" {
        value 413;
        description
          "Subscriber Label for Session";
        tailf:code-name "ENUM_aaa_attribute_type_tdl__AAA_AT_SUBSCRIBER_LABEL_TDL";
      }
      enum "aaa-at-session-time" {
        value 414;
        description
          "The number of seconds a session has been active";
        tailf:code-name "ENUM_aaa_attribute_type_tdl__AAA_AT_SESSION_TIME_TDL";
      }
      enum "aaa-at-override-session-time" {
        value 415;
        description
          "Override the number of seconds a session can been active";
        tailf:code-name "ENUM_aaa_attribute_type_tdl__AAA_AT_OVERRIDE_SESSION_TIME_TDL";
      }
      enum "aaa-at-vrrs" {
        value 416;
        description
          "Redundancy group name, used for VRRS accounting";
        tailf:code-name "ENUM_aaa_attribute_type_tdl__AAA_AT_VRRS_TDL";
      }
      enum "aaa-at-source-ip-address" {
        value 417;
        description
          "Source IP address";
        tailf:code-name "ENUM_aaa_attribute_type_tdl__AAA_AT_SOURCE_IP_ADDRESS_TDL";
      }
      enum "aaa-at-start-time" {
        value 418;
        description
          "The time the session started";
        tailf:code-name "ENUM_aaa_attribute_type_tdl__AAA_AT_START_TIME_TDL";
      }
      enum "aaa-at-stop-time" {
        value 419;
        description
          "The time the session stopped";
        tailf:code-name "ENUM_aaa_attribute_type_tdl__AAA_AT_STOP_TIME_TDL";
      }
      enum "aaa-at-sub-policy-in" {
        value 420;
        description
          "Upstream policy to be applied on subscriber side";
        tailf:code-name "ENUM_aaa_attribute_type_tdl__AAA_AT_SUB_POLICY_IN_TDL";
      }
      enum "aaa-at-sub-qos-policy-in" {
        value 421;
        description
          "Upstream QoS policy to be applied on subscriber side";
        tailf:code-name "ENUM_aaa_attribute_type_tdl__AAA_AT_SUB_QOS_POLICY_IN_TDL";
      }
      enum "aaa-at-sub-policy-out" {
        value 422;
        description
          "Downstream policy to be applied on subscriber side";
        tailf:code-name "ENUM_aaa_attribute_type_tdl__AAA_AT_SUB_POLICY_OUT_TDL";
      }
      enum "aaa-at-sub-qos-policy-out" {
        value 423;
        description
          "Downstream QoS policy to be applied on subscriber side";
        tailf:code-name "ENUM_aaa_attribute_type_tdl__AAA_AT_SUB_QOS_POLICY_OUT_TDL";
      }
      enum "aaa-at-acct-policy-map" {
        value 424;
        description
          "Session accounting policy map";
        tailf:code-name "ENUM_aaa_attribute_type_tdl__AAA_AT_ACCT_POLICY_MAP_TDL";
      }
      enum "aaa-at-acct-policy-in" {
        value 425;
        description
          "Upstream Accounting Policy for Subscriber";
        tailf:code-name "ENUM_aaa_attribute_type_tdl__AAA_AT_ACCT_POLICY_IN_TDL";
      }
      enum "aaa-at-acct-policy-out" {
        value 426;
        description
          "Downstream Accounting Policy for Subscriber";
        tailf:code-name "ENUM_aaa_attribute_type_tdl__AAA_AT_ACCT_POLICY_OUT_TDL";
      }
      enum "aaa-at-vc-qos-policy-in" {
        value 427;
        description
          "Upstream QoS policy to be applied on a ATM VC";
        tailf:code-name "ENUM_aaa_attribute_type_tdl__AAA_AT_VC_QOS_POLICY_IN_TDL";
      }
      enum "aaa-at-vc-qos-policy-out" {
        value 428;
        description
          "Downstream QoS policy to be applied on a ATM VC";
        tailf:code-name "ENUM_aaa_attribute_type_tdl__AAA_AT_VC_QOS_POLICY_OUT_TDL";
      }
      enum "aaa-at-vc-weight" {
        value 429;
        description
          "Weight to be applied on a ATM VC";
        tailf:code-name "ENUM_aaa_attribute_type_tdl__AAA_AT_VC_WEIGHT_TDL";
      }
      enum "aaa-at-vc-q-lwm" {
        value 430;
        description
          "Queue depth low watermark to be applied on a ATM VC";
        tailf:code-name "ENUM_aaa_attribute_type_tdl__AAA_AT_VC_Q_LWM_TDL";
      }
      enum "aaa-at-vc-q-hwm" {
        value 431;
        description
          "Queue depth high watermark to be applied on a ATM VC";
        tailf:code-name "ENUM_aaa_attribute_type_tdl__AAA_AT_VC_Q_HWM_TDL";
      }
      enum "aaa-at-sub-param-qos-policy-in" {
        value 432;
        description
          "Upstream para-metered QoS policy to be applied on subscriber side";
        tailf:code-name "ENUM_aaa_attribute_type_tdl__AAA_AT_SUB_PARAM_QOS_POLICY_IN_TDL";
      }
      enum "aaa-at-sub-param-qos-policy-out" {
        value 433;
        description
          "Downstream para-metered QoS policy to be applied on subscriber side";
        tailf:code-name "ENUM_aaa_attribute_type_tdl__AAA_AT_SUB_PARAM_QOS_POLICY_OUT_TDL";
      }
      enum "aaa-at-terminate-cause" {
        value 434;
        description
          "How the session was terminated";
        tailf:code-name "ENUM_aaa_attribute_type_tdl__AAA_AT_TERMINATE_CAUSE_TDL";
      }
      enum "aaa-at-timeout" {
        value 435;
        description
          "The maximum number of seconds a user can be connected";
        tailf:code-name "ENUM_aaa_attribute_type_tdl__AAA_AT_TIMEOUT_TDL";
      }
      enum "aaa-at-timezone" {
        value 436;
        description
          "Timezone";
        tailf:code-name "ENUM_aaa_attribute_type_tdl__AAA_AT_TIMEZONE_TDL";
      }
      enum "aaa-at-tunnel-client-endpoint" {
        value 437;
        description
          "Tunnel client endpoint";
        tailf:code-name "ENUM_aaa_attribute_type_tdl__AAA_AT_TUNNEL_CLIENT_ENDPOINT_TDL";
      }
      enum "aaa-at-tunnel-client-auth-id" {
        value 438;
        description
          "The authentication name of the tunnel initiator";
        tailf:code-name "ENUM_aaa_attribute_type_tdl__AAA_AT_TUNNEL_CLIENT_AUTH_ID_TDL";
      }
      enum "aaa-at-tunnel-server-auth-id" {
        value 439;
        description
          "The authentication name of the tunnel terminator";
        tailf:code-name "ENUM_aaa_attribute_type_tdl__AAA_AT_TUNNEL_SERVER_AUTH_ID_TDL";
      }
      enum "aaa-at-tunnel-medium-type" {
        value 440;
        description
          "The protocol over which the tunnel runs";
        tailf:code-name "ENUM_aaa_attribute_type_tdl__AAA_AT_TUNNEL_MEDIUM_TYPE_TDL";
      }
      enum "aaa-at-tunnel-password" {
        value 441;
        description
          "Tunnel password to authenticate with tunnel remote end";
        tailf:code-name "ENUM_aaa_attribute_type_tdl__AAA_AT_TUNNEL_PASSWORD_TDL";
      }
      enum "aaa-at-tunnel-preference" {
        value 442;
        description
          "Tunnel preference of the tunnel settings";
        tailf:code-name "ENUM_aaa_attribute_type_tdl__AAA_AT_TUNNEL_PREFERENCE_TDL";
      }
      enum "aaa-at-tunnel-server-endpoint" {
        value 443;
        description
          "Tunnel server endpoint";
        tailf:code-name "ENUM_aaa_attribute_type_tdl__AAA_AT_TUNNEL_SERVER_ENDPOINT_TDL";
      }
      enum "aaa-at-tunnel-connection-id" {
        value 444;
        description
          "Tunnel connection id";
        tailf:code-name "ENUM_aaa_attribute_type_tdl__AAA_AT_TUNNEL_CONNECTION_ID_TDL";
      }
      enum "aaa-at-event-timestamp" {
        value 445;
        description
          "Event timestamp";
        tailf:code-name "ENUM_aaa_attribute_type_tdl__AAA_AT_EVENT_TIMESTAMP_TDL";
      }
      enum "aaa-at-tunnel-direction" {
        value 446;
        description
          "Tunnel direction";
        tailf:code-name "ENUM_aaa_attribute_type_tdl__AAA_AT_TUNNEL_DIRECTION_TDL";
      }
      enum "aaa-at-tunnel-application-type" {
        value 447;
        description
          "VPDN tunnel application type";
        tailf:code-name "ENUM_aaa_attribute_type_tdl__AAA_AT_TUNNEL_APPLICATION_TYPE_TDL";
      }
      enum "aaa-at-tunnel-type" {
        value 448;
        description
          "Tunnel protocols";
        tailf:code-name "ENUM_aaa_attribute_type_tdl__AAA_AT_TUNNEL_TYPE_TDL";
      }
      enum "aaa-at-user-max-links" {
        value 449;
        description
          "User max-links";
        tailf:code-name "ENUM_aaa_attribute_type_tdl__AAA_AT_USER_MAX_LINKS_TDL";
      }
      enum "aaa-at-user-name" {
        value 450;
        description
          "The name of the user";
        tailf:code-name "ENUM_aaa_attribute_type_tdl__AAA_AT_USER_NAME_TDL";
      }
      enum "aaa-at-vpdn-active-sessions" {
        value 451;
        description
          "The number of VPDN active sessions";
        tailf:code-name "ENUM_aaa_attribute_type_tdl__AAA_AT_VPDN_ACTIVE_SESSIONS_TDL";
      }
      enum "aaa-at-v92-info" {
        value 452;
        description
          "V.92 modem connection info";
        tailf:code-name "ENUM_aaa_attribute_type_tdl__AAA_AT_V92_INFO_TDL";
      }
      enum "aaa-at-vpdn-logging-info" {
        value 453;
        description
          "VPDN logging information";
        tailf:code-name "ENUM_aaa_attribute_type_tdl__AAA_AT_VPDN_LOGGING_INFO_TDL";
      }
      enum "aaa-at-vpdn-dialout-type" {
        value 454;
        description
          "VPDN dial-out type";
        tailf:code-name "ENUM_aaa_attribute_type_tdl__AAA_AT_VPDN_DIALOUT_TYPE_TDL";
      }
      enum "aaa-at-vpdn-domain" {
        value 455;
        description
          "The name of VPDN domain";
        tailf:code-name "ENUM_aaa_attribute_type_tdl__AAA_AT_VPDN_DOMAIN_TDL";
      }
      enum "aaa-at-vpdn-group" {
        value 456;
        description
          "VPDN group to use";
        tailf:code-name "ENUM_aaa_attribute_type_tdl__AAA_AT_VPDN_GROUP_TDL";
      }
      enum "aaa-at-vpdn-domain-list" {
        value 457;
        description
          "List of domains used for VPDN pre-authorization";
        tailf:code-name "ENUM_aaa_attribute_type_tdl__AAA_AT_VPDN_DOMAIN_LIST_TDL";
      }
      enum "aaa-at-vpdn-lac-dialer" {
        value 458;
        description
          "VPDN LAC dialer";
        tailf:code-name "ENUM_aaa_attribute_type_tdl__AAA_AT_VPDN_LAC_DIALER_TDL";
      }
      enum "aaa-at-vpdn-rotary-group" {
        value 459;
        description
          "VPDN dialer rotary group number";
        tailf:code-name "ENUM_aaa_attribute_type_tdl__AAA_AT_VPDN_ROTARY_GROUP_TDL";
      }
      enum "aaa-at-vpdn-pool-member" {
        value 460;
        description
          "VPDN dialer pool member";
        tailf:code-name "ENUM_aaa_attribute_type_tdl__AAA_AT_VPDN_POOL_MEMBER_TDL";
      }
      enum "aaa-at-vpdn-profile" {
        value 461;
        description
          "VPDN profile";
        tailf:code-name "ENUM_aaa_attribute_type_tdl__AAA_AT_VPDN_PROFILE_TDL";
      }
      enum "aaa-at-vpdn-scal-vtemplate" {
        value 462;
        description
          "VPDN virtual template number";
        tailf:code-name "ENUM_aaa_attribute_type_tdl__AAA_AT_VPDN_SCAL_VTEMPLATE_TDL";
      }
      enum "aaa-at-vpdn-vtemplate" {
        value 463;
        description
          "Virtual template number for VPDN tunnel authorization";
        tailf:code-name "ENUM_aaa_attribute_type_tdl__AAA_AT_VPDN_VTEMPLATE_TDL";
      }
      enum "aaa-at-vpdn-redirect-id" {
        value 464;
        description
          "VPDN call redirection identifier string";
        tailf:code-name "ENUM_aaa_attribute_type_tdl__AAA_AT_VPDN_REDIRECT_ID_TDL";
      }
      enum "aaa-at-sss-policy-directive" {
        value 465;
        description
          "Subscriber policy directive type";
        tailf:code-name "ENUM_aaa_attribute_type_tdl__AAA_AT_SSS_POLICY_DIRECTIVE_TDL";
      }
      enum "aaa-at-sss-subscriber-keepalive" {
        value 466;
        description
          "Subscriber session keepalive";
        tailf:code-name "ENUM_aaa_attribute_type_tdl__AAA_AT_SSS_SUBSCRIBER_KEEPALIVE_TDL";
      }
      enum "aaa-at-linksec-security-policy" {
        value 467;
        description
          "LinkSec security policy type";
        tailf:code-name "ENUM_aaa_attribute_type_tdl__AAA_AT_LINKSEC_SECURITY_POLICY_TDL";
      }
      enum "aaa-at-proxy-method-list" {
        value 468;
        description
          "Method list to proxy Radius packets";
        tailf:code-name "ENUM_aaa_attribute_type_tdl__AAA_AT_PROXY_METHOD_LIST_TDL";
      }
      enum "aaa-at-proxy-acct-method-list" {
        value 469;
        description
          "Accounting Method list to proxy Radius packets";
        tailf:code-name "ENUM_aaa_attribute_type_tdl__AAA_AT_PROXY_ACCT_METHOD_LIST_TDL";
      }
      enum "aaa-at-sss-service-type" {
        value 470;
        description
          "Subscriber profile directive type";
        tailf:code-name "ENUM_aaa_attribute_type_tdl__AAA_AT_SSS_SERVICE_TYPE_TDL";
      }
      enum "aaa-at-tunnel-vpn-id" {
        value 471;
        description
          "Tunnel VPN-ID string";
        tailf:code-name "ENUM_aaa_attribute_type_tdl__AAA_AT_TUNNEL_VPN_ID_TDL";
      }
      enum "aaa-at-tunnel-vpn-vrf" {
        value 472;
        description
          "Tunnel VPN VRF string";
        tailf:code-name "ENUM_aaa_attribute_type_tdl__AAA_AT_TUNNEL_VPN_VRF_TDL";
      }
      enum "aaa-at-wins-server" {
        value 473;
        description
          "WINS server";
        tailf:code-name "ENUM_aaa_attribute_type_tdl__AAA_AT_WINS_SERVER_TDL";
      }
      enum "aaa-at-leap-session-key" {
        value 474;
        description
          "Key to encrypt LEAP session";
        tailf:code-name "ENUM_aaa_attribute_type_tdl__AAA_AT_LEAP_SESSION_KEY_TDL";
      }
      enum "aaa-at-wins-server-primary" {
        value 475;
        description
          "WINS server primary";
        tailf:code-name "ENUM_aaa_attribute_type_tdl__AAA_AT_WINS_SERVER_PRIMARY_TDL";
      }
      enum "aaa-at-client-password-local" {
        value 476;
        description
          "ikev2 sign password";
        tailf:code-name "ENUM_aaa_attribute_type_tdl__AAA_AT_CLIENT_PASSWORD_LOCAL_TDL";
      }
      enum "aaa-at-client-password-remote" {
        value 477;
        description
          "ikev2 verify password";
        tailf:code-name "ENUM_aaa_attribute_type_tdl__AAA_AT_CLIENT_PASSWORD_REMOTE_TDL";
      }
      enum "aaa-at-wins-server-secondary" {
        value 478;
        description
          "WINS server secondary";
        tailf:code-name "ENUM_aaa_attribute_type_tdl__AAA_AT_WINS_SERVER_SECONDARY_TDL";
      }
      enum "aaa-at-atm-qos-pcr" {
        value 479;
        description
          "ATM Peak Cell Rate";
        tailf:code-name "ENUM_aaa_attribute_type_tdl__AAA_AT_ATM_QOS_PCR_TDL";
      }
      enum "aaa-at-atm-qos-scr" {
        value 480;
        description
          "ATM Sustainable Cell Rate";
        tailf:code-name "ENUM_aaa_attribute_type_tdl__AAA_AT_ATM_QOS_SCR_TDL";
      }
      enum "aaa-at-xmit-rate" {
        value 481;
        description
          "The rate which packets are being sent to the user";
        tailf:code-name "ENUM_aaa_attribute_type_tdl__AAA_AT_XMIT_RATE_TDL";
      }
      enum "aaa-at-zone-list" {
        value 482;
        description
          "Zone list";
        tailf:code-name "ENUM_aaa_attribute_type_tdl__AAA_AT_ZONE_LIST_TDL";
      }
      enum "aaa-at-login-service" {
        value 483;
        description
          "Exec login connection service";
        tailf:code-name "ENUM_aaa_attribute_type_tdl__AAA_AT_LOGIN_SERVICE_TDL";
      }
      enum "aaa-at-sg-service" {
        value 484;
        description
          "SG service";
        tailf:code-name "ENUM_aaa_attribute_type_tdl__AAA_AT_SG_SERVICE_TDL";
      }
      enum "aaa-at-sg-rule" {
        value 485;
        description
          "SG rule";
        tailf:code-name "ENUM_aaa_attribute_type_tdl__AAA_AT_SG_RULE_TDL";
      }
      enum "aaa-at-sg-condition" {
        value 486;
        description
          "SG condition";
        tailf:code-name "ENUM_aaa_attribute_type_tdl__AAA_AT_SG_CONDITION_TDL";
      }
      enum "aaa-at-sg-action" {
        value 487;
        description
          "SG action";
        tailf:code-name "ENUM_aaa_attribute_type_tdl__AAA_AT_SG_ACTION_TDL";
      }
      enum "aaa-at-ssg-account-info" {
        value 488;
        description
          "Service Selection Gateway account info";
        tailf:code-name "ENUM_aaa_attribute_type_tdl__AAA_AT_SSG_ACCOUNT_INFO_TDL";
      }
      enum "aaa-at-ssg-service-info" {
        value 489;
        description
          "Service Selection Gateway service info";
        tailf:code-name "ENUM_aaa_attribute_type_tdl__AAA_AT_SSG_SERVICE_INFO_TDL";
      }
      enum "aaa-at-ssg-command-code" {
        value 490;
        description
          "Service Selection Gateway command code";
        tailf:code-name "ENUM_aaa_attribute_type_tdl__AAA_AT_SSG_COMMAND_CODE_TDL";
      }
      enum "aaa-at-ssg-control-info" {
        value 491;
        description
          "Service Selection Gateway control info";
        tailf:code-name "ENUM_aaa_attribute_type_tdl__AAA_AT_SSG_CONTROL_INFO_TDL";
      }
      enum "aaa-at-ssg-cookie" {
        value 492;
        description
          "Service Selection Gateway cookie";
        tailf:code-name "ENUM_aaa_attribute_type_tdl__AAA_AT_SSG_COOKIE_TDL";
      }
      enum "aaa-at-cdma-user-class" {
        value 493;
        description
          "CDMA user class";
        tailf:code-name "ENUM_aaa_attribute_type_tdl__AAA_AT_CDMA_USER_CLASS_TDL";
      }
      enum "aaa-at-cdma-realm" {
        value 494;
        description
          "CDMA realm";
        tailf:code-name "ENUM_aaa_attribute_type_tdl__AAA_AT_CDMA_REALM_TDL";
      }
      enum "aaa-at-mobileip-mn-ipaddr" {
        value 495;
        description
          "Mobile IP MN Address";
        tailf:code-name "ENUM_aaa_attribute_type_tdl__AAA_AT_MOBILEIP_MN_IPADDR_TDL";
      }
      enum "aaa-at-mobileip-mn-lifetime" {
        value 496;
        description
          "Mobile IP MN lifetime";
        tailf:code-name "ENUM_aaa_attribute_type_tdl__AAA_AT_MOBILEIP_MN_LIFETIME_TDL";
      }
      enum "aaa-at-mobileip-mn-flags" {
        value 497;
        description
          "Mobile IP MN flags";
        tailf:code-name "ENUM_aaa_attribute_type_tdl__AAA_AT_MOBILEIP_MN_FLAGS_TDL";
      }
      enum "aaa-at-mobileip-mn-reject-code" {
        value 498;
        description
          "Mobile IP MN Registration reject code";
        tailf:code-name "ENUM_aaa_attribute_type_tdl__AAA_AT_MOBILEIP_MN_REJECT_CODE_TDL";
      }
      enum "aaa-at-mobileip-mn-local-timezone" {
        value 499;
        description
          "Mobile IP MN Local Timezone Flag";
        tailf:code-name "ENUM_aaa_attribute_type_tdl__AAA_AT_MOBILEIP_MN_LOCAL_TIMEZONE_TDL";
      }
      enum "aaa-at-mobile-ip-prohibited" {
        value 500;
        description
          "Is the Mobile prohibited from creating binding";
        tailf:code-name "ENUM_aaa_attribute_type_tdl__AAA_AT_MOBILE_IP_PROHIBITED_TDL";
      }
      enum "aaa-at-mobileip-vrf-ha-ip-addr" {
        value 501;
        description
          "Mobile IP HA IP Address for VRF";
        tailf:code-name "ENUM_aaa_attribute_type_tdl__AAA_AT_MOBILEIP_VRF_HA_IP_ADDR_TDL";
      }
      enum "aaa-at-mobileip-reg-source-addr" {
        value 502;
        description
          "Mobile IP Registration Source IP Address";
        tailf:code-name "ENUM_aaa_attribute_type_tdl__AAA_AT_MOBILEIP_REG_SOURCE_ADDR_TDL";
      }
      enum "aaa-at-cdma-preshared-secret" {
        value 503;
        description
          "CDMA pre-shared secret";
        tailf:code-name "ENUM_aaa_attribute_type_tdl__AAA_AT_CDMA_PRESHARED_SECRET_TDL";
      }
      enum "aaa-at-cdma-container" {
        value 504;
        description
          "CDMA container";
        tailf:code-name "ENUM_aaa_attribute_type_tdl__AAA_AT_CDMA_CONTAINER_TDL";
      }
      enum "aaa-at-cdma-correlation-id" {
        value 505;
        description
          "CDMA correlation id";
        tailf:code-name "ENUM_aaa_attribute_type_tdl__AAA_AT_CDMA_CORRELATION_ID_TDL";
      }
      enum "aaa-at-cdma-always-on" {
        value 506;
        description
          "CDMA always-on";
        tailf:code-name "ENUM_aaa_attribute_type_tdl__AAA_AT_CDMA_ALWAYS_ON_TDL";
      }
      enum "aaa-at-cdma-rn-pdit" {
        value 507;
        description
          "CDMA Radio-Access Network Packet Data Inactivity Timer";
        tailf:code-name "ENUM_aaa_attribute_type_tdl__AAA_AT_CDMA_RN_PDIT_TDL";
      }
      enum "aaa-at-cdma-session-continue" {
        value 508;
        description
          "CDMA session continue";
        tailf:code-name "ENUM_aaa_attribute_type_tdl__AAA_AT_CDMA_SESSION_CONTINUE_TDL";
      }
      enum "aaa-at-cdma-begin-session" {
        value 509;
        description
          "CDMA begin session";
        tailf:code-name "ENUM_aaa_attribute_type_tdl__AAA_AT_CDMA_BEGIN_SESSION_TDL";
      }
      enum "aaa-at-cdma-ha-ip-addr" {
        value 510;
        description
          "CDMA HA IP address";
        tailf:code-name "ENUM_aaa_attribute_type_tdl__AAA_AT_CDMA_HA_IP_ADDR_TDL";
      }
      enum "aaa-at-cdma-ike-preshared-secret-request" {
        value 511;
        description
          "CDMA IPSec pre-shared secret request";
        tailf:code-name "ENUM_aaa_attribute_type_tdl__AAA_AT_CDMA_IKE_PRESHARED_SECRET_REQUEST_TDL";
      }
      enum "aaa-at-cdma-ipsec-security-level" {
        value 512;
        description
          "CDMA IPSec security";
        tailf:code-name "ENUM_aaa_attribute_type_tdl__AAA_AT_CDMA_IPSEC_SECURITY_LEVEL_TDL";
      }
      enum "aaa-at-cdma-reverse-tnl-spec" {
        value 513;
        description
          "CDMA reverse Tunnel specification";
        tailf:code-name "ENUM_aaa_attribute_type_tdl__AAA_AT_CDMA_REVERSE_TNL_SPEC_TDL";
      }
      enum "aaa-at-cdma-pcf-ip-addr" {
        value 514;
        description
          "CDMA PCF IP address";
        tailf:code-name "ENUM_aaa_attribute_type_tdl__AAA_AT_CDMA_PCF_IP_ADDR_TDL";
      }
      enum "aaa-at-cdma-bs-msc-addr" {
        value 515;
        description
          "CDMA BS MSC address";
        tailf:code-name "ENUM_aaa_attribute_type_tdl__AAA_AT_CDMA_BS_MSC_ADDR_TDL";
      }
      enum "aaa-at-cdma-user-id" {
        value 516;
        description
          "CDMA User id";
        tailf:code-name "ENUM_aaa_attribute_type_tdl__AAA_AT_CDMA_USER_ID_TDL";
      }
      enum "aaa-at-cdma-forward-mux" {
        value 517;
        description
          "CDMA forward mux";
        tailf:code-name "ENUM_aaa_attribute_type_tdl__AAA_AT_CDMA_FORWARD_MUX_TDL";
      }
      enum "aaa-at-cdma-reverse-mux" {
        value 518;
        description
          "CDMA reverse mux";
        tailf:code-name "ENUM_aaa_attribute_type_tdl__AAA_AT_CDMA_REVERSE_MUX_TDL";
      }
      enum "aaa-at-cdma-forward-rate" {
        value 519;
        description
          "CDMA forward rate";
        tailf:code-name "ENUM_aaa_attribute_type_tdl__AAA_AT_CDMA_FORWARD_RATE_TDL";
      }
      enum "aaa-at-cdma-reverse-rate" {
        value 520;
        description
          "CDMA reverse rate";
        tailf:code-name "ENUM_aaa_attribute_type_tdl__AAA_AT_CDMA_REVERSE_RATE_TDL";
      }
      enum "aaa-at-cdma-service-option" {
        value 521;
        description
          "CDMA service option";
        tailf:code-name "ENUM_aaa_attribute_type_tdl__AAA_AT_CDMA_SERVICE_OPTION_TDL";
      }
      enum "aaa-at-cdma-forward-type" {
        value 522;
        description
          "CDMA forward type";
        tailf:code-name "ENUM_aaa_attribute_type_tdl__AAA_AT_CDMA_FORWARD_TYPE_TDL";
      }
      enum "aaa-at-cdma-reverse-type" {
        value 523;
        description
          "CDMA reverse type";
        tailf:code-name "ENUM_aaa_attribute_type_tdl__AAA_AT_CDMA_REVERSE_TYPE_TDL";
      }
      enum "aaa-at-cdma-frame-size" {
        value 524;
        description
          "CDMA fundamental frame size";
        tailf:code-name "ENUM_aaa_attribute_type_tdl__AAA_AT_CDMA_FRAME_SIZE_TDL";
      }
      enum "aaa-at-cdma-forward-rc" {
        value 525;
        description
          "CDMA forward return code";
        tailf:code-name "ENUM_aaa_attribute_type_tdl__AAA_AT_CDMA_FORWARD_RC_TDL";
      }
      enum "aaa-at-cdma-reverse-rc" {
        value 526;
        description
          "CDMA reverse return code";
        tailf:code-name "ENUM_aaa_attribute_type_tdl__AAA_AT_CDMA_REVERSE_RC_TDL";
      }
      enum "aaa-at-cdma-ip-tech" {
        value 527;
        description
          "CDMA ip tech";
        tailf:code-name "ENUM_aaa_attribute_type_tdl__AAA_AT_CDMA_IP_TECH_TDL";
      }
      enum "aaa-at-cdma-comp-flag" {
        value 528;
        description
          "CDMA computational flag";
        tailf:code-name "ENUM_aaa_attribute_type_tdl__AAA_AT_CDMA_COMP_FLAG_TDL";
      }
      enum "aaa-at-cdma-reason-ind" {
        value 529;
        description
          "CDMA reason ind";
        tailf:code-name "ENUM_aaa_attribute_type_tdl__AAA_AT_CDMA_REASON_IND_TDL";
      }
      enum "aaa-at-cdma-dcch-frame-size" {
        value 530;
        description
          "CDMA Dedicated Control Channel frame size";
        tailf:code-name "ENUM_aaa_attribute_type_tdl__AAA_AT_CDMA_DCCH_FRAME_SIZE_TDL";
      }
      enum "aaa-at-cdma-bad-frame-count" {
        value 531;
        description
          "CDMA bad frame count";
        tailf:code-name "ENUM_aaa_attribute_type_tdl__AAA_AT_CDMA_BAD_FRAME_COUNT_TDL";
      }
      enum "aaa-at-cdma-active-time" {
        value 532;
        description
          "CDMA active time";
        tailf:code-name "ENUM_aaa_attribute_type_tdl__AAA_AT_CDMA_ACTIVE_TIME_TDL";
      }
      enum "aaa-at-cdma-num-active" {
        value 533;
        description
          "CDMA num active";
        tailf:code-name "ENUM_aaa_attribute_type_tdl__AAA_AT_CDMA_NUM_ACTIVE_TDL";
      }
      enum "aaa-at-cdma-sdb-input-octets" {
        value 534;
        description
          "CDMA short data burst input octets";
        tailf:code-name "ENUM_aaa_attribute_type_tdl__AAA_AT_CDMA_SDB_INPUT_OCTETS_TDL";
      }
      enum "aaa-at-cdma-sdb-output-octets" {
        value 535;
        description
          "CDMA short data burst output octets";
        tailf:code-name "ENUM_aaa_attribute_type_tdl__AAA_AT_CDMA_SDB_OUTPUT_OCTETS_TDL";
      }
      enum "aaa-at-cdma-numsdb-input" {
        value 536;
        description
          "CDMA numeric short data burst input";
        tailf:code-name "ENUM_aaa_attribute_type_tdl__AAA_AT_CDMA_NUMSDB_INPUT_TDL";
      }
      enum "aaa-at-cdma-numsdb-output" {
        value 537;
        description
          "CDMA numeric short data burst output";
        tailf:code-name "ENUM_aaa_attribute_type_tdl__AAA_AT_CDMA_NUMSDB_OUTPUT_TDL";
      }
      enum "aaa-at-cdma-hdlc-layer-bytes-in" {
        value 538;
        description
          "CDMA hdlc layer bytes in";
        tailf:code-name "ENUM_aaa_attribute_type_tdl__AAA_AT_CDMA_HDLC_LAYER_BYTES_IN_TDL";
      }
      enum "aaa-at-cdma-moip-inbound" {
        value 539;
        description
          "CDMA mobile-ip inbound count";
        tailf:code-name "ENUM_aaa_attribute_type_tdl__AAA_AT_CDMA_MOIP_INBOUND_TDL";
      }
      enum "aaa-at-cdma-moip-outbound" {
        value 540;
        description
          "CDMA mobile-ip outbound count";
        tailf:code-name "ENUM_aaa_attribute_type_tdl__AAA_AT_CDMA_MOIP_OUTBOUND_TDL";
      }
      enum "aaa-at-cdma-last-user-activity" {
        value 541;
        description
          "CDMA last user activity";
        tailf:code-name "ENUM_aaa_attribute_type_tdl__AAA_AT_CDMA_LAST_USER_ACTIVITY_TDL";
      }
      enum "aaa-at-cdma-ip-qos" {
        value 542;
        description
          "CDMA IP QoS";
        tailf:code-name "ENUM_aaa_attribute_type_tdl__AAA_AT_CDMA_IP_QOS_TDL";
      }
      enum "aaa-at-cdma-airlink-qos" {
        value 543;
        description
          "CDMA air-link QoS";
        tailf:code-name "ENUM_aaa_attribute_type_tdl__AAA_AT_CDMA_AIRLINK_QOS_TDL";
      }
      enum "aaa-at-cdma-diff-svc-class-opt" {
        value 544;
        description
          "CDMA diff svc class option";
        tailf:code-name "ENUM_aaa_attribute_type_tdl__AAA_AT_CDMA_DIFF_SVC_CLASS_OPT_TDL";
      }
      enum "aaa-at-cdma-rp-session-id" {
        value 545;
        description
          "CDMA rp session id";
        tailf:code-name "ENUM_aaa_attribute_type_tdl__AAA_AT_CDMA_RP_SESSION_ID_TDL";
      }
      enum "aaa-at-cdma-esn" {
        value 546;
        description
          "CDMA ESN";
        tailf:code-name "ENUM_aaa_attribute_type_tdl__AAA_AT_CDMA_ESN_TDL";
      }
      enum "aaa-at-cdma-mn-ha-spi" {
        value 547;
        description
          "CDMA mn ha spi";
        tailf:code-name "ENUM_aaa_attribute_type_tdl__AAA_AT_CDMA_MN_HA_SPI_TDL";
      }
      enum "aaa-at-cdma-mn-ha-shared-key" {
        value 548;
        description
          "CDMA mn ha shared key";
        tailf:code-name "ENUM_aaa_attribute_type_tdl__AAA_AT_CDMA_MN_HA_SHARED_KEY_TDL";
      }
      enum "aaa-at-cdma-mn-aaa-removal-ind" {
        value 549;
        description
          "CDMA MN AAA Removal Indication";
        tailf:code-name "ENUM_aaa_attribute_type_tdl__AAA_AT_CDMA_MN_AAA_REMOVAL_IND_TDL";
      }
      enum "aaa-at-cdma-sess-term-capability" {
        value 550;
        description
          "CDMA session termination capability";
        tailf:code-name "ENUM_aaa_attribute_type_tdl__AAA_AT_CDMA_SESS_TERM_CAPABILITY_TDL";
      }
      enum "aaa-at-cdma-prepaid-accounting-quota" {
        value 551;
        description
          "CDMA prepaid accounting quota";
        tailf:code-name "ENUM_aaa_attribute_type_tdl__AAA_AT_CDMA_PREPAID_ACCOUNTING_QUOTA_TDL";
      }
      enum "aaa-at-cdma-prepaid-accounting-capability" {
        value 552;
        description
          "CDMA prepaid accounting capability";
        tailf:code-name "ENUM_aaa_attribute_type_tdl__AAA_AT_CDMA_PREPAID_ACCOUNTING_CAPABILITY_TDL";
      }
      enum "aaa-at-cdma-disconnect-reason" {
        value 553;
        description
          "CDMA disconnect reason";
        tailf:code-name "ENUM_aaa_attribute_type_tdl__AAA_AT_CDMA_DISCONNECT_REASON_TDL";
      }
      enum "aaa-at-cdma-prepaid-tariff-switching" {
        value 554;
        description
          "CDMA prepaid tariff switching";
        tailf:code-name "ENUM_aaa_attribute_type_tdl__AAA_AT_CDMA_PREPAID_TARIFF_SWITCHING_TDL";
      }
      enum "aaa-at-cdma-allowed-differentiated-services-marking" {
        value 555;
        description
          "CDMA allowed differentiated service marking";
        tailf:code-name "ENUM_aaa_attribute_type_tdl__AAA_AT_CDMA_ALLOWED_DIFFERENTIATED_SERVICES_MARKING_TDL";
      }
      enum "aaa-at-cdma-forward-pdch-rc" {
        value 556;
        description
          "CDMA forward Packet Data Channel return code";
        tailf:code-name "ENUM_aaa_attribute_type_tdl__AAA_AT_CDMA_FORWARD_PDCH_RC_TDL";
      }
      enum "aaa-at-cdma-service-ref-id" {
        value 557;
        description
          "CDMA service reference id";
        tailf:code-name "ENUM_aaa_attribute_type_tdl__AAA_AT_CDMA_SERVICE_REF_ID_TDL";
      }
      enum "aaa-at-cdma-meid" {
        value 558;
        description
          "CDMA mobile equipment identifier";
        tailf:code-name "ENUM_aaa_attribute_type_tdl__AAA_AT_CDMA_MEID_TDL";
      }
      enum "aaa-at-cdma-dns-server-ip-address" {
        value 559;
        description
          "CDMA DNS server IP address";
        tailf:code-name "ENUM_aaa_attribute_type_tdl__AAA_AT_CDMA_DNS_SERVER_IP_ADDRESS_TDL";
      }
      enum "aaa-at-cdma-dns-update-required" {
        value 560;
        description
          "CDMA DNS update required";
        tailf:code-name "ENUM_aaa_attribute_type_tdl__AAA_AT_CDMA_DNS_UPDATE_REQUIRED_TDL";
      }
      enum "aaa-at-cdma-dns-update-capability" {
        value 561;
        description
          "CDMA DNS update capability";
        tailf:code-name "ENUM_aaa_attribute_type_tdl__AAA_AT_CDMA_DNS_UPDATE_CAPABILITY_TDL";
      }
      enum "aaa-at-cdma-rf-swact" {
        value 562;
        description
          "CDMA RF Switch of activity";
        tailf:code-name "ENUM_aaa_attribute_type_tdl__AAA_AT_CDMA_RF_SWACT_TDL";
      }
      enum "aaa-at-verizon-mip-key-update-req" {
        value 563;
        description
          "MIP key update req";
        tailf:code-name "ENUM_aaa_attribute_type_tdl__AAA_AT_VERIZON_MIP_KEY_UPDATE_REQ_TDL";
      }
      enum "aaa-at-verizon-mip-key-data" {
        value 564;
        description
          "MIP key data";
        tailf:code-name "ENUM_aaa_attribute_type_tdl__AAA_AT_VERIZON_MIP_KEY_DATA_TDL";
      }
      enum "aaa-at-verizon-aaa-authenticator" {
        value 565;
        description
          "AAA authenticator";
        tailf:code-name "ENUM_aaa_attribute_type_tdl__AAA_AT_VERIZON_AAA_AUTHENTICATOR_TDL";
      }
      enum "aaa-at-verizon-public-key-invalid" {
        value 566;
        description
          "Public key invalid";
        tailf:code-name "ENUM_aaa_attribute_type_tdl__AAA_AT_VERIZON_PUBLIC_KEY_INVALID_TDL";
      }
      enum "aaa-at-login-tcp-port" {
        value 567;
        description
          "TCP port used for connection";
        tailf:code-name "ENUM_aaa_attribute_type_tdl__AAA_AT_LOGIN_TCP_PORT_TDL";
      }
      enum "aaa-at-login-ip-addr-host" {
        value 568;
        description
          "Login IP address host";
        tailf:code-name "ENUM_aaa_attribute_type_tdl__AAA_AT_LOGIN_IP_ADDR_HOST_TDL";
      }
      enum "aaa-at-login-ipv6-addr-host" {
        value 569;
        description
          "Login IPv6 address host";
        tailf:code-name "ENUM_aaa_attribute_type_tdl__AAA_AT_LOGIN_IPV6_ADDR_HOST_TDL";
      }
      enum "aaa-at-login-ip-host" {
        value 570;
        description
          "Cisco VSA to pass Login-IP-Host in string format";
        tailf:code-name "ENUM_aaa_attribute_type_tdl__AAA_AT_LOGIN_IP_HOST_TDL";
      }
      enum "aaa-at-crb-auth-reason" {
        value 571;
        description
          "Authorization reason passed with (re)authorization";
        tailf:code-name "ENUM_aaa_attribute_type_tdl__AAA_AT_CRB_AUTH_REASON_TDL";
      }
      enum "aaa-at-crb-user-id" {
        value 572;
        description
          "Technology specific User-id";
        tailf:code-name "ENUM_aaa_attribute_type_tdl__AAA_AT_CRB_USER_ID_TDL";
      }
      enum "aaa-at-crb-session-id" {
        value 573;
        description
          "Realtime session id";
        tailf:code-name "ENUM_aaa_attribute_type_tdl__AAA_AT_CRB_SESSION_ID_TDL";
      }
      enum "aaa-at-crb-service-id" {
        value 574;
        description
          "Identify the service which the subscriber is using";
        tailf:code-name "ENUM_aaa_attribute_type_tdl__AAA_AT_CRB_SERVICE_ID_TDL";
      }
      enum "aaa-at-crb-entity-type" {
        value 575;
        description
          "CRB Entity type";
        tailf:code-name "ENUM_aaa_attribute_type_tdl__AAA_AT_CRB_ENTITY_TYPE_TDL";
      }
      enum "aaa-at-crb-duration" {
        value 576;
        description
          "IN - Duration quota, OUT - Duration used since the last quota";
        tailf:code-name "ENUM_aaa_attribute_type_tdl__AAA_AT_CRB_DURATION_TDL";
      }
      enum "aaa-at-crb-total-volume" {
        value 577;
        description
          "IN - Total volume quota in octets, OUT - Total volume in octets used since the last quota";
        tailf:code-name "ENUM_aaa_attribute_type_tdl__AAA_AT_CRB_TOTAL_VOLUME_TDL";
      }
      enum "aaa-at-crb-uplink-volume" {
        value 578;
        description
          "IN - UP volume quota in octets, OUT - UP volume in octets used since the last quota";
        tailf:code-name "ENUM_aaa_attribute_type_tdl__AAA_AT_CRB_UPLINK_VOLUME_TDL";
      }
      enum "aaa-at-crb-downlink-volume" {
        value 579;
        description
          "IN - DOWN volume quota in octets, OUT - DOWN volume in octets used since the last quota";
        tailf:code-name "ENUM_aaa_attribute_type_tdl__AAA_AT_CRB_DOWNLINK_VOLUME_TDL";
      }
      enum "aaa-at-crb-total-packets" {
        value 580;
        description
          "IN - Total pkts quota, OUT - Total pkts used since the last quota";
        tailf:code-name "ENUM_aaa_attribute_type_tdl__AAA_AT_CRB_TOTAL_PACKETS_TDL";
      }
      enum "aaa-at-crb-uplink-packets" {
        value 581;
        description
          "IN - Total UP pkts quota, OUT - Total UP pkts used since quota";
        tailf:code-name "ENUM_aaa_attribute_type_tdl__AAA_AT_CRB_UPLINK_PACKETS_TDL";
      }
      enum "aaa-at-crb-downlink-packets" {
        value 582;
        description
          "IN - Total DOWN pkts quota, OUT - Total DOWN pkts used since quota";
        tailf:code-name "ENUM_aaa_attribute_type_tdl__AAA_AT_CRB_DOWNLINK_PACKETS_TDL";
      }
      enum "aaa-at-crb-terminate-cause" {
        value 583;
        description
          "CRB termination cause";
        tailf:code-name "ENUM_aaa_attribute_type_tdl__AAA_AT_CRB_TERMINATE_CAUSE_TDL";
      }
      enum "aaa-at-cert-application" {
        value 584;
        description
          "Determines the valid application domain for a certificate";
        tailf:code-name "ENUM_aaa_attribute_type_tdl__AAA_AT_CERT_APPLICATION_TDL";
      }
      enum "aaa-at-cert-trustpoint" {
        value 585;
        description
          "Valid trustpoint label for the cert";
        tailf:code-name "ENUM_aaa_attribute_type_tdl__AAA_AT_CERT_TRUSTPOINT_TDL";
      }
      enum "aaa-at-cert-serial" {
        value 586;
        description
          "Serial number of the certificate";
        tailf:code-name "ENUM_aaa_attribute_type_tdl__AAA_AT_CERT_SERIAL_TDL";
      }
      enum "aaa-at-cert-serial-not" {
        value 587;
        description
          "Serial number of the certificate to reject";
        tailf:code-name "ENUM_aaa_attribute_type_tdl__AAA_AT_CERT_SERIAL_NOT_TDL";
      }
      enum "aaa-at-cert-lifetime-end" {
        value 588;
        description
          "Valid Lifetime end date of cert - Overrides actual cert lifetime end date";
        tailf:code-name "ENUM_aaa_attribute_type_tdl__AAA_AT_CERT_LIFETIME_END_TDL";
      }
      enum "aaa-at-tti-subjectname" {
        value 589;
        description
          "Subject name used by Certificate Server";
        tailf:code-name "ENUM_aaa_attribute_type_tdl__AAA_AT_TTI_SUBJECTNAME_TDL";
      }
      enum "aaa-at-tti-iosconfig1" {
        value 590;
        description
          "Trusted Transitive Introduction IOS configuration 1";
        tailf:code-name "ENUM_aaa_attribute_type_tdl__AAA_AT_TTI_IOSCONFIG1_TDL";
      }
      enum "aaa-at-tti-iosconfig2" {
        value 591;
        description
          "Trusted Transitive Introduction IOS configuration 2";
        tailf:code-name "ENUM_aaa_attribute_type_tdl__AAA_AT_TTI_IOSCONFIG2_TDL";
      }
      enum "aaa-at-tti-iosconfig3" {
        value 592;
        description
          "Trusted Transitive Introduction IOS configuration 3";
        tailf:code-name "ENUM_aaa_attribute_type_tdl__AAA_AT_TTI_IOSCONFIG3_TDL";
      }
      enum "aaa-at-tti-iosconfig4" {
        value 593;
        description
          "Trusted Transitive Introduction IOS configuration 4";
        tailf:code-name "ENUM_aaa_attribute_type_tdl__AAA_AT_TTI_IOSCONFIG4_TDL";
      }
      enum "aaa-at-tti-iosconfig5" {
        value 594;
        description
          "Trusted Transitive Introduction IOS configuration 5";
        tailf:code-name "ENUM_aaa_attribute_type_tdl__AAA_AT_TTI_IOSCONFIG5_TDL";
      }
      enum "aaa-at-tti-iosconfig6" {
        value 595;
        description
          "Trusted Transitive Introduction IOS configuration 6";
        tailf:code-name "ENUM_aaa_attribute_type_tdl__AAA_AT_TTI_IOSCONFIG6_TDL";
      }
      enum "aaa-at-tti-iosconfig7" {
        value 596;
        description
          "Trusted Transitive Introduction IOS configuration 7";
        tailf:code-name "ENUM_aaa_attribute_type_tdl__AAA_AT_TTI_IOSCONFIG7_TDL";
      }
      enum "aaa-at-tti-iosconfig8" {
        value 597;
        description
          "Trusted Transitive Introduction IOS configuration 8";
        tailf:code-name "ENUM_aaa_attribute_type_tdl__AAA_AT_TTI_IOSCONFIG8_TDL";
      }
      enum "aaa-at-tti-iosconfig9" {
        value 598;
        description
          "Trusted Transitive Introduction IOS configuration 9";
        tailf:code-name "ENUM_aaa_attribute_type_tdl__AAA_AT_TTI_IOSCONFIG9_TDL";
      }
      enum "aaa-at-tti-privilege" {
        value 599;
        description
          "Trusted Transitive Introduction privilege: admin or user";
        tailf:code-name "ENUM_aaa_attribute_type_tdl__AAA_AT_TTI_PRIVILEGE_TDL";
      }
      enum "aaa-at-nas-ip-address" {
        value 600;
        description
          "The IP address of the NAS";
        tailf:code-name "ENUM_aaa_attribute_type_tdl__AAA_AT_NAS_IP_ADDRESS_TDL";
      }
      enum "aaa-at-delay-time" {
        value 601;
        description
          "Accounting record delay time";
        tailf:code-name "ENUM_aaa_attribute_type_tdl__AAA_AT_DELAY_TIME_TDL";
      }
      enum "aaa-at-em-header" {
        value 602;
        description
          "EM header";
        tailf:code-name "ENUM_aaa_attribute_type_tdl__AAA_AT_EM_HEADER_TDL";
      }
      enum "aaa-at-called-party-number" {
        value 603;
        description
          "Called party number";
        tailf:code-name "ENUM_aaa_attribute_type_tdl__AAA_AT_CALLED_PARTY_NUMBER_TDL";
      }
      enum "aaa-at-call-termination-cause" {
        value 604;
        description
          "Call termination cause";
        tailf:code-name "ENUM_aaa_attribute_type_tdl__AAA_AT_CALL_TERMINATION_CAUSE_TDL";
      }
      enum "aaa-at-related-call-billing-correlation-id" {
        value 605;
        description
          "Related call billing correlation ID";
        tailf:code-name "ENUM_aaa_attribute_type_tdl__AAA_AT_RELATED_CALL_BILLING_CORRELATION_ID_TDL";
      }
      enum "aaa-at-mta-udp-portnum" {
        value 606;
        description
          "Mail Transfer Agent UDP port number";
        tailf:code-name "ENUM_aaa_attribute_type_tdl__AAA_AT_MTA_UDP_PORTNUM_TDL";
      }
      enum "aaa-at-sf-id" {
        value 607;
        description
          "Service flow ID";
        tailf:code-name "ENUM_aaa_attribute_type_tdl__AAA_AT_SF_ID_TDL";
      }
      enum "aaa-at-qos-descriptor" {
        value 608;
        description
          "QoS descriptor";
        tailf:code-name "ENUM_aaa_attribute_type_tdl__AAA_AT_QOS_DESCRIPTOR_TDL";
      }
      enum "aaa-at-time-adjustment" {
        value 609;
        description
          "Time adjustment";
        tailf:code-name "ENUM_aaa_attribute_type_tdl__AAA_AT_TIME_ADJUSTMENT_TDL";
      }
      enum "aaa-at-sdp-upstream" {
        value 610;
        description
          "SDP upstream";
        tailf:code-name "ENUM_aaa_attribute_type_tdl__AAA_AT_SDP_UPSTREAM_TDL";
      }
      enum "aaa-at-sdp-downstream" {
        value 611;
        description
          "SDP downstream";
        tailf:code-name "ENUM_aaa_attribute_type_tdl__AAA_AT_SDP_DOWNSTREAM_TDL";
      }
      enum "aaa-at-ccc-id" {
        value 612;
        description
          "CCC ID";
        tailf:code-name "ENUM_aaa_attribute_type_tdl__AAA_AT_CCC_ID_TDL";
      }
      enum "aaa-at-feid" {
        value 613;
        description
          "Financial entity ID";
        tailf:code-name "ENUM_aaa_attribute_type_tdl__AAA_AT_FEID_TDL";
      }
      enum "aaa-at-flow-direction" {
        value 614;
        description
          "Flow direction";
        tailf:code-name "ENUM_aaa_attribute_type_tdl__AAA_AT_FLOW_DIRECTION_TDL";
      }
      enum "aaa-at-gate-usage-info" {
        value 615;
        description
          "Gate usage information";
        tailf:code-name "ENUM_aaa_attribute_type_tdl__AAA_AT_GATE_USAGE_INFO_TDL";
      }
      enum "aaa-at-element-req-qos" {
        value 616;
        description
          "Element requested QoS";
        tailf:code-name "ENUM_aaa_attribute_type_tdl__AAA_AT_ELEMENT_REQ_QOS_TDL";
      }
      enum "aaa-at-qos-release-reason" {
        value 617;
        description
          "QoS release reason";
        tailf:code-name "ENUM_aaa_attribute_type_tdl__AAA_AT_QOS_RELEASE_REASON_TDL";
      }
      enum "aaa-at-gate-time-info" {
        value 618;
        description
          "Gate time information";
        tailf:code-name "ENUM_aaa_attribute_type_tdl__AAA_AT_GATE_TIME_INFO_TDL";
      }
      enum "aaa-at-threegenpp-imsi" {
        value 619;
        description
          "3GPP International Mobile Subscriber Id";
        tailf:code-name "ENUM_aaa_attribute_type_tdl__AAA_AT_THREEGENPP_IMSI_TDL";
      }
      enum "aaa-at-threegenpp-charging-id" {
        value 620;
        description
          "3GPP Charging ID";
        tailf:code-name "ENUM_aaa_attribute_type_tdl__AAA_AT_THREEGENPP_CHARGING_ID_TDL";
      }
      enum "aaa-at-threegenpp-pdp-type" {
        value 621;
        description
          "3GPP PDP type";
        tailf:code-name "ENUM_aaa_attribute_type_tdl__AAA_AT_THREEGENPP_PDP_TYPE_TDL";
      }
      enum "aaa-at-threegenpp-cg-address" {
        value 622;
        description
          "3GPP Charging Gateway Address";
        tailf:code-name "ENUM_aaa_attribute_type_tdl__AAA_AT_THREEGENPP_CG_ADDRESS_TDL";
      }
      enum "aaa-at-threegenpp-gprs-qos-profile" {
        value 623;
        description
          "3GPP GPRS QoS Profile";
        tailf:code-name "ENUM_aaa_attribute_type_tdl__AAA_AT_THREEGENPP_GPRS_QOS_PROFILE_TDL";
      }
      enum "aaa-at-threegenpp-sgsn-address" {
        value 624;
        description
          "3GPP Serving GPRS Support Node address";
        tailf:code-name "ENUM_aaa_attribute_type_tdl__AAA_AT_THREEGENPP_SGSN_ADDRESS_TDL";
      }
      enum "aaa-at-threegenpp-ggsn-address" {
        value 625;
        description
          "3GPP Gateway GPRS Support Node address";
        tailf:code-name "ENUM_aaa_attribute_type_tdl__AAA_AT_THREEGENPP_GGSN_ADDRESS_TDL";
      }
      enum "aaa-at-threegenpp-imsi-mcc-mnc" {
        value 626;
        description
          "3GPP IMSI MCC MNC";
        tailf:code-name "ENUM_aaa_attribute_type_tdl__AAA_AT_THREEGENPP_IMSI_MCC_MNC_TDL";
      }
      enum "aaa-at-threegenpp-ggsn-mcc-mnc" {
        value 627;
        description
          "3GPP Gateway GPRS Support Node MCC MNC";
        tailf:code-name "ENUM_aaa_attribute_type_tdl__AAA_AT_THREEGENPP_GGSN_MCC_MNC_TDL";
      }
      enum "aaa-at-threegenpp-nsapi" {
        value 628;
        description
          "3GPP Network Service Access Point Identifier of the PDP";
        tailf:code-name "ENUM_aaa_attribute_type_tdl__AAA_AT_THREEGENPP_NSAPI_TDL";
      }
      enum "aaa-at-threegenpp-sess-stop-ind" {
        value 629;
        description
          "3GPP Session Stop Ind";
        tailf:code-name "ENUM_aaa_attribute_type_tdl__AAA_AT_THREEGENPP_SESS_STOP_IND_TDL";
      }
      enum "aaa-at-threegenpp-selection-mode" {
        value 630;
        description
          "3GPP Selection Mode";
        tailf:code-name "ENUM_aaa_attribute_type_tdl__AAA_AT_THREEGENPP_SELECTION_MODE_TDL";
      }
      enum "aaa-at-threegenpp-charging-characteristics" {
        value 631;
        description
          "3GPP Charging Characteristics";
        tailf:code-name "ENUM_aaa_attribute_type_tdl__AAA_AT_THREEGENPP_CHARGING_CHARACTERISTICS_TDL";
      }
      enum "aaa-at-threegenpp-sgsn-mcc-mnc" {
        value 632;
        description
          "3GPP Serving GPRS Support Node MCC MNC";
        tailf:code-name "ENUM_aaa_attribute_type_tdl__AAA_AT_THREEGENPP_SGSN_MCC_MNC_TDL";
      }
      enum "aaa-at-threegenpp-cg-ipv6-address" {
        value 633;
        description
          "3GPP Charging gateway IPv6 address";
        tailf:code-name "ENUM_aaa_attribute_type_tdl__AAA_AT_THREEGENPP_CG_IPV6_ADDRESS_TDL";
      }
      enum "aaa-at-threegenpp-sgsn-ipv6-address" {
        value 634;
        description
          "3GPP Serving GPRS Support Node IPv6 address";
        tailf:code-name "ENUM_aaa_attribute_type_tdl__AAA_AT_THREEGENPP_SGSN_IPV6_ADDRESS_TDL";
      }
      enum "aaa-at-threegenpp-ggsn-ipv6-address" {
        value 635;
        description
          "3GPP Gateway GPRS Support Node IPv6 address";
        tailf:code-name "ENUM_aaa_attribute_type_tdl__AAA_AT_THREEGENPP_GGSN_IPV6_ADDRESS_TDL";
      }
      enum "aaa-at-threegenpp-ipv6-dns" {
        value 636;
        description
          "3GPP IPv6 DNS server";
        tailf:code-name "ENUM_aaa_attribute_type_tdl__AAA_AT_THREEGENPP_IPV6_DNS_TDL";
      }
      enum "aaa-at-threegenpp-imeisv" {
        value 637;
        description
          "3GPP International Mobile Equipment Identity-Software Version";
        tailf:code-name "ENUM_aaa_attribute_type_tdl__AAA_AT_THREEGENPP_IMEISV_TDL";
      }
      enum "aaa-at-access-technology-type" {
        value 638;
        description
          "Access technology type";
        tailf:code-name "ENUM_aaa_attribute_type_tdl__AAA_AT_ACCESS_TECHNOLOGY_TYPE_TDL";
      }
      enum "aaa-at-threegenpp-user-location-info" {
        value 639;
        description
          "3GPP User Location Information";
        tailf:code-name "ENUM_aaa_attribute_type_tdl__AAA_AT_THREEGENPP_USER_LOCATION_INFO_TDL";
      }
      enum "aaa-at-threegenpp-ms-timezone" {
        value 640;
        description
          "3GPP Mobile station timezone";
        tailf:code-name "ENUM_aaa_attribute_type_tdl__AAA_AT_THREEGENPP_MS_TIMEZONE_TDL";
      }
      enum "aaa-at-threegenpp-camel-charging-info" {
        value 641;
        description
          "3GPP Camel Charge Information Container";
        tailf:code-name "ENUM_aaa_attribute_type_tdl__AAA_AT_THREEGENPP_CAMEL_CHARGING_INFO_TDL";
      }
      enum "aaa-at-teardown-indicator" {
        value 642;
        description
          "Teardown indicator to be present in Disconnect-Request";
        tailf:code-name "ENUM_aaa_attribute_type_tdl__AAA_AT_TEARDOWN_INDICATOR_TDL";
      }
      enum "aaa-at-md-addr" {
        value 643;
        description
          "IP address of the Mediation Device";
        tailf:code-name "ENUM_aaa_attribute_type_tdl__AAA_AT_MD_ADDR_TDL";
      }
      enum "aaa-at-md-port" {
        value 644;
        description
          "UDP port of the Mediation Device";
        tailf:code-name "ENUM_aaa_attribute_type_tdl__AAA_AT_MD_PORT_TDL";
      }
      enum "aaa-at-intercept-action" {
        value 645;
        description
          "Intercept action";
        tailf:code-name "ENUM_aaa_attribute_type_tdl__AAA_AT_INTERCEPT_ACTION_TDL";
      }
      enum "aaa-at-intercept-id" {
        value 646;
        description
          "Intercept identifier";
        tailf:code-name "ENUM_aaa_attribute_type_tdl__AAA_AT_INTERCEPT_ID_TDL";
      }
      enum "aaa-at-charging-profile-index" {
        value 647;
        description
          "Charging profile to be applied for the user";
        tailf:code-name "ENUM_aaa_attribute_type_tdl__AAA_AT_CHARGING_PROFILE_INDEX_TDL";
      }
      enum "aaa-at-billing-plan" {
        value 648;
        description
          "Billing Rule to be applied for this user";
        tailf:code-name "ENUM_aaa_attribute_type_tdl__AAA_AT_BILLING_PLAN_TDL";
      }
      enum "aaa-at-quota-server" {
        value 649;
        description
          "Quota Server information from Gateway GPRS Support Node";
        tailf:code-name "ENUM_aaa_attribute_type_tdl__AAA_AT_QUOTA_SERVER_TDL";
      }
      enum "aaa-at-im-entry-allowed" {
        value 650;
        description
          "Indicates whether the MS is allowed to enter Idle Mode";
        tailf:code-name "ENUM_aaa_attribute_type_tdl__AAA_AT_IM_ENTRY_ALLOWED_TDL";
      }
      enum "aaa-at-downlink-nexthop-address" {
        value 651;
        description
          "Next Hop address to use by CSG for CSG->QS communication";
        tailf:code-name "ENUM_aaa_attribute_type_tdl__AAA_AT_DOWNLINK_NEXTHOP_ADDRESS_TDL";
      }
      enum "aaa-at-gtp-pdp-session" {
        value 652;
        description
          "GTP functionality for a PDP session";
        tailf:code-name "ENUM_aaa_attribute_type_tdl__AAA_AT_GTP_PDP_SESSION_TDL";
      }
      enum "aaa-at-apn" {
        value 653;
        description
          "APN name";
        tailf:code-name "ENUM_aaa_attribute_type_tdl__AAA_AT_APN_TDL";
      }
      enum "aaa-at-sslvpn-http-proxy-server" {
        value 654;
        description
          "SSLVPN back-end proxy server name";
        tailf:code-name "ENUM_aaa_attribute_type_tdl__AAA_AT_SSLVPN_HTTP_PROXY_SERVER_TDL";
      }
      enum "aaa-at-sslvpn-http-proxy-server-port" {
        value 655;
        description
          "SSLVPN back-end proxy server port";
        tailf:code-name "ENUM_aaa_attribute_type_tdl__AAA_AT_SSLVPN_HTTP_PROXY_SERVER_PORT_TDL";
      }
      enum "aaa-at-mschap-error" {
        value 656;
        description
          "MS-CHAP error";
        tailf:code-name "ENUM_aaa_attribute_type_tdl__AAA_AT_MSCHAP_ERROR_TDL";
      }
      enum "aaa-at-mschap-nt-enc-pw1" {
        value 657;
        description
          "MS-CHAP NT encrypted password 1";
        tailf:code-name "ENUM_aaa_attribute_type_tdl__AAA_AT_MSCHAP_NT_ENC_PW1_TDL";
      }
      enum "aaa-at-mschap-nt-enc-pw2" {
        value 658;
        description
          "MS-CHAP NT encrypted password 2";
        tailf:code-name "ENUM_aaa_attribute_type_tdl__AAA_AT_MSCHAP_NT_ENC_PW2_TDL";
      }
      enum "aaa-at-mschap-nt-enc-pw3" {
        value 659;
        description
          "MS-CHAP NT encrypted password 3";
        tailf:code-name "ENUM_aaa_attribute_type_tdl__AAA_AT_MSCHAP_NT_ENC_PW3_TDL";
      }
      enum "aaa-at-mschap-mppe-keys" {
        value 660;
        description
          "LM and NT sessions keys for Microsoft Point-to-Point Encryption";
        tailf:code-name "ENUM_aaa_attribute_type_tdl__AAA_AT_MSCHAP_MPPE_KEYS_TDL";
      }
      enum "aaa-at-ms-mppe-send-key" {
        value 661;
        description
          "Send session key for Microsoft Point-to-Point Encryption";
        tailf:code-name "ENUM_aaa_attribute_type_tdl__AAA_AT_MS_MPPE_SEND_KEY_TDL";
      }
      enum "aaa-at-ms-mppe-recv-key" {
        value 662;
        description
          "Receive session key for Microsoft Point-to-Point Encryption";
        tailf:code-name "ENUM_aaa_attribute_type_tdl__AAA_AT_MS_MPPE_RECV_KEY_TDL";
      }
      enum "aaa-at-rad-sg-serv" {
        value 663;
        description
          "Radius server host in server group";
        tailf:code-name "ENUM_aaa_attribute_type_tdl__AAA_AT_RAD_SG_SERV_TDL";
      }
      enum "aaa-at-rad-sg-vrf" {
        value 664;
        description
          "VRF to be used to access the servers";
        tailf:code-name "ENUM_aaa_attribute_type_tdl__AAA_AT_RAD_SG_VRF_TDL";
      }
      enum "aaa-at-rad-sg-source-if" {
        value 665;
        description
          "Source interface to use to access the servers";
        tailf:code-name "ENUM_aaa_attribute_type_tdl__AAA_AT_RAD_SG_SOURCE_IF_TDL";
      }
      enum "aaa-at-rad-sg-filter" {
        value 666;
        description
          "Radius filter list name for server group";
        tailf:code-name "ENUM_aaa_attribute_type_tdl__AAA_AT_RAD_SG_FILTER_TDL";
      }
      enum "aaa-at-ppp-authen-list" {
        value 667;
        description
          "PPP authentication method-list";
        tailf:code-name "ENUM_aaa_attribute_type_tdl__AAA_AT_PPP_AUTHEN_LIST_TDL";
      }
      enum "aaa-at-ppp-authen-type" {
        value 668;
        description
          "PPP authentication protocols";
        tailf:code-name "ENUM_aaa_attribute_type_tdl__AAA_AT_PPP_AUTHEN_TYPE_TDL";
      }
      enum "aaa-at-ppp-author-list" {
        value 669;
        description
          "PPP authorization method-list";
        tailf:code-name "ENUM_aaa_attribute_type_tdl__AAA_AT_PPP_AUTHOR_LIST_TDL";
      }
      enum "aaa-at-ppp-account-list" {
        value 670;
        description
          "PPP accounting method-list";
        tailf:code-name "ENUM_aaa_attribute_type_tdl__AAA_AT_PPP_ACCOUNT_LIST_TDL";
      }
      enum "aaa-at-ip-vrf" {
        value 671;
        description
          "VRF Information";
        tailf:code-name "ENUM_aaa_attribute_type_tdl__AAA_AT_IP_VRF_TDL";
      }
      enum "aaa-at-ip-addr" {
        value 672;
        description
          "IP address";
        tailf:code-name "ENUM_aaa_attribute_type_tdl__AAA_AT_IP_ADDR_TDL";
      }
      enum "aaa-at-ip-unnumbered" {
        value 673;
        description
          "IP unnumbered";
        tailf:code-name "ENUM_aaa_attribute_type_tdl__AAA_AT_IP_UNNUMBERED_TDL";
      }
      enum "aaa-at-peer-ip-pool" {
        value 674;
        description
          "Local IP pool address";
        tailf:code-name "ENUM_aaa_attribute_type_tdl__AAA_AT_PEER_IP_POOL_TDL";
      }
      enum "aaa-at-rad-attr44" {
        value 675;
        description
          "Include radius attribute 44 in access-req";
        tailf:code-name "ENUM_aaa_attribute_type_tdl__AAA_AT_RAD_ATTR44_TDL";
      }
      enum "aaa-at-account-delay" {
        value 676;
        description
          "Accounting delay start";
        tailf:code-name "ENUM_aaa_attribute_type_tdl__AAA_AT_ACCOUNT_DELAY_TDL";
      }
      enum "aaa-at-acct-send-stop-authen-failure" {
        value 677;
        description
          "Send accounting information even with failure";
        tailf:code-name "ENUM_aaa_attribute_type_tdl__AAA_AT_ACCT_SEND_STOP_AUTHEN_FAILURE_TDL";
      }
      enum "aaa-at-acct-send-stop-accept-remote" {
        value 678;
        description
          "Send accounting for remote authenticated users";
        tailf:code-name "ENUM_aaa_attribute_type_tdl__AAA_AT_ACCT_SEND_STOP_ACCEPT_REMOTE_TDL";
      }
      enum "aaa-at-cfg-template" {
        value 679;
        description
          "Name of template to be applied";
        tailf:code-name "ENUM_aaa_attribute_type_tdl__AAA_AT_CFG_TEMPLATE_TDL";
      }
      enum "aaa-at-mschap-v2-success" {
        value 680;
        description
          "MSCHAPv2 response string";
        tailf:code-name "ENUM_aaa_attribute_type_tdl__AAA_AT_MSCHAP_V2_SUCCESS_TDL";
      }
      enum "aaa-at-mschap-v2-cpw" {
        value 681;
        description
          "MSCHAPv2 change password on expiry";
        tailf:code-name "ENUM_aaa_attribute_type_tdl__AAA_AT_MSCHAP_V2_CPW_TDL";
      }
      enum "aaa-at-call-id" {
        value 682;
        description
          "Call-id for a voip call";
        tailf:code-name "ENUM_aaa_attribute_type_tdl__AAA_AT_CALL_ID_TDL";
      }
      enum "aaa-at-cust-biz-grp-id" {
        value 683;
        description
          "Customer business group ID for a voip call";
        tailf:code-name "ENUM_aaa_attribute_type_tdl__AAA_AT_CUST_BIZ_GRP_ID_TDL";
      }
      enum "aaa-at-ip-hop" {
        value 684;
        description
          "VIA header information from INVITE message";
        tailf:code-name "ENUM_aaa_attribute_type_tdl__AAA_AT_IP_HOP_TDL";
      }
      enum "aaa-at-nas-ipv6-address" {
        value 685;
        description
          "The IPv6 address of the NAS";
        tailf:code-name "ENUM_aaa_attribute_type_tdl__AAA_AT_NAS_IPV6_ADDRESS_TDL";
      }
      enum "aaa-at-ipv6-interfaceid" {
        value 686;
        description
          "The IPv6 Interface Id for the user";
        tailf:code-name "ENUM_aaa_attribute_type_tdl__AAA_AT_IPV6_INTERFACEID_TDL";
      }
      enum "aaa-at-ipv6-prefix" {
        value 687;
        description
          "IPv6 Prefix information for a user session";
        tailf:code-name "ENUM_aaa_attribute_type_tdl__AAA_AT_IPV6_PREFIX_TDL";
      }
      enum "aaa-at-ipv6-prefix-len" {
        value 688;
        description
          "IPv6 prefix length";
        tailf:code-name "ENUM_aaa_attribute_type_tdl__AAA_AT_IPV6_PREFIX_LEN_TDL";
      }
      enum "aaa-at-delegated-ipv6-prefix" {
        value 689;
        description
          "Delegated IPv6 prefix information for a user session";
        tailf:code-name "ENUM_aaa_attribute_type_tdl__AAA_AT_DELEGATED_IPV6_PREFIX_TDL";
      }
      enum "aaa-at-delegated-ipv6-pool" {
        value 690;
        description
          "DHCP pool name for assigning user session IPv6 prefix";
        tailf:code-name "ENUM_aaa_attribute_type_tdl__AAA_AT_DELEGATED_IPV6_POOL_TDL";
      }
      enum "aaa-at-ipv6-dns-servers" {
        value 691;
        description
          "The IPv6 address of a DNS server";
        tailf:code-name "ENUM_aaa_attribute_type_tdl__AAA_AT_IPV6_DNS_SERVERS_TDL";
      }
      enum "aaa-at-session-type" {
        value 692;
        description
          "Type of PPP stack session - IPv4/v6 or dual stack";
        tailf:code-name "ENUM_aaa_attribute_type_tdl__AAA_AT_SESSION_TYPE_TDL";
      }
      enum "aaa-at-remote-media-address" {
        value 693;
        description
          "Remote media gateway IP address";
        tailf:code-name "ENUM_aaa_attribute_type_tdl__AAA_AT_REMOTE_MEDIA_ADDRESS_TDL";
      }
      enum "aaa-at-carrier-id" {
        value 694;
        description
          "ISDN User Part carrier id";
        tailf:code-name "ENUM_aaa_attribute_type_tdl__AAA_AT_CARRIER_ID_TDL";
      }
      enum "aaa-at-calling-party-category" {
        value 695;
        description
          "Calling party category";
        tailf:code-name "ENUM_aaa_attribute_type_tdl__AAA_AT_CALLING_PARTY_CATEGORY_TDL";
      }
      enum "aaa-at-orig-line-info" {
        value 696;
        description
          "Originating line information";
        tailf:code-name "ENUM_aaa_attribute_type_tdl__AAA_AT_ORIG_LINE_INFO_TDL";
      }
      enum "aaa-at-charge-number" {
        value 697;
        description
          "Charge number";
        tailf:code-name "ENUM_aaa_attribute_type_tdl__AAA_AT_CHARGE_NUMBER_TDL";
      }
      enum "aaa-at-trans-med-req" {
        value 698;
        description
          "Transmission medium request";
        tailf:code-name "ENUM_aaa_attribute_type_tdl__AAA_AT_TRANS_MED_REQ_TDL";
      }
      enum "aaa-at-rdt-number" {
        value 699;
        description
          "Redirecting number";
        tailf:code-name "ENUM_aaa_attribute_type_tdl__AAA_AT_RDT_NUMBER_TDL";
      }
      enum "aaa-at-backward-call-ind" {
        value 700;
        description
          "Backward call indicators";
        tailf:code-name "ENUM_aaa_attribute_type_tdl__AAA_AT_BACKWARD_CALL_IND_TDL";
      }
      enum "aaa-at-remote-media-udp-port" {
        value 701;
        description
          "Remote media gateway UDP port";
        tailf:code-name "ENUM_aaa_attribute_type_tdl__AAA_AT_REMOTE_MEDIA_UDP_PORT_TDL";
      }
      enum "aaa-at-remote-media-id" {
        value 702;
        description
          "Remote media gateway DNS name";
        tailf:code-name "ENUM_aaa_attribute_type_tdl__AAA_AT_REMOTE_MEDIA_ID_TDL";
      }
      enum "aaa-at-supp-svc-xfer-by" {
        value 703;
        description
          "Transferor who initiates a call-transfer";
        tailf:code-name "ENUM_aaa_attribute_type_tdl__AAA_AT_SUPP_SVC_XFER_BY_TDL";
      }
      enum "aaa-at-faxrelay-start-time" {
        value 704;
        description
          "Fax relay start time";
        tailf:code-name "ENUM_aaa_attribute_type_tdl__AAA_AT_FAXRELAY_START_TIME_TDL";
      }
      enum "aaa-at-faxrelay-max-jit-buf-depth" {
        value 705;
        description
          "Fax relay maximum jitter buffer depth";
        tailf:code-name "ENUM_aaa_attribute_type_tdl__AAA_AT_FAXRELAY_MAX_JIT_BUF_DEPTH_TDL";
      }
      enum "aaa-at-faxrelay-jit-buf-ovflow" {
        value 706;
        description
          "Fax relay jitter buffer overflow";
        tailf:code-name "ENUM_aaa_attribute_type_tdl__AAA_AT_FAXRELAY_JIT_BUF_OVFLOW_TDL";
      }
      enum "aaa-at-faxrelay-mr-hs-mod" {
        value 707;
        description
          "Fax relay most recent high speed modulation";
        tailf:code-name "ENUM_aaa_attribute_type_tdl__AAA_AT_FAXRELAY_MR_HS_MOD_TDL";
      }
      enum "aaa-at-faxrelay-init-hs-mod" {
        value 708;
        description
          "Fax relay initial high speed modulation";
        tailf:code-name "ENUM_aaa_attribute_type_tdl__AAA_AT_FAXRELAY_INIT_HS_MOD_TDL";
      }
      enum "aaa-at-faxrelay-num-pages" {
        value 709;
        description
          "Fax relay number of pages transmitted";
        tailf:code-name "ENUM_aaa_attribute_type_tdl__AAA_AT_FAXRELAY_NUM_PAGES_TDL";
      }
      enum "aaa-at-faxrelay-direction" {
        value 710;
        description
          "Fax relay direction";
        tailf:code-name "ENUM_aaa_attribute_type_tdl__AAA_AT_FAXRELAY_DIRECTION_TDL";
      }
      enum "aaa-at-faxrelay-ecm-status" {
        value 711;
        description
          "Fax relay ECM status";
        tailf:code-name "ENUM_aaa_attribute_type_tdl__AAA_AT_FAXRELAY_ECM_STATUS_TDL";
      }
      enum "aaa-at-faxrelay-encap-prot" {
        value 712;
        description
          "Fax relay encapsulation protocol";
        tailf:code-name "ENUM_aaa_attribute_type_tdl__AAA_AT_FAXRELAY_ENCAP_PROT_TDL";
      }
      enum "aaa-at-faxrelay-nsf-country-code" {
        value 713;
        description
          "Fax relay NSF country code";
        tailf:code-name "ENUM_aaa_attribute_type_tdl__AAA_AT_FAXRELAY_NSF_COUNTRY_CODE_TDL";
      }
      enum "aaa-at-faxrelay-nsf-manuf-code" {
        value 714;
        description
          "Fax relay NSF manufacture code";
        tailf:code-name "ENUM_aaa_attribute_type_tdl__AAA_AT_FAXRELAY_NSF_MANUF_CODE_TDL";
      }
      enum "aaa-at-faxrelay-fax-success" {
        value 715;
        description
          "Fax relay fax success";
        tailf:code-name "ENUM_aaa_attribute_type_tdl__AAA_AT_FAXRELAY_FAX_SUCCESS_TDL";
      }
      enum "aaa-at-faxrelay-tx-packets" {
        value 716;
        description
          "Fax relay number of transmitted packets";
        tailf:code-name "ENUM_aaa_attribute_type_tdl__AAA_AT_FAXRELAY_TX_PACKETS_TDL";
      }
      enum "aaa-at-faxrelay-rx-packets" {
        value 717;
        description
          "Fax relay number of received packets";
        tailf:code-name "ENUM_aaa_attribute_type_tdl__AAA_AT_FAXRELAY_RX_PACKETS_TDL";
      }
      enum "aaa-at-faxrelay-pkt-conceal" {
        value 718;
        description
          "Fax relay packet concealment";
        tailf:code-name "ENUM_aaa_attribute_type_tdl__AAA_AT_FAXRELAY_PKT_CONCEAL_TDL";
      }
      enum "aaa-at-voice-feature" {
        value 719;
        description
          "Voice call feature name";
        tailf:code-name "ENUM_aaa_attribute_type_tdl__AAA_AT_VOICE_FEATURE_TDL";
      }
      enum "aaa-at-feature-operation" {
        value 720;
        description
          "Voice call feature operation name";
        tailf:code-name "ENUM_aaa_attribute_type_tdl__AAA_AT_FEATURE_OPERATION_TDL";
      }
      enum "aaa-at-feature-op-status" {
        value 721;
        description
          "Voice call feature operation status";
        tailf:code-name "ENUM_aaa_attribute_type_tdl__AAA_AT_FEATURE_OP_STATUS_TDL";
      }
      enum "aaa-at-feature-op-time" {
        value 722;
        description
          "Voice call feature operation time";
        tailf:code-name "ENUM_aaa_attribute_type_tdl__AAA_AT_FEATURE_OP_TIME_TDL";
      }
      enum "aaa-at-feature-id" {
        value 723;
        description
          "Voice call feature ID";
        tailf:code-name "ENUM_aaa_attribute_type_tdl__AAA_AT_FEATURE_ID_TDL";
      }
      enum "aaa-at-feature-vsa" {
        value 724;
        description
          "Gateway invoked feature information";
        tailf:code-name "ENUM_aaa_attribute_type_tdl__AAA_AT_FEATURE_VSA_TDL";
      }
      enum "aaa-at-ip-phone-info" {
        value 725;
        description
          "Details about the IP Phone";
        tailf:code-name "ENUM_aaa_attribute_type_tdl__AAA_AT_IP_PHONE_INFO_TDL";
      }
      enum "aaa-at-ip-pbx-mode" {
        value 726;
        description
          "Mode of the CME";
        tailf:code-name "ENUM_aaa_attribute_type_tdl__AAA_AT_IP_PBX_MODE_TDL";
      }
      enum "aaa-at-peer-sub-address" {
        value 727;
        description
          "The sub number this call was connected to";
        tailf:code-name "ENUM_aaa_attribute_type_tdl__AAA_AT_PEER_SUB_ADDRESS_TDL";
      }
      enum "aaa-at-faxrelay-stop-time" {
        value 728;
        description
          "Fax relay stop time";
        tailf:code-name "ENUM_aaa_attribute_type_tdl__AAA_AT_FAXRELAY_STOP_TIME_TDL";
      }
      enum "aaa-at-internal-error-code" {
        value 729;
        description
          "Internally detected error causing call to be released";
        tailf:code-name "ENUM_aaa_attribute_type_tdl__AAA_AT_INTERNAL_ERROR_CODE_TDL";
      }
      enum "aaa-at-account-code" {
        value 730;
        description
          "Account code input from telephony call leg";
        tailf:code-name "ENUM_aaa_attribute_type_tdl__AAA_AT_ACCOUNT_CODE_TDL";
      }
      enum "aaa-at-vrf-id" {
        value 731;
        description
          "The Virtual Route Forwarder ID";
        tailf:code-name "ENUM_aaa_attribute_type_tdl__AAA_AT_VRF_ID_TDL";
      }
      enum "aaa-at-allow-subvai" {
        value 732;
        description
          "Allow virtual-access sub-interface with interface-config attribute";
        tailf:code-name "ENUM_aaa_attribute_type_tdl__AAA_AT_ALLOW_SUBVAI_TDL";
      }
      enum "aaa-at-idb-description" {
        value 733;
        description
          "Interface description";
        tailf:code-name "ENUM_aaa_attribute_type_tdl__AAA_AT_IDB_DESCRIPTION_TDL";
      }
      enum "aaa-at-sg-service-type" {
        value 734;
        description
          "The type of ISG service";
        tailf:code-name "ENUM_aaa_attribute_type_tdl__AAA_AT_SG_SERVICE_TYPE_TDL";
      }
      enum "aaa-at-subscriber-policy-name" {
        value 735;
        description
          "The name of policy to be provisioned on external device";
        tailf:code-name "ENUM_aaa_attribute_type_tdl__AAA_AT_SUBSCRIBER_POLICY_NAME_TDL";
      }
      enum "aaa-at-service-group" {
        value 736;
        description
          "The SG Service Group Name";
        tailf:code-name "ENUM_aaa_attribute_type_tdl__AAA_AT_SERVICE_GROUP_TDL";
      }
      enum "aaa-at-isakmp-phase1-id" {
        value 737;
        description
          "The Phase 1 Identifier presented by a peer in ISAKMP";
        tailf:code-name "ENUM_aaa_attribute_type_tdl__AAA_AT_ISAKMP_PHASE1_ID_TDL";
      }
      enum "aaa-at-isakmp-initiator-v4-ip" {
        value 738;
        description
          "The IPv4 Address of the ISAKMP Initiator";
        tailf:code-name "ENUM_aaa_attribute_type_tdl__AAA_AT_ISAKMP_INITIATOR_V4_IP_TDL";
      }
      enum "aaa-at-isakmp-initiator-v6-ip" {
        value 739;
        description
          "The IPv6 Address of the ISAKMP Initiator";
        tailf:code-name "ENUM_aaa_attribute_type_tdl__AAA_AT_ISAKMP_INITIATOR_V6_IP_TDL";
      }
      enum "aaa-at-isakmp-group-id" {
        value 740;
        description
          "The group ID of the ISAKMP Initiator";
        tailf:code-name "ENUM_aaa_attribute_type_tdl__AAA_AT_ISAKMP_GROUP_ID_TDL";
      }
      enum "aaa-at-l4-redirect" {
        value 741;
        description
          "Layer 4 redirect details";
        tailf:code-name "ENUM_aaa_attribute_type_tdl__AAA_AT_L4REDIRECT_TDL";
      }
      enum "aaa-at-ip-portbundle" {
        value 742;
        description
          "IP Port-bundle Configuration";
        tailf:code-name "ENUM_aaa_attribute_type_tdl__AAA_AT_IP_PORTBUNDLE_TDL";
      }
      enum "aaa-at-traffic-class" {
        value 743;
        description
          "Traffic Class Configuration";
        tailf:code-name "ENUM_aaa_attribute_type_tdl__AAA_AT_TRAFFIC_CLASS_TDL";
      }
      enum "aaa-at-client-flash" {
        value 744;
        description
          "Total flash space in remote client";
        tailf:code-name "ENUM_aaa_attribute_type_tdl__AAA_AT_CLIENT_FLASH_TDL";
      }
      enum "aaa-at-client-available-flash" {
        value 745;
        description
          "Available flash space in remote client";
        tailf:code-name "ENUM_aaa_attribute_type_tdl__AAA_AT_CLIENT_AVAILABLE_FLASH_TDL";
      }
      enum "aaa-at-client-platform" {
        value 746;
        description
          "Platform of remote client";
        tailf:code-name "ENUM_aaa_attribute_type_tdl__AAA_AT_CLIENT_PLATFORM_TDL";
      }
      enum "aaa-at-client-image" {
        value 747;
        description
          "Image Version of remote client";
        tailf:code-name "ENUM_aaa_attribute_type_tdl__AAA_AT_CLIENT_IMAGE_TDL";
      }
      enum "aaa-at-client-hostname" {
        value 748;
        description
          "Remote client host name";
        tailf:code-name "ENUM_aaa_attribute_type_tdl__AAA_AT_CLIENT_HOSTNAME_TDL";
      }
      enum "aaa-at-client-serial" {
        value 749;
        description
          "Processor board serial number of remote client";
        tailf:code-name "ENUM_aaa_attribute_type_tdl__AAA_AT_CLIENT_SERIAL_TDL";
      }
      enum "aaa-at-client-memory" {
        value 750;
        description
          "Total DRAM in remote client";
        tailf:code-name "ENUM_aaa_attribute_type_tdl__AAA_AT_CLIENT_MEMORY_TDL";
      }
      enum "aaa-at-client-available-memory" {
        value 751;
        description
          "Available DRAM in remote client";
        tailf:code-name "ENUM_aaa_attribute_type_tdl__AAA_AT_CLIENT_AVAILABLE_MEMORY_TDL";
      }
      enum "aaa-at-client-config-version" {
        value 752;
        description
          "Configuration snippet version of remote client";
        tailf:code-name "ENUM_aaa_attribute_type_tdl__AAA_AT_CLIENT_CONFIG_VERSION_TDL";
      }
      enum "aaa-at-wispr-location-id" {
        value 753;
        description
          "WiFi Wireless Internet Service Provider roaming location ID";
        tailf:code-name "ENUM_aaa_attribute_type_tdl__AAA_AT_WISPR_LOCATION_ID_TDL";
      }
      enum "aaa-at-wispr-location-name" {
        value 754;
        description
          "WiFi Wireless Internet Service Provider roaming location name";
        tailf:code-name "ENUM_aaa_attribute_type_tdl__AAA_AT_WISPR_LOCATION_NAME_TDL";
      }
      enum "aaa-at-subscriber-acct-list" {
        value 755;
        description
          "Subscriber accounting method-list";
        tailf:code-name "ENUM_aaa_attribute_type_tdl__AAA_AT_SUBSCRIBER_ACCT_LIST_TDL";
      }
      enum "aaa-at-reauthenticate-type" {
        value 756;
        description
          "Type of re-authenticate command";
        tailf:code-name "ENUM_aaa_attribute_type_tdl__AAA_AT_REAUTHENTICATE_TYPE_TDL";
      }
      enum "aaa-at-method" {
        value 757;
        description
          "Type of authentication method";
        tailf:code-name "ENUM_aaa_attribute_type_tdl__AAA_AT_METHOD_TDL";
      }
      enum "aaa-at-precedence" {
        value 758;
        description
          "Precedence of the profile or template being applied";
        tailf:code-name "ENUM_aaa_attribute_type_tdl__AAA_AT_PRECEDENCE_TDL";
      }
      enum "aaa-at-activation-mode" {
        value 759;
        description
          "Directive to set activation mode of user profile or service template";
        tailf:code-name "ENUM_aaa_attribute_type_tdl__AAA_AT_ACTIVATION_MODE_TDL";
      }
      enum "aaa-at-sg-version" {
        value 760;
        description
          "The version of the SG";
        tailf:code-name "ENUM_aaa_attribute_type_tdl__AAA_AT_SG_VERSION_TDL";
      }
      enum "aaa-at-policy-route" {
        value 761;
        description
          "Peruser policy route";
        tailf:code-name "ENUM_aaa_attribute_type_tdl__AAA_AT_POLICY_ROUTE_TDL";
      }
      enum "aaa-at-default-domain" {
        value 762;
        description
          "Default VPN domain";
        tailf:code-name "ENUM_aaa_attribute_type_tdl__AAA_AT_DEFAULT_DOMAIN_TDL";
      }
      enum "aaa-at-user-realm" {
        value 763;
        description
          "The domain/realm name of the user";
        tailf:code-name "ENUM_aaa_attribute_type_tdl__AAA_AT_USER_REALM_TDL";
      }
      enum "aaa-at-sla-profile-name" {
        value 764;
        description
          "The Service Level Agreement profile name of the user";
        tailf:code-name "ENUM_aaa_attribute_type_tdl__AAA_AT_SLA_PROFILE_NAME_TDL";
      }
      enum "aaa-at-group-lock" {
        value 765;
        description
          "VPN group lock";
        tailf:code-name "ENUM_aaa_attribute_type_tdl__AAA_AT_GROUP_LOCK_TDL";
      }
      enum "aaa-at-configuration-url" {
        value 766;
        description
          "URL to the client configuration file";
        tailf:code-name "ENUM_aaa_attribute_type_tdl__AAA_AT_CONFIGURATION_URL_TDL";
      }
      enum "aaa-at-configuration-version" {
        value 767;
        description
          "version of configuration";
        tailf:code-name "ENUM_aaa_attribute_type_tdl__AAA_AT_CONFIGURATION_VERSION_TDL";
      }
      enum "aaa-at-crypto-pfs" {
        value 768;
        description
          "Propose Crypto PFS";
        tailf:code-name "ENUM_aaa_attribute_type_tdl__AAA_AT_CRYPTO_PFS_TDL";
      }
      enum "aaa-at-crypto-metric" {
        value 769;
        description
          "Virtual Tunnel Interface Route Metric";
        tailf:code-name "ENUM_aaa_attribute_type_tdl__AAA_AT_CRYPTO_METRIC_TDL";
      }
      enum "aaa-at-access-restrict" {
        value 770;
        description
          "VPN group access";
        tailf:code-name "ENUM_aaa_attribute_type_tdl__AAA_AT_ACCESS_RESTRICT_TDL";
      }
      enum "aaa-at-include-local-lan" {
        value 771;
        description
          "Include Local LAN";
        tailf:code-name "ENUM_aaa_attribute_type_tdl__AAA_AT_INCLUDE_LOCAL_LAN_TDL";
      }
      enum "aaa-at-user-include-local-lan" {
        value 772;
        description
          "Include Local LAN per user";
        tailf:code-name "ENUM_aaa_attribute_type_tdl__AAA_AT_USER_INCLUDE_LOCAL_LAN_TDL";
      }
      enum "aaa-at-firewall-are-u-there" {
        value 773;
        description
          "Is Firewall present";
        tailf:code-name "ENUM_aaa_attribute_type_tdl__AAA_AT_FIREWALL_ARE_U_THERE_TDL";
      }
      enum "aaa-at-cpp-policy" {
        value 774;
        description
          "CPP policy name";
        tailf:code-name "ENUM_aaa_attribute_type_tdl__AAA_AT_CPP_POLICY_TDL";
      }
      enum "aaa-at-browser-proxy" {
        value 775;
        description
          "Browser-proxy settings";
        tailf:code-name "ENUM_aaa_attribute_type_tdl__AAA_AT_BROWSER_PROXY_TDL";
      }
      enum "aaa-at-cfg-banner" {
        value 776;
        description
          "Xauth banner";
        tailf:code-name "ENUM_aaa_attribute_type_tdl__AAA_AT_CFG_BANNER_TDL";
      }
      enum "aaa-at-save-password" {
        value 777;
        description
          "Save Password";
        tailf:code-name "ENUM_aaa_attribute_type_tdl__AAA_AT_SAVE_PASSWORD_TDL";
      }
      enum "aaa-at-user-save-password" {
        value 778;
        description
          "Save Password per user";
        tailf:code-name "ENUM_aaa_attribute_type_tdl__AAA_AT_USER_SAVE_PASSWORD_TDL";
      }
      enum "aaa-at-route-set-interface" {
        value 779;
        description
          "Route set interface";
        tailf:code-name "ENUM_aaa_attribute_type_tdl__AAA_AT_ROUTE_SET_INTERFACE_TDL";
      }
      enum "aaa-at-route-accept" {
        value 780;
        description
          "Route accept with tag and distance";
        tailf:code-name "ENUM_aaa_attribute_type_tdl__AAA_AT_ROUTE_ACCEPT_TDL";
      }
      enum "aaa-at-smartcard-removal-disconnect" {
        value 781;
        description
          "Smartcard removal disconnect";
        tailf:code-name "ENUM_aaa_attribute_type_tdl__AAA_AT_SMARTCARD_REMOVAL_DISCONNECT_TDL";
      }
      enum "aaa-at-user-smartcard-removal-disconnect" {
        value 782;
        description
          "Smartcard removal disconnect per user";
        tailf:code-name "ENUM_aaa_attribute_type_tdl__AAA_AT_USER_SMARTCARD_REMOVAL_DISCONNECT_TDL";
      }
      enum "aaa-at-group-dhcp-server" {
        value 783;
        description
          "VPN DHCP Server";
        tailf:code-name "ENUM_aaa_attribute_type_tdl__AAA_AT_GROUP_DHCP_SERVER_TDL";
      }
      enum "aaa-at-dhcp-timeout" {
        value 784;
        description
          "VPN DHCP Timeout";
        tailf:code-name "ENUM_aaa_attribute_type_tdl__AAA_AT_DHCP_TIMEOUT_TDL";
      }
      enum "aaa-at-dhcp-giaddr" {
        value 785;
        description
          "VPN DHCP GI address";
        tailf:code-name "ENUM_aaa_attribute_type_tdl__AAA_AT_DHCP_GIADDR_TDL";
      }
      enum "aaa-at-split-dns" {
        value 786;
        description
          "VPN Split DNS";
        tailf:code-name "ENUM_aaa_attribute_type_tdl__AAA_AT_SPLIT_DNS_TDL";
      }
      enum "aaa-at-ipv4-group-netmask" {
        value 787;
        description
          "IPv4 netmask";
        tailf:code-name "ENUM_aaa_attribute_type_tdl__AAA_AT_IPV4_GROUP_NETMASK_TDL";
      }
      enum "aaa-at-user-vpn-group" {
        value 788;
        description
          "VPN Group for User";
        tailf:code-name "ENUM_aaa_attribute_type_tdl__AAA_AT_USER_VPN_GROUP_TDL";
      }
      enum "aaa-at-backup-gateway" {
        value 789;
        description
          "IPSec backup gateway";
        tailf:code-name "ENUM_aaa_attribute_type_tdl__AAA_AT_BACKUP_GATEWAY_TDL";
      }
      enum "aaa-at-max-users" {
        value 790;
        description
          "Maximum users";
        tailf:code-name "ENUM_aaa_attribute_type_tdl__AAA_AT_MAX_USERS_TDL";
      }
      enum "aaa-at-max-logins" {
        value 791;
        description
          "Maximum logins per user";
        tailf:code-name "ENUM_aaa_attribute_type_tdl__AAA_AT_MAX_LOGINS_TDL";
      }
      enum "aaa-at-ipv6-subnet-acl" {
        value 792;
        description
          "IPv6 Subnet ACL";
        tailf:code-name "ENUM_aaa_attribute_type_tdl__AAA_AT_IPV6_SUBNET_ACL_TDL";
      }
      enum "aaa-at-ipv6-address-pool" {
        value 793;
        description
          "The local IPv6 address pool name";
        tailf:code-name "ENUM_aaa_attribute_type_tdl__AAA_AT_IPV6_ADDRESS_POOL_TDL";
      }
      enum "aaa-at-ipsec-flow-limit" {
        value 794;
        description
          "IPSec flow limit per multi-SA dynamic virtual tunnel interfaces session";
        tailf:code-name "ENUM_aaa_attribute_type_tdl__AAA_AT_IPSEC_FLOW_LIMIT_TDL";
      }
      enum "aaa-at-max-bit-rate" {
        value 795;
        description
          "Max bit rate used in a call";
        tailf:code-name "ENUM_aaa_attribute_type_tdl__AAA_AT_MAX_BIT_RATE_TDL";
      }
      enum "aaa-at-qos-class-name" {
        value 796;
        description
          "Name for the session QoS classmap";
        tailf:code-name "ENUM_aaa_attribute_type_tdl__AAA_AT_QOS_CLASS_NAME_TDL";
      }
      enum "aaa-at-qos-policy-name" {
        value 797;
        description
          "Name for the session QoS policy-map";
        tailf:code-name "ENUM_aaa_attribute_type_tdl__AAA_AT_QOS_POLICY_NAME_TDL";
      }
      enum "aaa-at-time-quota" {
        value 798;
        description
          "Time quota in seconds";
        tailf:code-name "ENUM_aaa_attribute_type_tdl__AAA_AT_TIME_QUOTA_TDL";
      }
      enum "aaa-at-volume-quota" {
        value 799;
        description
          "Volume quota in bytes";
        tailf:code-name "ENUM_aaa_attribute_type_tdl__AAA_AT_VOLUME_QUOTA_TDL";
      }
      enum "aaa-at-giga-words-volume-quota" {
        value 800;
        description
          "Number of times that volume-quota has wrapped";
        tailf:code-name "ENUM_aaa_attribute_type_tdl__AAA_AT_GIGA_WORDS_VOLUME_QUOTA_TDL";
      }
      enum "aaa-at-tariff-time" {
        value 801;
        description
          "Time for tariff switch in seconds";
        tailf:code-name "ENUM_aaa_attribute_type_tdl__AAA_AT_TARIFF_TIME_TDL";
      }
      enum "aaa-at-post-tariff-volume-quota" {
        value 802;
        description
          "Volume quota after tariff switch in bytes";
        tailf:code-name "ENUM_aaa_attribute_type_tdl__AAA_AT_POST_TARIFF_VOLUME_QUOTA_TDL";
      }
      enum "aaa-at-giga-words-post-tariff-volume-quota" {
        value 803;
        description
          "Number of times that post-tariff-volume-quota has wrapped";
        tailf:code-name "ENUM_aaa_attribute_type_tdl__AAA_AT_GIGA_WORDS_POST_TARIFF_VOLUME_QUOTA_TDL";
      }
      enum "aaa-at-idle" {
        value 804;
        description
          "If the session is idle";
        tailf:code-name "ENUM_aaa_attribute_type_tdl__AAA_AT_IDLE_TDL";
      }
      enum "aaa-at-volume-threshold" {
        value 805;
        description
          "Volume threshold before which re-authorization will be issued";
        tailf:code-name "ENUM_aaa_attribute_type_tdl__AAA_AT_VOLUME_THRESHOLD_TDL";
      }
      enum "aaa-at-time-threshold" {
        value 806;
        description
          "Time threshold before which re-authorization will be issued";
        tailf:code-name "ENUM_aaa_attribute_type_tdl__AAA_AT_TIME_THRESHOLD_TDL";
      }
      enum "aaa-at-prepaid-config" {
        value 807;
        description
          "Name of the prepaid config that is referred for this session";
        tailf:code-name "ENUM_aaa_attribute_type_tdl__AAA_AT_PREPAID_CONFIG_TDL";
      }
      enum "aaa-at-prepaid-idle-timeout" {
        value 808;
        description
          "Prepaid idle timeout";
        tailf:code-name "ENUM_aaa_attribute_type_tdl__AAA_AT_PREPAID_IDLE_TIMEOUT_TDL";
      }
      enum "aaa-at-prepaid-absolute-timeout" {
        value 809;
        description
          "Prepaid absolute timeout";
        tailf:code-name "ENUM_aaa_attribute_type_tdl__AAA_AT_PREPAID_ABSOLUTE_TIMEOUT_TDL";
      }
      enum "aaa-at-drop-at-quota-reached" {
        value 810;
        description
          "Drop prepaid traffic when volume quota is reached";
        tailf:code-name "ENUM_aaa_attribute_type_tdl__AAA_AT_DROP_AT_QUOTA_REACHED_TDL";
      }
      enum "aaa-at-volume-monitor-dropping" {
        value 811;
        description
          "Drop all prepaid traffic";
        tailf:code-name "ENUM_aaa_attribute_type_tdl__AAA_AT_VOLUME_MONITOR_DROPPING_TDL";
      }
      enum "aaa-at-dhcp-vendor-class" {
        value 812;
        description
          "Hex-encoded version of the DHCP vendor class option no 60";
        tailf:code-name "ENUM_aaa_attribute_type_tdl__AAA_AT_DHCP_VENDOR_CLASS_TDL";
      }
      enum "aaa-at-dhcp-client-id" {
        value 813;
        description
          "Hex-encoded version of the DHCP client-id option no 61";
        tailf:code-name "ENUM_aaa_attribute_type_tdl__AAA_AT_DHCP_CLIENT_ID_TDL";
      }
      enum "aaa-at-dhcp-relay-info" {
        value 814;
        description
          "Hex-encoded version of the DHCP relay info option no 80";
        tailf:code-name "ENUM_aaa_attribute_type_tdl__AAA_AT_DHCP_RELAY_INFO_TDL";
      }
      enum "aaa-at-session-duration" {
        value 815;
        description
          "Maximum duration of session in seconds";
        tailf:code-name "ENUM_aaa_attribute_type_tdl__AAA_AT_SESSION_DURATION_TDL";
      }
      enum "aaa-at-epd-session-notify-changes" {
        value 816;
        description
          "Inform external policy device of changes in session";
        tailf:code-name "ENUM_aaa_attribute_type_tdl__AAA_AT_EPD_SESSION_NOTIFY_CHANGES_TDL";
      }
      enum "aaa-at-subscriber-service-monitor" {
        value 817;
        description
          "Turn on service monitoring on external policy device";
        tailf:code-name "ENUM_aaa_attribute_type_tdl__AAA_AT_SUBSCRIBER_SERVICE_MONITOR_TDL";
      }
      enum "aaa-at-subscriber-command" {
        value 818;
        description
          "ISG command code type";
        tailf:code-name "ENUM_aaa_attribute_type_tdl__AAA_AT_SUBSCRIBER_COMMAND_TDL";
      }
      enum "aaa-at-audit-session-id" {
        value 819;
        description
          "Session ID used for Audit scenarios";
        tailf:code-name "ENUM_aaa_attribute_type_tdl__AAA_AT_AUDIT_SESSION_ID_TDL";
      }
      enum "aaa-at-status-query-timeout" {
        value 820;
        description
          "Status Query Timeout Period";
        tailf:code-name "ENUM_aaa_attribute_type_tdl__AAA_AT_STATUS_QUERY_TIMEOUT_TDL";
      }
      enum "aaa-at-url-redirect" {
        value 821;
        description
          "URL Redirect User Sessions";
        tailf:code-name "ENUM_aaa_attribute_type_tdl__AAA_AT_URL_REDIRECT_TDL";
      }
      enum "aaa-at-url-redirect-acl" {
        value 822;
        description
          "URL Redirect ACL";
        tailf:code-name "ENUM_aaa_attribute_type_tdl__AAA_AT_URL_REDIRECT_ACL_TDL";
      }
      enum "aaa-at-url-redirect-acl-no-match" {
        value 823;
        description
          "URL Redirect ACL No Match";
        tailf:code-name "ENUM_aaa_attribute_type_tdl__AAA_AT_URL_REDIRECT_ACL_NO_MATCH_TDL";
      }
      enum "aaa-at-url-redirect-acl-one-time" {
        value 824;
        description
          "URL Redirect ACL One Time";
        tailf:code-name "ENUM_aaa_attribute_type_tdl__AAA_AT_URL_REDIRECT_ACL_ONE_TIME_TDL";
      }
      enum "aaa-at-posture-token" {
        value 825;
        description
          "Posture Token for the user Device";
        tailf:code-name "ENUM_aaa_attribute_type_tdl__AAA_AT_POSTURE_TOKEN_TDL";
      }
      enum "aaa-at-ciscosecure-defined-acl" {
        value 826;
        description
          "Specifies the ACL name for the Downloadable ACL";
        tailf:code-name "ENUM_aaa_attribute_type_tdl__AAA_AT_CISCOSECURE_DEFINED_ACL_TDL";
      }
      enum "aaa-at-banner" {
        value 827;
        description
          "Browser banner for the group";
        tailf:code-name "ENUM_aaa_attribute_type_tdl__AAA_AT_BANNER_TDL";
      }
      enum "aaa-at-home-page" {
        value 828;
        description
          "Default home page";
        tailf:code-name "ENUM_aaa_attribute_type_tdl__AAA_AT_HOME_PAGE_TDL";
      }
      enum "aaa-at-urllist-name" {
        value 829;
        description
          "URL list name";
        tailf:code-name "ENUM_aaa_attribute_type_tdl__AAA_AT_URLLIST_NAME_TDL";
      }
      enum "aaa-at-sslvpn-acl-name" {
        value 830;
        description
          "SSLVPN ACL name";
        tailf:code-name "ENUM_aaa_attribute_type_tdl__AAA_AT_SSLVPN_ACL_NAME_TDL";
      }
      enum "aaa-at-nbnslist-name" {
        value 831;
        description
          "NetBIOS Name Service list name";
        tailf:code-name "ENUM_aaa_attribute_type_tdl__AAA_AT_NBNSLIST_NAME_TDL";
      }
      enum "aaa-at-file-browse" {
        value 832;
        description
          "Enable / Disable Common Internet File System Network browsing";
        tailf:code-name "ENUM_aaa_attribute_type_tdl__AAA_AT_FILE_BROWSE_TDL";
      }
      enum "aaa-at-file-entry" {
        value 833;
        description
          "Enable / Disable Common Internet File System file entry";
        tailf:code-name "ENUM_aaa_attribute_type_tdl__AAA_AT_FILE_ENTRY_TDL";
      }
      enum "aaa-at-file-access" {
        value 834;
        description
          "Enable / Disable Common Internet File System file access";
        tailf:code-name "ENUM_aaa_attribute_type_tdl__AAA_AT_FILE_ACCESS_TDL";
      }
      enum "aaa-at-port-forward-name" {
        value 835;
        description
          "Port forwarding instance name";
        tailf:code-name "ENUM_aaa_attribute_type_tdl__AAA_AT_PORT_FORWARD_NAME_TDL";
      }
      enum "aaa-at-port-forward-auto" {
        value 836;
        description
          "Port forwarding auto applet download";
        tailf:code-name "ENUM_aaa_attribute_type_tdl__AAA_AT_PORT_FORWARD_AUTO_TDL";
      }
      enum "aaa-at-port-forward-http-proxy" {
        value 837;
        description
          "Port forwarding http proxy";
        tailf:code-name "ENUM_aaa_attribute_type_tdl__AAA_AT_PORT_FORWARD_HTTP_PROXY_TDL";
      }
      enum "aaa-at-port-forward-http-proxy-url" {
        value 838;
        description
          "Port forwarding http proxy URL";
        tailf:code-name "ENUM_aaa_attribute_type_tdl__AAA_AT_PORT_FORWARD_HTTP_PROXY_URL_TDL";
      }
      enum "aaa-at-svc-enabled" {
        value 839;
        description
          "Enable / Disable SSLVPN client";
        tailf:code-name "ENUM_aaa_attribute_type_tdl__AAA_AT_SVC_ENABLED_TDL";
      }
      enum "aaa-at-svc-required" {
        value 840;
        description
          "Enable / Disable SSLVPN client required option";
        tailf:code-name "ENUM_aaa_attribute_type_tdl__AAA_AT_SVC_REQUIRED_TDL";
      }
      enum "aaa-at-hide-urlbar" {
        value 841;
        description
          "Enable / Disable hide-url-bar option";
        tailf:code-name "ENUM_aaa_attribute_type_tdl__AAA_AT_HIDE_URLBAR_TDL";
      }
      enum "aaa-at-maskurls" {
        value 842;
        description
          "Mask host/port portion of mangled URLs";
        tailf:code-name "ENUM_aaa_attribute_type_tdl__AAA_AT_MASKURLS_TDL";
      }
      enum "aaa-at-dpd-client-timeout" {
        value 843;
        description
          "Dead Peer Detection client-side timeout";
        tailf:code-name "ENUM_aaa_attribute_type_tdl__AAA_AT_DPD_CLIENT_TIMEOUT_TDL";
      }
      enum "aaa-at-dpd-gateway-timeout" {
        value 844;
        description
          "Dead Peer Detection gateway-side timeout";
        tailf:code-name "ENUM_aaa_attribute_type_tdl__AAA_AT_DPD_GATEWAY_TIMEOUT_TDL";
      }
      enum "aaa-at-keep-svc-installed" {
        value 845;
        description
          "Keep SVC installed option";
        tailf:code-name "ENUM_aaa_attribute_type_tdl__AAA_AT_KEEP_SVC_INSTALLED_TDL";
      }
      enum "aaa-at-rekey-interval" {
        value 846;
        description
          "Re-key interval";
        tailf:code-name "ENUM_aaa_attribute_type_tdl__AAA_AT_REKEY_INTERVAL_TDL";
      }
      enum "aaa-at-lease-duration" {
        value 847;
        description
          "IP address lease duration";
        tailf:code-name "ENUM_aaa_attribute_type_tdl__AAA_AT_LEASE_DURATION_TDL";
      }
      enum "aaa-at-svc-ie-proxy-policy" {
        value 848;
        description
          "Microsoft Internet Explorer proxy server policy";
        tailf:code-name "ENUM_aaa_attribute_type_tdl__AAA_AT_SVC_IE_PROXY_POLICY_TDL";
      }
      enum "aaa-at-ie-proxy-server" {
        value 849;
        description
          "Microsoft Internet Explorer proxy server";
        tailf:code-name "ENUM_aaa_attribute_type_tdl__AAA_AT_IE_PROXY_SERVER_TDL";
      }
      enum "aaa-at-ie-proxy-exception" {
        value 850;
        description
          "Microsoft Internet Explorer proxy server exception list";
        tailf:code-name "ENUM_aaa_attribute_type_tdl__AAA_AT_IE_PROXY_EXCEPTION_TDL";
      }
      enum "aaa-at-split-include" {
        value 851;
        description
          "Include networks in tunnel";
        tailf:code-name "ENUM_aaa_attribute_type_tdl__AAA_AT_SPLIT_INCLUDE_TDL";
      }
      enum "aaa-at-split-exclude" {
        value 852;
        description
          "Exclude networks from tunnel";
        tailf:code-name "ENUM_aaa_attribute_type_tdl__AAA_AT_SPLIT_EXCLUDE_TDL";
      }
      enum "aaa-at-cifsurllist-name" {
        value 853;
        description
          "Common Internet File System URL list name";
        tailf:code-name "ENUM_aaa_attribute_type_tdl__AAA_AT_CIFSURLLIST_NAME_TDL";
      }
      enum "aaa-at-sso-server-name" {
        value 854;
        description
          "SSO Server Name";
        tailf:code-name "ENUM_aaa_attribute_type_tdl__AAA_AT_SSO_SERVER_NAME_TDL";
      }
      enum "aaa-at-webvpn-context" {
        value 855;
        description
          "Webvpn virtual context";
        tailf:code-name "ENUM_aaa_attribute_type_tdl__AAA_AT_WEBVPN_CONTEXT_TDL";
      }
      enum "aaa-at-webvpn-client-ip" {
        value 856;
        description
          "WEBVPN Client IP address";
        tailf:code-name "ENUM_aaa_attribute_type_tdl__AAA_AT_WEBVPN_CLIENT_IP_TDL";
      }
      enum "aaa-at-anyconnect-profile" {
        value 857;
        description
          "Anyconnect profile name";
        tailf:code-name "ENUM_aaa_attribute_type_tdl__AAA_AT_ANYCONNECT_PROFILE_TDL";
      }
      enum "aaa-at-dsp-id" {
        value 858;
        description
          "DSP used for the leg";
        tailf:code-name "ENUM_aaa_attribute_type_tdl__AAA_AT_DSP_ID_TDL";
      }
      enum "aaa-at-mcast-source-v4" {
        value 859;
        description
          "IPv4 multicast group source address";
        tailf:code-name "ENUM_aaa_attribute_type_tdl__AAA_AT_MCAST_SOURCE_V4_TDL";
      }
      enum "aaa-at-mcast-source-v6" {
        value 860;
        description
          "IPv6 multicast group source address";
        tailf:code-name "ENUM_aaa_attribute_type_tdl__AAA_AT_MCAST_SOURCE_V6_TDL";
      }
      enum "aaa-at-mcast-group-v4" {
        value 861;
        description
          "IPv4 multicast group identifier address";
        tailf:code-name "ENUM_aaa_attribute_type_tdl__AAA_AT_MCAST_GROUP_V4_TDL";
      }
      enum "aaa-at-mcast-group-v6" {
        value 862;
        description
          "IPv6 multicast group identifier address";
        tailf:code-name "ENUM_aaa_attribute_type_tdl__AAA_AT_MCAST_GROUP_V6_TDL";
      }
      enum "aaa-at-local-hostname" {
        value 863;
        description
          "Local Hostname in Multi-Homed Environment";
        tailf:code-name "ENUM_aaa_attribute_type_tdl__AAA_AT_LOCAL_HOSTNAME_TDL";
      }
      enum "aaa-at-authz-directive" {
        value 864;
        description
          "Specifies the directive as open or default";
        tailf:code-name "ENUM_aaa_attribute_type_tdl__AAA_AT_AUTHZ_DIRECTIVE_TDL";
      }
      enum "aaa-at-method-list" {
        value 865;
        description
          "AAA Method list";
        tailf:code-name "ENUM_aaa_attribute_type_tdl__AAA_AT_METHOD_LIST_TDL";
      }
      enum "aaa-at-template-name" {
        value 866;
        description
          "Template name";
        tailf:code-name "ENUM_aaa_attribute_type_tdl__AAA_AT_TEMPLATE_NAME_TDL";
      }
      enum "aaa-at-timer-name" {
        value 867;
        description
          "Timer name";
        tailf:code-name "ENUM_aaa_attribute_type_tdl__AAA_AT_TIMER_NAME_TDL";
      }
      enum "aaa-at-timer-value" {
        value 868;
        description
          "Timer value";
        tailf:code-name "ENUM_aaa_attribute_type_tdl__AAA_AT_TIMER_VALUE_TDL";
      }
      enum "aaa-at-nas-port-sub-id-type" {
        value 869;
        description
          "NAS Port Sub Id Type";
        tailf:code-name "ENUM_aaa_attribute_type_tdl__AAA_AT_NAS_PORT_SUB_ID_TYPE_TDL";
      }
      enum "aaa-at-identity-policy-name" {
        value 870;
        description
          "Specifies the identity policy name for local policy application";
        tailf:code-name "ENUM_aaa_attribute_type_tdl__AAA_AT_IDENTITY_POLICY_NAME_TDL";
      }
      enum "aaa-at-media-type" {
        value 871;
        description
          "Media type";
        tailf:code-name "ENUM_aaa_attribute_type_tdl__AAA_AT_MEDIA_TYPE_TDL";
      }
      enum "aaa-at-protocol-type" {
        value 872;
        description
          "Protocol type";
        tailf:code-name "ENUM_aaa_attribute_type_tdl__AAA_AT_PROTOCOL_TYPE_TDL";
      }
      enum "aaa-at-domain" {
        value 873;
        description
          "Session Domain";
        tailf:code-name "ENUM_aaa_attribute_type_tdl__AAA_AT_DOMAIN_TDL";
      }
      enum "aaa-at-unauthen-domain" {
        value 874;
        description
          "Un-authenticate Domain";
        tailf:code-name "ENUM_aaa_attribute_type_tdl__AAA_AT_UNAUTHEN_DOMAIN_TDL";
      }
      enum "aaa-at-unauthen-username" {
        value 875;
        description
          "Un-authenticate Username";
        tailf:code-name "ENUM_aaa_attribute_type_tdl__AAA_AT_UNAUTHEN_USERNAME_TDL";
      }
      enum "aaa-at-nas-port" {
        value 876;
        description
          "NAS Port";
        tailf:code-name "ENUM_aaa_attribute_type_tdl__AAA_AT_NAS_PORT_TDL";
      }
      enum "aaa-at-tunnel-name" {
        value 877;
        description
          "Tunnel Name";
        tailf:code-name "ENUM_aaa_attribute_type_tdl__AAA_AT_TUNNEL_NAME_TDL";
      }
      enum "aaa-at-if-handle" {
        value 878;
        description
          "Interface Handle";
        tailf:code-name "ENUM_aaa_attribute_type_tdl__AAA_AT_IF_HANDLE_TDL";
      }
      enum "aaa-at-parent-if-handle" {
        value 879;
        description
          "Parent interface handle";
        tailf:code-name "ENUM_aaa_attribute_type_tdl__AAA_AT_PARENT_IF_HANDLE_TDL";
      }
      enum "aaa-at-tag-name" {
        value 880;
        description
          "Tag attribute received from ACS";
        tailf:code-name "ENUM_aaa_attribute_type_tdl__AAA_AT_TAG_NAME_TDL";
      }
      enum "aaa-at-supplicant-group" {
        value 881;
        description
          "Supplicant-Group attribute received from ACS";
        tailf:code-name "ENUM_aaa_attribute_type_tdl__AAA_AT_SUPPLICANT_GROUP_TDL";
      }
      enum "aaa-at-vpdn-dsl-line-info-forwarding" {
        value 882;
        description
          "VPDN DSL Line Info Forwarding";
        tailf:code-name "ENUM_aaa_attribute_type_tdl__AAA_AT_VPDN_DSL_LINE_INFO_FORWARDING_TDL";
      }
      enum "aaa-at-gk-operation" {
        value 883;
        description
          "Gatekeeper RAS operation";
        tailf:code-name "ENUM_aaa_attribute_type_tdl__AAA_AT_GK_OPERATION_TDL";
      }
      enum "aaa-at-supplicant-name" {
        value 884;
        description
          "Supplicant-Name attribute received from ACS";
        tailf:code-name "ENUM_aaa_attribute_type_tdl__AAA_AT_SUPPLICANT_NAME_TDL";
      }
      enum "aaa-at-device-traffic-class" {
        value 885;
        description
          "The type of client device that is being authenticated";
        tailf:code-name "ENUM_aaa_attribute_type_tdl__AAA_AT_DEVICE_TRAFFIC_CLASS_TDL";
      }
      enum "aaa-at-identity-request" {
        value 886;
        description
          "Request for additional keys";
        tailf:code-name "ENUM_aaa_attribute_type_tdl__AAA_AT_IDENTITY_REQUEST_TDL";
      }
      enum "aaa-at-termination-action-modifier" {
        value 887;
        description
          "Extensions to IETF defined Termination Actions";
        tailf:code-name "ENUM_aaa_attribute_type_tdl__AAA_AT_TERMINATION_ACTION_MODIFIER_TDL";
      }
      enum "aaa-at-ntlm-client-cred" {
        value 888;
        description
          "NT LAN Manager credentials like NT LAN Manager type 1 and 3 messages";
        tailf:code-name "ENUM_aaa_attribute_type_tdl__AAA_AT_NTLM_CLIENT_CRED_TDL";
      }
      enum "aaa-at-ntlm-server-cred" {
        value 889;
        description
          "NT LAN Manager credentials like NT LAN Manager type 2 messages";
        tailf:code-name "ENUM_aaa_attribute_type_tdl__AAA_AT_NTLM_SERVER_CRED_TDL";
      }
      enum "aaa-at-cts-pac-opaque" {
        value 890;
        description
          "Include CTS PAC Opaque";
        tailf:code-name "ENUM_aaa_attribute_type_tdl__AAA_AT_CTS_PAC_OPAQUE_TDL";
      }
      enum "aaa-at-cts-capabilities" {
        value 891;
        description
          "Advertise authenticator's CTS capabilities";
        tailf:code-name "ENUM_aaa_attribute_type_tdl__AAA_AT_CTS_CAPABILITIES_TDL";
      }
      enum "aaa-at-cts-supp-caps" {
        value 892;
        description
          "Supplicant's CTS capabilities";
        tailf:code-name "ENUM_aaa_attribute_type_tdl__AAA_AT_CTS_SUPP_CAPS_TDL";
      }
      enum "aaa-at-security-group-tag" {
        value 893;
        description
          "Security group tag to apply to local device or peer";
        tailf:code-name "ENUM_aaa_attribute_type_tdl__AAA_AT_SECURITY_GROUP_TAG_TDL";
      }
      enum "aaa-at-trusted-device" {
        value 894;
        description
          "Trust SGT's from the peer";
        tailf:code-name "ENUM_aaa_attribute_type_tdl__AAA_AT_TRUSTED_DEVICE_TDL";
      }
      enum "aaa-at-rbacl-source-list-outbound" {
        value 895;
        description
          "Role-Based ACL source list name";
        tailf:code-name "ENUM_aaa_attribute_type_tdl__AAA_AT_RBACL_SOURCE_LIST_OUTBOUND_TDL";
      }
      enum "aaa-at-rbacl-destination-list-outbound" {
        value 896;
        description
          "Role-Based ACL destination list name";
        tailf:code-name "ENUM_aaa_attribute_type_tdl__AAA_AT_RBACL_DESTINATION_LIST_OUTBOUND_TDL";
      }
      enum "aaa-at-rbacl-any-any-outbound" {
        value 897;
        description
          "Role-Based ACL any source and any destination list name";
        tailf:code-name "ENUM_aaa_attribute_type_tdl__AAA_AT_RBACL_ANY_ANY_OUTBOUND_TDL";
      }
      enum "aaa-at-rbacl-src-dst-list-inbound" {
        value 898;
        description
          "Role-Based ACL source or destination list name";
        tailf:code-name "ENUM_aaa_attribute_type_tdl__AAA_AT_RBACL_SRC_DST_LIST_INBOUND_TDL";
      }
      enum "aaa-at-rbacl-list-name-outbound" {
        value 899;
        description
          "Role-Based ACL list name to request for ACEs";
        tailf:code-name "ENUM_aaa_attribute_type_tdl__AAA_AT_RBACL_LIST_NAME_OUTBOUND_TDL";
      }
      enum "aaa-at-rbacl-list-name-inbound" {
        value 900;
        description
          "Role-Based ACL name and gen ID being requested";
        tailf:code-name "ENUM_aaa_attribute_type_tdl__AAA_AT_RBACL_LIST_NAME_INBOUND_TDL";
      }
      enum "aaa-at-rbacl-ace-inbound" {
        value 901;
        description
          "Role-Based ACL ACEs being requested";
        tailf:code-name "ENUM_aaa_attribute_type_tdl__AAA_AT_RBACL_ACE_INBOUND_TDL";
      }
      enum "aaa-at-server-list-inbound" {
        value 902;
        description
          "Server list name and generation number";
        tailf:code-name "ENUM_aaa_attribute_type_tdl__AAA_AT_SERVER_LIST_INBOUND_TDL";
      }
      enum "aaa-at-server-list-outbound" {
        value 903;
        description
          "Server list name";
        tailf:code-name "ENUM_aaa_attribute_type_tdl__AAA_AT_SERVER_LIST_OUTBOUND_TDL";
      }
      enum "aaa-at-server" {
        value 904;
        description
          "Server in a server list, format <AID>:<IP addr>:<port>";
        tailf:code-name "ENUM_aaa_attribute_type_tdl__AAA_AT_SERVER_TDL";
      }
      enum "aaa-at-authorization-expiry" {
        value 905;
        description
          "Number of seconds before policy expires";
        tailf:code-name "ENUM_aaa_attribute_type_tdl__AAA_AT_AUTHORIZATION_EXPIRY_TDL";
      }
      enum "aaa-at-environment-data-outbound" {
        value 906;
        description
          "Environment Data";
        tailf:code-name "ENUM_aaa_attribute_type_tdl__AAA_AT_ENVIRONMENT_DATA_OUTBOUND_TDL";
      }
      enum "aaa-at-imt-traffic-policy-get" {
        value 907;
        description
          "CTS tunnel traffic policy download";
        tailf:code-name "ENUM_aaa_attribute_type_tdl__AAA_AT_IMT_TRAFFIC_POLICY_GET_TDL";
      }
      enum "aaa-at-imt-traffic-policy-inbound" {
        value 908;
        description
          "CTS tunnel traffic policy name and generation number";
        tailf:code-name "ENUM_aaa_attribute_type_tdl__AAA_AT_IMT_TRAFFIC_POLICY_INBOUND_TDL";
      }
      enum "aaa-at-imt-traffic-policy-outbound" {
        value 909;
        description
          "CTS tunnel traffic policy send";
        tailf:code-name "ENUM_aaa_attribute_type_tdl__AAA_AT_IMT_TRAFFIC_POLICY_OUTBOUND_TDL";
      }
      enum "aaa-at-imt-tunnel-default-sgt" {
        value 910;
        description
          "Implicit Tunnel default SGT";
        tailf:code-name "ENUM_aaa_attribute_type_tdl__AAA_AT_IMT_TUNNEL_DEFAULT_SGT_TDL";
      }
      enum "aaa-at-imt-reverse-check-fail-drop" {
        value 911;
        description
          "Implicit Tunnel reverse check fail drop flag";
        tailf:code-name "ENUM_aaa_attribute_type_tdl__AAA_AT_IMT_REVERSE_CHECK_FAIL_DROP_TDL";
      }
      enum "aaa-at-imt-tunnel-gateway" {
        value 912;
        description
          "CTS Tunnel Gateway, format <IP addr>";
        tailf:code-name "ENUM_aaa_attribute_type_tdl__AAA_AT_IMT_TUNNEL_GATEWAY_TDL";
      }
      enum "aaa-at-imt-tunnel-unicast-address" {
        value 913;
        description
          "CTS Tunnel unicast address, format <IP addr>:<mask>";
        tailf:code-name "ENUM_aaa_attribute_type_tdl__AAA_AT_IMT_TUNNEL_UNICAST_ADDRESS_TDL";
      }
      enum "aaa-at-imt-tunnel-multicast-group-address" {
        value 914;
        description
          "CTS Tunnel multicast group address, format <src IP addr>:<dst group address>";
        tailf:code-name "ENUM_aaa_attribute_type_tdl__AAA_AT_IMT_TUNNEL_MULTICAST_GROUP_ADDRESS_TDL";
      }
      enum "aaa-at-mcast-group-sgt-table-inbound" {
        value 915;
        description
          "Multicast group SGT table name and generation number";
        tailf:code-name "ENUM_aaa_attribute_type_tdl__AAA_AT_MCAST_GROUP_SGT_TABLE_INBOUND_TDL";
      }
      enum "aaa-at-mcast-group-sgt-table-outbound" {
        value 916;
        description
          "Multicast group SGT table name";
        tailf:code-name "ENUM_aaa_attribute_type_tdl__AAA_AT_MCAST_GROUP_SGT_TABLE_OUTBOUND_TDL";
      }
      enum "aaa-at-mcast-sgt" {
        value 917;
        description
          "SGT for the multicast address, format <multicast IP>-<sgt>";
        tailf:code-name "ENUM_aaa_attribute_type_tdl__AAA_AT_MCAST_SGT_TDL";
      }
      enum "aaa-at-imt-current-group-key-outbound" {
        value 918;
        description
          "Implicit Tunnel current group key";
        tailf:code-name "ENUM_aaa_attribute_type_tdl__AAA_AT_IMT_CURRENT_GROUP_KEY_OUTBOUND_TDL";
      }
      enum "aaa-at-imt-next-group-key-outbound" {
        value 919;
        description
          "Implicit Tunnel next group key";
        tailf:code-name "ENUM_aaa_attribute_type_tdl__AAA_AT_IMT_NEXT_GROUP_KEY_OUTBOUND_TDL";
      }
      enum "aaa-at-imt-group-spi" {
        value 920;
        description
          "Implicit Tunnel Group SPI value";
        tailf:code-name "ENUM_aaa_attribute_type_tdl__AAA_AT_IMT_GROUP_SPI_TDL";
      }
      enum "aaa-at-imt-group-algorithm" {
        value 921;
        description
          "Implicit Tunnel Group Algorithm";
        tailf:code-name "ENUM_aaa_attribute_type_tdl__AAA_AT_IMT_GROUP_ALGORITHM_TDL";
      }
      enum "aaa-at-imt-gcm-sequence-range" {
        value 922;
        description
          "GCM cipher sequence number range";
        tailf:code-name "ENUM_aaa_attribute_type_tdl__AAA_AT_IMT_GCM_SEQUENCE_RANGE_TDL";
      }
      enum "aaa-at-imt-encapsulation-protocol-number" {
        value 923;
        description
          "Protocol number for C-ESP encapsulated packets, value = 50 or 99";
        tailf:code-name "ENUM_aaa_attribute_type_tdl__AAA_AT_IMT_ENCAPSULATION_PROTOCOL_NUMBER_TDL";
      }
      enum "aaa-at-imt-group-key-expiry" {
        value 924;
        description
          "Number of seconds before CIT group key and SPI expire";
        tailf:code-name "ENUM_aaa_attribute_type_tdl__AAA_AT_IMT_GROUP_KEY_EXPIRY_TDL";
      }
      enum "aaa-at-imt-min-rekey-windows" {
        value 925;
        description
          "Minimum number of seconds before CIT key expiration to rekey";
        tailf:code-name "ENUM_aaa_attribute_type_tdl__AAA_AT_IMT_MIN_REKEY_WINDOWS_TDL";
      }
      enum "aaa-at-imt-expired-key-hold-down-time" {
        value 926;
        description
          "Time in seconds after expiration that the expired key and SPI must be active";
        tailf:code-name "ENUM_aaa_attribute_type_tdl__AAA_AT_IMT_EXPIRED_KEY_HOLD_DOWN_TIME_TDL";
      }
      enum "aaa-at-imt-tunnel-traffic-policy-expiry" {
        value 927;
        description
          "Time in seconds that the current traffic policy expires";
        tailf:code-name "ENUM_aaa_attribute_type_tdl__AAA_AT_IMT_TUNNEL_TRAFFIC_POLICY_EXPIRY_TDL";
      }
      enum "aaa-at-environment-data-expiry" {
        value 928;
        description
          "Number of seconds before environment data expires";
        tailf:code-name "ENUM_aaa_attribute_type_tdl__AAA_AT_ENVIRONMENT_DATA_EXPIRY_TDL";
      }
      enum "aaa-at-peer-authorization-token-outbound" {
        value 929;
        description
          "Device's authorization token";
        tailf:code-name "ENUM_aaa_attribute_type_tdl__AAA_AT_PEER_AUTHORIZATION_TOKEN_OUTBOUND_TDL";
      }
      enum "aaa-at-l2tp-silent-switchover" {
        value 930;
        description
          "Is L2TP silent switchover enabled";
        tailf:code-name "ENUM_aaa_attribute_type_tdl__AAA_AT_L2TP_SILENT_SWITCHOVER_TDL";
      }
      enum "aaa-at-gk-endp-addr" {
        value 931;
        description
          "Call Signaling address of endpoint";
        tailf:code-name "ENUM_aaa_attribute_type_tdl__AAA_AT_GK_ENDP_ADDR_TDL";
      }
      enum "aaa-at-gk-endp-alias" {
        value 932;
        description
          "Comma separated list of endpoint's h323 id and e164 aliases";
        tailf:code-name "ENUM_aaa_attribute_type_tdl__AAA_AT_GK_ENDP_ALIAS_TDL";
      }
      enum "aaa-at-keywrap-key" {
        value 933;
        description
          "Key wrap key";
        tailf:code-name "ENUM_aaa_attribute_type_tdl__AAA_AT_KEYWRAP_KEY_TDL";
      }
      enum "aaa-at-keywrap-nonce" {
        value 934;
        description
          "Key wrap randomize";
        tailf:code-name "ENUM_aaa_attribute_type_tdl__AAA_AT_KEYWRAP_NONCE_TDL";
      }
      enum "aaa-at-keywrap-message-auth-code" {
        value 935;
        description
          "Key wrap message authenticator code";
        tailf:code-name "ENUM_aaa_attribute_type_tdl__AAA_AT_KEYWRAP_MESSAGE_AUTH_CODE_TDL";
      }
      enum "aaa-at-in-lpcor-grp" {
        value 936;
        description
          "Logical partition class of restriction group of an incoming call leg";
        tailf:code-name "ENUM_aaa_attribute_type_tdl__AAA_AT_IN_LPCOR_GRP_TDL";
      }
      enum "aaa-at-out-lpcor-grp" {
        value 937;
        description
          "Logical partition class of restriction group of an outgoing call leg";
        tailf:code-name "ENUM_aaa_attribute_type_tdl__AAA_AT_OUT_LPCOR_GRP_TDL";
      }
      enum "aaa-at-evc-service-id" {
        value 938;
        description
          "Service instance values for Ethernet VC";
        tailf:code-name "ENUM_aaa_attribute_type_tdl__AAA_AT_EVC_SERVICE_ID_TDL";
      }
      enum "aaa-at-bsn-vap-id" {
        value 939;
        description
          "WLAN-ID";
        tailf:code-name "ENUM_aaa_attribute_type_tdl__AAA_AT_BSN_VAP_ID_TDL";
      }
      enum "aaa-at-bsn-qos-level" {
        value 940;
        description
          "QoS Level";
        tailf:code-name "ENUM_aaa_attribute_type_tdl__AAA_AT_BSN_QOS_LEVEL_TDL";
      }
      enum "aaa-at-bsn-dscp" {
        value 941;
        description
          "Differentiated Services Code Point";
        tailf:code-name "ENUM_aaa_attribute_type_tdl__AAA_AT_BSN_DSCP_TDL";
      }
      enum "aaa-at-bsn-8021-p-type" {
        value 942;
        description
          "802.1P Type";
        tailf:code-name "ENUM_aaa_attribute_type_tdl__AAA_AT_BSN_8021P_TYPE_TDL";
      }
      enum "aaa-at-bsn-vlan-interface-name" {
        value 943;
        description
          "Vlan interface name";
        tailf:code-name "ENUM_aaa_attribute_type_tdl__AAA_AT_BSN_VLAN_INTERFACE_NAME_TDL";
      }
      enum "aaa-at-bsn-acl-name" {
        value 944;
        description
          "Wlan ACL name";
        tailf:code-name "ENUM_aaa_attribute_type_tdl__AAA_AT_BSN_ACL_NAME_TDL";
      }
      enum "aaa-at-bsn-data-bw-average-contract" {
        value 945;
        description
          "Data Bandwidth Average Contract";
        tailf:code-name "ENUM_aaa_attribute_type_tdl__AAA_AT_BSN_DATA_BW_AVERAGE_CONTRACT_TDL";
      }
      enum "aaa-at-bsn-real-time-bw-average-contract" {
        value 946;
        description
          "RealTime Bandwidth Average Contract";
        tailf:code-name "ENUM_aaa_attribute_type_tdl__AAA_AT_BSN_REAL_TIME_BW_AVERAGE_CONTRACT_TDL";
      }
      enum "aaa-at-bsn-data-bw-burst-contract" {
        value 947;
        description
          "Data Bandwidth Burst Contract";
        tailf:code-name "ENUM_aaa_attribute_type_tdl__AAA_AT_BSN_DATA_BW_BURST_CONTRACT_TDL";
      }
      enum "aaa-at-bsn-real-time-bw-burst-contract" {
        value 948;
        description
          "RealTime Bandwidth Burst Contract";
        tailf:code-name "ENUM_aaa_attribute_type_tdl__AAA_AT_BSN_REAL_TIME_BW_BURST_CONTRACT_TDL";
      }
      enum "aaa-at-bsn-guest-role-name" {
        value 949;
        description
          "Guest Role Name";
        tailf:code-name "ENUM_aaa_attribute_type_tdl__AAA_AT_BSN_GUEST_ROLE_NAME_TDL";
      }
      enum "aaa-at-hwidb" {
        value 950;
        description
          "IOS Hardware IDB";
        tailf:code-name "ENUM_aaa_attribute_type_tdl__AAA_AT_HWIDB_TDL";
      }
      enum "aaa-at-swidb" {
        value 951;
        description
          "IOS Software IDB";
        tailf:code-name "ENUM_aaa_attribute_type_tdl__AAA_AT_SWIDB_TDL";
      }
      enum "aaa-at-iif-id" {
        value 952;
        description
          "IIF ID 64 bits";
        tailf:code-name "ENUM_aaa_attribute_type_tdl__AAA_AT_IIF_ID_TDL";
      }
      enum "aaa-at-auth-profile" {
        value 953;
        description
          "Auth profile name";
        tailf:code-name "ENUM_aaa_attribute_type_tdl__AAA_AT_AUTH_PROFILE_TDL";
      }
      enum "aaa-at-auth-domain" {
        value 954;
        description
          "Authentication domain";
        tailf:code-name "ENUM_aaa_attribute_type_tdl__AAA_AT_AUTH_DOMAIN_TDL";
      }
      enum "aaa-at-auth-mgr-ctx-state" {
        value 955;
        description
          "State of the Auth Manager Context";
        tailf:code-name "ENUM_aaa_attribute_type_tdl__AAA_AT_AUTH_MGR_CTX_STATE_TDL";
      }
      enum "aaa-at-service-template" {
        value 956;
        description
          "Profile being downloaded is a service-template";
        tailf:code-name "ENUM_aaa_attribute_type_tdl__AAA_AT_SERVICE_TEMPLATE_TDL";
      }
      enum "aaa-at-aaa-authen-type" {
        value 957;
        description
          "Authentication type required for AAA APIs";
        tailf:code-name "ENUM_aaa_attribute_type_tdl__AAA_AT_AAA_AUTHEN_TYPE_TDL";
      }
      enum "aaa-at-aaa-author-type" {
        value 958;
        description
          "Authorization type required for AAA APIs";
        tailf:code-name "ENUM_aaa_attribute_type_tdl__AAA_AT_AAA_AUTHOR_TYPE_TDL";
      }
      enum "aaa-at-aaa-authen-service" {
        value 959;
        description
          "Authentication Service type required for AAA APIs";
        tailf:code-name "ENUM_aaa_attribute_type_tdl__AAA_AT_AAA_AUTHEN_SERVICE_TDL";
      }
      enum "aaa-at-aaa-author-service" {
        value 960;
        description
          "Authorization Service type required for AAA APIs";
        tailf:code-name "ENUM_aaa_attribute_type_tdl__AAA_AT_AAA_AUTHOR_SERVICE_TDL";
      }
      enum "aaa-at-arp-probe" {
        value 961;
        description
          "Enable ARP Probe functionality";
        tailf:code-name "ENUM_aaa_attribute_type_tdl__AAA_AT_ARP_PROBE_TDL";
      }
      enum "aaa-at-arp-probe-timeout" {
        value 962;
        description
          "ARP probe timeout period";
        tailf:code-name "ENUM_aaa_attribute_type_tdl__AAA_AT_ARP_PROBE_TIMEOUT_TDL";
      }
      enum "aaa-at-iaf-local-db" {
        value 963;
        description
          "IAF local DB attribute";
        tailf:code-name "ENUM_aaa_attribute_type_tdl__AAA_AT_IAF_LOCAL_DB_TDL";
      }
      enum "aaa-at-authz-fail-reason" {
        value 964;
        description
          "The reason for a failure from an authorization feature";
        tailf:code-name "ENUM_aaa_attribute_type_tdl__AAA_AT_AUTHZ_FAIL_REASON_TDL";
      }
      enum "aaa-at-vlan-id" {
        value 965;
        description
          "Virtual LAN Identifier";
        tailf:code-name "ENUM_aaa_attribute_type_tdl__AAA_AT_VLAN_ID_TDL";
      }
      enum "aaa-at-nas-update" {
        value 966;
        description
          "Indicator of change of subscriber's NAS";
        tailf:code-name "ENUM_aaa_attribute_type_tdl__AAA_AT_NAS_UPDATE_TDL";
      }
      enum "aaa-at-sam-account-name" {
        value 967;
        description
          "Logon name for older versions";
        tailf:code-name "ENUM_aaa_attribute_type_tdl__AAA_AT_SAM_ACCOUNT_NAME_TDL";
      }
      enum "aaa-at-employee-type" {
        value 968;
        description
          "Job category of employee";
        tailf:code-name "ENUM_aaa_attribute_type_tdl__AAA_AT_EMPLOYEE_TYPE_TDL";
      }
      enum "aaa-at-contact-info" {
        value 969;
        description
          "Meeting contact information";
        tailf:code-name "ENUM_aaa_attribute_type_tdl__AAA_AT_CONTACT_INFO_TDL";
      }
      enum "aaa-at-telephone-number" {
        value 970;
        description
          "Primary telephone number";
        tailf:code-name "ENUM_aaa_attribute_type_tdl__AAA_AT_TELEPHONE_NUMBER_TDL";
      }
      enum "aaa-at-encapsulation-untagged" {
        value 971;
        description
          "Encapsulation as untagged for Ethernet service";
        tailf:code-name "ENUM_aaa_attribute_type_tdl__AAA_AT_ENCAPSULATION_UNTAGGED_TDL";
      }
      enum "aaa-at-encapsulation-default" {
        value 972;
        description
          "Encapsulation as default for Ethernet service";
        tailf:code-name "ENUM_aaa_attribute_type_tdl__AAA_AT_ENCAPSULATION_DEFAULT_TDL";
      }
      enum "aaa-at-encapsulation-priority-tagged" {
        value 973;
        description
          "Encapsulation as priority tagged for Ethernet service";
        tailf:code-name "ENUM_aaa_attribute_type_tdl__AAA_AT_ENCAPSULATION_PRIORITY_TAGGED_TDL";
      }
      enum "aaa-at-efp-session-name" {
        value 974;
        description
          "EFP Session name";
        tailf:code-name "ENUM_aaa_attribute_type_tdl__AAA_AT_EFP_SESSION_NAME_TDL";
      }
      enum "aaa-at-stag-type" {
        value 975;
        description
          "Vlan type associated with EFP encapsulation";
        tailf:code-name "ENUM_aaa_attribute_type_tdl__AAA_AT_STAG_TYPE_TDL";
      }
      enum "aaa-at-idmgr-mask" {
        value 976;
        description
          "The netmask to be used in id-manager for subnet session";
        tailf:code-name "ENUM_aaa_attribute_type_tdl__AAA_AT_IDMGR_MASK_TDL";
      }
      enum "aaa-at-fac-digits" {
        value 977;
        description
          "Input FAC digits of a leg";
        tailf:code-name "ENUM_aaa_attribute_type_tdl__AAA_AT_FAC_DIGITS_TDL";
      }
      enum "aaa-at-fac-status" {
        value 978;
        description
          "Authenticated fac status of a leg";
        tailf:code-name "ENUM_aaa_attribute_type_tdl__AAA_AT_FAC_STATUS_TDL";
      }
      enum "aaa-at-dynamic-vrf-service-type" {
        value 979;
        description
          "Specifies type of vrf service : mapping or transfer";
        tailf:code-name "ENUM_aaa_attribute_type_tdl__AAA_AT_DYNAMIC_VRF_SERVICE_TYPE_TDL";
      }
      enum "aaa-at-media-protocol-state" {
        value 980;
        description
          "Specifies the state of media protocol";
        tailf:code-name "ENUM_aaa_attribute_type_tdl__AAA_AT_MEDIA_PROTOCOL_STATE_TDL";
      }
      enum "aaa-at-stag-vlanid" {
        value 981;
        description
          "Outer vlan ids associated with EFP encapsulation";
        tailf:code-name "ENUM_aaa_attribute_type_tdl__AAA_AT_STAG_VLANID_TDL";
      }
      enum "aaa-at-stag-cos" {
        value 982;
        description
          "Outer COS associated with EFP encapsulation";
        tailf:code-name "ENUM_aaa_attribute_type_tdl__AAA_AT_STAG_COS_TDL";
      }
      enum "aaa-at-ctag-vlanid" {
        value 983;
        description
          "Inner vlan ids associated with EFP encapsulation";
        tailf:code-name "ENUM_aaa_attribute_type_tdl__AAA_AT_CTAG_VLANID_TDL";
      }
      enum "aaa-at-ctag-cos" {
        value 984;
        description
          "Inner COS associated with EFP encapsulation";
        tailf:code-name "ENUM_aaa_attribute_type_tdl__AAA_AT_CTAG_COS_TDL";
      }
      enum "aaa-at-payload-etype" {
        value 985;
        description
          "Ether type of the payload associated with EFP";
        tailf:code-name "ENUM_aaa_attribute_type_tdl__AAA_AT_PAYLOAD_ETYPE_TDL";
      }
      enum "aaa-at-encapsulation-match-exact" {
        value 986;
        description
          "Encapsulation matching criteria is for exact match";
        tailf:code-name "ENUM_aaa_attribute_type_tdl__AAA_AT_ENCAPSULATION_MATCH_EXACT_TDL";
      }
      enum "aaa-at-rewrite-ingress" {
        value 987;
        description
          "Rewrite ingress direction";
        tailf:code-name "ENUM_aaa_attribute_type_tdl__AAA_AT_REWRITE_INGRESS_TDL";
      }
      enum "aaa-at-rewrite-ingress-stag-type" {
        value 988;
        description
          "Vlan ethertype for vlan push and translation operation";
        tailf:code-name "ENUM_aaa_attribute_type_tdl__AAA_AT_REWRITE_INGRESS_STAG_TYPE_TDL";
      }
      enum "aaa-at-rewrite-ingress-tag-operation" {
        value 989;
        description
          "Rewrite ingress vlan tag operation";
        tailf:code-name "ENUM_aaa_attribute_type_tdl__AAA_AT_REWRITE_INGRESS_TAG_OPERATION_TDL";
      }
      enum "aaa-at-rewrite-ingress-stag-vlanid" {
        value 990;
        description
          "Rewrite ingress stag vlanid";
        tailf:code-name "ENUM_aaa_attribute_type_tdl__AAA_AT_REWRITE_INGRESS_STAG_VLANID_TDL";
      }
      enum "aaa-at-rewrite-ingress-ctag-vlanid" {
        value 991;
        description
          "Rewrite ingress C-Tag vlanid";
        tailf:code-name "ENUM_aaa_attribute_type_tdl__AAA_AT_REWRITE_INGRESS_CTAG_VLANID_TDL";
      }
      enum "aaa-at-rewrite-ingress-symmetric" {
        value 992;
        description
          "Symmetric operation needed for vlan translation";
        tailf:code-name "ENUM_aaa_attribute_type_tdl__AAA_AT_REWRITE_INGRESS_SYMMETRIC_TDL";
      }
      enum "aaa-at-rewrite-egress" {
        value 993;
        description
          "Rewrite egress direction";
        tailf:code-name "ENUM_aaa_attribute_type_tdl__AAA_AT_REWRITE_EGRESS_TDL";
      }
      enum "aaa-at-rewrite-egress-stag-type" {
        value 994;
        description
          "Vlan ethertype for vlan push and translation operation";
        tailf:code-name "ENUM_aaa_attribute_type_tdl__AAA_AT_REWRITE_EGRESS_STAG_TYPE_TDL";
      }
      enum "aaa-at-rewrite-egress-tag-operation" {
        value 995;
        description
          "Rewrite egress vlan tag operation";
        tailf:code-name "ENUM_aaa_attribute_type_tdl__AAA_AT_REWRITE_EGRESS_TAG_OPERATION_TDL";
      }
      enum "aaa-at-rewrite-egress-stag-vlanid" {
        value 996;
        description
          "Rewrite egress stag vlanid";
        tailf:code-name "ENUM_aaa_attribute_type_tdl__AAA_AT_REWRITE_EGRESS_STAG_VLANID_TDL";
      }
      enum "aaa-at-rewrite-egress-ctag-vlanid" {
        value 997;
        description
          "Rewrite egress c-tag vlanid";
        tailf:code-name "ENUM_aaa_attribute_type_tdl__AAA_AT_REWRITE_EGRESS_CTAG_VLANID_TDL";
      }
      enum "aaa-at-rewrite-egress-symmetric" {
        value 998;
        description
          "Symmetric operation needed for vlan translation";
        tailf:code-name "ENUM_aaa_attribute_type_tdl__AAA_AT_REWRITE_EGRESS_SYMMETRIC_TDL";
      }
      enum "aaa-at-service-instance-description" {
        value 999;
        description
          "Textual description associated with EFP";
        tailf:code-name "ENUM_aaa_attribute_type_tdl__AAA_AT_SERVICE_INSTANCE_DESCRIPTION_TDL";
      }
      enum "aaa-at-snmp-ifindex-persist" {
        value 1000;
        description
          "SNMP index is persistent or need to clear";
        tailf:code-name "ENUM_aaa_attribute_type_tdl__AAA_AT_SNMP_IFINDEX_PERSIST_TDL";
      }
      enum "aaa-at-evc-name" {
        value 1001;
        description
          "EVC name to be attached with ethernet services instance";
        tailf:code-name "ENUM_aaa_attribute_type_tdl__AAA_AT_EVC_NAME_TDL";
      }
      enum "aaa-at-ce-vlan-map" {
        value 1002;
        description
          "CE-VLAN to EVC map for a particular UNI";
        tailf:code-name "ENUM_aaa_attribute_type_tdl__AAA_AT_CE_VLAN_MAP_TDL";
      }
      enum "aaa-at-redundancy-group" {
        value 1003;
        description
          "Defines the redundancy group of PE";
        tailf:code-name "ENUM_aaa_attribute_type_tdl__AAA_AT_REDUNDANCY_GROUP_TDL";
      }
      enum "aaa-at-elmi-vlan-map-untagged" {
        value 1004;
        description
          "Vlan map encapsulation as untagged";
        tailf:code-name "ENUM_aaa_attribute_type_tdl__AAA_AT_ELMI_VLAN_MAP_UNTAGGED_TDL";
      }
      enum "aaa-at-elmi-vlan-map-default" {
        value 1005;
        description
          "Vlan map encapsulation as default";
        tailf:code-name "ENUM_aaa_attribute_type_tdl__AAA_AT_ELMI_VLAN_MAP_DEFAULT_TDL";
      }
      enum "aaa-at-service-group-id" {
        value 1006;
        description
          "Service group number newly created EFP should be member";
        tailf:code-name "ENUM_aaa_attribute_type_tdl__AAA_AT_SERVICE_GROUP_ID_TDL";
      }
      enum "aaa-at-subscriber-id" {
        value 1007;
        description
          "Subscriber ID";
        tailf:code-name "ENUM_aaa_attribute_type_tdl__AAA_AT_SUBSCRIBER_ID_TDL";
      }
      enum "aaa-at-port-security-enabled" {
        value 1008;
        description
          "SNMP index is persistent or need to clear";
        tailf:code-name "ENUM_aaa_attribute_type_tdl__AAA_AT_PORT_SECURITY_ENABLED_TDL";
      }
      enum "aaa-at-static-mac-address" {
        value 1009;
        description
          "Static mac address for EFP";
        tailf:code-name "ENUM_aaa_attribute_type_tdl__AAA_AT_STATIC_MAC_ADDRESS_TDL";
      }
      enum "aaa-at-static-mac-address-drop" {
        value 1010;
        description
          "Static mac address to be dropped";
        tailf:code-name "ENUM_aaa_attribute_type_tdl__AAA_AT_STATIC_MAC_ADDRESS_DROP_TDL";
      }
      enum "aaa-at-static-mac-address-autolearn" {
        value 1011;
        description
          "Static mac address to be auto learn";
        tailf:code-name "ENUM_aaa_attribute_type_tdl__AAA_AT_STATIC_MAC_ADDRESS_AUTOLEARN_TDL";
      }
      enum "aaa-at-static-mac-address-disable-snooping" {
        value 1012;
        description
          "Static mac address with snooping disable";
        tailf:code-name "ENUM_aaa_attribute_type_tdl__AAA_AT_STATIC_MAC_ADDRESS_DISABLE_SNOOPING_TDL";
      }
      enum "aaa-at-recovery-mac-sec-time-interval" {
        value 1013;
        description
          "Recovery time interval for mac-security cause";
        tailf:code-name "ENUM_aaa_attribute_type_tdl__AAA_AT_RECOVERY_MAC_SEC_TIME_INTERVAL_TDL";
      }
      enum "aaa-at-l2protocol-pdu-action" {
        value 1014;
        description
          "L2 protocol PDU action";
        tailf:code-name "ENUM_aaa_attribute_type_tdl__AAA_AT_L2PROTOCOL_PDU_ACTION_TDL";
      }
      enum "aaa-at-mac-tunnel-id" {
        value 1015;
        description
          "MAC tunnel ID";
        tailf:code-name "ENUM_aaa_attribute_type_tdl__AAA_AT_MAC_TUNNEL_ID_TDL";
      }
      enum "aaa-at-mac-tunnel-description" {
        value 1016;
        description
          "Textual description associated with MAC tunnel";
        tailf:code-name "ENUM_aaa_attribute_type_tdl__AAA_AT_MAC_TUNNEL_DESCRIPTION_TDL";
      }
      enum "aaa-at-btag-type" {
        value 1017;
        description
          "B-Vlan type associated with ethernet mac encapsulation";
        tailf:code-name "ENUM_aaa_attribute_type_tdl__AAA_AT_BTAG_TYPE_TDL";
      }
      enum "aaa-at-btag-vlan-id" {
        value 1018;
        description
          "Backbone Vlan-id required for defining matching criteria";
        tailf:code-name "ENUM_aaa_attribute_type_tdl__AAA_AT_BTAG_VLAN_ID_TDL";
      }
      enum "aaa-at-default-destination-mac" {
        value 1019;
        description
          "Default destination mac";
        tailf:code-name "ENUM_aaa_attribute_type_tdl__AAA_AT_DEFAULT_DESTINATION_MAC_TDL";
      }
      enum "aaa-at-itag" {
        value 1020;
        description
          "I-Tag value under EFP";
        tailf:code-name "ENUM_aaa_attribute_type_tdl__AAA_AT_ITAG_TDL";
      }
      enum "aaa-at-mac-flush-proto" {
        value 1021;
        description
          "Protocol used for MAC flush";
        tailf:code-name "ENUM_aaa_attribute_type_tdl__AAA_AT_MAC_FLUSH_PROTO_TDL";
      }
      enum "aaa-at-mac-flush-cos-value" {
        value 1022;
        description
          "Cos value used for MAC flush";
        tailf:code-name "ENUM_aaa_attribute_type_tdl__AAA_AT_MAC_FLUSH_COS_VALUE_TDL";
      }
      enum "aaa-at-bridge-domain-id" {
        value 1023;
        description
          "Bridge domain to be used";
        tailf:code-name "ENUM_aaa_attribute_type_tdl__AAA_AT_BRIDGE_DOMAIN_ID_TDL";
      }
      enum "aaa-at-split-horizon-group" {
        value 1024;
        description
          "Bridge domain split horizon group";
        tailf:code-name "ENUM_aaa_attribute_type_tdl__AAA_AT_SPLIT_HORIZON_GROUP_TDL";
      }
      enum "aaa-at-bridge-domain-type" {
        value 1025;
        description
          "Bridge domain type";
        tailf:code-name "ENUM_aaa_attribute_type_tdl__AAA_AT_BRIDGE_DOMAIN_TYPE_TDL";
      }
      enum "aaa-at-max-mac-addr" {
        value 1026;
        description
          "Bridge domain max address";
        tailf:code-name "ENUM_aaa_attribute_type_tdl__AAA_AT_MAX_MAC_ADDR_TDL";
      }
      enum "aaa-at-mac-learning" {
        value 1027;
        description
          "Bridge domain mac learning enable";
        tailf:code-name "ENUM_aaa_attribute_type_tdl__AAA_AT_MAC_LEARNING_TDL";
      }
      enum "aaa-at-snmp-context" {
        value 1028;
        description
          "Bridge domain snmp context";
        tailf:code-name "ENUM_aaa_attribute_type_tdl__AAA_AT_SNMP_CONTEXT_TDL";
      }
      enum "aaa-at-bridge-domain-member" {
        value 1029;
        description
          "Bridge domain member";
        tailf:code-name "ENUM_aaa_attribute_type_tdl__AAA_AT_BRIDGE_DOMAIN_MEMBER_TDL";
      }
      enum "aaa-at-bridge-domain-profile" {
        value 1030;
        description
          "Bridge domain profile";
        tailf:code-name "ENUM_aaa_attribute_type_tdl__AAA_AT_BRIDGE_DOMAIN_PROFILE_TDL";
      }
      enum "aaa-at-mac-security-enabled" {
        value 1031;
        description
          "MAC security enabled";
        tailf:code-name "ENUM_aaa_attribute_type_tdl__AAA_AT_MAC_SECURITY_ENABLED_TDL";
      }
      enum "aaa-at-permit-mac-addr-list" {
        value 1032;
        description
          "Permit address list (white list)";
        tailf:code-name "ENUM_aaa_attribute_type_tdl__AAA_AT_PERMIT_MAC_ADDR_LIST_TDL";
      }
      enum "aaa-at-deny-mac-addr-list" {
        value 1033;
        description
          "Deny address list (black list)";
        tailf:code-name "ENUM_aaa_attribute_type_tdl__AAA_AT_DENY_MAC_ADDR_LIST_TDL";
      }
      enum "aaa-at-max-mac-addr-limit" {
        value 1034;
        description
          "Per service instance max address limit";
        tailf:code-name "ENUM_aaa_attribute_type_tdl__AAA_AT_MAX_MAC_ADDR_LIMIT_TDL";
      }
      enum "aaa-at-mac-security-sticky" {
        value 1035;
        description
          "MAC security sticky address enable";
        tailf:code-name "ENUM_aaa_attribute_type_tdl__AAA_AT_MAC_SECURITY_STICKY_TDL";
      }
      enum "aaa-at-mac-security-violation-mode" {
        value 1036;
        description
          "MAC security violation mode";
        tailf:code-name "ENUM_aaa_attribute_type_tdl__AAA_AT_MAC_SECURITY_VIOLATION_MODE_TDL";
      }
      enum "aaa-at-mac-security-aging-inactive" {
        value 1037;
        description
          "MAC security aging timer for inactive type";
        tailf:code-name "ENUM_aaa_attribute_type_tdl__AAA_AT_MAC_SECURITY_AGING_INACTIVE_TDL";
      }
      enum "aaa-at-mac-security-aging-absolute" {
        value 1038;
        description
          "MAC security aging timer for absolute type";
        tailf:code-name "ENUM_aaa_attribute_type_tdl__AAA_AT_MAC_SECURITY_AGING_ABSOLUTE_TDL";
      }
      enum "aaa-at-mac-security-aging-sticky" {
        value 1039;
        description
          "Aging for sticky address enable";
        tailf:code-name "ENUM_aaa_attribute_type_tdl__AAA_AT_MAC_SECURITY_AGING_STICKY_TDL";
      }
      enum "aaa-at-mac-security-aging-static" {
        value 1040;
        description
          "Aging for static address enable";
        tailf:code-name "ENUM_aaa_attribute_type_tdl__AAA_AT_MAC_SECURITY_AGING_STATIC_TDL";
      }
      enum "aaa-at-uni-count" {
        value 1041;
        description
          "Total number of uni on a given evc";
        tailf:code-name "ENUM_aaa_attribute_type_tdl__AAA_AT_UNI_COUNT_TDL";
      }
      enum "aaa-at-multi-point" {
        value 1042;
        description
          "Uni count of 2 is multipoint";
        tailf:code-name "ENUM_aaa_attribute_type_tdl__AAA_AT_MULTI_POINT_TDL";
      }
      enum "aaa-at-oam-protocol" {
        value 1043;
        description
          "Protocol used for MAC flush";
        tailf:code-name "ENUM_aaa_attribute_type_tdl__AAA_AT_OAM_PROTOCOL_TDL";
      }
      enum "aaa-at-cfm-svlan-id" {
        value 1044;
        description
          "CFM Vlan id for CFM protocol";
        tailf:code-name "ENUM_aaa_attribute_type_tdl__AAA_AT_CFM_SVLAN_ID_TDL";
      }
      enum "aaa-at-cfm-vlan-id" {
        value 1045;
        description
          "Maintainance association of format vlan id";
        tailf:code-name "ENUM_aaa_attribute_type_tdl__AAA_AT_CFM_VLAN_ID_TDL";
      }
      enum "aaa-at-service-text" {
        value 1046;
        description
          "Maintainance association of format text";
        tailf:code-name "ENUM_aaa_attribute_type_tdl__AAA_AT_SERVICE_TEXT_TDL";
      }
      enum "aaa-at-domain-name" {
        value 1047;
        description
          "Domain name associated with CFM";
        tailf:code-name "ENUM_aaa_attribute_type_tdl__AAA_AT_DOMAIN_NAME_TDL";
      }
      enum "aaa-at-service-profile" {
        value 1048;
        description
          "Service profile for CFM";
        tailf:code-name "ENUM_aaa_attribute_type_tdl__AAA_AT_SERVICE_PROFILE_TDL";
      }
      enum "aaa-at-service-instance-id" {
        value 1049;
        description
          "Service instance id";
        tailf:code-name "ENUM_aaa_attribute_type_tdl__AAA_AT_SERVICE_INSTANCE_ID_TDL";
      }
      enum "aaa-at-service-direction" {
        value 1050;
        description
          "Service direction of MEP(default is up)";
        tailf:code-name "ENUM_aaa_attribute_type_tdl__AAA_AT_SERVICE_DIRECTION_TDL";
      }
      enum "aaa-at-mip-level" {
        value 1051;
        description
          "Identify MIP level";
        tailf:code-name "ENUM_aaa_attribute_type_tdl__AAA_AT_MIP_LEVEL_TDL";
      }
      enum "aaa-at-mep-domain" {
        value 1052;
        description
          "MEP domain name";
        tailf:code-name "ENUM_aaa_attribute_type_tdl__AAA_AT_MEP_DOMAIN_TDL";
      }
      enum "aaa-at-mep-mpid" {
        value 1053;
        description
          "Attribute specify MEP id";
        tailf:code-name "ENUM_aaa_attribute_type_tdl__AAA_AT_MEP_MPID_TDL";
      }
      enum "aaa-at-mep-cos" {
        value 1054;
        description
          "Attribute specify COS priority for MEP";
        tailf:code-name "ENUM_aaa_attribute_type_tdl__AAA_AT_MEP_COS_TDL";
      }
      enum "aaa-at-mep-alarm-notification" {
        value 1055;
        description
          "Attribute specify MEP alarm notification";
        tailf:code-name "ENUM_aaa_attribute_type_tdl__AAA_AT_MEP_ALARM_NOTIFICATION_TDL";
      }
      enum "aaa-at-mep-alarm-delay" {
        value 1056;
        description
          "Attribute specify MEP alarm delay time";
        tailf:code-name "ENUM_aaa_attribute_type_tdl__AAA_AT_MEP_ALARM_DELAY_TDL";
      }
      enum "aaa-at-mep-alarm-reset" {
        value 1057;
        description
          "Attribute specify MEP alarm reset time";
        tailf:code-name "ENUM_aaa_attribute_type_tdl__AAA_AT_MEP_ALARM_RESET_TDL";
      }
      enum "aaa-at-mip-auto-create-level" {
        value 1058;
        description
          "MIP level for mips to be auto created";
        tailf:code-name "ENUM_aaa_attribute_type_tdl__AAA_AT_MIP_AUTO_CREATE_LEVEL_TDL";
      }
      enum "aaa-at-mip-auto-create-evc" {
        value 1059;
        description
          "EVC name for mips to be auto created";
        tailf:code-name "ENUM_aaa_attribute_type_tdl__AAA_AT_MIP_AUTO_CREATE_EVC_TDL";
      }
      enum "aaa-at-mip-auto-create-lower-mep-only" {
        value 1060;
        description
          "MIPs to be auto created only if active lower level";
        tailf:code-name "ENUM_aaa_attribute_type_tdl__AAA_AT_MIP_AUTO_CREATE_LOWER_MEP_ONLY_TDL";
      }
      enum "aaa-at-mip-auto-create-sender-id" {
        value 1061;
        description
          "MIP auto create sensor ID";
        tailf:code-name "ENUM_aaa_attribute_type_tdl__AAA_AT_MIP_AUTO_CREATE_SENDER_ID_TDL";
      }
      enum "aaa-at-service-short-ma-name" {
        value 1062;
        description
          "Maintainance association name under domain";
        tailf:code-name "ENUM_aaa_attribute_type_tdl__AAA_AT_SERVICE_SHORT_MA_NAME_TDL";
      }
      enum "aaa-at-service-fmt" {
        value 1063;
        description
          "Service format";
        tailf:code-name "ENUM_aaa_attribute_type_tdl__AAA_AT_SERVICE_FMT_TDL";
      }
      enum "aaa-at-service-vlanid" {
        value 1064;
        description
          "Maintainance association of format vlan id";
        tailf:code-name "ENUM_aaa_attribute_type_tdl__AAA_AT_SERVICE_VLANID_TDL";
      }
      enum "aaa-at-service-number" {
        value 1065;
        description
          "Maintainance association of format number";
        tailf:code-name "ENUM_aaa_attribute_type_tdl__AAA_AT_SERVICE_NUMBER_TDL";
      }
      enum "aaa-at-service-vpnid" {
        value 1066;
        description
          "Maintainance association of format VPN ID";
        tailf:code-name "ENUM_aaa_attribute_type_tdl__AAA_AT_SERVICE_VPNID_TDL";
      }
      enum "aaa-at-cfm-service-type" {
        value 1067;
        description
          "Maintainance association type";
        tailf:code-name "ENUM_aaa_attribute_type_tdl__AAA_AT_CFM_SERVICE_TYPE_TDL";
      }
      enum "aaa-at-service-continuity-check" {
        value 1068;
        description
          "Service continuity check";
        tailf:code-name "ENUM_aaa_attribute_type_tdl__AAA_AT_SERVICE_CONTINUITY_CHECK_TDL";
      }
      enum "aaa-at-service-continuity-check-interval" {
        value 1069;
        description
          "Time interval at which continuity check messages transmitted";
        tailf:code-name "ENUM_aaa_attribute_type_tdl__AAA_AT_SERVICE_CONTINUITY_CHECK_INTERVAL_TDL";
      }
      enum "aaa-at-service-continuity-check-loss-threshold" {
        value 1070;
        description
          "Service continuity check loss threshold";
        tailf:code-name "ENUM_aaa_attribute_type_tdl__AAA_AT_SERVICE_CONTINUITY_CHECK_LOSS_THRESHOLD_TDL";
      }
      enum "aaa-at-service-continuity-check-static-rmep" {
        value 1071;
        description
          "Service continuity check received MEP id validation";
        tailf:code-name "ENUM_aaa_attribute_type_tdl__AAA_AT_SERVICE_CONTINUITY_CHECK_STATIC_RMEP_TDL";
      }
      enum "aaa-at-service-continuity-check-auto-traceroute" {
        value 1072;
        description
          "Service continuity check auto traceroute enabled";
        tailf:code-name "ENUM_aaa_attribute_type_tdl__AAA_AT_SERVICE_CONTINUITY_CHECK_AUTO_TRACEROUTE_TDL";
      }
      enum "aaa-at-service-mip-autocreate" {
        value 1073;
        description
          "Service mip auto create at domain maintainance level";
        tailf:code-name "ENUM_aaa_attribute_type_tdl__AAA_AT_SERVICE_MIP_AUTOCREATE_TDL";
      }
      enum "aaa-at-service-mep-mpid" {
        value 1074;
        description
          "Static MEP id in MA";
        tailf:code-name "ENUM_aaa_attribute_type_tdl__AAA_AT_SERVICE_MEP_MPID_TDL";
      }
      enum "aaa-at-service-maximum-meps" {
        value 1075;
        description
          "Maximum meps supported";
        tailf:code-name "ENUM_aaa_attribute_type_tdl__AAA_AT_SERVICE_MAXIMUM_MEPS_TDL";
      }
      enum "aaa-at-service-ais" {
        value 1076;
        description
          "AIS enabled or disabled for the service";
        tailf:code-name "ENUM_aaa_attribute_type_tdl__AAA_AT_SERVICE_AIS_TDL";
      }
      enum "aaa-at-service-ais-period" {
        value 1077;
        description
          "AIS transmission period for the service";
        tailf:code-name "ENUM_aaa_attribute_type_tdl__AAA_AT_SERVICE_AIS_PERIOD_TDL";
      }
      enum "aaa-at-service-ais-level" {
        value 1078;
        description
          "AIS transmission level for the service";
        tailf:code-name "ENUM_aaa_attribute_type_tdl__AAA_AT_SERVICE_AIS_LEVEL_TDL";
      }
      enum "aaa-at-service-ais-expiry-threshold" {
        value 1079;
        description
          "AIS specific expiry threshold";
        tailf:code-name "ENUM_aaa_attribute_type_tdl__AAA_AT_SERVICE_AIS_EXPIRY_THRESHOLD_TDL";
      }
      enum "aaa-at-service-ais-suppress-alarms" {
        value 1080;
        description
          "AIS enable/disable of suppression of alarms";
        tailf:code-name "ENUM_aaa_attribute_type_tdl__AAA_AT_SERVICE_AIS_SUPPRESS_ALARMS_TDL";
      }
      enum "aaa-at-service-lck" {
        value 1081;
        description
          "Enable/disable LCK generation for the service";
        tailf:code-name "ENUM_aaa_attribute_type_tdl__AAA_AT_SERVICE_LCK_TDL";
      }
      enum "aaa-at-service-lck-period" {
        value 1082;
        description
          "Service transmission period for all meps";
        tailf:code-name "ENUM_aaa_attribute_type_tdl__AAA_AT_SERVICE_LCK_PERIOD_TDL";
      }
      enum "aaa-at-service-lck-level" {
        value 1083;
        description
          "Maintainance level to send LCK frames";
        tailf:code-name "ENUM_aaa_attribute_type_tdl__AAA_AT_SERVICE_LCK_LEVEL_TDL";
      }
      enum "aaa-at-service-lck-expiry-threshold" {
        value 1084;
        description
          "LCK specific expiry threshold";
        tailf:code-name "ENUM_aaa_attribute_type_tdl__AAA_AT_SERVICE_LCK_EXPIRY_THRESHOLD_TDL";
      }
      enum "aaa-at-service-sender-id-chassis" {
        value 1085;
        description
          "Include sender id TLV in CFM packet";
        tailf:code-name "ENUM_aaa_attribute_type_tdl__AAA_AT_SERVICE_SENDER_ID_CHASSIS_TDL";
      }
      enum "aaa-at-forwarding-service-type" {
        value 1086;
        description
          "Represents the type of forwarding service";
        tailf:code-name "ENUM_aaa_attribute_type_tdl__AAA_AT_FORWARDING_SERVICE_TYPE_TDL";
      }
      enum "aaa-at-forwarding-service-id" {
        value 1087;
        description
          "Represents the forwarding service id";
        tailf:code-name "ENUM_aaa_attribute_type_tdl__AAA_AT_FORWARDING_SERVICE_ID_TDL";
      }
      enum "aaa-at-composite-key" {
        value 1088;
        description
          "Composite key";
        tailf:code-name "ENUM_aaa_attribute_type_tdl__AAA_AT_COMPOSITE_KEY_TDL";
      }
      enum "aaa-at-vcid" {
        value 1089;
        description
          "VC-ID associated with PW";
        tailf:code-name "ENUM_aaa_attribute_type_tdl__AAA_AT_VCID_TDL";
      }
      enum "aaa-at-vpnid" {
        value 1090;
        description
          "VPN-ID associated with VPLS";
        tailf:code-name "ENUM_aaa_attribute_type_tdl__AAA_AT_VPNID_TDL";
      }
      enum "aaa-at-pw-encapsulation" {
        value 1091;
        description
          "pw-class specification";
        tailf:code-name "ENUM_aaa_attribute_type_tdl__AAA_AT_PW_ENCAPSULATION_TDL";
      }
      enum "aaa-at-pw-classname" {
        value 1092;
        description
          "pw-class name for the class defined";
        tailf:code-name "ENUM_aaa_attribute_type_tdl__AAA_AT_PW_CLASSNAME_TDL";
      }
      enum "aaa-at-preferred-path-tunnel" {
        value 1093;
        description
          "Preferred path tunnel interface";
        tailf:code-name "ENUM_aaa_attribute_type_tdl__AAA_AT_PREFERRED_PATH_TUNNEL_TDL";
      }
      enum "aaa-at-interworking" {
        value 1094;
        description
          "Ethernet or IP interworking";
        tailf:code-name "ENUM_aaa_attribute_type_tdl__AAA_AT_INTERWORKING_TDL";
      }
      enum "aaa-at-pw-status" {
        value 1095;
        description
          "Enable PW status extension";
        tailf:code-name "ENUM_aaa_attribute_type_tdl__AAA_AT_PW_STATUS_TDL";
      }
      enum "aaa-at-sequencing-type" {
        value 1096;
        description
          "Sequencing type";
        tailf:code-name "ENUM_aaa_attribute_type_tdl__AAA_AT_SEQUENCING_TYPE_TDL";
      }
      enum "aaa-at-primary-pw" {
        value 1097;
        description
          "Primary PW";
        tailf:code-name "ENUM_aaa_attribute_type_tdl__AAA_AT_PRIMARY_PW_TDL";
      }
      enum "aaa-at-backup-delay" {
        value 1098;
        description
          "Backup PW enable delay";
        tailf:code-name "ENUM_aaa_attribute_type_tdl__AAA_AT_BACKUP_DELAY_TDL";
      }
      enum "aaa-at-redundancy-enable-delay" {
        value 1099;
        description
          "Redundancy enable delay interval";
        tailf:code-name "ENUM_aaa_attribute_type_tdl__AAA_AT_REDUNDANCY_ENABLE_DELAY_TDL";
      }
      enum "aaa-at-redundancy-disable-delay" {
        value 1100;
        description
          "Redundancy disable delay interval";
        tailf:code-name "ENUM_aaa_attribute_type_tdl__AAA_AT_REDUNDANCY_DISABLE_DELAY_TDL";
      }
      enum "aaa-at-redundancy-disable-never" {
        value 1101;
        description
          "Never disable redundancy";
        tailf:code-name "ENUM_aaa_attribute_type_tdl__AAA_AT_REDUNDANCY_DISABLE_NEVER_TDL";
      }
      enum "aaa-at-redundancy-priority" {
        value 1102;
        description
          "Redundancy PW priority";
        tailf:code-name "ENUM_aaa_attribute_type_tdl__AAA_AT_REDUNDANCY_PRIORITY_TDL";
      }
      enum "aaa-at-vfi-name" {
        value 1103;
        description
          "Name of the VPLS used for forwarding service";
        tailf:code-name "ENUM_aaa_attribute_type_tdl__AAA_AT_VFI_NAME_TDL";
      }
      enum "aaa-at-vpls-id" {
        value 1104;
        description
          "VPLS ID";
        tailf:code-name "ENUM_aaa_attribute_type_tdl__AAA_AT_VPLS_ID_TDL";
      }
      enum "aaa-at-route-distinguisher" {
        value 1105;
        description
          "Route distinguisher";
        tailf:code-name "ENUM_aaa_attribute_type_tdl__AAA_AT_ROUTE_DISTINGUISHER_TDL";
      }
      enum "aaa-at-route-target" {
        value 1106;
        description
          "Route target";
        tailf:code-name "ENUM_aaa_attribute_type_tdl__AAA_AT_ROUTE_TARGET_TDL";
      }
      enum "aaa-at-auto-route-target" {
        value 1107;
        description
          "Automatically set a route target";
        tailf:code-name "ENUM_aaa_attribute_type_tdl__AAA_AT_AUTO_ROUTE_TARGET_TDL";
      }
      enum "aaa-at-l2-router-id" {
        value 1108;
        description
          "PE-router id";
        tailf:code-name "ENUM_aaa_attribute_type_tdl__AAA_AT_L2_ROUTER_ID_TDL";
      }
      enum "aaa-at-forward-l2protocol-all" {
        value 1109;
        description
          "Permit forwarding of all L2 protocol";
        tailf:code-name "ENUM_aaa_attribute_type_tdl__AAA_AT_FORWARD_L2PROTOCOL_ALL_TDL";
      }
      enum "aaa-at-peer-ip-address" {
        value 1110;
        description
          "Peer PE ip address";
        tailf:code-name "ENUM_aaa_attribute_type_tdl__AAA_AT_PEER_IP_ADDRESS_TDL";
      }
      enum "aaa-at-preferred-peer" {
        value 1111;
        description
          "Preferred path peer ip address";
        tailf:code-name "ENUM_aaa_attribute_type_tdl__AAA_AT_PREFERRED_PEER_TDL";
      }
      enum "aaa-at-disable-fallback" {
        value 1112;
        description
          "Disable Fallback from preferred peer or path";
        tailf:code-name "ENUM_aaa_attribute_type_tdl__AAA_AT_DISABLE_FALLBACK_TDL";
      }
      enum "aaa-at-l2vpn-control-word" {
        value 1113;
        description
          "L2VPn control word";
        tailf:code-name "ENUM_aaa_attribute_type_tdl__AAA_AT_L2VPN_CONTROL_WORD_TDL";
      }
      enum "aaa-at-vccv" {
        value 1114;
        description
          "Virtual Circuit Connectivity Verification";
        tailf:code-name "ENUM_aaa_attribute_type_tdl__AAA_AT_VCCV_TDL";
      }
      enum "aaa-at-service-id" {
        value 1115;
        description
          "Service id for downloading profile";
        tailf:code-name "ENUM_aaa_attribute_type_tdl__AAA_AT_SERVICE_ID_TDL";
      }
      enum "aaa-at-member" {
        value 1116;
        description
          "Member of a container";
        tailf:code-name "ENUM_aaa_attribute_type_tdl__AAA_AT_MEMBER_TDL";
      }
      enum "aaa-at-l2vpn-service-type" {
        value 1117;
        description
          "L2VPN service type";
        tailf:code-name "ENUM_aaa_attribute_type_tdl__AAA_AT_L2VPN_SERVICE_TYPE_TDL";
      }
      enum "aaa-at-mtp-isid" {
        value 1118;
        description
          "I-Tag profile name for I-EFP";
        tailf:code-name "ENUM_aaa_attribute_type_tdl__AAA_AT_MTP_ISID_TDL";
      }
      enum "aaa-at-bmac" {
        value 1119;
        description
          "Bridge MAC Address";
        tailf:code-name "ENUM_aaa_attribute_type_tdl__AAA_AT_BMAC_TDL";
      }
      enum "aaa-at-cmac" {
        value 1120;
        description
          "Customer MAC Address";
        tailf:code-name "ENUM_aaa_attribute_type_tdl__AAA_AT_CMAC_TDL";
      }
      enum "aaa-at-sgt-name-list-inbound" {
        value 1121;
        description
          "SG Name list and generation number";
        tailf:code-name "ENUM_aaa_attribute_type_tdl__AAA_AT_SGT_NAME_LIST_INBOUND_TDL";
      }
      enum "aaa-at-sgt-name-list-outbound" {
        value 1122;
        description
          "SG Name list table";
        tailf:code-name "ENUM_aaa_attribute_type_tdl__AAA_AT_SGT_NAME_LIST_OUTBOUND_TDL";
      }
      enum "aaa-at-sgt-name" {
        value 1123;
        description
          "SG name for the SGT, format <sgt>-<sg name>";
        tailf:code-name "ENUM_aaa_attribute_type_tdl__AAA_AT_SGT_NAME_TDL";
      }
      enum "aaa-at-cdp-opaque" {
        value 1124;
        description
          "CDP TLV";
        tailf:code-name "ENUM_aaa_attribute_type_tdl__AAA_AT_CDP_OPAQUE_TDL";
      }
      enum "aaa-at-lldp-opaque" {
        value 1125;
        description
          "LLDP TLV";
        tailf:code-name "ENUM_aaa_attribute_type_tdl__AAA_AT_LLDP_OPAQUE_TDL";
      }
      enum "aaa-at-dhcp-opaque" {
        value 1126;
        description
          "DHCP TLV";
        tailf:code-name "ENUM_aaa_attribute_type_tdl__AAA_AT_DHCP_OPAQUE_TDL";
      }
      enum "aaa-at-mdns-opaque" {
        value 1127;
        description
          "MDNS TLV";
        tailf:code-name "ENUM_aaa_attribute_type_tdl__AAA_AT_MDNS_OPAQUE_TDL";
      }
      enum "aaa-at-sip-opaque" {
        value 1128;
        description
          "SIP TLV";
        tailf:code-name "ENUM_aaa_attribute_type_tdl__AAA_AT_SIP_OPAQUE_TDL";
      }
      enum "aaa-at-h323-opaque" {
        value 1129;
        description
          "H323 TLV";
        tailf:code-name "ENUM_aaa_attribute_type_tdl__AAA_AT_H323_OPAQUE_TDL";
      }
      enum "aaa-at-dc-profile-name" {
        value 1130;
        description
          "Device Classifier Profile Name";
        tailf:code-name "ENUM_aaa_attribute_type_tdl__AAA_AT_DC_PROFILE_NAME_TDL";
      }
      enum "aaa-at-dc-device-name" {
        value 1131;
        description
          "Device Classifier Device Name";
        tailf:code-name "ENUM_aaa_attribute_type_tdl__AAA_AT_DC_DEVICE_NAME_TDL";
      }
      enum "aaa-at-dc-device-class-tag" {
        value 1132;
        description
          "Device Classifier Device Class Tag";
        tailf:code-name "ENUM_aaa_attribute_type_tdl__AAA_AT_DC_DEVICE_CLASS_TAG_TDL";
      }
      enum "aaa-at-dc-profile-tags" {
        value 1133;
        description
          "Device Classifier Profile Tags";
        tailf:code-name "ENUM_aaa_attribute_type_tdl__AAA_AT_DC_PROFILE_TAGS_TDL";
      }
      enum "aaa-at-dc-protocol-map" {
        value 1134;
        description
          "Device Classifier Protocol Map";
        tailf:code-name "ENUM_aaa_attribute_type_tdl__AAA_AT_DC_PROTOCOL_MAP_TDL";
      }
      enum "aaa-at-dc-certainty-metric" {
        value 1135;
        description
          "Device Classifier Certainty Metric";
        tailf:code-name "ENUM_aaa_attribute_type_tdl__AAA_AT_DC_CERTAINTY_METRIC_TDL";
      }
      enum "aaa-at-dc-device-id" {
        value 1136;
        description
          "Device Classifier Certainty Metric";
        tailf:code-name "ENUM_aaa_attribute_type_tdl__AAA_AT_DC_DEVICE_ID_TDL";
      }
      enum "aaa-at-dc-opaque" {
        value 1137;
        description
          "Device Classifier Opaque";
        tailf:code-name "ENUM_aaa_attribute_type_tdl__AAA_AT_DC_OPAQUE_TDL";
      }
      enum "aaa-at-pmip6-domain-identifier" {
        value 1138;
        description
          "Proxy Mobile IPv6 Domain name";
        tailf:code-name "ENUM_aaa_attribute_type_tdl__AAA_AT_PMIP6_DOMAIN_IDENTIFIER_TDL";
      }
      enum "aaa-at-pmip6-spi-value" {
        value 1139;
        description
          "Proxy Mobile IPv6 Security Associations";
        tailf:code-name "ENUM_aaa_attribute_type_tdl__AAA_AT_PMIP6_SPI_VALUE_TDL";
      }
      enum "aaa-at-pmip6-spi-key" {
        value 1140;
        description
          "Proxy Mobile IPv6 SPI key";
        tailf:code-name "ENUM_aaa_attribute_type_tdl__AAA_AT_PMIP6_SPI_KEY_TDL";
      }
      enum "aaa-at-pmip6-fixed-ll-address" {
        value 1141;
        description
          "Proxy Mobile IPv6 fixed link local address";
        tailf:code-name "ENUM_aaa_attribute_type_tdl__AAA_AT_PMIP6_FIXED_LL_ADDRESS_TDL";
      }
      enum "aaa-at-pmip6-fixed-l2-address" {
        value 1142;
        description
          "Proxy Mobile IPv6 fixed L2 address";
        tailf:code-name "ENUM_aaa_attribute_type_tdl__AAA_AT_PMIP6_FIXED_L2_ADDRESS_TDL";
      }
      enum "aaa-at-pmip6-replay-protection" {
        value 1143;
        description
          "Proxy Mobile IPv6 replay protection type";
        tailf:code-name "ENUM_aaa_attribute_type_tdl__AAA_AT_PMIP6_REPLAY_PROTECTION_TDL";
      }
      enum "aaa-at-pmip6-timestamp-window" {
        value 1144;
        description
          "Proxy Mobile IPv6 timestamp validity window";
        tailf:code-name "ENUM_aaa_attribute_type_tdl__AAA_AT_PMIP6_TIMESTAMP_WINDOW_TDL";
      }
      enum "aaa-at-pmip6-encap-type" {
        value 1145;
        description
          "Proxy Mobile IPv6 tunnel encapsulation type";
        tailf:code-name "ENUM_aaa_attribute_type_tdl__AAA_AT_PMIP6_ENCAP_TYPE_TDL";
      }
      enum "aaa-at-pmip6-lma-identifier" {
        value 1146;
        description
          "Proxy Mobile IPv6 Local Mobility Anchor name";
        tailf:code-name "ENUM_aaa_attribute_type_tdl__AAA_AT_PMIP6_LMA_IDENTIFIER_TDL";
      }
      enum "aaa-at-pmip6-lma-v4-address" {
        value 1147;
        description
          "Proxy Mobile IPv6 Local Mobility Anchor IPv4 address";
        tailf:code-name "ENUM_aaa_attribute_type_tdl__AAA_AT_PMIP6_LMA_V4_ADDRESS_TDL";
      }
      enum "aaa-at-pmip6-lma-v6-address" {
        value 1148;
        description
          "Proxy Mobile IPv6 Local Mobility Anchor IPv6 address";
        tailf:code-name "ENUM_aaa_attribute_type_tdl__AAA_AT_PMIP6_LMA_V6_ADDRESS_TDL";
      }
      enum "aaa-at-pmip6-mag-identifier" {
        value 1149;
        description
          "Proxy Mobile IPv6 MAG name";
        tailf:code-name "ENUM_aaa_attribute_type_tdl__AAA_AT_PMIP6_MAG_IDENTIFIER_TDL";
      }
      enum "aaa-at-pmip6-mag-v4-address" {
        value 1150;
        description
          "Proxy Mobile IPv6 MAG IPv4 address";
        tailf:code-name "ENUM_aaa_attribute_type_tdl__AAA_AT_PMIP6_MAG_V4_ADDRESS_TDL";
      }
      enum "aaa-at-pmip6-mag-v6-address" {
        value 1151;
        description
          "Proxy Mobile IPv6 MAG IPv6 address";
        tailf:code-name "ENUM_aaa_attribute_type_tdl__AAA_AT_PMIP6_MAG_V6_ADDRESS_TDL";
      }
      enum "aaa-at-mn-identifier" {
        value 1152;
        description
          "Mobile Node Identifier";
        tailf:code-name "ENUM_aaa_attribute_type_tdl__AAA_AT_MN_IDENTIFIER_TDL";
      }
      enum "aaa-at-mn-multihomed" {
        value 1153;
        description
          "Mobile Node multi-homed service";
        tailf:code-name "ENUM_aaa_attribute_type_tdl__AAA_AT_MN_MULTIHOMED_TDL";
      }
      enum "aaa-at-mip6-feature-vector" {
        value 1154;
        description
          "Mobile IPv6 feature vector";
        tailf:code-name "ENUM_aaa_attribute_type_tdl__AAA_AT_MIP6_FEATURE_VECTOR_TDL";
      }
      enum "aaa-at-pmip6-home-lma-identifier" {
        value 1155;
        description
          "Proxy Mobile IPv6 MN's Home Local Mobility Anchor Identifier";
        tailf:code-name "ENUM_aaa_attribute_type_tdl__AAA_AT_PMIP6_HOME_LMA_IDENTIFIER_TDL";
      }
      enum "aaa-at-pmip6-visited-lma-identifier" {
        value 1156;
        description
          "Proxy Mobile IPv6 MN's Visited Local Mobility Anchor Identifier";
        tailf:code-name "ENUM_aaa_attribute_type_tdl__AAA_AT_PMIP6_VISITED_LMA_IDENTIFIER_TDL";
      }
      enum "aaa-at-mn-gre-encap-key" {
        value 1157;
        description
          "Mobile Nodes GRE Encap Key";
        tailf:code-name "ENUM_aaa_attribute_type_tdl__AAA_AT_MN_GRE_ENCAP_KEY_TDL";
      }
      enum "aaa-at-mn-service" {
        value 1158;
        description
          "Mobile Node's service type";
        tailf:code-name "ENUM_aaa_attribute_type_tdl__AAA_AT_MN_SERVICE_TDL";
      }
      enum "aaa-at-mn-max-hnp" {
        value 1159;
        description
          "MN's Maximum Home Network Prefixes";
        tailf:code-name "ENUM_aaa_attribute_type_tdl__AAA_AT_MN_MAX_HNP_TDL";
      }
      enum "aaa-at-pmip6-home-lma-ipv6-address" {
        value 1160;
        description
          "MN's Home Local Mobility Anchor IPv6 address";
        tailf:code-name "ENUM_aaa_attribute_type_tdl__AAA_AT_PMIP6_HOME_LMA_IPV6_ADDRESS_TDL";
      }
      enum "aaa-at-pmip6-visited-lma-ipv6-address" {
        value 1161;
        description
          "MN's Visited Local Mobility Anchor IPv6 address";
        tailf:code-name "ENUM_aaa_attribute_type_tdl__AAA_AT_PMIP6_VISITED_LMA_IPV6_ADDRESS_TDL";
      }
      enum "aaa-at-pmip6-home-lma-ipv4-address" {
        value 1162;
        description
          "MN's Home Local Mobility Anchor IPv4 address";
        tailf:code-name "ENUM_aaa_attribute_type_tdl__AAA_AT_PMIP6_HOME_LMA_IPV4_ADDRESS_TDL";
      }
      enum "aaa-at-pmip6-visited-lma-ipv4-address" {
        value 1163;
        description
          "MN's Visited Local Mobility Anchor IPv4 address";
        tailf:code-name "ENUM_aaa_attribute_type_tdl__AAA_AT_PMIP6_VISITED_LMA_IPV4_ADDRESS_TDL";
      }
      enum "aaa-at-pmip6-home-hl-prefix" {
        value 1164;
        description
          "MN's Home Prefix length";
        tailf:code-name "ENUM_aaa_attribute_type_tdl__AAA_AT_PMIP6_HOME_HL_PREFIX_TDL";
      }
      enum "aaa-at-pmip6-home-dhcp6-server-address" {
        value 1165;
        description
          "MN's Home DHCPv6 Server address";
        tailf:code-name "ENUM_aaa_attribute_type_tdl__AAA_AT_PMIP6_HOME_DHCP6_SERVER_ADDRESS_TDL";
      }
      enum "aaa-at-pmip6-visited-dhcp6-server-address" {
        value 1166;
        description
          "MN's Visited DHCPv6 Server address";
        tailf:code-name "ENUM_aaa_attribute_type_tdl__AAA_AT_PMIP6_VISITED_DHCP6_SERVER_ADDRESS_TDL";
      }
      enum "aaa-at-pmip6-home-dhcp4-server-address" {
        value 1167;
        description
          "MN's Home DHCPv4 Server address";
        tailf:code-name "ENUM_aaa_attribute_type_tdl__AAA_AT_PMIP6_HOME_DHCP4_SERVER_ADDRESS_TDL";
      }
      enum "aaa-at-pmip6-visited-dhcp4-server-address" {
        value 1168;
        description
          "MN's Visited DHCPv4 Server address";
        tailf:code-name "ENUM_aaa_attribute_type_tdl__AAA_AT_PMIP6_VISITED_DHCP4_SERVER_ADDRESS_TDL";
      }
      enum "aaa-at-pmip6-home-ipv4-hoa" {
        value 1169;
        description
          "MN's Home IPv4 address";
        tailf:code-name "ENUM_aaa_attribute_type_tdl__AAA_AT_PMIP6_HOME_IPV4_HOA_TDL";
      }
      enum "aaa-at-pmip6-visited-ipv4-hoa" {
        value 1170;
        description
          "MN's Visited IPv4 address";
        tailf:code-name "ENUM_aaa_attribute_type_tdl__AAA_AT_PMIP6_VISITED_IPV4_HOA_TDL";
      }
      enum "aaa-at-capwap-tunnel-profile-name" {
        value 1171;
        description
          "CAPWAP tunnel profile name";
        tailf:code-name "ENUM_aaa_attribute_type_tdl__AAA_AT_CAPWAP_TUNNEL_PROFILE_NAME_TDL";
      }
      enum "aaa-at-ppp-ipv4-addr-save" {
        value 1172;
        description
          "PPP IPv4 Address Saving";
        tailf:code-name "ENUM_aaa_attribute_type_tdl__AAA_AT_PPP_IPV4_ADDR_SAVE_TDL";
      }
      enum "aaa-at-app-attr" {
        value 1173;
        description
          "Application Specific Attribute defined for Connected-Apps";
        tailf:code-name "ENUM_aaa_attribute_type_tdl__AAA_AT_APP_ATTR_TDL";
      }
      enum "aaa-at-allowed-app" {
        value 1174;
        description
          "Application that a user is allowed to perform";
        tailf:code-name "ENUM_aaa_attribute_type_tdl__AAA_AT_ALLOWED_APP_TDL";
      }
      enum "aaa-at-allowed-action" {
        value 1175;
        description
          "Action that an Application is allowed to perform";
        tailf:code-name "ENUM_aaa_attribute_type_tdl__AAA_AT_ALLOWED_ACTION_TDL";
      }
      enum "aaa-at-auto-acct" {
        value 1176;
        description
          "Whether auto accounting is enabled for a user";
        tailf:code-name "ENUM_aaa_attribute_type_tdl__AAA_AT_AUTO_ACCT_TDL";
      }
      enum "aaa-at-fnf-monitor" {
        value 1177;
        description
          "FNF Monitor Name";
        tailf:code-name "ENUM_aaa_attribute_type_tdl__AAA_AT_FNF_MONITOR_TDL";
      }
      enum "aaa-at-fnf-sampler" {
        value 1178;
        description
          "FNF Sampler Name";
        tailf:code-name "ENUM_aaa_attribute_type_tdl__AAA_AT_FNF_SAMPLER_TDL";
      }
      enum "aaa-at-fnf-direction" {
        value 1179;
        description
          "Direction to apply FNF monitor";
        tailf:code-name "ENUM_aaa_attribute_type_tdl__AAA_AT_FNF_DIRECTION_TDL";
      }
      enum "aaa-at-fnf-traffic-type" {
        value 1180;
        description
          "Type of traffic to apply an FNF monitor to";
        tailf:code-name "ENUM_aaa_attribute_type_tdl__AAA_AT_FNF_TRAFFIC_TYPE_TDL";
      }
      enum "aaa-at-fnf-subtraffic-type" {
        value 1181;
        description
          "Type of sub-traffic to apply an FNF monitor to";
        tailf:code-name "ENUM_aaa_attribute_type_tdl__AAA_AT_FNF_SUBTRAFFIC_TYPE_TDL";
      }
      enum "aaa-at-rpclient-source-address" {
        value 1182;
        description
          "Radius Proxy Client Source address";
        tailf:code-name "ENUM_aaa_attribute_type_tdl__AAA_AT_RPCLIENT_SOURCE_ADDRESS_TDL";
      }
      enum "aaa-at-mn-apn" {
        value 1183;
        description
          "Mobile Node Access Point Network";
        tailf:code-name "ENUM_aaa_attribute_type_tdl__AAA_AT_MN_APN_TDL";
      }
      enum "aaa-at-mn-network" {
        value 1184;
        description
          "Mobile Node Network";
        tailf:code-name "ENUM_aaa_attribute_type_tdl__AAA_AT_MN_NETWORK_TDL";
      }
      enum "aaa-at-idle-timeout-direction" {
        value 1185;
        description
          "Direction of Idle timeout";
        tailf:code-name "ENUM_aaa_attribute_type_tdl__AAA_AT_IDLE_TIMEOUT_DIRECTION_TDL";
      }
      enum "aaa-at-rem-lifetime" {
        value 1186;
        description
          "Remaining Lifetime";
        tailf:code-name "ENUM_aaa_attribute_type_tdl__AAA_AT_REM_LIFETIME_TDL";
      }
      enum "aaa-at-user-type" {
        value 1187;
        description
          "Type of User";
        tailf:code-name "ENUM_aaa_attribute_type_tdl__AAA_AT_USER_TYPE_TDL";
      }
      enum "aaa-at-device-capability" {
        value 1188;
        description
          "Device capability";
        tailf:code-name "ENUM_aaa_attribute_type_tdl__AAA_AT_DEVICE_CAPABILITY_TDL";
      }
      enum "aaa-at-route-set" {
        value 1189;
        description
          "Route set parameters";
        tailf:code-name "ENUM_aaa_attribute_type_tdl__AAA_AT_ROUTE_SET_TDL";
      }
      enum "aaa-at-chargeable-user-identity" {
        value 1190;
        description
          "Chargeable User Identity";
        tailf:code-name "ENUM_aaa_attribute_type_tdl__AAA_AT_CHARGEABLE_USER_IDENTITY_TDL";
      }
      enum "aaa-at-cisco-service-selection" {
        value 1191;
        description
          "Service Identifier";
        tailf:code-name "ENUM_aaa_attribute_type_tdl__AAA_AT_CISCO_SERVICE_SELECTION_TDL";
      }
      enum "aaa-at-cisco-mobile-node-identifier" {
        value 1192;
        description
          "Mobile Node Identifier";
        tailf:code-name "ENUM_aaa_attribute_type_tdl__AAA_AT_CISCO_MOBILE_NODE_IDENTIFIER_TDL";
      }
      enum "aaa-at-cisco-wlan-ssid" {
        value 1193;
        description
          "SSID of the Access Point";
        tailf:code-name "ENUM_aaa_attribute_type_tdl__AAA_AT_CISCO_WLAN_SSID_TDL";
      }
      enum "aaa-at-cisco-msisdn" {
        value 1194;
        description
          "Mobile Subscriber ISDN Number";
        tailf:code-name "ENUM_aaa_attribute_type_tdl__AAA_AT_CISCO_MSISDN_TDL";
      }
      enum "aaa-at-cisco-mn-service" {
        value 1195;
        description
          "Mobile Node Service Type";
        tailf:code-name "ENUM_aaa_attribute_type_tdl__AAA_AT_CISCO_MN_SERVICE_TDL";
      }
      enum "aaa-at-cisco-mpc-protocol-interface" {
        value 1196;
        description
          "Protocol Interface to be used for interfacing with MPC";
        tailf:code-name "ENUM_aaa_attribute_type_tdl__AAA_AT_CISCO_MPC_PROTOCOL_INTERFACE_TDL";
      }
      enum "aaa-at-cisco-multihoming-support" {
        value 1197;
        description
          "Enable/Disable Multihoming support for mobile node";
        tailf:code-name "ENUM_aaa_attribute_type_tdl__AAA_AT_CISCO_MULTIHOMING_SUPPORT_TDL";
      }
      enum "aaa-at-cisco-uplink-gre-key" {
        value 1198;
        description
          "32-bit GRE Key to be used on the uplink path";
        tailf:code-name "ENUM_aaa_attribute_type_tdl__AAA_AT_CISCO_UPLINK_GRE_KEY_TDL";
      }
      enum "aaa-at-cisco-downlink-gre-key" {
        value 1199;
        description
          "32-bit GRE Key to be used on the downlink path";
        tailf:code-name "ENUM_aaa_attribute_type_tdl__AAA_AT_CISCO_DOWNLINK_GRE_KEY_TDL";
      }
      enum "aaa-at-cisco-url-redirect" {
        value 1200;
        description
          "HTTP URL of the Captive Portal";
        tailf:code-name "ENUM_aaa_attribute_type_tdl__AAA_AT_CISCO_URL_REDIRECT_TDL";
      }
      enum "aaa-at-cisco-url-redirect-acl" {
        value 1201;
        description
          "The specific Redirect rule";
        tailf:code-name "ENUM_aaa_attribute_type_tdl__AAA_AT_CISCO_URL_REDIRECT_ACL_TDL";
      }
      enum "aaa-at-cisco-home-lma-ipv6-address" {
        value 1202;
        description
          "Mobile node's Home Local Mobility Anchor IPv6 address";
        tailf:code-name "ENUM_aaa_attribute_type_tdl__AAA_AT_CISCO_HOME_LMA_IPV6_ADDRESS_TDL";
      }
      enum "aaa-at-cisco-visited-lma-ipv6-address" {
        value 1203;
        description
          "Mobile node's Visited Local Mobility Anchor IPv6 address";
        tailf:code-name "ENUM_aaa_attribute_type_tdl__AAA_AT_CISCO_VISITED_LMA_IPV6_ADDRESS_TDL";
      }
      enum "aaa-at-cisco-home-lma-ipv4-address" {
        value 1204;
        description
          "Mobile node's Home Local Mobility Anchor IPv4 address";
        tailf:code-name "ENUM_aaa_attribute_type_tdl__AAA_AT_CISCO_HOME_LMA_IPV4_ADDRESS_TDL";
      }
      enum "aaa-at-cisco-visited-lma-ipv4-address" {
        value 1205;
        description
          "Mobile node's Visited Local Mobility Anchor IPv4 address";
        tailf:code-name "ENUM_aaa_attribute_type_tdl__AAA_AT_CISCO_VISITED_LMA_IPV4_ADDRESS_TDL";
      }
      enum "aaa-at-cisco-home-ipv4-home-address" {
        value 1206;
        description
          "Mobile node's Home IPv4 address";
        tailf:code-name "ENUM_aaa_attribute_type_tdl__AAA_AT_CISCO_HOME_IPV4_HOME_ADDRESS_TDL";
      }
      enum "aaa-at-cisco-visited-ipv4-home-address" {
        value 1207;
        description
          "Mobile node's Visited IPv4 address";
        tailf:code-name "ENUM_aaa_attribute_type_tdl__AAA_AT_CISCO_VISITED_IPV4_HOME_ADDRESS_TDL";
      }
      enum "aaa-at-target-scope" {
        value 1208;
        description
          "The scope of the target for feature application";
        tailf:code-name "ENUM_aaa_attribute_type_tdl__AAA_AT_TARGET_SCOPE_TDL";
      }
      enum "aaa-at-roaming-info" {
        value 1209;
        description
          "Information about a roaming event";
        tailf:code-name "ENUM_aaa_attribute_type_tdl__AAA_AT_ROAMING_INFO_TDL";
      }
      enum "aaa-at-rbacl-monitor-all" {
        value 1210;
        description
          "Config from server for CTS Role-Based ACL Monitor mode";
        tailf:code-name "ENUM_aaa_attribute_type_tdl__AAA_AT_RBACL_MONITOR_ALL_TDL";
      }
      enum "aaa-at-cisco-access-vrf-id" {
        value 1211;
        description
          "ACCESS Virtual Route Forwarder ID";
        tailf:code-name "ENUM_aaa_attribute_type_tdl__AAA_AT_CISCO_ACCESS_VRF_ID_TDL";
      }
      enum "aaa-at-cisco-apn-vrf-id" {
        value 1212;
        description
          "APN Virtual Route Forwarder ID";
        tailf:code-name "ENUM_aaa_attribute_type_tdl__AAA_AT_CISCO_APN_VRF_ID_TDL";
      }
      enum "aaa-at-rp-eapuser-ignore-open-session" {
        value 1213;
        description
          "Ignored Open Radius Accounting For Active Authenticated Session";
        tailf:code-name "ENUM_aaa_attribute_type_tdl__AAA_AT_RP_EAPUSER_IGNORE_OPEN_SESSION_TDL";
      }
      enum "aaa-at-cisco-tunnel-if-handle" {
        value 1214;
        description
          "Mobile tunnel interface handle";
        tailf:code-name "ENUM_aaa_attribute_type_tdl__AAA_AT_CISCO_TUNNEL_IF_HANDLE_TDL";
      }
      enum "aaa-at-cisco-mobility-core-mtu" {
        value 1215;
        description
          "MTU towards Mobility core";
        tailf:code-name "ENUM_aaa_attribute_type_tdl__AAA_AT_CISCO_MOBILITY_CORE_MTU_TDL";
      }
      enum "aaa-at-cisco-if-adjacency-handle" {
        value 1216;
        description
          "Mobile tunnel interface adjacency";
        tailf:code-name "ENUM_aaa_attribute_type_tdl__AAA_AT_CISCO_IF_ADJACENCY_HANDLE_TDL";
      }
      enum "aaa-at-cisco-teid-enable" {
        value 1217;
        description
          "Mobile tunnel endpoint enable";
        tailf:code-name "ENUM_aaa_attribute_type_tdl__AAA_AT_CISCO_TEID_ENABLE_TDL";
      }
      enum "aaa-at-cisco-upstream-key-teid" {
        value 1218;
        description
          "Mobile upstream key Tunnel endpoint identifier";
        tailf:code-name "ENUM_aaa_attribute_type_tdl__AAA_AT_CISCO_UPSTREAM_KEY_TEID_TDL";
      }
      enum "aaa-at-cisco-downstream-key-teid" {
        value 1219;
        description
          "Mobile downstream key Tunnel endpoint identifier";
        tailf:code-name "ENUM_aaa_attribute_type_tdl__AAA_AT_CISCO_DOWNSTREAM_KEY_TEID_TDL";
      }
      enum "aaa-at-default-ipv4-gw" {
        value 1220;
        description
          "The default gateway for the mobile user";
        tailf:code-name "ENUM_aaa_attribute_type_tdl__AAA_AT_DEFAULT_IPV4_GW_TDL";
      }
      enum "aaa-at-default-gw-mac-address" {
        value 1221;
        description
          "MAC address of mobile node's default gateway";
        tailf:code-name "ENUM_aaa_attribute_type_tdl__AAA_AT_DEFAULT_GW_MAC_ADDRESS_TDL";
      }
      enum "aaa-at-mobile-ipv4-address" {
        value 1222;
        description
          "The IP address for the Mobile user";
        tailf:code-name "ENUM_aaa_attribute_type_tdl__AAA_AT_MOBILE_IPV4_ADDRESS_TDL";
      }
      enum "aaa-at-mobile-ipv4-netmask" {
        value 1223;
        description
          "The IP netmask for the mobile user";
        tailf:code-name "ENUM_aaa_attribute_type_tdl__AAA_AT_MOBILE_IPV4_NETMASK_TDL";
      }
      enum "aaa-at-download-request" {
        value 1224;
        description
          "Type of Download-request";
        tailf:code-name "ENUM_aaa_attribute_type_tdl__AAA_AT_DOWNLOAD_REQUEST_TDL";
      }
      enum "aaa-at-pmip6-visited-hn-prefix" {
        value 1225;
        description
          "Visited HN Prefix";
        tailf:code-name "ENUM_aaa_attribute_type_tdl__AAA_AT_PMIP6_VISITED_HN_PREFIX_TDL";
      }
      enum "aaa-at-pmip6-home-interface-id" {
        value 1226;
        description
          "Home Interface ID";
        tailf:code-name "ENUM_aaa_attribute_type_tdl__AAA_AT_PMIP6_HOME_INTERFACE_ID_TDL";
      }
      enum "aaa-at-pmip6-visited-interface-id" {
        value 1227;
        description
          "Proxy Mobile IPv6 Visited Interface ID";
        tailf:code-name "ENUM_aaa_attribute_type_tdl__AAA_AT_PMIP6_VISITED_INTERFACE_ID_TDL";
      }
      enum "aaa-at-cts-local-db" {
        value 1228;
        description
          "CTS local DB attribute";
        tailf:code-name "ENUM_aaa_attribute_type_tdl__AAA_AT_CTS_LOCAL_DB_TDL";
      }
      enum "aaa-at-mos-con" {
        value 1229;
        description
          "MOS SCORE - conversational";
        tailf:code-name "ENUM_aaa_attribute_type_tdl__AAA_AT_MOS_CON_TDL";
      }
      enum "aaa-at-rtcp-jitter-buffer-nominal-delay" {
        value 1230;
        description
          "Nominal delay of jitter buffer for RTP Control Protocol";
        tailf:code-name "ENUM_aaa_attribute_type_tdl__AAA_AT_RTCP_JITTER_BUFFER_NOMINAL_DELAY_TDL";
      }
      enum "aaa-at-vq-total-packet-loss" {
        value 1231;
        description
          "The loss rate of total packet";
        tailf:code-name "ENUM_aaa_attribute_type_tdl__AAA_AT_VQ_TOTAL_PACKET_LOSS_TDL";
      }
      enum "aaa-at-vq-out-of-order" {
        value 1232;
        description
          "The out of order rate";
        tailf:code-name "ENUM_aaa_attribute_type_tdl__AAA_AT_VQ_OUT_OF_ORDER_TDL";
      }
      enum "aaa-at-entity-attr" {
        value 1233;
        description
          "Entity attributes";
        tailf:code-name "ENUM_aaa_attribute_type_tdl__AAA_AT_ENTITY_ATTR_TDL";
      }
      enum "aaa-at-voice-vlan" {
        value 1234;
        description
          "Voice plug-in attribute";
        tailf:code-name "ENUM_aaa_attribute_type_tdl__AAA_AT_VOICE_VLAN_TDL";
      }
      enum "aaa-at-authz-directive-local" {
        value 1235;
        description
          "Authorization Directive Local";
        tailf:code-name "ENUM_aaa_attribute_type_tdl__AAA_AT_AUTHZ_DIRECTIVE_LOCAL_TDL";
      }
      enum "aaa-at-eap-msk" {
        value 1236;
        description
          "EAP Master Session Key";
        tailf:code-name "ENUM_aaa_attribute_type_tdl__AAA_AT_EAP_MSK_TDL";
      }
      enum "aaa-at-eap-emsk" {
        value 1237;
        description
          "EAP Extended Master Session Key";
        tailf:code-name "ENUM_aaa_attribute_type_tdl__AAA_AT_EAP_EMSK_TDL";
      }
      enum "aaa-at-eap-session-id-fake" {
        value 1238;
        description
          "EAP keys session id";
        tailf:code-name "ENUM_aaa_attribute_type_tdl__AAA_AT_EAP_SESSION_ID_FAKE_TDL";
      }
      enum "aaa-at-session-linksec-secured" {
        value 1239;
        description
          "Link Security Status of the session";
        tailf:code-name "ENUM_aaa_attribute_type_tdl__AAA_AT_SESSION_LINKSEC_SECURED_TDL";
      }
      enum "aaa-at-eap-ether" {
        value 1240;
        description
          "Ether passed to linksec";
        tailf:code-name "ENUM_aaa_attribute_type_tdl__AAA_AT_EAP_ETHER_TDL";
      }
      enum "aaa-at-reroute-ipv4" {
        value 1241;
        description
          "Reroute ipv4 details";
        tailf:code-name "ENUM_aaa_attribute_type_tdl__AAA_AT_REROUTE_IPV4_TDL";
      }
      enum "aaa-at-reroute-ipv6" {
        value 1242;
        description
          "Reroute ipv6 details";
        tailf:code-name "ENUM_aaa_attribute_type_tdl__AAA_AT_REROUTE_IPV6_TDL";
      }
      enum "aaa-at-relay-session-id" {
        value 1243;
        description
          "Relay Session ID";
        tailf:code-name "ENUM_aaa_attribute_type_tdl__AAA_AT_RELAY_SESSION_ID_TDL";
      }
      enum "aaa-at-dhcp-option-82-str" {
        value 1244;
        description
          "DHCP relay info option 82 from lease query";
        tailf:code-name "ENUM_aaa_attribute_type_tdl__AAA_AT_DHCP_OPTION_82_STR_TDL";
      }
      enum "aaa-at-mobileopt-server-ipv4addr" {
        value 1245;
        description
          "IPv4 addr of the Mobile Optimization SCTP server";
        tailf:code-name "ENUM_aaa_attribute_type_tdl__AAA_AT_MOBILEOPT_SERVER_IPV4ADDR_TDL";
      }
      enum "aaa-at-mobileopt-server-port" {
        value 1246;
        description
          "SCTP port of the Mobile Optimization server";
        tailf:code-name "ENUM_aaa_attribute_type_tdl__AAA_AT_MOBILEOPT_SERVER_PORT_TDL";
      }
      enum "aaa-at-cisco-customer-identifier" {
        value 1247;
        description
          "Customer Identifier for Proxy Mobile IPv6 mobile node profile";
        tailf:code-name "ENUM_aaa_attribute_type_tdl__AAA_AT_CISCO_CUSTOMER_IDENTIFIER_TDL";
      }
      enum "aaa-at-http-opaque" {
        value 1248;
        description
          "HTTP User Agent";
        tailf:code-name "ENUM_aaa_attribute_type_tdl__AAA_AT_HTTP_OPAQUE_TDL";
      }
      enum "aaa-at-cisco-user-role" {
        value 1249;
        description
          "Specifies the User Role";
        tailf:code-name "ENUM_aaa_attribute_type_tdl__AAA_AT_CISCO_USER_ROLE_TDL";
      }
      enum "aaa-at-interface-template-name" {
        value 1250;
        description
          "Specifies the interface template to be applied";
        tailf:code-name "ENUM_aaa_attribute_type_tdl__AAA_AT_INTERFACE_TEMPLATE_NAME_TDL";
      }
      enum "aaa-at-frmd-ipv6-address" {
        value 1251;
        description
          "The IPv6 address for the user";
        tailf:code-name "ENUM_aaa_attribute_type_tdl__AAA_AT_FRMD_IPV6_ADDRESS_TDL";
      }
      enum "aaa-at-identity-session-type" {
        value 1252;
        description
          "Identity Session Type";
        tailf:code-name "ENUM_aaa_attribute_type_tdl__AAA_AT_IDENTITY_SESSION_TYPE_TDL";
      }
      enum "aaa-at-author-status" {
        value 1253;
        description
          "Identity session authorization status";
        tailf:code-name "ENUM_aaa_attribute_type_tdl__AAA_AT_AUTHOR_STATUS_TDL";
      }
      enum "aaa-at-security-violation-action" {
        value 1254;
        description
          "Identity session security violation";
        tailf:code-name "ENUM_aaa_attribute_type_tdl__AAA_AT_SECURITY_VIOLATION_ACTION_TDL";
      }
      enum "aaa-at-fqdn-acl-name" {
        value 1255;
        description
          "Specifies the FQDN ACL Name to be used";
        tailf:code-name "ENUM_aaa_attribute_type_tdl__AAA_AT_FQDN_ACL_NAME_TDL";
      }
      enum "aaa-at-vlan-autoconfig" {
        value 1256;
        description
          "VLAN Auto-configuration enable";
        tailf:code-name "ENUM_aaa_attribute_type_tdl__AAA_AT_VLAN_AUTOCONFIG_TDL";
      }
      enum "aaa-at-vlan-autoconfig-service-info" {
        value 1257;
        description
          "VLAN Auto-configuration Service Info";
        tailf:code-name "ENUM_aaa_attribute_type_tdl__AAA_AT_VLAN_AUTOCONFIG_SERVICE_INFO_TDL";
      }
      enum "aaa-at-vlan-autoconfig-command" {
        value 1258;
        description
          "Type of vlan-auto-config command";
        tailf:code-name "ENUM_aaa_attribute_type_tdl__AAA_AT_VLAN_AUTOCONFIG_COMMAND_TDL";
      }
      enum "aaa-at-vlan-autoconfig-subinterface-id" {
        value 1259;
        description
          "VLAN Auto-config Sub Interface ID";
        tailf:code-name "ENUM_aaa_attribute_type_tdl__AAA_AT_VLAN_AUTOCONFIG_SUBINTERFACE_ID_TDL";
      }
      enum "aaa-at-cpeid" {
        value 1260;
        description
          "Common Platform Enumeration ID Tag";
        tailf:code-name "ENUM_aaa_attribute_type_tdl__AAA_AT_CPEID_TDL";
      }
      enum "aaa-at-cisco-config-macro" {
        value 1261;
        description
          "Specifies the config macro to be applied";
        tailf:code-name "ENUM_aaa_attribute_type_tdl__AAA_AT_CISCO_CONFIG_MACRO_TDL";
      }
      enum "aaa-at-client-type" {
        value 1262;
        description
          "Specifies the VPN Client type";
        tailf:code-name "ENUM_aaa_attribute_type_tdl__AAA_AT_CLIENT_TYPE_TDL";
      }
      enum "aaa-at-swbidb" {
        value 1263;
        description
          "Bin-OS Software IDB";
        tailf:code-name "ENUM_aaa_attribute_type_tdl__AAA_AT_SWBIDB_TDL";
      }
      enum "aaa-at-client-iif-id" {
        value 1264;
        description
          "Client IIF-ID";
        tailf:code-name "ENUM_aaa_attribute_type_tdl__AAA_AT_CLIENT_IIF_ID_TDL";
      }
      enum "aaa-at-intf-id" {
        value 1265;
        description
          "Interface index";
        tailf:code-name "ENUM_aaa_attribute_type_tdl__AAA_AT_INTF_ID_TDL";
      }
      enum "aaa-at-auth-level" {
        value 1266;
        description
          "Authentication level";
        tailf:code-name "ENUM_aaa_attribute_type_tdl__AAA_AT_AUTH_LEVEL_TDL";
      }
      enum "aaa-at-is-basic" {
        value 1267;
        description
          "Is Basic";
        tailf:code-name "ENUM_aaa_attribute_type_tdl__AAA_AT_IS_BASIC_TDL";
      }
      enum "aaa-at-nsh-dc-tenant-id" {
        value 1268;
        description
          "IKE client tenant id";
        tailf:code-name "ENUM_aaa_attribute_type_tdl__AAA_AT_NSH_DC_TENANT_ID_TDL";
      }
      enum "aaa-at-nsh-dc-source-node-id" {
        value 1269;
        description
          "IKE client source node id";
        tailf:code-name "ENUM_aaa_attribute_type_tdl__AAA_AT_NSH_DC_SOURCE_NODE_ID_TDL";
      }
      enum "aaa-at-nsh-dc-source-interface-id" {
        value 1270;
        description
          "IKE client source interface id";
        tailf:code-name "ENUM_aaa_attribute_type_tdl__AAA_AT_NSH_DC_SOURCE_INTERFACE_ID_TDL";
      }
      enum "aaa-at-ancp-access-loop-rem-id" {
        value 1271;
        description
          "Access Node Control Protocol access loop rem ID";
        tailf:code-name "ENUM_aaa_attribute_type_tdl__AAA_AT_ANCP_ACCESS_LOOP_REM_ID_TDL";
      }
      enum "aaa-at-fqdn-webauth-acl-name" {
        value 1272;
        description
          "Specifies the FQDN WebAuth ACL Name to be used";
        tailf:code-name "ENUM_aaa_attribute_type_tdl__AAA_AT_FQDN_WEBAUTH_ACL_NAME_TDL";
      }
      enum "aaa-at-security-group-sgt-epg-table" {
        value 1273;
        description
          "Security group sgt to End Point Grouping translation table";
        tailf:code-name "ENUM_aaa_attribute_type_tdl__AAA_AT_SECURITY_GROUP_SGT_EPG_TABLE_TDL";
      }
      enum "aaa-at-security-group-sgt-epg-table-outbound" {
        value 1274;
        description
          "Security group sgt to End Point Grouping translation outbound table";
        tailf:code-name "ENUM_aaa_attribute_type_tdl__AAA_AT_SECURITY_GROUP_SGT_EPG_TABLE_OUTBOUND_TDL";
      }
      enum "aaa-at-security-group-sg-epg-table-info" {
        value 1275;
        description
          "SG-End Point Grouping Translation table entry, format <sgt>-<gen-id>-<flag>-<End Point Grouping Class-Id>-<gen-id><VRF-Name>-<gen-id>";
        tailf:code-name "ENUM_aaa_attribute_type_tdl__AAA_AT_SECURITY_GROUP_SG_EPG_TABLE_INFO_TDL";
      }
      enum "aaa-at-security-group-default-epg-table" {
        value 1276;
        description
          "Security group default End Point Grouping table to derive End Point Grouping";
        tailf:code-name "ENUM_aaa_attribute_type_tdl__AAA_AT_SECURITY_GROUP_DEFAULT_EPG_TABLE_TDL";
      }
      enum "aaa-at-security-group-default-epg-table-outbound" {
        value 1277;
        description
          "Security group default End Point Grouping table to derive outbound End Point Grouping";
        tailf:code-name "ENUM_aaa_attribute_type_tdl__AAA_AT_SECURITY_GROUP_DEFAULT_EPG_TABLE_OUTBOUND_TDL";
      }
      enum "aaa-at-security-group-default-epg-table-info" {
        value 1278;
        description
          "Default End Point Grouping Translation table entry, format <End Point Grouping Class-Id>-<gen-id><VRF-Name>-<gen-id>";
        tailf:code-name "ENUM_aaa_attribute_type_tdl__AAA_AT_SECURITY_GROUP_DEFAULT_EPG_TABLE_INFO_TDL";
      }
      enum "aaa-at-security-group-default-sgt-table" {
        value 1279;
        description
          "Security group default SGT table to derive sgt";
        tailf:code-name "ENUM_aaa_attribute_type_tdl__AAA_AT_SECURITY_GROUP_DEFAULT_SGT_TABLE_TDL";
      }
      enum "aaa-at-security-group-default-sgt-table-outbound" {
        value 1280;
        description
          "Security group default SGT table to derive outbound sgt";
        tailf:code-name "ENUM_aaa_attribute_type_tdl__AAA_AT_SECURITY_GROUP_DEFAULT_SGT_TABLE_OUTBOUND_TDL";
      }
      enum "aaa-at-security-group-default-sgt-table-info" {
        value 1281;
        description
          "Default SGT Translation table entry, format <sgt>-<gen-id><VRF-Name>-<gen-id>";
        tailf:code-name "ENUM_aaa_attribute_type_tdl__AAA_AT_SECURITY_GROUP_DEFAULT_SGT_TABLE_INFO_TDL";
      }
      enum "aaa-at-security-group-sg-epg-translation-return-code" {
        value 1282;
        description
          "SG-End Point Grouping Translation feature status on ISE";
        tailf:code-name "ENUM_aaa_attribute_type_tdl__AAA_AT_SECURITY_GROUP_SG_EPG_TRANSLATION_RETURN_CODE_TDL";
      }
      enum "aaa-at-security-group-default-sgt-scalar" {
        value 1283;
        description
          "SG-End Point Grouping Translation default SGT scalar value";
        tailf:code-name "ENUM_aaa_attribute_type_tdl__AAA_AT_SECURITY_GROUP_DEFAULT_SGT_SCALAR_TDL";
      }
      enum "aaa-at-web-secure-acl" {
        value 1284;
        description
          "web secure acl";
        tailf:code-name "ENUM_aaa_attribute_type_tdl__AAA_AT_WEB_SECURE_ACL_TDL";
      }
      enum "aaa-at-delegated-ipv4-prefix" {
        value 1285;
        description
          "Delegated IPv4 Prefix";
        tailf:code-name "ENUM_aaa_attribute_type_tdl__AAA_AT_DELEGATED_IPV4_PREFIX_TDL";
      }
      enum "aaa-at-service-selection" {
        value 1286;
        description
          "Service Selection";
        tailf:code-name "ENUM_aaa_attribute_type_tdl__AAA_AT_SERVICE_SELECTION_TDL";
      }
      enum "aaa-at-pmip6-mobile-node-identifier" {
        value 1287;
        description
          "Mobile Node Identifier";
        tailf:code-name "ENUM_aaa_attribute_type_tdl__AAA_AT_PMIP6_MOBILE_NODE_IDENTIFIER_TDL";
      }
      enum "aaa-at-coa-push" {
        value 1288;
        description
          "coa-push";
        tailf:code-name "ENUM_aaa_attribute_type_tdl__AAA_AT_COA_PUSH_TDL";
      }
      enum "aaa-at-anchor-vlan-id" {
        value 1289;
        description
          "anchor-vlan";
        tailf:code-name "ENUM_aaa_attribute_type_tdl__AAA_AT_ANCHOR_VLAN_ID_TDL";
      }
      enum "aaa-at-route-redistribute" {
        value 1290;
        description
          "Redistribute routes from routing protocols";
        tailf:code-name "ENUM_aaa_attribute_type_tdl__AAA_AT_ROUTE_REDISTRIBUTE_TDL";
      }
      enum "aaa-at-bsn-ipv6-acl-name" {
        value 1291;
        description
          "IPV6 ACL Name";
        tailf:code-name "ENUM_aaa_attribute_type_tdl__AAA_AT_BSN_IPV6_ACL_NAME_TDL";
      }
      enum "aaa-at-psk" {
        value 1292;
        description
          "Pre-Shared Key";
        tailf:code-name "ENUM_aaa_attribute_type_tdl__AAA_AT_PSK_TDL";
      }
      enum "aaa-at-psk-mode" {
        value 1293;
        description
          "PSK mode";
        tailf:code-name "ENUM_aaa_attribute_type_tdl__AAA_AT_PSK_MODE_TDL";
      }
      enum "aaa-at-nas-identifier-wireless" {
        value 1294;
        description
          "A string identifying the NAS in Authentication and Accounting Packets";
        tailf:code-name "ENUM_aaa_attribute_type_tdl__AAA_AT_NAS_IDENTIFIER_WIRELESS";
      }
      enum "aaa-at-ericssion-rtts-estm-thrhput" {
        value 1295;
        description
          "Ericsson RTTS Estimated Throughput";
        tailf:code-name "ENUM_aaa_attribute_type_tdl__AAA_AT_ERICSSON_RTTS_ESTM_THRHPUT";
      }
      enum "aaa-at-ericsson-rtts-result" {
        value 1296;
        description
          "Ericsson RTTS Result";
        tailf:code-name "ENUM_aaa_attribute_type_tdl__AAA_AT_ERICSSON_RTTS_RESULT";
      }
      enum "aaa-at-ericsson-rtts-bckoff-tmr" {
        value 1297;
        description
          "Ericsson RTTS Backoff Timer";
        tailf:code-name "ENUM_aaa_attribute_type_tdl__AAA_AT_ERICSSON_RTTS_BCKOFF_TMR";
      }
      enum "aaa-at-ericsson-rtts-reestm-period" {
        value 1298;
        description
          "Ericsson RTTS Re-estimation Period";
        tailf:code-name "ENUM_aaa_attribute_type_tdl__AAA_AT_ERICSSON_RTTS_REESTM_PERIOD";
      }
      enum "aaa-at-ericsson-rtts-reestm-bel-thrhput" {
        value 1299;
        description
          "Ericsson RTTS Re-estimate When Below Throughput";
        tailf:code-name "ENUM_aaa_attribute_type_tdl__AAA_AT_ERICSSON_RTTS_REESTM_BEL_THRHPUT";
      }
      enum "aaa-at-ericsson-rtts-reestm-keepalive-num" {
        value 1300;
        description
          "Ericsson RTTS Re-estimate Keepalive Number";
        tailf:code-name "ENUM_aaa_attribute_type_tdl__AAA_AT_ERICSSON_RTTS_REESTM_KEEPALIVE_NUM";
      }
      enum "aaa-at-ericsson-rtts-early-lift-thrput-thrhold" {
        value 1301;
        description
          "Ericsson RTTS Early Lift Throughput Threshold";
        tailf:code-name "ENUM_aaa_attribute_type_tdl__AAA_AT_ERICSSON_RTTS_EARLY_LIFT_THRPUT_THRHOLD";
      }
      enum "aaa-at-bsn-data-bs-average-contract-up" {
        value 1302;
        description
          "Data Bandwidth Average Contract Upstream";
        tailf:code-name "ENUM_aaa_attribute_type_tdl__AAA_AT_BSN_DATA_BW_AVERAGE_CONTRACT_UP";
      }
      enum "aaa-at-bsn-real-time-bw-average-contract-up" {
        value 1303;
        description
          "RealTime Bandwidth Average Contract Upstream";
        tailf:code-name "ENUM_aaa_attribute_type_tdl__AAA_AT_BSN_REAL_TIME_BW_AVERAGE_CONTRACT_UP";
      }
      enum "aaa-at-bsn-data-bw-burst-contract-up" {
        value 1304;
        description
          "Data Bandwidth Burst Contract Upstream";
        tailf:code-name "ENUM_aaa_attribute_type_tdl__AAA_AT_BSN_DATA_BW_BURST_CONTRACT_UP";
      }
      enum "aaa-at-bsn-real-time-bw-burst-contract-up" {
        value 1305;
        description
          "RealTime Bandwidth Burst Contract Upstream";
        tailf:code-name "ENUM_aaa_attribute_type_tdl__AAA_AT_BSN_REAL_TIME_BW_BURST_CONTRACT_UP";
      }
      enum "aaa-at-opendns-param" {
        value 1306;
        description
          "Open DNS profiling option under wireless policy";
        tailf:code-name "ENUM_aaa_attribute_type_tdl__AAA_AT_OPENDNS_PARAM";
      }
      enum "aaa-at-url-filter-preauth" {
        value 1307;
        description
          "Pre-authentication URL filter";
        tailf:code-name "ENUM_aaa_attribute_type_tdl__AAA_AT_URL_FILTER_PREAUTH_TDL";
      }
      enum "aaa-at-url-filter-postauth" {
        value 1308;
        description
          "Post-authentication URL filter";
        tailf:code-name "ENUM_aaa_attribute_type_tdl__AAA_AT_URL_FILTER_POSTAUTH_TDL";
      }
      enum "aaa-at-primary-tgw-ip" {
        value 1309;
        description
          "Primary tunnel gateway IP address";
        tailf:code-name "ENUM_aaa_attribute_type_tdl__AAA_AT_PRIMARY_TGW_IP_TDL";
      }
      enum "aaa-at-secondary-tgw-ip" {
        value 1310;
        description
          "Secondary tunnel gateway IP address";
        tailf:code-name "ENUM_aaa_attribute_type_tdl__AAA_AT_SECONDARY_TGW_IP_TDL";
      }
      enum "aaa-at-gw-domain-name" {
        value 1311;
        description
          "Tunnel gateway domain name";
        tailf:code-name "ENUM_aaa_attribute_type_tdl__AAA_AT_GW_DOMAIN_NAME_TDL";
      }
      enum "aaa-at-eogre-vlan" {
        value 1312;
        description
          "User VLAN id for EoGRE tunneling";
        tailf:code-name "ENUM_aaa_attribute_type_tdl__AAA_AT_EOGRE_VLAN_TDL";
      }
      enum "aaa-at-mdns-profile-name" {
        value 1313;
        description
          "Used as mdns policy name in case of AAA override";
        tailf:code-name "ENUM_aaa_attribute_type_tdl__AAA_AT_MDNS_PROFILE_NAME_TDL";
      }
      enum "aaa-at-wfa-subscription-remediation" {
        value 1314;
        description
          "WiFi Alliance subscription remediation";
        tailf:code-name "ENUM_aaa_attribute_type_tdl__AAA_ATT_WFA_SUBSCRIPTION_REMEDIATION_TDL";
      }
      enum "aaa-at-wfa-ap-version" {
        value 1315;
        description
          "WiFi Alliance AP version";
        tailf:code-name "ENUM_aaa_attribute_type_tdl__AAA_ATT_WFA_AP_VERSION_TDL";
      }
      enum "aaa-at-wfa-mobile-device-version" {
        value 1316;
        description
          "WiFi Alliance mobile device version";
        tailf:code-name "ENUM_aaa_attribute_type_tdl__AAA_ATT_WFA_MOBILE_DEVICE_VERSION_TDL";
      }
      enum "aaa-at-wfa-deauthentication-request" {
        value 1317;
        description
          "WiFi Alliance deauthentication request";
        tailf:code-name "ENUM_aaa_attribute_type_tdl__AAA_ATT_WFA_DEAUTHENTICATION_REQUEST_TDL";
      }
      enum "aaa-at-wfa-session-information" {
        value 1318;
        description
          "WiFi Alliance session information";
        tailf:code-name "ENUM_aaa_attribute_type_tdl__AAA_ATT_WFA_SESSION_INFORMATION_TDL";
      }
      enum "aaa-at-wfa-roaming-consortium" {
        value 1319;
        description
          "WiFi Alliance roaming consortium information";
        tailf:code-name "ENUM_aaa_attribute_type_tdl__AAA_ATT_WFA_ROAMING_CONSORTIUM_TDL";
      }
      enum "aaa-at-wfa-tc-filename" {
        value 1320;
        description
          "WiFi Alliance terms and conditions filename";
        tailf:code-name "ENUM_aaa_attribute_type_tdl__AAA_ATT_WFA_TC_FILENAME_TDL";
      }
      enum "aaa-at-wfa-tc-filtering" {
        value 1321;
        description
          "WiFi Alliance terms and conditions filtering";
        tailf:code-name "ENUM_aaa_attribute_type_tdl__AAA_ATT_WFA_TC_FILTERING_TDL";
      }
      enum "aaa-at-wfa-timestamp" {
        value 1322;
        description
          "WiFi Alliance timestamp";
        tailf:code-name "ENUM_aaa_attribute_type_tdl__AAA_ATT_WFA_TIMESTAMP_TDL";
      }
      enum "aaa-at-dhcpv6-opaque" {
        value 1323;
        description
          "DHCPv6 TLV";
        tailf:code-name "ENUM_aaa_attribute_type_tdl__AAA_AT_DHCPV6_OPAQUE";
      }
      enum "aaa-at-cts-pac-capability" {
        value 1324;
        description
          "Include CTS PAC Capability";
        tailf:code-name "ENUM_aaa_attribute_type_tdl__AAA_AT_CTS_PAC_CAPABILITY";
      }
      enum "aaa-at-redirect-append-client-mac" {
        value 1325;
        description
          "Append client Mac Address in the URL";
        tailf:code-name "ENUM_aaa_attribute_type_tdl__AAA_AT_URL_REDIRECT_APPEND_CLIENT_MAC_TDL";
      }
      enum "aaa-at-url-redirect-append-switch-mac" {
        value 1326;
        description
          "Append switch Mac Address in the URL";
        tailf:code-name "ENUM_aaa_attribute_type_tdl__AAA_AT_URL_REDIRECT_APPEND_SWITCH_MAC_TDL";
      }
      enum "aaa-at-dns-acl-preauth" {
        value 1327;
        description
          "Pre-authentication DNS ACL";
        tailf:code-name "ENUM_aaa_attribute_type_tdl__AAA_AT_DNS_ACL_PREAUTH_TDL";
      }
      enum "aaa-at-dns-acl" {
        value 1328;
        description
          "DNS ACL";
        tailf:code-name "ENUM_aaa_attribute_type_tdl__AAA_AT_DNS_ACL_TDL";
      }
      enum "aaa-at-private-group-id" {
        value 1329;
        description
          "Windows Private Network Group ID";
        tailf:code-name "ENUM_aaa_attribute_type_tdl__AAA_AT_PRIVATE_GROUP_ID_TDL";
      }
      enum "aaa-at-private-group-name" {
        value 1330;
        description
          "Windows Private Network Group name";
        tailf:code-name "ENUM_aaa_attribute_type_tdl__AAA_AT_PRIVATE_GROUP_NAME_TDL";
      }
      enum "aaa-at-private-group-owner" {
        value 1331;
        description
          "Windows Private Network Group owner";
        tailf:code-name "ENUM_aaa_attribute_type_tdl__AAA_AT_PRIVATE_GROUP_OWNER_TDL";
      }
      enum "aaa-at-fqdn-domain-list" {
        value 1332;
        description
          "FQDN profile list for MUD";
        tailf:code-name "ENUM_aaa_attribute_type_tdl__AAA_AT_FQDN_DOMAIN_LIST";
      }
      enum "aaa-at-fqdn-domain-url" {
        value 1333;
        description
          "Domain names as part of download";
        tailf:code-name "ENUM_aaa_attribute_type_tdl__AAA_AT_FQDN_DOMAIN_URL";
      }
      enum "aaa-at-fqdn-domain-acl-name" {
        value 1334;
        description
          "FQDN acl for MUD";
        tailf:code-name "ENUM_aaa_attribute_type_tdl__AAA_AT_FQDN_DOMAIN_ACL_NAME";
      }
      enum "aaa-at-cts-sgt-acct" {
        value 1335;
        description
          "Cisco trustsec SGT for accounting";
        tailf:code-name "ENUM_aaa_attribute_type_tdl__AAA_AT_CTS_SGT_ACCT";
      }
      enum "aaa-at-cts-vn-acct" {
        value 1336;
        description
          "Cisco trustsec VRF name for accounting";
        tailf:code-name "ENUM_aaa_attribute_type_tdl__AAA_AT_CTS_VN_ACCT";
      }
      enum "aaa-at-device-analytics" {
        value 1337;
        description
          "Attribute for device classification";
        tailf:code-name "ENUM_aaa_attribute_type_tdl__AAA_AT_DEVICE_ANALYTICS";
      }
      enum "aaa-at-wfa-tc-url" {
        value 1338;
        description
          "WiFi Alliance terms and conditions URL";
        tailf:code-name "ENUM_aaa_attribute_type_tdl__AAA_ATT_WFA_TC_URL_TDL";
      }
      enum "aaa-at-server-ipv4" {
        value 1339;
        description
          "Support multiple IPv4 addresses per server";
        tailf:code-name "ENUM_aaa_attribute_type_tdl__AAA_AT_SERVER_IPV4";
      }
      enum "aaa-at-server-ipv6" {
        value 1340;
        description
          "Support multiple IPv6 addresses per server";
        tailf:code-name "ENUM_aaa_attribute_type_tdl__AAA_AT_SERVER_IPV6";
      }
    }
    description
      "AAA Attribute Type";
  }

  grouping aaa-protocol-type {
    description
      "AAA Protocol Type";
    leaf protocol {
      type aaa-types:protocol-type;
      description
        "Protocol value";
    }
  }

  grouping aaa-service-type {
    description
      "AAA Service Type";
    leaf svc-type {
      type aaa-types:serv-type;
      description
        "Service value";
    }
  }

  grouping __yangpp_metadata {
    description
      "Internal metadata for this module and imported modules";
  }

  container gnmi-model-data {
    description
      "This container makes accessible the information necessary to respond to a GNMI Capabilities RPC";
    tailf:hidden "full";
    tailf:meta-data "module-name" {
      tailf:meta-value "Cisco-IOS-XE-aaa-types";
    }
    tailf:meta-data "organization" {
      tailf:meta-value "Cisco Systems, Inc.";
    }
    tailf:meta-data "semver" {
      tailf:meta-value "2020-03-01";
    }
  }
}
