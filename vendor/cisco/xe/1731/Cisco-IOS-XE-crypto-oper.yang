module Cisco-IOS-XE-crypto-oper {
  yang-version 1;
  namespace "http://cisco.com/ns/yang/Cisco-IOS-XE-crypto-oper";
  prefix crypto-ios-xe-oper;
  import ietf-inet-types {
    prefix inet;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for crypto operational data.
     Copyright (c) 2017-2020 by Cisco Systems, Inc.
     All rights reserved.";

  revision 2020-07-01 {
    description
      "- Added IPSEC policy statistics";
    reference "0.0.0";
    cisco-semver:module-version "0.0.0";
    cisco-semver-internal:os-version "17.3.1";
  }
  revision 2019-05-01 {
    description
      "- Added info for Crypto Export Restrictions.
       - Added semantic version";
    reference "1.1.0";
    cisco-semver:module-version "1.1.0";
  }
  revision 2018-12-18 {
    description
      "Initial revision";
    reference "1.0.0";
    cisco-semver:module-version "1.0.0";
  }

  typedef crypto-dir-type {
    type enumeration {
      enum "crypto-dir-inbound" {
        value 0;
        description
          "Inbound direction";
        tailf:code-name "ENUM_crypto_dir_type_CRYPTO_DIR_INBOUND";
      }
      enum "crypto-dir-outbound" {
        value 1;
        description
          "Outbound direction";
        tailf:code-name "ENUM_crypto_dir_type_CRYPTO_DIR_OUTBOUND";
      }
    }
    description
      "Traffic direction";
  }

  typedef crypto-prot-type {
    type enumeration {
      enum "crypto-prot-esp" {
        value 0;
        description
          "ESP protocol";
        tailf:code-name "ENUM_crypto_prot_type_CRYPTO_PROT_ESP";
      }
      enum "crypto-prot-ah" {
        value 1;
        description
          "AH protocol";
        tailf:code-name "ENUM_crypto_prot_type_CRYPTO_PROT_AH";
      }
      enum "crypto-prot-pcp" {
        value 2;
        description
          "PCP protocol";
        tailf:code-name "ENUM_crypto_prot_type_CRYPTO_PROT_PCP";
      }
    }
    description
      "Crypto Protocol Type";
  }

  typedef crypto-dh-group-type {
    type enumeration {
      enum "crypto-dh-grouptype-none" {
        value 0;
        description
          "No DH Group";
        tailf:code-name "ENUM_crypto_dh_group_type_CRYPTO_DH_GROUPTYPE_NONE";
      }
      enum "crypto-dh-grouptype-group1" {
        value 1;
        description
          "DH group 1";
        tailf:code-name "ENUM_crypto_dh_group_type_CRYPTO_DH_GROUPTYPE_GROUP1";
      }
      enum "crypto-dh-grouptype-group2" {
        value 2;
        description
          "DH group 2";
        tailf:code-name "ENUM_crypto_dh_group_type_CRYPTO_DH_GROUPTYPE_GROUP2";
      }
      enum "crypto-dh-grouptype-group3" {
        value 3;
        description
          "DH group 3";
        tailf:code-name "ENUM_crypto_dh_group_type_CRYPTO_DH_GROUPTYPE_GROUP3";
      }
      enum "crypto-dh-grouptype-group4" {
        value 4;
        description
          "DH group 4";
        tailf:code-name "ENUM_crypto_dh_group_type_CRYPTO_DH_GROUPTYPE_GROUP4";
      }
      enum "crypto-dh-grouptype-group5" {
        value 5;
        description
          "DH group 5";
        tailf:code-name "ENUM_crypto_dh_group_type_CRYPTO_DH_GROUPTYPE_GROUP5";
      }
      enum "crypto-dh-grouptype-group14" {
        value 6;
        description
          "DH group 14";
        tailf:code-name "ENUM_crypto_dh_group_type_CRYPTO_DH_GROUPTYPE_GROUP14";
      }
      enum "crypto-dh-grouptype-group15" {
        value 7;
        description
          "DH group 15";
        tailf:code-name "ENUM_crypto_dh_group_type_CRYPTO_DH_GROUPTYPE_GROUP15";
      }
      enum "crypto-dh-grouptype-group16" {
        value 8;
        description
          "DH group 16";
        tailf:code-name "ENUM_crypto_dh_group_type_CRYPTO_DH_GROUPTYPE_GROUP16";
      }
      enum "crypto-dh-grouptype-group19" {
        value 9;
        description
          "DH group 19";
        tailf:code-name "ENUM_crypto_dh_group_type_CRYPTO_DH_GROUPTYPE_GROUP19";
      }
      enum "crypto-dh-grouptype-group20" {
        value 10;
        description
          "DH group 20";
        tailf:code-name "ENUM_crypto_dh_group_type_CRYPTO_DH_GROUPTYPE_GROUP20";
      }
      enum "crypto-dh-grouptype-group21" {
        value 11;
        description
          "DH group 21";
        tailf:code-name "ENUM_crypto_dh_group_type_CRYPTO_DH_GROUPTYPE_GROUP21";
      }
      enum "crypto-dh-grouptype-group24" {
        value 12;
        description
          "DH group 24";
        tailf:code-name "ENUM_crypto_dh_group_type_CRYPTO_DH_GROUPTYPE_GROUP24";
      }
    }
    description
      "DH group type";
  }

  typedef crypto-sa-status {
    type enumeration {
      enum "crypto-ipsec-sa-status-down" {
        value 0;
        description
          "IPSEC SA is down";
        tailf:code-name "ENUM_crypto_sa_status_CRYPTO_IPSEC_SA_STATUS_DOWN";
      }
      enum "crypto-sa-status-active" {
        value 1;
        description
          "SA is active";
        tailf:code-name "ENUM_crypto_sa_status_CRYPTO_SA_STATUS_ACTIVE";
      }
      enum "crypto-sa-status-standby" {
        value 2;
        description
          "SA is standby";
        tailf:code-name "ENUM_crypto_sa_status_CRYPTO_SA_STATUS_STANDBY";
      }
      enum "crypto-sa-status-pending" {
        value 3;
        description
          "SA is pending";
        tailf:code-name "ENUM_crypto_sa_status_CRYPTO_SA_STATUS_PENDING";
      }
    }
    description
      "SA status";
  }

  typedef crypto-hash-alg {
    type enumeration {
      enum "crypto-hash-alg-auth-none" {
        value 0;
        description
          "No Hash";
        tailf:code-name "ENUM_crypto_hash_alg_CRYPTO_HASH_ALG_AUTH_NONE";
      }
      enum "crypto-hash-alg-auth-hmac-md5-96" {
        value 1;
        description
          "Hash hmac md5";
        tailf:code-name "ENUM_crypto_hash_alg_CRYPTO_HASH_ALG_AUTH_HMAC_MD5_96";
      }
      enum "crypto-hash-alg-auth-hmac-sha1-96" {
        value 2;
        description
          "Hash hmac sha1 96";
        tailf:code-name "ENUM_crypto_hash_alg_CRYPTO_HASH_ALG_AUTH_HMAC_SHA1_96";
      }
      enum "crypto-hash-alg-auth-hmac-des" {
        value 3;
        description
          "Hash hmac des";
        tailf:code-name "ENUM_crypto_hash_alg_CRYPTO_HASH_ALG_AUTH_DES_MAC";
      }
      enum "crypto-hash-alg-auth-kpdk-md5" {
        value 4;
        description
          "Hash hmac kpdk md5";
        tailf:code-name "ENUM_crypto_hash_alg_CRYPTO_HASH_ALG_AUTH_KPDK_MD5";
      }
      enum "crypto-hash-alg-auth-hmac-aes-xcbc-96" {
        value 5;
        description
          "Hash hmac aes xcbc 96";
        tailf:code-name "ENUM_crypto_hash_alg_CRYPTO_HASH_ALG_AUTH_AES_XCBC_96";
      }
      enum "crypto-hash-alg-auth-hmac-sha256" {
        value 6;
        description
          "Hash hmac sha256";
        tailf:code-name "ENUM_crypto_hash_alg_CRYPTO_HASH_ALG_AUTH_HMAC_SHA256";
      }
      enum "crypto-hash-alg-auth-hmac-sha384" {
        value 7;
        description
          "Hash hmac sha384";
        tailf:code-name "ENUM_crypto_hash_alg_CRYPTO_HASH_ALG_AUTH_HMAC_SHA384";
      }
      enum "crypto-hash-alg-auth-hmac-sha512" {
        value 8;
        description
          "Hash hmac sha512";
        tailf:code-name "ENUM_crypto_hash_alg_CRYPTO_HASH_ALG_AUTH_HMAC_SHA512";
      }
    }
    description
      "HASH algorithm";
  }

  typedef crypto-auth-method {
    type enumeration {
      enum "crypto-auth-no-method" {
        value 0;
        description
          "IKEV2 No Authentication Method";
        tailf:code-name "ENUM_crypto_auth_method_CRYPTO_AUTH_NO_METHOD";
      }
      enum "crypto-ikev2-auth-rsa-sig" {
        value 1;
        description
          "IKEv2 Authentication type RSA-SIG";
        tailf:code-name "ENUM_crypto_auth_method_CRYPTO_AUTH_RSA_SIG";
      }
      enum "crypto-ikev2-auth-psk" {
        value 2;
        description
          "IKEv2 Authentication type PSK";
        tailf:code-name "ENUM_crypto_auth_method_CRYPTO_AUTH_PRESHARED";
      }
      enum "crypto-ikev2-auth-dss" {
        value 3;
        description
          "IKEv2 Authentication type DSS";
        tailf:code-name "ENUM_crypto_auth_method_CRYPTO_AUTH_DSS_SIG";
      }
      enum "crypto-ikev2-auth-ecdsa-256" {
        value 4;
        description
          "IKEv2 Authentication type ECDSA 256";
        tailf:code-name "ENUM_crypto_auth_method_CRYPTO_AUTH_ECDSA_256_SIG";
      }
      enum "crypto-ikev2-auth-ecdsa-384" {
        value 5;
        description
          "IKEv2 Authentication type ECDSA 384";
        tailf:code-name "ENUM_crypto_auth_method_CRYPTO_AUTH_ECDSA_384_SIG";
      }
      enum "crypto-ikev2-auth-anyconnect-eap" {
        value 6;
        description
          "IKEv2 Authentication type AnyConnect EAP";
        tailf:code-name "ENUM_crypto_auth_method_CRYPTO_AUTH_ANYCONNECT_EAP";
      }
      enum "crypto-ikev2-auth-eap" {
        value 7;
        description
          "IKEv2 Authentication type EAP";
        tailf:code-name "ENUM_crypto_auth_method_CRYPTO_AUTH_EAP";
      }
    }
    description
      "IKEv2 Authentication Method";
  }

  typedef crypto-encryption-alg {
    type enumeration {
      enum "crypto-encr-alg-none" {
        value 0;
        description
          "No Encryption";
        tailf:code-name "ENUM_crypto_encryption_alg_CRYPTO_ENCR_NONE";
      }
      enum "crypto-encr-alg-des-iv64" {
        value 1;
        description
          "Encryption DES IV64";
        tailf:code-name "ENUM_crypto_encryption_alg_CRYPTO_ENCR_DES_IV64";
      }
      enum "crypto-encr-alg-des" {
        value 2;
        description
          "Encryption DES";
        tailf:code-name "ENUM_crypto_encryption_alg_CRYPTO_ENCR_DES";
      }
      enum "crypto-encr-alg-3des" {
        value 3;
        description
          "Encryption 3DES";
        tailf:code-name "ENUM_crypto_encryption_alg_CRYPTO_ENCR_3DES";
      }
      enum "crypto-encr-alg-rc5" {
        value 4;
        description
          "Encryption RC5";
        tailf:code-name "ENUM_crypto_encryption_alg_CRYPTO_ENCR_RC5";
      }
      enum "crypto-encr-alg-idea" {
        value 5;
        description
          "Encryption IDEA";
        tailf:code-name "ENUM_crypto_encryption_alg_CRYPTO_ENCR_IDEA";
      }
      enum "crypto-encr-alg-cast" {
        value 6;
        description
          "Encryption CAST";
        tailf:code-name "ENUM_crypto_encryption_alg_CRYPTO_ENCR_CAST";
      }
      enum "crypto-encr-alg-blowfish" {
        value 7;
        description
          "Encryption BLOWFISH";
        tailf:code-name "ENUM_crypto_encryption_alg_CRYPTO_ENCR_BLOWFISH";
      }
      enum "crypto-encr-alg-3idea" {
        value 8;
        description
          "Encryption 3IDEA";
        tailf:code-name "ENUM_crypto_encryption_alg_CRYPTO_ENCR_3IDEA";
      }
      enum "crypto-encr-alg-iv32" {
        value 9;
        description
          "Encryption IV32";
        tailf:code-name "ENUM_crypto_encryption_alg_CRYPTO_ENCR_DES_IV32";
      }
      enum "crypto-encr-alg-rc4" {
        value 10;
        description
          "Encryption RC4";
        tailf:code-name "ENUM_crypto_encryption_alg_CRYPTO_ENCR_RC4";
      }
      enum "crypto-encr-alg-null" {
        value 11;
        description
          "Encryption Null";
        tailf:code-name "ENUM_crypto_encryption_alg_CRYPTO_ENCR_NULL";
      }
      enum "crypto-encr-alg-aes-cbc" {
        value 12;
        description
          "Encryption AES CBC";
        tailf:code-name "ENUM_crypto_encryption_alg_CRYPTO_ENCR_AES_CBC";
      }
      enum "crypto-encr-alg-aes-ctr" {
        value 13;
        description
          "Encryption AES CTR";
        tailf:code-name "ENUM_crypto_encryption_alg_CRYPTO_ENCR_AES_CTR";
      }
      enum "crypto-encr-alg-aes-gcm" {
        value 14;
        description
          "Encryption AES GCM";
        tailf:code-name "ENUM_crypto_encryption_alg_CRYPTO_ENCR_AES_GCM";
      }
      enum "crypto-encr-alg-aes-gmac" {
        value 15;
        description
          "Encryption AES GMAC";
        tailf:code-name "ENUM_crypto_encryption_alg_CRYPTO_ENCR_AES_GMAC";
      }
    }
    description
      "Encryption algorithm";
  }

  typedef crypto-policy-notify-type {
    type enumeration {
      enum "crypto-notify-rp" {
        value 0;
        description
          "Notify RP";
        tailf:code-name "ENUM_crypto_policy_notify_type_CRYPTO_POLICY_NOTIFY_NOTIFY_RP";
      }
      enum "crypto-notify-sa-dead" {
        value 1;
        description
          "SA dead";
        tailf:code-name "ENUM_crypto_policy_notify_type_CRYPTO_POLICY_NOTIFY_SA_DEAD";
      }
      enum "crypto-notify-sa-soft-lifetime" {
        value 2;
        description
          "SA soft lifetime";
        tailf:code-name "ENUM_crypto_policy_notify_type_CRYPTO_POLICY_NOTIFY_SA_SOFT_LIFE";
      }
      enum "crypto-notify-idle-timer" {
        value 3;
        description
          "Idle timer";
        tailf:code-name "ENUM_crypto_policy_notify_type_CRYPTO_POLICY_NOTIFY_IDLE_TIMER";
      }
      enum "crypto-notify-dpd-timer" {
        value 4;
        description
          "Dead peer detection timer";
        tailf:code-name "ENUM_crypto_policy_notify_type_CRYPTO_POLICY_NOTIFY_DPD_TIMER";
      }
      enum "crypto-notify-invalid-spi" {
        value 5;
        description
          "Invalid SPI";
        tailf:code-name "ENUM_crypto_policy_notify_type_CRYPTO_POLICY_NOTIFY_INVALID_SPI";
      }
    }
    description
      "Crypto policy notification types";
  }

  typedef crypto-policy-cmd-type {
    type enumeration {
      enum "crypto-cmd-sadb-init-start" {
        value 0;
        description
          "SA database initialization";
        tailf:code-name "ENUM_crypto_policy_cmd_type_CRYPTO_POLICY_CMD_SADB_INIT_START";
      }
      enum "crypto-cmd-sadb-init-complete" {
        value 1;
        description
          "SA database init complete";
        tailf:code-name "ENUM_crypto_policy_cmd_type_CRYPTO_POLICY_CMD_SADB_INIT_COMPLETED";
      }
      enum "crypto-cmd-sadb-delete" {
        value 2;
        description
          "SA database deletion";
        tailf:code-name "ENUM_crypto_policy_cmd_type_CRYPTO_POLICY_CMD_SADB_DELETE";
      }
      enum "crypto-cmd-sadb-attr-update" {
        value 3;
        description
          "SA database attr update";
        tailf:code-name "ENUM_crypto_policy_cmd_type_CRYPTO_POLICY_CMD_SADB_ATTR_UPDATE";
      }
      enum "crypto-cmd-sadb-intf-attach" {
        value 4;
        description
          "SA database interface attach";
        tailf:code-name "ENUM_crypto_policy_cmd_type_CRYPTO_POLICY_CMD_SADB_INTF_ATTACH";
      }
      enum "crypto-cmd-sadb-intf-update" {
        value 5;
        description
          "SA database interface update";
        tailf:code-name "ENUM_crypto_policy_cmd_type_CRYPTO_POLICY_CMD_SADB_INTF_UPDATE";
      }
      enum "crypto-cmd-sadb-intf-detach" {
        value 6;
        description
          "SA database interface detach";
        tailf:code-name "ENUM_crypto_policy_cmd_type_CRYPTO_POLICY_CMD_SADB_INTF_DETACH";
      }
      enum "crypto-cmd-acl-insert" {
        value 7;
        description
          "ACL insert";
        tailf:code-name "ENUM_crypto_policy_cmd_type_CRYPTO_POLICY_CMD_ACL_INSERT";
      }
      enum "crypto-cmd-acl-modify" {
        value 8;
        description
          "ACL modify";
        tailf:code-name "ENUM_crypto_policy_cmd_type_CRYPTO_POLICY_CMD_ACL_MODIFY";
      }
      enum "crypto-cmd-acl-delete" {
        value 9;
        description
          "ACL delete";
        tailf:code-name "ENUM_crypto_policy_cmd_type_CRYPTO_POLICY_CMD_ACL_DELETE";
      }
      enum "crypto-cmd-peer-insert" {
        value 10;
        description
          "Peer insert";
        tailf:code-name "ENUM_crypto_policy_cmd_type_CRYPTO_POLICY_CMD_PEER_INSERT";
      }
      enum "crypto-cmd-peer-delete" {
        value 11;
        description
          "Peer delete";
        tailf:code-name "ENUM_crypto_policy_cmd_type_CRYPTO_POLICY_CMD_PEER_DELETE";
      }
      enum "crypto-cmd-spi-insert" {
        value 12;
        description
          "SPI insert";
        tailf:code-name "ENUM_crypto_policy_cmd_type_CRYPTO_POLICY_CMD_SPI_INSERT";
      }
      enum "crypto-cmd-spi-delete" {
        value 13;
        description
          "SPI delete";
        tailf:code-name "ENUM_crypto_policy_cmd_type_CRYPTO_POLICY_CMD_SPI_DELETE";
      }
      enum "crypto-cmd-cflow-insert" {
        value 14;
        description
          "Outbound flow insert";
        tailf:code-name "ENUM_crypto_policy_cmd_type_CRYPTO_POLICY_CMD_CFLOW_INSERT";
      }
      enum "crypto-cmd-cflow-modify" {
        value 15;
        description
          "Outbound flow modify";
        tailf:code-name "ENUM_crypto_policy_cmd_type_CRYPTO_POLICY_CMD_CFLOW_MODIFY";
      }
      enum "crypto-cmd-cflow-delete" {
        value 16;
        description
          "Outbound flow delete";
        tailf:code-name "ENUM_crypto_policy_cmd_type_CRYPTO_POLICY_CMD_CFLOW_DELETE";
      }
      enum "crypto-cmd-ipsec-sa-delete" {
        value 17;
        description
          "IPSEC SA delete";
        tailf:code-name "ENUM_crypto_policy_cmd_type_CRYPTO_POLICY_CMD_IPSEC_SA_DELETE";
      }
      enum "crypto-cmd-tbar-create" {
        value 18;
        description
          "Time based anti replay create";
        tailf:code-name "ENUM_crypto_policy_cmd_type_CRYPTO_POLICY_CMD_TBAR_CREATE";
      }
      enum "crypto-cmd-tbar-update" {
        value 19;
        description
          "Time based anti replay update";
        tailf:code-name "ENUM_crypto_policy_cmd_type_CRYPTO_POLICY_CMD_TBAR_UPDATE";
      }
      enum "crypto-cmd-tbar-remove" {
        value 20;
        description
          "Time based anti replay remove";
        tailf:code-name "ENUM_crypto_policy_cmd_type_CRYPTO_POLICY_CMD_TBAR_REMOVE";
      }
    }
    description
      "Crypto policy command types";
  }

  typedef crypto-policy-dbase-type {
    type enumeration {
      enum "crypto-policy-db-pal-sadb" {
        value 0;
        description
          "PAL SA database";
        tailf:code-name "ENUM_crypto_policy_dbase_type_CRYPTO_POLICY_DB_PAL_SADB";
      }
      enum "crypto-policy-db-pal-sadb-id" {
        value 1;
        description
          "PAL SA ID database";
        tailf:code-name "ENUM_crypto_policy_dbase_type_CRYPTO_POLICY_DB_PAL_SADB_ID";
      }
      enum "crypto-policy-db-pal-intf" {
        value 2;
        description
          "PAL interface database";
        tailf:code-name "ENUM_crypto_policy_dbase_type_CRYPTO_POLICY_DB_PAL_INTF";
      }
      enum "crypto-policy-db-pal-sa-id" {
        value 3;
        description
          "PAL SA ID database";
        tailf:code-name "ENUM_crypto_policy_dbase_type_CRYPTO_POLICY_DB_PAL_SA_ID";
      }
      enum "crypto-policy-db-pal-acl" {
        value 4;
        description
          "PAL ACL database";
        tailf:code-name "ENUM_crypto_policy_dbase_type_CRYPTO_POLICY_DB_PAL_ACL";
      }
      enum "crypto-policy-db-pal-peer" {
        value 5;
        description
          "PAL peer database";
        tailf:code-name "ENUM_crypto_policy_dbase_type_CRYPTO_POLICY_DB_PAL_PEER";
      }
      enum "crypto-policy-db-pal-spi" {
        value 6;
        description
          "PAL SPI database";
        tailf:code-name "ENUM_crypto_policy_dbase_type_CRYPTO_POLICY_DB_PAL_SPI";
      }
      enum "crypto-policy-db-pal-cflow" {
        value 7;
        description
          "PAL outbound flow database";
        tailf:code-name "ENUM_crypto_policy_dbase_type_CRYPTO_POLICY_DB_PAL_CFLOW";
      }
      enum "crypto-policy-db-pal-tbar" {
        value 8;
        description
          "PAL time base replay database";
        tailf:code-name "ENUM_crypto_policy_dbase_type_CRYPTO_POLICY_DB_PAL_TBAR";
      }
    }
    description
      "Crypto policy database types";
  }

  typedef crypto-transform-options {
    type bits {
      bit crypto-transform-ah-hmac-sha {
        position 0;
        description
          "AH-HMAC-SHA";
      }
      bit crypto-transform-ah-hmac-sha256 {
        position 1;
        description
          "AH-HMAC-SHA-256";
      }
      bit crypto-transform-ah-hmac-sha384 {
        position 2;
        description
          "AH-HMAC-SHA-384";
      }
      bit crypto-transform-ah-hmac-sha512 {
        position 3;
        description
          "AH-HMAC-SHA-512";
      }
      bit crypto-transform-ah-hmac-md5 {
        position 4;
        description
          "AH-HMAC-MD5";
      }
      bit crypto-transform-esp-des {
        position 5;
        description
          "ESP-DES";
      }
      bit crypto-transform-esp-3-des {
        position 6;
        description
          "ESP-3DES";
      }
      bit crypto-transform-esp-seal {
        position 7;
        description
          "ESP-SEAL";
      }
      bit crypto-transform-esp-aes-cbc {
        position 8;
        description
          "ESP-AES-CBC";
      }
      bit crypto-transform-esp-aes-cbc-192 {
        position 9;
        description
          "ESP-AES-CBC-192";
      }
      bit crypto-transform-esp-aes-cbc-256 {
        position 10;
        description
          "ESP-AES-CBC-256";
      }
      bit crypto-transform-esp-aes-gcm {
        position 11;
        description
          "ESP-AES-GCM";
      }
      bit crypto-transform-esp-aes-gcm-192 {
        position 12;
        description
          "ESP-AES-GCM-192";
      }
      bit crypto-transform-esp-aes-gcm-256 {
        position 13;
        description
          "ESP-AES-GCM-256";
      }
      bit crypto-transform-esp-aes-gmac {
        position 14;
        description
          "ESP-AES-GMAC";
      }
      bit crypto-transform-esp-aes-gmac-192 {
        position 15;
        description
          "ESP-AES-GMAC-192";
      }
      bit crypto-transform-esp-aes-gmac-256 {
        position 16;
        description
          "ESP-AES-GMAC-256";
      }
      bit crypto-transform-esp-null {
        position 17;
        description
          "ESP-NULL";
      }
      bit crypto-transform-esp-hmac-md5 {
        position 18;
        description
          "ESP-HMAC-MD5";
      }
      bit crypto-transform-esp-hmac-sha {
        position 19;
        description
          "ESP-HMAC-SHA";
      }
      bit crypto-transform-esp-hmac-sha256 {
        position 20;
        description
          "ESP-HMAC-SHA-256";
      }
      bit crypto-transform-esp-hmac-sha384 {
        position 21;
        description
          "ESP-HMAC-SHA-384";
      }
      bit crypto-transform-esp-hmac-sha512 {
        position 22;
        description
          "ESP-HMAC-SHA-512";
      }
      bit crypto-transform-pcp-lzs {
        position 23;
        description
          "PCP-LZS";
      }
    }
    description
      "The cryptographic transform set options available in the connection";
  }

  grouping crypto-ike-sa-data {
    description
      "Crypto IKE Security Association Data";
    leaf sa-id {
      type uint32;
      description
        "IKE security association identifier";
    }
    leaf sa-status {
      type crypto-ios-xe-oper:crypto-sa-status;
      description
        "IKE security association Status";
    }
    leaf local-ip-addr {
      type inet:ip-address;
      description
        "Local IP Address";
    }
    leaf local-port {
      type uint16;
      description
        "Local Port number";
    }
    leaf remote-ip-addr {
      type inet:ip-address;
      description
        "Remote IP Address";
    }
    leaf remote-port {
      type uint16;
      description
        "Remote Port number";
    }
    leaf dh-group {
      type crypto-ios-xe-oper:crypto-dh-group-type;
      description
        "DH group";
    }
    leaf init-spi {
      type binary;
      description
        "Initiator security parameter index";
    }
    leaf resp-spi {
      type binary;
      description
        "Responder security parameter index";
    }
    leaf ivrf {
      type string;
      description
        "IKE IVRF";
    }
    leaf fvrf {
      type string;
      description
        "IKE FVRF";
    }
    leaf lifetime {
      type uint32;
      units "seconds";
      description
        "Security association lifetime";
    }
    leaf hash-algo {
      type crypto-ios-xe-oper:crypto-hash-alg;
      description
        "HASH Algorithm";
    }
    leaf encr-alg {
      type crypto-ios-xe-oper:crypto-encryption-alg;
      description
        "Encryption algorithm";
    }
    leaf my-auth-method {
      type crypto-ios-xe-oper:crypto-auth-method;
      description
        "Self authentication method";
    }
    leaf peer-auth-method {
      type crypto-ios-xe-oper:crypto-auth-method;
      description
        "Peer authentication Method";
    }
  }

  grouping crypto-ikev2-sa-entry {
    description
      "Crypto IKEV2 Security Association Entry";
    leaf sa-id {
      type uint32;
      description
        "Security association identifier";
    }
    container sa-data {
      description
        "Security association Data";
      uses crypto-ios-xe-oper:crypto-ike-sa-data;
    }
  }

  grouping crypto-ikev1-sa-entry {
    description
      "Crypto IKEV1 Security association Entry";
    leaf sa-id {
      type uint32;
      description
        "Security association identifier";
    }
    container sa-data {
      description
        "Security association Data";
      uses crypto-ios-xe-oper:crypto-ike-sa-data;
    }
  }

  grouping crypto-ipsec-sa-entry {
    description
      "Crypto IPSEC SA entry";
    leaf spi {
      type uint32;
      description
        "IPSEC SPI number";
    }
    leaf dir {
      type crypto-ios-xe-oper:crypto-dir-type;
      description
        "Traffic Direction";
    }
    leaf protocol {
      type crypto-ios-xe-oper:crypto-prot-type;
      description
        "IPSEC Protocol";
    }
    leaf flow-id {
      type uint32;
      description
        "FLow ID";
    }
    leaf sa-status {
      type crypto-ios-xe-oper:crypto-sa-status;
      description
        "IPSEC SA status";
    }
    leaf transform-set {
      type crypto-ios-xe-oper:crypto-transform-options;
      description
        "Crypto transform set";
    }
  }

  grouping crypto-ipsec-ident-data {
    description
      "Crypto IPSEC Identity Data";
    leaf protected-vrf {
      type uint32;
      description
        "Protected VRF";
    }
    leaf local-ident-addr {
      type inet:ip-address;
      description
        "Local IPSEC Identity Address";
    }
    leaf local-ident-mask {
      type inet:ip-address;
      description
        "Local IPSEC Identity Mask";
    }
    leaf local-ident-protocol {
      type uint32;
      description
        "Local IPSEC Identity Protocol";
    }
    leaf remote-ident-addr {
      type inet:ip-address;
      description
        "Remote IPSEC Identity Address";
    }
    leaf remote-ident-mask {
      type inet:ip-address;
      description
        "Remote IPSEC Identity Mask";
    }
    leaf remote-ident-protocol {
      type uint32;
      description
        "Remote IPSEC Identity Protocol";
    }
    leaf plaintext-mtu {
      type uint16;
      description
        "Plain text MTU value";
    }
    leaf local-endpt-addr {
      type inet:ip-address;
      description
        "Local Endpoint Address";
    }
    leaf remote-endpt-addr {
      type inet:ip-address;
      description
        "Remote Endpoint Address";
    }
    leaf dh-group {
      type crypto-ios-xe-oper:crypto-dh-group-type;
      description
        "DH group";
    }
    container inbound-esp-sa {
      description
        "Inbound ESP SA";
      uses crypto-ios-xe-oper:crypto-ipsec-sa-entry;
    }
    container inbound-ah-sa {
      description
        "Inbound AH SA";
      uses crypto-ios-xe-oper:crypto-ipsec-sa-entry;
    }
    container inbound-pcp-sa {
      description
        "Inbound PCP SA";
      uses crypto-ios-xe-oper:crypto-ipsec-sa-entry;
    }
    container outbound-esp-sa {
      description
        "Outbound ESP SA";
      uses crypto-ios-xe-oper:crypto-ipsec-sa-entry;
    }
    container outbound-ah-sa {
      description
        "Outbound AH SA";
      uses crypto-ios-xe-oper:crypto-ipsec-sa-entry;
    }
    container outbound-pcp-sa {
      description
        "Outbound PCP SA";
      uses crypto-ios-xe-oper:crypto-ipsec-sa-entry;
    }
  }

  grouping crypto-ipsec-ident-entry {
    description
      "Crypto IPSEC Identity Entry";
    leaf interface {
      type string;
      description
        "Interface";
    }
    container ident-data {
      description
        "IPSEC Identity Data";
      uses crypto-ios-xe-oper:crypto-ipsec-ident-data;
    }
  }

  grouping crypto-cerm-tunnels-entry {
    description
      "Details on Number of Resource Entries";
    leaf maximum {
      type uint32;
      description
        "Maximum tunnels supported on platform due to Export Restrictions";
    }
    leaf available {
      type uint32;
      description
        "Currently Available tunnels based on Export Restriction";
    }
  }

  grouping crypto-cerm-resource-info-entry {
    description
      "Tunnel based Resource Info";
    container ipsec-tunnels {
      description
        "Number of IPSEC tunnels";
      uses crypto-ios-xe-oper:crypto-cerm-tunnels-entry;
    }
    container tls-sessions {
      description
        "Number of TLS sessions";
      uses crypto-ios-xe-oper:crypto-cerm-tunnels-entry;
    }
  }

  grouping crypto-cerm-resv-entry {
    description
      "Dynamic Client Resource reservation info";
    leaf tunnels {
      type uint32;
      description
        "Number of tunnels created by a client";
    }
    leaf tls-sessions {
      type uint32;
      description
        "Number of TLS sessions created by a client";
    }
  }

  grouping crypto-cerm-client-info-entry {
    description
      "Client Related Information";
    container voice {
      description
        "Voice client";
      uses crypto-ios-xe-oper:crypto-cerm-resv-entry;
    }
    container ipsec {
      description
        "IPSEC client";
      uses crypto-ios-xe-oper:crypto-cerm-resv-entry;
    }
    container sslvpn {
      description
        "SSLVPN client";
      uses crypto-ios-xe-oper:crypto-cerm-resv-entry;
    }
  }

  grouping crypto-cerm-stats-entry {
    description
      "Statistics Information";
    leaf failed-tunnels {
      type uint32;
      description
        "Failed tunnel creation attempts due to Export Restriction";
    }
    leaf failed-sessions {
      type uint32;
      description
        "Failed session creation attempts due to Export Restriction";
    }
  }

  grouping crypto-cerm-info-entry {
    description
      "Crypto Export Restriction Information";
    leaf enabled {
      type boolean;
      description
        "Indicates if Export Restriction has been enabled";
    }
    container resource-info {
      description
        "Export Resource Limits for the platform";
      uses crypto-ios-xe-oper:crypto-cerm-resource-info-entry;
    }
    container resv-info {
      description
        "Dynamic Client Reservation Information";
      uses crypto-ios-xe-oper:crypto-cerm-client-info-entry;
    }
    container stats-info {
      description
        "Statistics info resulting from Export Restrictions";
      uses crypto-ios-xe-oper:crypto-cerm-stats-entry;
    }
  }

  grouping crypto-notify-stats-entry {
    description
      "Crypto Policy Abstraction Layer (PAL) Notification Statistics";
    leaf notification-type {
      type crypto-ios-xe-oper:crypto-policy-notify-type;
      description
        "Notification type";
    }
    leaf num-received {
      type uint32;
      description
        "Number of notify messages received";
    }
    leaf num-completed {
      type uint32;
      description
        "Number of successful notifications to PAL";
    }
    leaf num-rcv-error {
      type uint32;
      description
        "Number of message processing error";
    }
    leaf num-rcv-ignore {
      type uint32;
      description
        "Number of notify messages ignored";
    }
  }

  grouping crypto-cmd-stats-entry {
    description
      "Crypto Policy Abstraction Layer (PAL) Command Statistics";
    leaf cmd-type {
      type crypto-ios-xe-oper:crypto-policy-cmd-type;
      description
        "Command type";
    }
    leaf num-request {
      type uint32;
      description
        "Number of command messages received from PAL";
    }
    leaf num-reply-ok {
      type uint32;
      description
        "Number of successful replies sent to PAL";
    }
    leaf num-reply-error {
      type uint32;
      description
        "Number of error replies sent to PAL";
    }
    leaf num-abort {
      type uint32;
      description
        "Number of command messages aborted by PAL";
    }
    leaf total-time {
      type uint64;
      units "milliseconds";
      description
        "Round trip time";
    }
  }

  grouping crypto-database-stats-entry {
    description
      "Crypto Policy Abstraction Layer (PAL) Database Statistics";
    leaf dbase-type {
      type crypto-ios-xe-oper:crypto-policy-dbase-type;
      description
        "Database type";
    }
    leaf num-add {
      type uint32;
      description
        "Number of additions to database";
    }
    leaf num-delete {
      type uint32;
      description
        "Number of deletions from database";
    }
    leaf num-abort {
      type uint32;
      description
        "Number of aborted calls to database";
    }
  }

  grouping crypto-ipsec-policy-stats-entry {
    description
      "Crypto Policy Stats Information";
    list notify-stats {
      description
        "Policy Notification Statistics";
      uses crypto-ios-xe-oper:crypto-notify-stats-entry;
    }
    list cmd-stats {
      description
        "Policy Command Statistics";
      uses crypto-ios-xe-oper:crypto-cmd-stats-entry;
    }
    list dbase-stats {
      description
        "Policy Database Summary Statistics";
      uses crypto-ios-xe-oper:crypto-database-stats-entry;
    }
  }

  container crypto-oper-data {
    config false;
    description
      "crypto operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    tailf:meta-data "name" {
      tailf:meta-value "Cisco-IOS-XE-crypto-oper";
    }
    list crypto-ipsec-ident {
      key "interface";
      description
        "Crypto IPSEC Identity Entry";
      uses crypto-ios-xe-oper:crypto-ipsec-ident-entry;
    }
    list crypto-ikev2-sa {
      key "sa-id";
      description
        "Crypto IKEv2 SA Entry";
      uses crypto-ios-xe-oper:crypto-ikev2-sa-entry;
    }
    list crypto-ikev1-sa {
      key "sa-id";
      description
        "Crypto IKEv1 SA Entry";
      uses crypto-ios-xe-oper:crypto-ikev1-sa-entry;
    }
    container crypto-cerm-info {
      presence "crypto-cerm-info";
      description
        "Crypto Export Restrictions Entry";
      uses crypto-ios-xe-oper:crypto-cerm-info-entry;
    }
    container crypto-ipsec-policy-stats {
      presence "crypto-ipsec-policy-stats";
      description
        "Crypto policy statistics";
      uses crypto-ios-xe-oper:crypto-ipsec-policy-stats-entry;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWfLRz08ADU3fgEAAEAZ/cD/v3/q/79/6YAbg7b7XbAAA0yAAFYg1EyTaaU/CpoZBk0ADRtMkwmg0GSKeAT0pqep6QAAGho0AAAOYBNMAmQwABMEwAAAbSUEYk0aH6oYmmIAAGmEA00OYBNMAmQwABMEwAAARKBAIAkEgGQAek/Uaaj1PSGjhr2o+v3v0vXBkoQYyKNtcT/i3brGrcyx1NWxVcWoamrZtTB+gAEENHECCHV+bobpF9KNMaqalEMVdk5SlPjC8ICgFtaptEyhvwl3+F2wAAghKHqSiCH0usfksyMZkRtLiv8vS+0QgyptlVq641IamLZfoRC4kugWmihleu5tFyUqngLA7E+UYxnMLwgKAW1qm0TJmPrPf1ZcxZc3DSRkRmmpCiCGkJKGEMBKIIaiboVv2QkGYdVx2OH0t6A3NzW1K6CsZlAhRDLCpFgdBAQEJp065EgAqAkJxEp7zBkZOqysGcyKdOgLr0VxzzVHiMze+UENYBTuIXA/uDdG6EdISMhITjntrheerxffkvbkMIYJJbrL34GFFhfNjgWRYLKQKZZqFgQOI7bGvOsvnTFYVzJE3sD1LWdd87he4ctAGzddUlcfU676J522285kOee/xrMO1NCmHrCihtuMwhSIkUTEPe+HuyJiYgNHpNZ89XFzquzuAdCGY1yx9rbh4dhbds+rQaUaD1607AXA6vZ+xAA+s/sD/R+JdKIFv3oVBKRDbwhj7QG1z10vRoh6di8wYCIGqlahdLfGthDPySamE+mpQLD9xREhPu5FOqgu4BiuX3ghtaSRqQHB/quRLYO4aNbwDRC5F9JIIZl6GL0OpMwCsS3VDxMn8K9e741PEMqmdtHA0wAV1OmQQwGMKHRGrJ8VyzRptry+XQOAHrZC7A58IBohkZcRGwDkUQg8I2pISSSJuZAhg7QoYLrkELVintjQ77FS+hS+e027Di9UOQITL6G3pGtjUkgw9tY+5WgVROxR31segD4xcA3NaZPW7TRSgXAYFCU19Dx1BDjRnMBzKryehEHbTsdo90ByggHIy436g6qR+mtQ96OA3qAnIsoLkjcAzht3d6AOZetOvcBj5QamTeYUVpSgbUoUhXOWD8dMkORHpB2OoLtUHPRCiUgQQyrUeVkkUnKU11S29qDgMVDKSQmoSqBmtzjdQWUAdMxsjffFPErqUFzYjmEzQLl60g39kyPOM0eSgFaAoGk2mS9zSVUcDTd1W9tzY8dciVNoaY2+/nslBOfX2+JAixzNA22fcibXvVDpj6qX19lOcOXLhXba28bAFOYhcD3A3RuhNISKIEQJWtJowKrVbkLurLS4Vtc3bxL6LltO4lGTRSBW+ShagECSGJm17wiENuax7UFGAGOf2wEpIHcWC1g56gPHiZn8fr9+Xp8CfA9T1+ClBL/eiWPsTGEKAlNkPpVB/nj1Aa4M/wC+yHr6uJbIgRA6VEKhdPW+9r6Xk7FKSSJowGpuZp+VyiXH5BRE6k+XY4AK6ioSAJz00t8xPORQt3AKRNIGKNkKIXuUX1ihkWoYvQ7ks9xPM1pkj6eXrmeKNDTD5wOLgFumpRob76hmnRGTNQpuun+PmuYdPnsHTcB7XQrqg7oBfBxRDROEYVkhJJIlQbiNOYZCVJ3oUyLjiy0YVg+IBQ/adNyxjLHC204nH+SFSSL34zonOWQegk0/I5h6V1Paw9iD7w/MgcrImA6seOPZpewBwcqYfNwpmJQLgMShKcc9vICGcVSkOXuPTuJfDOu5oA9G49yiDbT0TzzL77QAkO4Ns1MVfd9SNg8OQbVR8MuArkj387QPPABWpnJS8gDmXmypiTw+xBsVcpgBXiiZ/+3qkiEJ0M3rBeCbvgFruhZG0yUIGVqLSJFjaSsxRsbUkTMBWgOQIiBSGkANiCjhNVRbymlgHNbI5mYtmI3CXEM11MWhopsUqxKEOmoRdSQEs+to/jTvbIgcN/4u5IpwoSHlo56eA";
      }
      tailf:meta-data "uncompressed_size" {
        tailf:meta-value "6831";
      }
    }
  }

  container schema-metadata-Cisco-IOS-XE-crypto-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-crypto-oper";
    }
    tailf:meta-data "organization" {
      tailf:meta-value "Cisco Systems, Inc.";
    }
    tailf:meta-data "semver" {
      tailf:meta-value "2020-07-01";
    }
  }
}
