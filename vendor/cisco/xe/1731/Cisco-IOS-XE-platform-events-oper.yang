module Cisco-IOS-XE-platform-events-oper {
  yang-version 1;
  namespace "http://cisco.com/ns/yang/Cisco-IOS-XE-platform-events-oper";
  prefix platform-events-ios-xe-oper;

  import Cisco-IOS-XE-platform-common-oper {
    prefix platform-common-ios-xe-oper;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of platform components events.
     Copyright (c) 2019-2020 by Cisco Systems, Inc.
     All rights reserved.";

  revision 2020-07-01 {
    description
      "- Remove unused empty container platform-events";
    reference "0.0.0";
    cisco-semver:module-version "0.0.0";
    cisco-semver-internal:os-version "17.3.1";
  }
  revision 2019-11-01 {
    description
      "Initial revision";
    reference "1.0.0";
    cisco-semver:module-version "1.0.0";
    cisco-semver-internal:os-version "17.1.1";
  }

  typedef plat-notif-severity {
    type enumeration {
      enum "notif-sev-critical" {
        value 0;
        description
          "Notification severity - critical";
        tailf:code-name "ENUM_plat_notif_severity_PLAT_NOTF_SEV_CRITICAL";
      }
      enum "notif-sev-major" {
        value 1;
        description
          "Notification severity - major";
        tailf:code-name "ENUM_plat_notif_severity_PLAT_NOTF_SEV_MAJOR";
      }
      enum "notif-sev-minor" {
        value 2;
        description
          "Notification severity - minor";
        tailf:code-name "ENUM_plat_notif_severity_PLAT_NOTF_SEV_MINOR";
      }
    }
    description
      "Notification severity";
  }

  typedef plat-comp-state {
    type enumeration {
      enum "module-present" {
        value 0;
        description
          "Module present";
        tailf:code-name "ENUM_plat_comp_state_PLAT_NOTF_MODULE_STATE_PRESENT";
      }
      enum "module-inserted" {
        value 1;
        description
          "Module inserted";
        tailf:code-name "ENUM_plat_comp_state_PLAT_NOTF_MODULE_STATE_INSERTED";
      }
      enum "module-removed" {
        value 2;
        description
          "Module removed";
        tailf:code-name "ENUM_plat_comp_state_PLAT_NOTF_MODULE_STATE_REMOVED";
      }
    }
    description
      "Platform module state";
  }

  grouping plat-sensor-state-data {
    description
      "platform sensor state events data model";
    leaf severity {
      type platform-events-ios-xe-oper:plat-notif-severity;
      description
        "Event severity";
    }
    leaf comp-type {
      type platform-common-ios-xe-oper:plat-comp-type;
      description
        "Platform component type";
    }
    leaf sensor-type {
      type platform-common-ios-xe-oper:plat-sensor-type;
      description
        "Platform sensor type";
    }
    leaf description {
      type string;
      description
        "Platform sensor description";
    }
    leaf location {
      type string;
      description
        "Platform sensor location containing chassis, slot, bay";
    }
    leaf id {
      type string;
      description
        "Platform sensor SNMP physical index";
    }
    container sensor-val {
      description
        "Sensor readings of a component. Values include
         the instantaneous, average, max, and min statistics";
      uses platform-common-ios-xe-oper:plat-sensor-data;
    }
    container alarm-data {
      description
        "Contains sensor alarm data. It includes alarm status, 
         high threshold, low threshold and alarm severity";
      uses platform-common-ios-xe-oper:plat-sensor-alarm-data;
    }
    leaf new-state {
      type platform-common-ios-xe-oper:plat-sensor-state;
      description
        "Platform sensor temperature new state";
    }
    leaf time-stamp {
      type yang:date-and-time;
      description
        "Notification time stamp";
    }
  }

  grouping plat-comp-state-data {
    description
      "platform component state events data model";
    leaf severity {
      type platform-events-ios-xe-oper:plat-notif-severity;
      description
        "Event severity";
    }
    leaf comp-type {
      type platform-common-ios-xe-oper:plat-comp-type;
      description
        "Platform component type";
    }
    leaf description {
      type string;
      description
        "Platform component description";
    }
    leaf location {
      type string;
      description
        "Platform component location containing chassis, slot, bay";
    }
    leaf id {
      type string;
      description
        "Platform component SNMP physical index";
    }
    leaf part-no {
      type string;
      description
        "Platform component part number";
    }
    leaf comp-state {
      type platform-events-ios-xe-oper:plat-comp-state;
      description
        "Platform component state";
    }
    leaf new-status {
      type platform-common-ios-xe-oper:plat-comp-status;
      description
        "Platform component new status";
    }
    leaf status-desc {
      type platform-common-ios-xe-oper:plat-comp-status-desc;
      description
        "Platform component new status description";
    }
    leaf time-stamp {
      type yang:date-and-time;
      description
        "Notification time stamp";
    }
  }

  notification platform-sensor-state-update {
    description
      "Component sensor state change notification";
    uses platform-events-ios-xe-oper:plat-sensor-state-data;
  }
  notification platform-component-state-update {
    description
      "Platform component state change notification";
    uses platform-events-ios-xe-oper:plat-comp-state-data;
  }
  container Cisco-IOS-XE-platform-events-oper {
    config false;
    tailf:callpoint "ios-eventq-db";
    tailf:meta-data "callpoint" {
      tailf:meta-value "ios-eventq-db";
    }
    tailf:meta-data "greenprefix" {
      tailf:meta-value "/services;serviceName=iosevent";
    }
    tailf:meta-data "name" {
      tailf:meta-value "Cisco-IOS-XE-platform-events-oper";
    }
    tailf:hidden "full";
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWWnG/QIABNbfgEQAEAYAED//3+q//9+qUAQya2eVTtWpSFhIlNU8kyaeJGj0nqaaaYQ2kZPUBoNCGqeSAAAaA00xBoNGgSJACSnmKJMTEAxMI9TaRkxgAAAABoNAGgGgEkQJiNCmajKAAAaAAfh18ikUT+m0VKaOOo3qPSNrab1rgpfXRKbzNENE+MgwbZBwEeth8kj5qaOkfz6PCq9A4zYauErhYgpTQbCdrrV2ZXrj2R8d+WAzy5I1ghM2gMIgQNwmkMYENEJo6NC2Ahatb/gzhip1OqMgzSzT/8+5u15H71xdUerxTDcUsOFjzBGt4xG8anMOn/Jix4Q82icmjA46khKE0lWX77dF+qRwWv0OBgFBGO4rNTPYUw0FK5QSmAA0AEIipEPBIyPAgYZEziSFyGStmVZUsksz5CkFa6vncg8QpTNKSZ2p8KzaNYBb1x8XxTVeELJImgyiE9xYgVoNoQhN1Pv3UoPSUeBl9wyzMyZtU5ljSEWwwmAR06GtKxU8WrfLtVyhKhNhOJxdhGDzhVh7tVmRNlhcDIlqMApSJRrgK0xt1Uzx6cRFJCLg8Bc52a8jlMGzlr0ARMvFmNxp4K3RA3G2cxwXVzwenkqVSteXocA2LhgzaSE7pDu4jR0iFMpAYQmOrLABxk7XqPZJEZPNFRUE9zEcGUq0kAlOrS7EMWOS1AJc670vgk3SgcmiwMNVnNjlvVylKlKgromVbrtKEKh1Zb2o+17PtKlMA+ExSTKxtLZ2O94kkebDbbWcc9A2505rIRE2KeUon8c2TZcbUP1Py26eY3blg3HE9nF+mWKlj5X6fX4Z0TA+lICwrKEWhb7bHirQj7KP15uTcHJJJkoG9iaKRUZI4d6XlwGU9ORa+bMKidXWcxm9O/wtRozgAwWfJ21EBJLm9sKg63GFhOG80PW5EbUlKjrL9OuxSi9I1lwMcXtweANQKnLM7TQ2gRYGviADIOgdxvlae17bW5Wie6ohWH0guOa4KzQ2MYNg/KaiIkWrDViGGCMR41HGDmPCj1AHdnH3CpttoFss6ICJs61F/rM3Al1RMgHdWlb50XdkNIEb89UYjn3mnMIydZNqoy25tB3NMG2htJrl7Flm/i9DyWSwXGmKB4tOfPfPSqSNmDytmmlclIR0gSlXVapr8Yh17ulyinqd0EspTkFpXRSaLaOuFPqZL3VKKwrZeF1vyhq+x3LssuJZ7LLGCUR2E5FhV263gyNdOZ/GQv6u8kzJkcl/i7kinChINON+gQA=";
      }
      tailf:meta-data "uncompressed_size" {
        tailf:meta-value "2511";
      }
    }
    container Cisco-IOS-XE-platform-common-oper {
      description
        "Hidden internal container used for metadata";
      uses platform-common-ios-xe-oper:__yangpp_metadata;
    }
  }

  container schema-metadata-Cisco-IOS-XE-platform-events-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-platform-events-oper";
    }
    tailf:meta-data "organization" {
      tailf:meta-value "Cisco Systems, Inc.";
    }
    tailf:meta-data "semver" {
      tailf:meta-value "2020-07-01";
    }
  }
}
