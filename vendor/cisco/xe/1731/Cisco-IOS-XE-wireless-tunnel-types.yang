module Cisco-IOS-XE-wireless-tunnel-types {
  yang-version 1;
  namespace "http://cisco.com/ns/yang/Cisco-IOS-XE-wireless-tunnel-types";
  prefix wireless-tunnel-types;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing tunnel configurations
     Copyright (c) 2018-2020 by Cisco Systems, Inc.
     All rights reserved.";

  revision 2020-07-01 {
    description
      "Add EoGRE DHCP opt82 format";
    reference "1.3.0";
    cisco-semver:module-version "1.3.0";
  }
  revision 2020-03-01 {
    description
      "Added central forwarding";
    reference "1.2.0";
    cisco-semver:module-version "1.2.0";
  }
  revision 2019-05-01 {
    description
      "Added semantic version";
    reference "1.1.0";
    cisco-semver:module-version "1.1.0";
  }
  revision 2018-11-01 {
    description
      "Initial revision";
    reference "1.0.0";
    cisco-semver:module-version "1.0.0";
  }

  typedef tunnel-dhcp-opt82-mac-format {
    type enumeration {
      enum "raw" {
        value 0;
        description
          "Raw mac format ";
      }
      enum "colon-delimited" {
        value 1;
        description
          "Colon delimited mac format ";
      }
    }
    description
      "Option82 mac format";
  }

  grouping st-tunnel-profile-base {
    description
      "Configuration of wireless tunnel profile";
    leaf status {
      type boolean;
      default "false";
      description
        "Whether tunnel profile is enabled";
    }
    leaf aaa-override {
      type boolean;
      default "false";
      description
        "Whether AAA override is enabled";
    }
    leaf aaa-proxy {
      type boolean;
      default "false";
      description
        "Whether AAA proxy is enabled";
    }
    leaf aaa-accounting-proxy {
      type boolean;
      description
        "Whether AAA accounting proxy is enabled";
    }
    leaf opt82-enable {
      type boolean;
      description
        "Whether DHCP-opt82 is enabled";
    }
    leaf opt82-ascii {
      type boolean;
      description
        "Whether DHCP Option 82 format is ASCII. Binary if false";
    }
    leaf opt82-delimiter {
      type string {
        length "0 .. 1";
      }
      description
        "DHCP-opt82 Delimiter character";
    }
    leaf central-fwd {
      type boolean;
      description
        "Whether Central forwarding is enabled";
    }
    leaf mac-format {
      type wireless-tunnel-types:tunnel-dhcp-opt82-mac-format;
      default "raw";
      description
        "Option82 mac format";
    }
  }

  grouping st-tunnel-rule-base {
    description
      "Configuration of wireless tunnel rule";
    leaf realm {
      type string;
      description
        "The rule realm to match with";
    }
    leaf vlan-id {
      type uint32 {
        range "1 .. 4094";
      }
      description
        "The rule VLAN";
    }
    leaf domain-name {
      type string;
      description
        "The rule's destination domain name";
    }
  }
}
