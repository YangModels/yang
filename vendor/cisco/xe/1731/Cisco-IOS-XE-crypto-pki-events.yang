module Cisco-IOS-XE-crypto-pki-events {
  yang-version 1;
  namespace "http://cisco.com/ns/yang/Cisco-IOS-XE-crypto-pki-events";
  prefix crypto-pki-ios-xe-events;
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for crypto PKI events data.
     Copyright (c) 2019-2020 by Cisco Systems, Inc.
     All rights reserved.";

  revision 2020-07-01 {
    description
      "- Remove unused empty container crypto-pki-events";
    reference "0.0.0";
    cisco-semver:module-version "0.0.0";
    cisco-semver-internal:os-version "17.3.1";
  }
  revision 2019-11-01 {
    description
      "Initial revision";
    reference "1.0.0";
    cisco-semver:module-version "1.0.0";
    cisco-semver-internal:os-version "17.1.1";
  }

  grouping pki-certificate-expiry-update {
    description
      "Certificate expiry update";
    leaf trust-point {
      type string;
      description
        "Trustpoint name";
    }
    leaf expires-at {
      type yang:date-and-time;
      description
        "Absolute time of expiry";
    }
    leaf is-ca-cert {
      type boolean;
      description
        "Set to true if expiring certificate is a CA certificate";
    }
    leaf subject-name {
      type string;
      description
        "Subject name of expiring certificate";
    }
    leaf issuer-name {
      type string;
      description
        "Issuer name of expiring certificate";
    }
    leaf serial-number {
      type string;
      description
        "Serial number of the expiring certificate";
    }
  }

  notification pki-certificate-expiry {
    description
      "Certificate expiry update";
    uses crypto-pki-ios-xe-events:pki-certificate-expiry-update;
  }
  container Cisco-IOS-XE-crypto-pki-events {
    config false;
    tailf:callpoint "ios-eventq-db";
    tailf:meta-data "callpoint" {
      tailf:meta-value "ios-eventq-db";
    }
    tailf:meta-data "greenprefix" {
      tailf:meta-value "/services;serviceName=iosevent";
    }
    tailf:meta-data "name" {
      tailf:meta-value "Cisco-IOS-XE-crypto-pki-events";
    }
    tailf:hidden "full";
  }

  grouping __yangpp_metadata {
    description
      "Internal metadata for this module and imported modules";
  }

  container schema-metadata-Cisco-IOS-XE-crypto-pki-events {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-crypto-pki-events";
    }
    tailf:meta-data "organization" {
      tailf:meta-value "Cisco Systems, Inc.";
    }
    tailf:meta-data "semver" {
      tailf:meta-value "2020-07-01";
    }
  }
}
