module Cisco-IOS-XE-mroute-oper {
  yang-version 1;
  namespace "http://cisco.com/ns/yang/Cisco-IOS-XE-mroute-oper";
  prefix mroute-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG
     definitions for Mroute operational data.
     Copyright (c) 2017-2020 by Cisco Systems, Inc.
     All rights reserved.";

  revision 2020-07-01 {
    description
      "Initial revision";
    reference "1.0.0";
    cisco-semver:module-version "1.0.0";
  }

  typedef mroute-addr-family {
    type enumeration {
      enum "mroute-af-ipv4" {
        value 0;
        description
          "Address Family IPV4";
      }
      enum "mroute-af-ipv6" {
        value 1;
        description
          "Address Family IPV6";
      }
    }
    description
      "Multicast Address Family";
  }

  typedef interface-state-type {
    type enumeration {
      enum "intf-invalid" {
        value 0;
        description
          "Interface Invalid";
      }
      enum "intf-prune" {
        value 1;
        description
          "Prune";
      }
      enum "intf-forward" {
        value 2;
        description
          "Forward";
      }
      enum "intf-bidir-upstream" {
        value 3;
        description
          "Bidir-Upstream";
      }
    }
    description
      "Multicast Interface State Type";
  }

  typedef mroute-mode-type {
    type enumeration {
      enum "mroute-none" {
        value 0;
        description
          "Mroute mode None";
      }
      enum "mroute-dense" {
        value 1;
        description
          "Mroute Dense mode";
      }
      enum "mroute-sparse" {
        value 2;
        description
          "Mroute Sparse mode";
      }
      enum "mroute-bidir" {
        value 3;
        description
          "Mroute bidirectional mode";
      }
    }
    description
      "Mroute Mode Type";
  }

  typedef mfib-nh-type {
    type enumeration {
      enum "mfib-nh-type-invalid" {
        value 0;
        description
          "Invalid Type";
      }
      enum "mfib-nh-type-ipv4" {
        value 1;
        description
          "IPv4 Type";
      }
      enum "mfib-nh-type-ipv6" {
        value 2;
        description
          "IPv6 Type";
      }
      enum "mfib-nh-type-mdt-encap-ipv4" {
        value 3;
        description
          "IPv4 MDT Encap";
      }
      enum "mfib-nh-type-mdt-encap-ipv6" {
        value 4;
        description
          "IPv6 MDT Encap";
      }
      enum "mfib-nh-type-mdt-encap-ipv4-mapped-ipv6" {
        value 5;
        description
          "IPv4 mapped IPv6 MDT Encap";
      }
      enum "mfib-nh-type-lsm" {
        value 6;
        description
          "Label Switched Multicast";
      }
      enum "mfib-nh-type-lsm-nbma" {
        value 7;
        description
          "Label Switched Multicast Non-Broadcast Multi Access";
      }
      enum "mfib-nh-type-mdt-decap-ipv4" {
        value 8;
        description
          "IPv4 MDT Decap";
      }
      enum "mfib-nh-type-mdt-decap-ipv6" {
        value 9;
        description
          "IPv6 MDT Decap";
      }
      enum "mfib-nh-type-mdt-decap-ipv4-mapped-ipv6" {
        value 10;
        description
          "IPv4 mapped IPv6 MDT Decap";
      }
      enum "mfib-nh-type-otv-decap-ipv4" {
        value 11;
        description
          "IPv4 OTV Decap";
      }
      enum "mfib-nh-type-otv-decap-ipv6" {
        value 12;
        description
          "IPv6 OTV Decap";
      }
      enum "mfib-nh-type-service-reflect" {
        value 13;
        description
          "Service Reflect";
      }
      enum "mfib-nh-type-vxlan-decap-ipv4" {
        value 14;
        description
          "IPv4 VxLAN Decap";
      }
      enum "mfib-nh-type-amt-ipv4" {
        value 15;
        description
          "IPv4 Automatic Multicast Tunnelling";
      }
      enum "mfib-nh-type-amt-ipv6" {
        value 16;
        description
          "IPv6 Automatic Multicast Tunnelling";
      }
      enum "mfib-nh-type-lisp-ipv4" {
        value 17;
        description
          "IPv4 LISP";
      }
      enum "mfib-nh-type-l2lisp-decap-ipv4" {
        value 18;
        description
          "IPv4 L2 LISP Decap";
      }
      enum "mfib-nh-type-lisp-decap-ipv4" {
        value 19;
        description
          "IPv4 LISP Decap";
      }
      enum "mfib-nh-type-cb" {
        value 20;
        description
          "CB Type";
      }
      enum "mfib-nh-type-vxlan-ipv4" {
        value 21;
        description
          "IPv4 VxLAN";
      }
      enum "mfib-nh-type-vxlan-ipv6" {
        value 22;
        description
          "IPv6 VxLAN";
      }
      enum "mfib-nh-type-vxlan-decap-ipv6" {
        value 23;
        description
          "IPv6 VxLAN Decap";
      }
    }
    description
      "MFIB next hop Type";
  }

  typedef mcast-cef-status {
    type enumeration {
      enum "mfib-cef-process-switching" {
        value 0;
        description
          "Process Switching";
      }
      enum "mfib-cef-sepcial-punt-adjacency" {
        value 1;
        description
          "Punt Adjacency";
      }
      enum "mfib-cef-sepcial-drop-adjacency" {
        value 2;
        description
          "Drop Adjacency";
      }
      enum "mfib-cef-sepcial-discard-adjacency" {
        value 3;
        description
          "Discard Adjacency";
      }
      enum "mfib-cef-sepcial-null-adjacency" {
        value 4;
        description
          "Null Adjacency";
      }
      enum "mfib-cef-sepcial-glean-adjacency" {
        value 5;
        description
          "Glean Adjacency";
      }
      enum "mfib-cef-sepcial-unresolved-adjacency" {
        value 6;
        description
          "Unresolved Adjacency";
      }
      enum "mfib-cef-sepcial-no-route-oce" {
        value 7;
        description
          "No Route OCE";
      }
      enum "mfib-cef-sepcial-ra-exception-oce" {
        value 8;
        description
          "Router alert exception OCE";
      }
      enum "mfib-cef-sepcial-gal-exception-oce" {
        value 9;
        description
          "Gal exception OCE";
      }
      enum "mfib-cef-sepcial-eli-exception-oce" {
        value 10;
        description
          "Entropy label indicator OCE";
      }
      enum "mfib-cef-sepcial-illegal-oce" {
        value 11;
        description
          "Illegal OCE";
      }
      enum "mfib-cef-oce-type-unknown" {
        value 12;
        description
          "Unknown type of output chain element";
      }
      enum "mfib-cef-oce-type-special" {
        value 13;
        description
          "Special";
      }
      enum "mfib-cef-oce-type-adj" {
        value 14;
        description
          "Adjacency";
      }
      enum "mfib-cef-oce-type-label" {
        value 15;
        description
          "Label";
      }
      enum "mfib-cef-oce-type-loadbalance" {
        value 16;
        description
          "Load Balance";
      }
      enum "mfib-cef-oce-type-bundle" {
        value 17;
        description
          "Bundle";
      }
      enum "mfib-cef-oce-type-mpls-eos" {
        value 18;
        description
          "MPLS EOS";
      }
      enum "mfib-cef-oce-type-qos" {
        value 19;
        description
          "Quality of service";
      }
      enum "mfib-cef-oce-type-frr" {
        value 20;
        description
          "Fast reroute";
      }
      enum "mfib-cef-oce-type-lookup" {
        value 21;
        description
          "Lookup";
      }
      enum "mfib-cef-oce-type-receive" {
        value 22;
        description
          "Receive";
      }
      enum "mfib-cef-oce-type-multicast" {
        value 23;
        description
          "Multicast";
      }
      enum "mfib-cef-oce-type-push-counter" {
        value 24;
        description
          "Push counter";
      }
      enum "mfib-cef-oce-type-atom-imp" {
        value 25;
        description
          "Atom IMP";
      }
      enum "mfib-cef-oce-type-atom-disp" {
        value 26;
        description
          "Atom disp";
      }
      enum "mfib-cef-oce-type-tunnel-decap" {
        value 27;
        description
          "Tunnel decap";
      }
      enum "mfib-cef-oce-type-replicate" {
        value 28;
        description
          "Replicate";
      }
      enum "mfib-cef-oce-type-interface" {
        value 29;
        description
          "Interface";
      }
      enum "mfib-cef-oce-type-lisp-elig" {
        value 30;
        description
          "LISP check eligibility";
      }
      enum "mfib-cef-oce-type-gal-check" {
        value 31;
        description
          "Gal Check";
      }
      enum "mfib-cef-oce-type-lisp-decap" {
        value 32;
        description
          "LISP Decap";
      }
      enum "mfib-cef-oce-type-bier-fmask" {
        value 33;
        description
          "BIER fmask";
      }
      enum "mfib-cef-oce-type-bier-disp" {
        value 34;
        description
          "BIER Disposition and Dispatch";
      }
      enum "mfib-cef-oce-type-srv6" {
        value 35;
        description
          "Segment Routing over IPv6 encap or insert";
      }
      enum "mfib-cef-oce-type-srv6-dispatch" {
        value 36;
        description
          "Segment Routing over IPv6 dispatch";
      }
      enum "mfib-cef-oce-type-srv6-end" {
        value 37;
        description
          "Segment Routing over IPv6 end";
      }
      enum "mfib-cef-oce-type-evpn-disp" {
        value 38;
        description
          "EVPN Disp";
      }
      enum "mfib-cef-oce-type-sadr" {
        value 39;
        description
          "Sadr OCE";
      }
      enum "mfib-cef-oce-type-signal" {
        value 40;
        description
          "Signal";
      }
      enum "mfib-cef-incomplete-adjacency" {
        value 41;
        description
          "Incomplete Adjacency";
      }
      enum "mfib-cef-mid-chain-adjacency" {
        value 42;
        description
          "Mid chain Adjacency";
      }
      enum "mfib-cef-empty-mac-adjacency" {
        value 43;
        description
          "Empty MAC Adjacency";
      }
      enum "mfib-cef-adjacency-with-mac" {
        value 44;
        description
          "Adjacency with MAC";
      }
    }
    description
      "Multicast MFIB CEF Type Status";
  }

  typedef mvpn-lsm-type {
    type enumeration {
      enum "mvpn-lsm-none" {
        value 0;
        description
          "Invalid Type";
      }
      enum "mvpn-lsm-nopta" {
        value 1;
        description
          "No Tunnel";
      }
      enum "mvpn-lsm-mldp" {
        value 2;
        description
          "MLDP Type";
      }
      enum "mvpn-lsm-ir" {
        value 3;
        description
          "Ingress Replication Type";
      }
      enum "mvpn-lsm-bier" {
        value 4;
        description
          "BIER Type";
      }
      enum "mvpn-lsm-vxlan" {
        value 5;
        description
          "VXLAN Type";
      }
    }
    description
      "MVPN Labeled Switched Multicast Transport Type";
  }

  typedef mroute-flag-type {
    type bits {
      bit mroute-connected {
        position 0;
        description
          "Mroute Connected";
      }
      bit mroute-local {
        position 1;
        description
          "Mroute Local";
      }
      bit mroute-register {
        position 2;
        description
          "Mroute Register";
      }
      bit mroute-rp-bit-set {
        position 3;
        description
          "Mroute RP-bit set";
      }
      bit mroute-spt-bit-set {
        position 4;
        description
          "Mroute SPT-bit set";
      }
      bit mroute-join-spt {
        position 5;
        description
          "Mroute Join SPT";
      }
      bit mroute-pim-join {
        position 6;
        description
          "Mroute PIM join";
      }
      bit mroute-vxlan-group {
        position 7;
        description
          "Mroute VxLAN group";
      }
      bit mroute-msdp-created-entry {
        position 8;
        description
          "Mroute MSDP created entry";
      }
      bit mroute-multicast-tunnel {
        position 9;
        description
          "Multicast Tunnel";
      }
      bit mroute-ssm {
        position 10;
        description
          "Mroute SSM";
      }
      bit mroute-urd {
        position 11;
        description
          "Mroute URD";
      }
      bit mroute-received-source-specific-host-report {
        position 12;
        description
          "Received Source Specific Host Report";
      }
      bit mroute-rd-vector {
        position 13;
        description
          "Mroute RD & Vector";
      }
      bit mroute-vector {
        position 14;
        description
          "Mroute Vector";
      }
    }
    description
      "Mroute Flags";
  }

  typedef mroute-ext-flag-type {
    type bits {
      bit mroute-pruned {
        position 0;
        description
          "Mroute Pruned";
      }
      bit mroute-extranet {
        position 1;
        description
          "Mroute Extranet";
      }
      bit mroute-proxy-join-timer-running {
        position 2;
        description
          " Mroute Proxy Join Timer Running";
      }
      bit mroute-candidate-for-msdp-advertisement {
        position 3;
        description
          "Mroute Candidate for MSDP advertisement";
      }
      bit mroute-mdt-data-group-sender {
        position 4;
        description
          "Mroute MDT-data group sender";
      }
      bit mroute-joined-mdt-data-group {
        position 5;
        description
          "Mroute Joined MDT-data group";
      }
      bit mroute-sending-to-mdt-data-group {
        position 6;
        description
          "Mroute Sending to MDT-data group";
      }
      bit mroute-received-bgp-c-mroute {
        position 7;
        description
          "Received BGP C-Mroute";
      }
      bit mroute-sent-bgp-c-mroute {
        position 8;
        description
          "Sent BGP C-Mroute";
      }
      bit mroute-received-bgp-shared-tree-prune {
        position 9;
        description
          "Mroute Received BGP Shared-Tree Prune";
      }
      bit mroute-bgp-c-mroute-suppressed {
        position 10;
        description
          "BGP C-Mroute suppressed";
      }
      bit mroute-received-bgp-s-a-route {
        position 11;
        description
          "Received BGP S-A Route";
      }
      bit mroute-sent-bgp-s-a-route {
        position 12;
        description
          "Sent BGP S-A Route";
      }
      bit mroute-pfp-sa-cache-created-entry {
        position 13;
        description
          "Populate from Packet SA cache created entry";
      }
      bit mroute-determined-by-assert {
        position 14;
        description
          "Mroute Determined by Assert";
      }
      bit mroute-iif-starg-configured {
        position 15;
        description
          "IIF-starg configured on RPF Interface";
      }
    }
    description
      "Mroute Flags Extended";
  }

  typedef mfib-flag-type {
    type bits {
      bit mfib-directly-connected {
        position 0;
        description
          "MFIB Directly Connected";
      }
      bit mfib-signal {
        position 1;
        description
          "MFIB Signal";
      }
      bit mfib-inherit-a-flag {
        position 2;
        description
          "MFIB Inherit A Flag";
      }
      bit mfib-hardware-installed {
        position 3;
        description
          "MFIB Hardware Installed";
      }
      bit mfib-data-rate-exceeds-threshold {
        position 4;
        description
          "MFIB Data Rate Exceeds Threshold";
      }
      bit mfib-keepalive {
        position 5;
        description
          "MFIB Keepalive";
      }
      bit mfib-data-driven-event {
        position 6;
        description
          "MFIB Data Driven Event";
      }
      bit mfib-mofrr-ecmp-entry {
        position 7;
        description
          "MFIB MoFRR ECMP Entry";
      }
      bit mfib-mofrr-non-ecmp-entry {
        position 8;
        description
          "MFIB MoFRR Non-ECMP Entry";
      }
      bit mfib-mrib-mofrr-primary {
        position 9;
        description
          "MRIB MoFRR Primary";
      }
      bit mfib-mfib-mofrr-primary {
        position 10;
        description
          "MFIB MoFRR Primary";
      }
      bit mfib-mofrr-primary {
        position 11;
        description
          "MoFRR Primary";
      }
      bit mfib-mofrr-entry-in-sync {
        position 12;
        description
          "MoFRR Entry in Sync";
      }
      bit mfib-mofrr-entry-in-mofrr-client {
        position 13;
        description
          "MoFRR entry in MoFRR Client";
      }
    }
    description
      "MFIB Flags";
  }

  typedef mfib-if-flag-type {
    type bits {
      bit mfib-intf-accept {
        position 0;
        description
          "MFIB Interface Accept";
      }
      bit mfib-intf-forward {
        position 1;
        description
          "MFIB Interface Forward";
      }
      bit mfib-intf-negate-signalling {
        position 2;
        description
          "MFIB Interface Negate Signalling";
      }
      bit mfib-intf-internal-copy {
        position 3;
        description
          "MFIB Interface Internal Copy";
      }
      bit mfib-intf-signal-present {
        position 4;
        description
          "MFIB Interface Signal Present";
      }
      bit mfib-intf-do-not-preserve {
        position 5;
        description
          "MFIB Interface Do not Preserve";
      }
      bit mfib-intf-not-platform-switched {
        position 6;
        description
          "MFIB Interface Not platform switched";
      }
      bit mfib-intf-mrib-forward {
        position 7;
        description
          "MFIB Interface MRIB Forward";
      }
      bit mfib-intf-mrib-accept {
        position 8;
        description
          "MFIB Interface MRIB Accept";
      }
      bit mfib-intf-mrib-signal-present {
        position 9;
        description
          "MFIB Interface MRIB Signal Present";
      }
      bit mfib-intf-force-dummy-update {
        position 10;
        description
          "MFIB Force Dummy Update";
      }
      bit mfib-intf-mfib-accept {
        position 11;
        description
          "MFIB Accept";
      }
      bit mfib-intf-mrib-accept-backup {
        position 12;
        description
          "MRIB Accept Backup";
      }
      bit mfib-intf-mfib-accept-backup {
        position 13;
        description
          "MFIB Accept Backup";
      }
      bit mfib-intf-accept-backup {
        position 14;
        description
          "MFIB Interface Accept Backup";
      }
      bit mfib-intf-force-update {
        position 15;
        description
          "MFIB Force Update";
      }
      bit mfib-intf-active {
        position 16;
        description
          "MFIB Interface Active";
      }
    }
    description
      "MFIB Interface Flags";
  }

  typedef interface-flag-type {
    type bits {
      bit intf-flag-hw-switched {
        position 0;
        description
          "Hardware Switched";
      }
      bit intf-flag-assert-winner {
        position 1;
        description
          "Assert Winner";
      }
    }
    description
      "Interface Flags Type";
  }

  grouping sr-next-hop-addr-type {
    description
      "Service Reflect next hop address type";
    leaf next-hop-source {
      type inet:ip-address;
      description
        "Next hop source";
    }
    leaf next-hop-group {
      type inet:ip-address;
      description
        "Next hop group";
    }
    leaf gr-index {
      type uint32;
      description
        "Next hop group index";
    }
  }

  grouping amt-next-hop-addr-type {
    description
      "Automatic Multicast Tunnelling next hop address type";
    leaf nh-ip-addr {
      type inet:ip-address;
      description
        "Next hop IP address";
    }
    leaf amt-udp-port {
      type uint16;
      description
        "Automatic Multicast Tunnelling UDP port";
    }
  }

  grouping lisp-next-hop-type {
    description
      "LISP next hop address type";
    leaf rloc-addr {
      type inet:ip-address;
      description
        "Routing Locator address";
    }
    leaf group-addr {
      type inet:ip-address;
      description
        "Group address";
    }
  }

  grouping vxlan-next-hop-addr-type {
    description
      "VxLAN next hop address type";
    leaf group-addr {
      type inet:ip-address;
      description
        "Group address";
    }
    leaf vni {
      type uint32;
      description
        "Virtual Network Identifier";
    }
  }

  grouping mfib-next-hop-addr-type {
    description
      "MFIB next hop address type";
    choice next-hop-addr-choice {
      description
        "MFIB next hop address based on address type";
      case mfib-nh-type-ipv4 {
        leaf next-hop-addr-v4 {
          type inet:ip-address;
          description
            "IPv4 next hop address";
        }
      }
      case mfib-nh-type-mdt-encap-ipv4 {
        leaf next-hop-addr-encap-v4 {
          type inet:ip-address;
          description
            "MDT Encap IPv4 next hop address";
        }
      }
      case mfib-nh-type-lsm {
        leaf next-hop-lsm {
          type uint32;
          description
            "Label Switched Multicast next hop address";
        }
      }
      case mfib-nh-type-lsm-nbma {
        leaf next-hop-lsm-nbma {
          type uint32;
          description
            "Label Switched Multicast Non-Broadcast Multi Access next hop address";
        }
      }
      case mfib-nh-type-cb {
        leaf next-hop-cb {
          type uint32;
          description
            "CB next hop address";
        }
      }
      case mfib-nh-type-ipv6 {
        leaf next-hop-addr-v6 {
          type inet:ip-address;
          description
            "IPv6 next hop address";
        }
      }
      case mfib-nh-type-mdt-encap-ipv6 {
        leaf next-hop-addr-encap-v6 {
          type inet:ip-address;
          description
            "MDT Encap IPv6 next hop address";
        }
      }
      case mfib-nh-type-mdt-encap-ipv4-mapped-ipv6 {
        leaf next-hop-addr-encap-v4-mapped-v6 {
          type inet:ip-address;
          description
            "MDT Encap IPv4 mapped IPv6 next hop address";
        }
      }
      case mfib-nh-type-service-reflect {
        container sr-next-hop-addr {
          description
            "Service Reflect next hop address";
          uses mroute-ios-xe-oper:sr-next-hop-addr-type;
        }
      }
      case mfib-nh-type-amt-ipv4 {
        container amt-next-hop-addr-v4 {
          description
            "Automatic Multicast Tunnelling IPv4 next hop address";
          uses mroute-ios-xe-oper:amt-next-hop-addr-type;
        }
      }
      case mfib-nh-type-amt-ipv6 {
        container amt-next-hop-addr-v6 {
          description
            "Automatic Multicast Tunnelling IPv6 next hop address";
          uses mroute-ios-xe-oper:amt-next-hop-addr-type;
        }
      }
      case mfib-nh-type-lisp-ipv4 {
        container lisp-next-hop {
          description
            "LISP next hop";
          uses mroute-ios-xe-oper:lisp-next-hop-type;
        }
      }
      case mfib-nh-type-vxlan-ipv4 {
        container vxlan-next-hop-addr-v4 {
          description
            "VxLAN IPv4 next hop address";
          uses mroute-ios-xe-oper:vxlan-next-hop-addr-type;
        }
      }
      case mfib-nh-type-vxlan-ipv6 {
        container vxlan-next-hop-addr-v6 {
          description
            "VxLAN IPv6 next hop address";
          uses mroute-ios-xe-oper:vxlan-next-hop-addr-type;
        }
      }
    }
  }

  grouping mcast-incoming-interface {
    description
      "Multicast Incoming Interface Grouping";
    leaf if-name {
      type string;
      description
        "Multicast incoming interface name";
    }
    leaf mfib-if-flags {
      type mroute-ios-xe-oper:mfib-if-flag-type;
      description
        "Mfib incoming interface flags";
    }
    leaf rpf-id {
      type uint32;
      description
        "Multicast incoming interface RPF Id";
    }
    leaf mfib-next-hop-type {
      type mroute-ios-xe-oper:mfib-nh-type;
      description
        "Incoming Interface MFIB next hop type";
    }
    container mfib-next-hop-addr {
      description
        "Incoming Interface MFIB next hop address";
      uses mroute-ios-xe-oper:mfib-next-hop-addr-type;
    }
  }

  grouping mcast-outgoing-interface {
    description
      "Multicast Outgoing Interface Grouping";
    leaf mfib-if-flags {
      type mroute-ios-xe-oper:mfib-if-flag-type;
      description
        "Mfib outgoing interface flags";
    }
    leaf output-if-counters {
      type uint64;
      description
        "Multicast outgoing interface packet counters";
    }
    leaf if-uptime {
      type yang:date-and-time;
      description
        "Multicast outgoing interface uptime";
    }
    leaf if-expiry-set {
      type empty;
      description
        "Multicast outgoing interface expiry state";
    }
    leaf if-expires {
      when "(../if-expiry-set)";
      type yang:date-and-time;
      description
        "Multicast outgoing interface expiry";
    }
    leaf is-static {
      type boolean;
      description
        "Multicast outgoing interface is static";
    }
    leaf is-proxy {
      type boolean;
      description
        "Multicast outgoing interface is proxy";
    }
    leaf next-hop {
      type inet:ip-address;
      description
        "Multicast outgoing interface next hop";
    }
    leaf outer-src {
      type inet:ip-address;
      description
        "Multicast outgoing interface outer source";
    }
    leaf aux-next-hop {
      type uint64;
      description
        "Multicast outgoing interface auxiliary next hop";
    }
    leaf if-state {
      type mroute-ios-xe-oper:interface-state-type;
      description
        "Multicast outgoing interface state";
    }
    leaf blocked {
      type boolean;
      description
        "Multicast outgoing interface blocked";
    }
    leaf if-threshold {
      type uint64;
      description
        "Multicast outgoing interface threshold";
    }
    leaf out-rate-limit {
      type uint64;
      description
        "Multicast outgoing interface out rate-limit";
    }
    leaf port-number {
      type uint32;
      description
        "Multicast outgoing interface port number";
    }
    leaf if-flags {
      type mroute-ios-xe-oper:interface-flag-type;
      description
        "Multicast outgoing interface flags";
    }
    leaf hw-packet-count {
      type uint64;
      description
        "Multicast outgoing interface hardware packet count";
    }
    leaf fs-packet-count {
      type uint64;
      description
        "Multicast outgoing interface fast switched packet count";
    }
    leaf ps-packet-count {
      type uint64;
      description
        "Multicast outgoing interface process switched packet count";
    }
    leaf egress-rate-pps {
      type uint64;
      description
        "Multicast outgoing interface egress rate in packets per second";
    }
    leaf rpf-id {
      type uint32;
      description
        "Multicast outgoing interface RPF ID";
    }
    leaf mfib-next-hop-type {
      type mroute-ios-xe-oper:mfib-nh-type;
      description
        "Outgoing interface MFIB next hop type";
    }
    container mfib-next-hop-addr {
      description
        "Outgoing interface MFIB next hop address";
      uses mroute-ios-xe-oper:mfib-next-hop-addr-type;
    }
    leaf cef-status {
      type mroute-ios-xe-oper:mcast-cef-status;
      description
        "Multicast outgoing interface CEF Status";
    }
    leaf cef-adjacency-mac {
      type binary;
      description
        "Multicast outgoing interface CEF adjacency MAC";
    }
  }

  grouping mcast-egress-if-entry {
    description
      "Multicast Outgoing Interface Entry";
    leaf if-name {
      type string;
      description
        "Multicast outgoing interface name";
    }
    container mcast-egress-if-data {
      description
        "Multicast egress interface data";
      uses mroute-ios-xe-oper:mcast-outgoing-interface;
    }
  }

  grouping mroute-state {
    description
      "Mroute oper state";
    container ingress-if {
      description
        "Mroute ingress Interface";
      uses mroute-ios-xe-oper:mcast-incoming-interface;
    }
    list mcast-egress-if-entry {
      key "if-name";
      description
        "Mroute Outgoing Interface List Entry";
      uses mroute-ios-xe-oper:mcast-egress-if-entry;
    }
    leaf in-rate-limit {
      type uint64;
      description
        "Input rate-limit";
    }
    leaf port-number {
      type uint32;
      description
        "Port-number";
    }
    leaf rp {
      type inet:ip-address;
      description
        "RP address";
    }
    leaf rpf-nbr {
      type inet:ip-address;
      description
        "RPF neighbor";
    }
    leaf mdt-join-timer-set {
      type empty;
      description
        "MDT Join timer state";
    }
    leaf mdt-join-timer {
      when "(../mdt-join-timer-set)";
      type yang:date-and-time;
      description
        "MDT Join timer";
    }
    leaf mvpn-lsm-tree-num {
      type uint32;
      description
        "MVPN Labeled Switched Multicast Tree number";
    }
    leaf lsm-root {
      type inet:ip-address;
      description
        "Labeled Switched Multicast root";
    }
    leaf lsm-type {
      type mroute-ios-xe-oper:mvpn-lsm-type;
      description
        "Labeled Switched Multicast Transport Type";
    }
    leaf sec-if-name {
      type string;
      description
        "Secondary Interface Name";
    }
    leaf sec-rpf-nbr {
      type inet:ip-address;
      description
        "Secondary RPF neighbor";
    }
    leaf mofrr-primary {
      type boolean;
      description
        "MOFRR primary";
    }
    leaf mofrr-peer-group {
      type inet:ip-address;
      description
        "MOFRR Peer Group";
    }
    leaf mofrr-peer-source {
      type inet:ip-address;
      description
        "MOFRR Peer Source";
    }
    leaf mroute-uptime {
      type yang:date-and-time;
      description
        "Mroute uptime";
    }
    leaf mroute-expiry-set {
      type empty;
      description
        "Mroute expiry state";
    }
    leaf mroute-expires {
      when "(../mroute-expiry-set)";
      type yang:date-and-time;
      description
        "Mroute expiry";
    }
    leaf mroute-mode {
      type mroute-ios-xe-oper:mroute-mode-type;
      description
        "Mroute Modes";
    }
    leaf mroute-flags {
      type mroute-ios-xe-oper:mroute-flag-type;
      description
        "Mroute flags";
    }
    leaf mroute-ext-flags {
      type mroute-ios-xe-oper:mroute-ext-flag-type;
      description
        "Mroute extended flags";
    }
    leaf mfib-flags {
      type mroute-ios-xe-oper:mfib-flag-type;
      description
        "MFIB flags";
    }
    leaf sw-packet-count {
      type uint64;
      description
        "Multicast Software packet count";
    }
    leaf sw-packets-per-second {
      type uint64;
      description
        "Multicast Software packets per second";
    }
    leaf sw-average-packet-size {
      type uint64;
      description
        "Multicast Software average packets size";
    }
    leaf sw-kbits-per-second {
      type uint64;
      description
        "Multicast Software kilo bits per second";
    }
    leaf sw-total {
      type uint64;
      description
        "Software Total Packets";
    }
    leaf sw-rpf-failed {
      type uint64;
      description
        "Software RPF failed count";
    }
    leaf sw-other-drops {
      type uint64;
      description
        "Software Other drops";
    }
    leaf hw-packet-count {
      type uint64;
      description
        "Multicast Hardware packet count";
    }
    leaf hw-packets-per-second {
      type uint64;
      description
        "Multicast Hardware packets per second";
    }
    leaf hw-average-packet-size {
      type uint64;
      description
        "Multicast Hardware average packets size";
    }
    leaf hw-kbits-per-second {
      type uint64;
      description
        "Multicast Hardware kilo bits per second";
    }
    leaf hw-total {
      type uint64;
      description
        "Hardware Total Packets";
    }
    leaf hw-rpf-failed {
      type uint64;
      description
        "Hardware RPF failed count";
    }
    leaf hw-other-drops {
      type uint64;
      description
        "Hardware Other drops";
    }
  }

  grouping mroute-key {
    description
      "Mroute key";
    leaf source {
      type inet:ip-address;
      description
        "Multicast source";
    }
    leaf group {
      type inet:ip-address;
      description
        "Multicast group";
    }
    leaf vrf {
      type string;
      description
        "VRF name";
    }
    leaf af {
      type mroute-ios-xe-oper:mroute-addr-family;
      description
        "Address Family";
    }
  }

  container mroute-oper-data {
    config false;
    description
      "Mroute operational data";
    list mroute-state {
      key "source group vrf af";
      description
        "Mroute operational state";
      uses mroute-ios-xe-oper:mroute-key;
      uses mroute-ios-xe-oper:mroute-state;
    }
  }
}
