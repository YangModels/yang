module Cisco-IOS-XE-acl-oper {
  yang-version 1;
  namespace "http://cisco.com/ns/yang/Cisco-IOS-XE-acl-oper";
  prefix acl-ios-xe-oper;
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for ACL statistical data.
     Copyright (c) 2016-2017, 2019 by Cisco Systems, Inc.
     All rights reserved.";

  revision 2020-03-01 {
    description
      "Augmented Access Lists with Access List type and Access List Entries with ACE rule data";
    reference "1.3.0";
    cisco-semver:module-version "1.3.0";
    cisco-semver-internal:os-version "17.2.1";
  }
  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2017-02-07 {
    description
      "Initial revision";
    reference "1.0.0";
    cisco-semver:module-version "1.0.0";
  }

  typedef acl-action-type {
    type enumeration {
      enum "permit" {
        value 0;
        description
          "Permit matching packets";
        tailf:code-name "ENUM_acl_action_type_ACL_ACTION_TYPE_PERMIT";
      }
      enum "deny" {
        value 1;
        description
          "Deny matching packets";
        tailf:code-name "ENUM_acl_action_type_ACL_ACTION_TYPE_DENY";
      }
    }
    description
      "Action to be taken on packets matching the rule";
  }

  typedef acl-port-operator-type {
    type enumeration {
      enum "equals" {
        value 0;
        description
          "Equals to the given port";
        tailf:code-name "ENUM_acl_port_operator_type_ACL_PORT_OPERATOR_EQ";
      }
      enum "not-equals" {
        value 1;
        description
          "Not equal to the given port";
        tailf:code-name "ENUM_acl_port_operator_type_ACL_PORT_OPERATOR_NEQ";
      }
      enum "lesser-than" {
        value 2;
        description
          "Lesser than the given port";
        tailf:code-name "ENUM_acl_port_operator_type_ACL_PORT_OPERATOR_LT";
      }
      enum "greater-than" {
        value 3;
        description
          "Greater than the given port";
        tailf:code-name "ENUM_acl_port_operator_type_ACL_PORT_OPERATOR_GT";
      }
      enum "range" {
        value 4;
        description
          "Range between the ports, including the given ports";
        tailf:code-name "ENUM_acl_port_operator_type_ACL_PORT_OPERATOR_RANGE";
      }
    }
    description
      "Specifies what operation to use while checking if the protocol port matches the given port(s)";
  }

  typedef access-list-type {
    type enumeration {
      enum "v4-standard-acl" {
        value 0;
        description
          "IPv4 standard Access Control List";
        tailf:code-name "ENUM_access_list_type_ACL_TYPE_IPV4_STANDARD";
      }
      enum "v4-extended-acl" {
        value 1;
        description
          "Ipv4 Extended Access Control List";
        tailf:code-name "ENUM_access_list_type_ACL_TYPE_IPV4_EXTENDED";
      }
      enum "v4-role-based-acl" {
        value 2;
        description
          "IPv4 Role based Access Control List";
        tailf:code-name "ENUM_access_list_type_ACL_TYPE_IPV4_ROLE_BASED";
      }
      enum "v6-acl" {
        value 3;
        description
          "Regular IPv6 Access Control List";
        tailf:code-name "ENUM_access_list_type_ACL_TYPE_IPV6";
      }
      enum "v6-role-based-acl" {
        value 4;
        description
          "IPv6 Role based Access Control List";
        tailf:code-name "ENUM_access_list_type_ACL_TYPE_IPV6_ROLE_BASED";
      }
    }
    description
      "Basic Access Control List type";
  }

  typedef acl-protocol-type {
    type enumeration {
      enum "protocol-any" {
        value 0;
        description
          "Any IP protocol";
        tailf:code-name "ENUM_acl_protocol_type_ACL_PROTOCOL_ANY";
      }
      enum "protocol-number" {
        value 1;
        description
          "Number assigned to the IP protocol";
        tailf:code-name "ENUM_acl_protocol_type_ACL_PROTOCOL_NUMBER";
      }
      enum "protocol-object-group" {
        value 2;
        description
          "Service object-group name containing the protocol(s)";
        tailf:code-name "ENUM_acl_protocol_type_ACL_PROTOCOL_OBJECT_GROUP";
      }
    }
    description
      "Options to configure the protocol for matching packets";
  }

  typedef acl-port-option-type {
    type enumeration {
      enum "port-any" {
        value 0;
        description
          "Protocol port is not configured";
        tailf:code-name "ENUM_acl_port_option_type_ACL_PORT_ANY";
      }
      enum "port-configured" {
        value 1;
        description
          "Protocol port is configured";
        tailf:code-name "ENUM_acl_port_option_type_ACL_PORT_CONFIG";
      }
    }
    description
      "ACL port configuration options";
  }

  typedef acl-v4-address-type {
    type enumeration {
      enum "v4-address-wildcard" {
        value 0;
        description
          "IPv4 address and wildcard";
        tailf:code-name "ENUM_acl_v4_address_type_ACL_V4_ADDRESS_WILDCARD";
      }
      enum "v4-host" {
        value 1;
        description
          "IPv4 host address";
        tailf:code-name "ENUM_acl_v4_address_type_ACL_V4_HOST";
      }
      enum "v4-object-group" {
        value 2;
        description
          "IPv4 network object group containing IPv4 addresses";
        tailf:code-name "ENUM_acl_v4_address_type_ACL_V4_OBJECT_GROUP";
      }
      enum "v4-fqdn-group" {
        value 3;
        description
          "Name of the FQDN group associated with this entry";
        tailf:code-name "ENUM_acl_v4_address_type_ACL_V4_FQDN_GROUP";
      }
      enum "v4-any" {
        value 4;
        description
          "Any IPv4 address in this position";
        tailf:code-name "ENUM_acl_v4_address_type_ACL_V4_ANY";
      }
    }
    description
      "Options to configure IPv4 address";
  }

  typedef acl-v6-address-type {
    type enumeration {
      enum "v6-address-prefix" {
        value 0;
        description
          "IPv6 address and prefix length used to match the packet";
        tailf:code-name "ENUM_acl_v6_address_type_ACL_V6_ADDRESS_PREFIX";
      }
      enum "v6-address-wildcard" {
        value 1;
        description
          "IPv6 address and wildcard used to match the packet";
        tailf:code-name "ENUM_acl_v6_address_type_ACL_V6_ADDRESS_WILDCARD";
      }
      enum "v6-host" {
        value 2;
        description
          "IPv6 host address used to match the packet";
        tailf:code-name "ENUM_acl_v6_address_type_ACL_V6_HOST";
      }
      enum "v6-object-group" {
        value 3;
        description
          "Name of IPv6 network object group containing the address(es)";
        tailf:code-name "ENUM_acl_v6_address_type_ACL_V6_OBJECT_GROUP";
      }
      enum "v6-fqdn-group" {
        value 4;
        description
          "Name of the FQDN group associated with this entry";
        tailf:code-name "ENUM_acl_v6_address_type_ACL_V6_FQDN_GROUP";
      }
      enum "v6-any" {
        value 5;
        description
          "Matches with any IPv6 address on the packet";
        tailf:code-name "ENUM_acl_v6_address_type_ACL_V6_ANY";
      }
    }
    description
      "Options to configure IPv6 address";
  }

  typedef access-list-type-flags {
    type bits {
      bit internal {
        position 0;
        description
          "ACL generated by the system for internal use";
      }
      bit downloaded {
        position 1;
        description
          "ACL downloaded into the device";
      }
      bit per-user {
        position 2;
        description
          "Per user ACL, configured programmatically";
      }
    }
    description
      "Access Control List flags";
  }

  grouping acl-protocol {
    description
      "Protocol to match packets";
    leaf protocol {
      type acl-ios-xe-oper:acl-protocol-type;
      config false;
      description
        "DO NOT USE!  -- hidden internal";
      tailf:hidden "full";
      tailf:meta-data "hidden" {
        tailf:meta-value "true";
      }
    }
    choice protocol-choice {
      description
        "Protocol configuration options";
      case protocol-any {
        leaf any {
          type empty;
          description
            "Any IP protocol";
        }
      }
      case protocol-number {
        leaf number {
          type uint8;
          description
            "Number assigned to the IP protocol";
        }
      }
      case protocol-object-group {
        leaf object-group {
          type string;
          description
            "Service object-group name containing the protocol(s)";
        }
      }
    }
  }

  grouping acl-port-data {
    description
      "ACL entry port configuration data";
    leaf port-operator {
      type acl-ios-xe-oper:acl-port-operator-type;
      description
        "Specifies what operation to use while checking if the protocol port matches the given port(s)";
    }
    leaf-list ports {
      type uint16;
      ordered-by user;
      description
        "When the port match is \"less than\" or \"greater than\" then the port list will have one entry for the operation. When the port match is \"range\" then port list will have two values with the range being between the values. When the port match is \"equals\" and \"not equals\", then there may be up to 10 number of ports.";
    }
  }

  grouping acl-port {
    description
      "Port configuration for the protocol";
    leaf port-option {
      type acl-ios-xe-oper:acl-port-option-type;
      config false;
      description
        "DO NOT USE!  -- hidden internal";
      tailf:hidden "full";
      tailf:meta-data "hidden" {
        tailf:meta-value "true";
      }
    }
    choice port-option-choice {
      description
        "Indicates whether the port was configured or not";
      case port-any {
        leaf any {
          type empty;
          description
            "Port is not configured. So, all ports will be matched";
        }
      }
      case port-configured {
        container port-data {
          description
            "Port configuration to be matched against the packet";
          uses acl-ios-xe-oper:acl-port-data;
        }
      }
    }
  }

  grouping acl-v4-address-wildcard {
    description
      "IPv4 network address and wildcard";
    leaf address {
      type inet:ipv4-address;
      description
        "IPv4 network address";
    }
    leaf wildcard {
      type inet:ipv4-address;
      description
        "Wildcard or inverted network mask";
    }
  }

  grouping acl-v4-address {
    description
      "IPv4 address to be matched in this position";
    leaf v4-address {
      type acl-ios-xe-oper:acl-v4-address-type;
      config false;
      description
        "DO NOT USE!  -- hidden internal";
      tailf:hidden "full";
      tailf:meta-data "hidden" {
        tailf:meta-value "true";
      }
    }
    choice v4-address-choice {
      description
        "Options to configure IPv4 address";
      case v4-address-wildcard {
        container address-wildcard {
          description
            "IPv4 address and wildcard";
          uses acl-ios-xe-oper:acl-v4-address-wildcard;
        }
      }
      case v4-host {
        leaf host {
          type inet:ipv4-address;
          description
            "IPv4 host address";
        }
      }
      case v4-object-group {
        leaf object-group {
          type string;
          description
            "IPv4 network object group containing IPv4 addresses";
        }
      }
      case v4-fqdn-group {
        leaf fqdn-group {
          type string;
          description
            "Name of the FQDN group associated with this entry";
        }
      }
      case v4-any {
        leaf any {
          type empty;
          description
            "Any IPv4 address in this position";
        }
      }
    }
  }

  grouping acl-v4-standard-ace-data {
    description
      "IPv4 Standard Access List entry details";
    leaf action {
      type acl-ios-xe-oper:acl-action-type;
      description
        "Indicates if the packets were permitted or denied";
    }
    container source-address {
      description
        "Source address used to match the packets";
      uses acl-ios-xe-oper:acl-v4-address;
    }
  }

  grouping acl-v4-extended-ace-data {
    description
      "IPv4 ACE data";
    leaf action {
      type acl-ios-xe-oper:acl-action-type;
      description
        "Indicates if the packets were permitted or denied";
    }
    container protocol {
      description
        "Protocol used to match the packets";
      uses acl-ios-xe-oper:acl-protocol;
    }
    container source-address {
      description
        "Source address used to match the packets";
      uses acl-ios-xe-oper:acl-v4-address;
    }
    container source-port {
      description
        "Source port used to match the packets";
      uses acl-ios-xe-oper:acl-port;
    }
    container destination-address {
      description
        "Destination address used to match the packets";
      uses acl-ios-xe-oper:acl-v4-address;
    }
    container destination-port {
      description
        "Destination port used to match the packets";
      uses acl-ios-xe-oper:acl-port;
    }
  }

  grouping acl-v4-role-based-ace-data {
    description
      "IPv4 Role based ACE data";
    leaf action {
      type acl-ios-xe-oper:acl-action-type;
      description
        "Indicates if the packets were permitted or denied";
    }
    container protocol {
      description
        "Protocol used to match the packets";
      uses acl-ios-xe-oper:acl-protocol;
    }
    container source-port {
      description
        "Source port used to match the packets";
      uses acl-ios-xe-oper:acl-port;
    }
    container destination-port {
      description
        "Destination port used to match the packets";
      uses acl-ios-xe-oper:acl-port;
    }
  }

  grouping acl-v6-address-wildcard {
    description
      "IPv6 address and wildcard";
    leaf address {
      type inet:ipv6-address;
      description
        "IPv6 address";
    }
    leaf wildcard {
      type inet:ipv6-address;
      description
        "Wildcard used with the IPv6 address";
    }
  }

  grouping acl-v6-address {
    description
      "IPv6 address configuration";
    leaf v6-address {
      type acl-ios-xe-oper:acl-v6-address-type;
      config false;
      description
        "DO NOT USE!  -- hidden internal";
      tailf:hidden "full";
      tailf:meta-data "hidden" {
        tailf:meta-value "true";
      }
    }
    choice v6-address-choice {
      description
        "Options to configure IPv6 address";
      case v6-address-prefix {
        leaf address-prefix {
          type inet:ip-prefix;
          description
            "IPv6 address and prefix length used to match the packet";
        }
      }
      case v6-address-wildcard {
        container address-wildcard {
          description
            "IPv6 address and wildcard used to match the packet";
          uses acl-ios-xe-oper:acl-v6-address-wildcard;
        }
      }
      case v6-host {
        leaf host {
          type inet:ipv6-address;
          description
            "IPv6 host address used to match the packet";
        }
      }
      case v6-object-group {
        leaf object-group {
          type string;
          description
            "Name of IPv6 network object group containing the address(es)";
        }
      }
      case v6-fqdn-group {
        leaf fqdn-group {
          type string;
          description
            "Name of the FQDN group associated with this entry";
        }
      }
      case v6-any {
        leaf any {
          type empty;
          description
            "Matches with any IPv6 address on the packet";
        }
      }
    }
  }

  grouping acl-v6-ace-data {
    description
      "IPv6 Access Control List entry";
    leaf action {
      type acl-ios-xe-oper:acl-action-type;
      description
        "Indicates if the packets were permitted or denied";
    }
    container protocol {
      description
        "Protocol used to match the packets";
      uses acl-ios-xe-oper:acl-protocol;
    }
    container source-address {
      description
        "Source address used to match the packets";
      uses acl-ios-xe-oper:acl-v6-address;
    }
    container source-port {
      description
        "Source port used to match the packets";
      uses acl-ios-xe-oper:acl-port;
    }
    container destination-address {
      description
        "Destination address used to match the packets";
      uses acl-ios-xe-oper:acl-v6-address;
    }
    container destination-port {
      description
        "Destination port used to match the packets";
      uses acl-ios-xe-oper:acl-port;
    }
  }

  grouping acl-v6-role-based-ace-data {
    description
      "IPv6 Role based Access Control List entry";
    leaf action {
      type acl-ios-xe-oper:acl-action-type;
      description
        "Indicates if the packets were permitted or denied";
    }
    container protocol {
      description
        "Protocol used to match the packets";
      uses acl-ios-xe-oper:acl-protocol;
    }
    container source-port {
      description
        "Source port used to match the packets";
      uses acl-ios-xe-oper:acl-port;
    }
    container destination-port {
      description
        "Destination port used to match the packets";
      uses acl-ios-xe-oper:acl-port;
    }
  }

  grouping ace-rule-data {
    description
      "ACL entry parameters used for matching";
    leaf acl-rule {
      type acl-ios-xe-oper:access-list-type;
      config false;
      description
        "DO NOT USE!  -- hidden internal";
      tailf:hidden "full";
      tailf:meta-data "hidden" {
        tailf:meta-value "true";
      }
    }
    choice acl-rule-choice {
      description
        "ACL entry rules based on ACL type";
      case v4-standard-acl {
        container v4-standard-ace-rule {
          description
            "IPv4 Standard ACL rule matching parameters";
          uses acl-ios-xe-oper:acl-v4-standard-ace-data;
        }
      }
      case v4-extended-acl {
        container v4-extended-ace-rule {
          description
            "IPv4 extended ACL rule matching parameters";
          uses acl-ios-xe-oper:acl-v4-extended-ace-data;
        }
      }
      case v4-role-based-acl {
        container v4-role-based-ace-rule {
          description
            "IPv4 Role-based ACL rule matching parameters";
          uses acl-ios-xe-oper:acl-v4-role-based-ace-data;
        }
      }
      case v6-acl {
        container v6-ace-rule {
          description
            "IPv6 regular ACL rule matching parameters";
          uses acl-ios-xe-oper:acl-v6-ace-data;
        }
      }
      case v6-role-based-acl {
        container v6-role-based-ace-rule {
          description
            "IPv6 Role based ACL rule matching parameters";
          uses acl-ios-xe-oper:acl-v6-role-based-ace-data;
        }
      }
    }
  }

  grouping ace-oper-data {
    description
      "ACE operational data";
    leaf match-counter {
      type yang:counter64;
      description
        "Number of matches for an access list entry";
    }
  }

  grouping access-list-entry {
    description
      "Entry representing ACE list entry";
    leaf rule-name {
      type uint32;
      description
        "Entry number.";
    }
    container access-list-entries-oper-data {
      description
        "Per access list entries operational data";
      uses acl-ios-xe-oper:ace-oper-data;
    }
    container access-list-entries-rule-data {
      description
        "Per access list entries rule data";
      uses acl-ios-xe-oper:ace-rule-data;
    }
  }

  grouping access-list {
    description
      "A list of access-list-entry(ACE)";
    leaf access-control-list-name {
      type string;
      description
        "The name of access-list. A device MAY restrict the length
         and value of this name, possibly space and special characters are not
         allowed";
    }
    container access-list-entries {
      description
        "access-list-entry(ACE) information";
      list access-list-entry {
        key "rule-name";
        description
          "A list of ACEs";
        uses acl-ios-xe-oper:access-list-entry;
      }
    }
    leaf access-control-list-type {
      type acl-ios-xe-oper:access-list-type;
      description
        "Basic type of access control list";
    }
    leaf access-control-list-type-flags {
      type acl-ios-xe-oper:access-list-type-flags;
      description
        "Other information about the access list";
    }
  }

  container access-lists {
    config false;
    description
      "This is top level container for Access Control Lists. It can have one
       or more Access Control List.";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list access-list {
      key "access-control-list-name";
      description
        "An access list (acl) is an ordered list of
         access list entries (ACE). Each access control entries has a
         list of match criteria, and a list of actions.
         Since there are several kinds of access control lists
         implemented with different attributes for
         each and different for each vendor, this
         model accommodates customizing access control lists for
         each kind and for each vendor.";
      uses acl-ios-xe-oper:access-list;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWcwWAnsAArhfgFAAEAYFED/3/+q/9//qQAKNwC7VRiKejVPTSYIBhMjJo9RoBo0fqRoEoVT9omp6SenqmmEyaAAaMJkBoGmppqmmjQAGjRpoAAAA0EkJMmgTQp7SmjTJoNqNGeqaDQ2o/Au8xrPyA8yP2q1ItAgiWN5EklQGHKPbvpFDEYNYpY6JTCxfAXCTc5nsV9Jy62DfIpuJM8oREIkIAc4BmHdnYYQ47oDSnm3ESXUdbnQd50rRuI/vbZ1xHtJKCH7GZojeiZEORENkoOYH2QMAyWSSCTJCOKNfcterssDu627iSJGtVM+iSTqTmiwTUYYa/AsB58hqrlyNVB0l+2KVsz5Cm1FPEgRdblYjWHFsTHh4j3mo4uFmSo6qcC6mhCZCXjtLcpzjKsrJBvJm6xZqpeFSSNyViIPEaYFcUXItPAQyRNGJmMQyMlhVQSIXFFUpMlMuhQT0TzzvktN+4or0VEZkkyLLEPIxZMmEJCw3QtSBBaCDamtGrCaY0FVaIebNVlQs1Iks98fGSDlhGMkHk6JhVJSks4AKqIOnp0ztt7ggXKZpWMrO07j+Hy+Mw11Pr5HfhM8qYrILSSKoYDwTpKaFBRVuqSBr3AWifkSzgiwLRsFb7zaEcZFmTnPaiqvtyzce90M9LSRTn/i+3h2rBGlM1wzRomGq08A5S5CthxJHLWByjDUm17kmw9FcIFqYaxR1CuGxkbz0mc0GzNGGZizQxVluNgnGBprjPCq2UVSSmK4zHnPQDcry+JILSwLmJGCZZDWbk/9u2lS+iidegiQsqWzAHJYY0R6vNkjmu0qShE5BH8XckU4UJDMFgJ7A";
      }
      tailf:meta-data "uncompressed_size" {
        tailf:meta-value "1421";
      }
    }
  }

  container schema-metadata-Cisco-IOS-XE-acl-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-acl-oper";
    }
    tailf:meta-data "organization" {
      tailf:meta-value "Cisco Systems, Inc.";
    }
    tailf:meta-data "semver" {
      tailf:meta-value "2020-03-01";
    }
  }
}
