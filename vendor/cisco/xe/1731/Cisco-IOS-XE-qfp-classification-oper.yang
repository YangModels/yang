module Cisco-IOS-XE-qfp-classification-oper {
  yang-version 1;
  namespace "http://cisco.com/ns/yang/Cisco-IOS-XE-qfp-classification-oper";
  prefix datapath-classification;

  import Cisco-IOS-XE-common-types {
    prefix common-types-ios-xe;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Quantum Flow Processor (QFP) classification operational data.
     Copyright (c) 2019-2020 by Cisco Systems, Inc.
     All rights reserved.";

  revision 2020-07-01 {
    description
      "Use extended location";
    reference "0.0.0";
    cisco-semver:module-version "0.0.0";
    cisco-semver-internal:os-version "17.3.1";
  }
  revision 2020-03-01 {
    description
      "Initial revision";
    reference "1.0.0";
    cisco-semver:module-version "1.0.0";
    cisco-semver-internal:os-version "17.2.1";
  }

  grouping exmem-usage {
    description
      "The memory usage of the Quantum Flow Processor features";
    leaf feature-id {
      type uint32;
      description
        "The internally assign identifier for the feature";
    }
    leaf client-name {
      type string;
      description
        "The human readable name of the feature";
    }
    leaf total-vmr-entries {
      type uint32;
      description
        "The number of value/mask allocations for this feature";
    }
    leaf total-exmem-usage {
      type uint32;
      units "bytes";
      description
        "Total external memory usage";
    }
    leaf total-percent-exmem-usage {
      type uint32;
      units "percentage";
      description
        "Total percentage of external memory usage";
    }
    leaf total-alloc {
      type uint32;
      description
        "Total number of allocations";
    }
    leaf total-free {
      type uint32;
      description
        "Total number of frees";
    }
  }

  container qfp-classification-oper-data {
    config false;
    description
      "QFP classification operational data";
    tailf:callpoint "datapath-oper-db";
    tailf:meta-data "callpoint" {
      tailf:meta-value "datapath-oper-db";
    }
    tailf:meta-data "greenprefix" {
      tailf:meta-value "//locations/services;serviceName=dp_oper";
    }
    tailf:meta-data "name" {
      tailf:meta-value "Cisco-IOS-XE-qfp-classification-oper";
    }
    list location {
      key "fru slot bay chassis node";
      description
        "A list of data provider locations";
      uses common-types-ios-xe:extended-location;
      list exmem-usage {
        key "feature-id";
        description
          "The memory usage of various features within the Quantum Flow Processor";
        uses datapath-classification:exmem-usage;
      }
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWUY8L2kAALbfgEAAEAYAEDsj2kq/J/5qMADsiGJJMxTyKfqNRkHqeU08pvRQwAyaaDIYIaYjRgSU0mpkGg0HtUMT1AA4HuPFdtZjHuvI1GUX7ZuZcUAQ6osxDMizM2G7+oXbWuMTJWPZE7w0lTNYI+wAwgid+6KdMlejmMYJYohXSpkUAiilZJxxuqmh2GfXJpfDfPRztGPxmRCzR3mR5ip6F+RaqnKuFCl62xK3MyLzIzgRmaYWUL4oOanRA+Lr7nnniGsAeoxF8UJKR45SumGQdaQ0DgYG0KvsxGsOUyLBCmI2RG6WQeYB+P4u5IpwoSCMeF7S";
      }
      tailf:meta-data "uncompressed_size" {
        tailf:meta-value "383";
      }
    }
    container Cisco-IOS-XE-common-types {
      description
        "Hidden internal container used for metadata";
      uses common-types-ios-xe:__yangpp_metadata;
    }
  }

  container schema-metadata-Cisco-IOS-XE-qfp-classification-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-qfp-classification-oper";
    }
    tailf:meta-data "organization" {
      tailf:meta-value "Cisco Systems, Inc.";
    }
    tailf:meta-data "semver" {
      tailf:meta-value "2020-07-01";
    }
  }
}
