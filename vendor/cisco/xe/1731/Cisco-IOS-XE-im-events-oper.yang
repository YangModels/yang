module Cisco-IOS-XE-im-events-oper {
  yang-version 1;
  namespace "http://cisco.com/ns/yang/Cisco-IOS-XE-im-events-oper";
  prefix im-events-ios-xe-oper;
  import ietf-inet-types {
    prefix inet;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for ioxman eventq data.
     Copyright (c) 2018-2020 by Cisco Systems, Inc.
     All rights reserved.";

  revision 2020-07-01 {
    description
      "- Remove unused empty container im-events";
    reference "0.0.0";
    cisco-semver:module-version "0.0.0";
    cisco-semver-internal:os-version "17.3.1";
  }
  revision 2019-05-01 {
    description
      "Added semantic version";
    reference "1.1.0";
    cisco-semver:module-version "1.1.0";
  }
  revision 2018-03-19 {
    description
      "Initial revision";
    reference "1.0.0";
    cisco-semver:module-version "1.0.0";
  }

  typedef im-event-type {
    type enumeration {
      enum "im-iox-enable" {
        value 0;
        description
          "IOX enable";
        tailf:code-name "ENUM_im_event_type_IM_EVT_IOX_ENABLE";
      }
      enum "im-app-install" {
        value 1;
        description
          "IOxMan application install";
        tailf:code-name "ENUM_im_event_type_IM_EVT_INSTALL";
      }
      enum "im-app-uninstall" {
        value 2;
        description
          "IOxMan application uninstall";
        tailf:code-name "ENUM_im_event_type_IM_EVT_UNINSTALL";
      }
      enum "im-app-start" {
        value 3;
        description
          "IOxMan application start event";
        tailf:code-name "ENUM_im_event_type_IM_EVT_APP_START";
      }
      enum "im-app-no-start" {
        value 4;
        description
          "IOxMan application stop event";
        tailf:code-name "ENUM_im_event_type_IM_EVT_APP_NO_START";
      }
      enum "im-unsolicited-event" {
        value 5;
        description
          "IOxMan unsolicited event";
        tailf:code-name "ENUM_im_event_type_IM_EVT_UNSOLICITED";
      }
    }
    description
      "IOxMan event type";
  }

  typedef im-notification-severity {
    type enumeration {
      enum "critical" {
        value 0;
        tailf:code-name "ENUM_im_notification_severity_IM_NOTF_SEV_CRITICAL";
      }
      enum "major" {
        value 1;
        tailf:code-name "ENUM_im_notification_severity_IM_NOTF_SEV_MAJOR";
      }
      enum "minor" {
        value 2;
        tailf:code-name "ENUM_im_notification_severity_IM_NOTF_SEV_MINOR";
      }
    }
    description
      "Notification severity";
  }

  typedef im-status-type {
    type enumeration {
      enum "im-status-pass" {
        value 0;
        description
          "IOxMan status pass";
        tailf:code-name "ENUM_im_status_type_IM_STS_PASS";
      }
      enum "im-status-fail" {
        value 1;
        description
          "IOxMan status fail";
        tailf:code-name "ENUM_im_status_type_IM_STS_FAIL";
      }
    }
    description
      "IOxMan status type";
  }

  typedef im-app-state {
    type enumeration {
      enum "im-state-deployed" {
        value 0;
        description
          "Deployed state";
        tailf:code-name "ENUM_im_app_state_IM_STATE_DEPLOYED";
      }
      enum "im-state-activated" {
        value 1;
        description
          "Activated state";
        tailf:code-name "ENUM_im_app_state_IM_STATE_ACTIVATED";
      }
      enum "im-state-running" {
        value 2;
        description
          "Running state";
        tailf:code-name "ENUM_im_app_state_IM_STATE_RUNNING";
      }
      enum "im-state-stopped" {
        value 3;
        description
          "Stopped state";
        tailf:code-name "ENUM_im_app_state_IM_STATE_STOPPED";
      }
      enum "im-state-uninstalled" {
        value 4;
        description
          "Uninstalled state";
        tailf:code-name "ENUM_im_app_state_IM_STATE_UNINSTALLED";
      }
    }
    description
      "IOxMan Application state";
  }

  grouping im-event {
    description
      "IOxMan eventq element example";
    leaf severity-level {
      type im-events-ios-xe-oper:im-notification-severity;
      description
        "Event severity";
    }
    leaf host-name {
      type string;
      description
        "Host name";
    }
    leaf system-ip {
      type inet:ip-address;
      description
        "IP address";
    }
    leaf vrf-name {
      type string;
      description
        "VRF name";
    }
    leaf app-id {
      type string;
      description
        "App ID";
    }
    leaf ev-type {
      type im-events-ios-xe-oper:im-event-type;
      description
        "Event type";
    }
    leaf status {
      type im-events-ios-xe-oper:im-status-type;
      description
        "Status for the event";
    }
    leaf message {
      type string;
      description
        "Message describing the event";
    }
    leaf app-state {
      type im-events-ios-xe-oper:im-app-state;
      description
        "App State";
    }
  }

  notification im-event {
    description
      "IOxMan eventq";
    uses im-events-ios-xe-oper:im-event;
  }
  container Cisco-IOS-XE-im-events-oper {
    config false;
    tailf:callpoint "im-eventq-db";
    tailf:meta-data "callpoint" {
      tailf:meta-value "im-eventq-db";
    }
    tailf:meta-data "greenprefix" {
      tailf:meta-value "/services;serviceName=imevent";
    }
    tailf:hidden "full";
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWQIXtpgAAZnfgBAAEAYAED+332q/t/9qQAGuDaVhKmmojJpvUg0ANAGTQGmQSSGU0NE1MgBoaANAAMANNGg0xAAAAyAEiRCZqTNTRo8oaDBGQDTS74VdEens6lKC/LdBQJPOZ0FofQe2ET06urHAK0yy5rtSTG8YYQNBEEDGDgcV2cniksEzoLzDOD54SRd2HKWMTVlsqkpQ4uAWViNun0269SmM3+0I2biqLjQiXnwLON05Va2LFSRDV7qpQAnnrg3kX7LchaX+scJrPaVgGh5eKiYRCvpxrmNOkWW20oSIM0iqkyFZNqBFDMViKqNFijJNaRVLmfFBoVO1blD2L5cnCKzjk1pSOVY0dFGLpNt0SbLaKnW5bL3eCtywg8kRxchJYSutKR60uI2iHVSTnj+xJLfBIeHDJiw2rJojKguqCSCt2GjzKS3GverY2G2bJNfrfDihZ6lekDVa/Ghn7LCcmTgzKBi82SIfdBgjmlBonzDNCCsgrxGR1kJEyzRqJhLzOrKojMlRMqgnFE2xq9E45FSrWwIiwicx8tKD+G91GNPmN/4u5IpwoSAEL20w";
      }
      tailf:meta-data "uncompressed_size" {
        tailf:meta-value "846";
      }
    }
  }

  container schema-metadata-Cisco-IOS-XE-im-events-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-im-events-oper";
    }
    tailf:meta-data "organization" {
      tailf:meta-value "Cisco Systems, Inc.";
    }
    tailf:meta-data "semver" {
      tailf:meta-value "2020-07-01";
    }
  }
}
