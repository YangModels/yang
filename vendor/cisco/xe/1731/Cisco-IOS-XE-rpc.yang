module Cisco-IOS-XE-rpc {
  namespace "http://cisco.com/ns/yang/Cisco-IOS-XE-rpc";
  prefix ios-xe-rpc;

  import cisco-semver {
    prefix cisco-semver;
  }
  import ietf-inet-types {
    prefix inet;
  }
  include Cisco-IOS-XE-aaa-rpc;
  include Cisco-IOS-XE-arp-rpc;
  include Cisco-IOS-XE-bgp-rpc;
  include Cisco-IOS-XE-crypto-rpc;
  include Cisco-IOS-XE-multicast-rpc;
  include Cisco-IOS-XE-dhcp-rpc;
  include Cisco-IOS-XE-ospf-rpc;
  include Cisco-IOS-XE-platform-rpc;

  organization
    "Cisco Systems";
  contact
    "<mailto:cs-yang@cisco.com>";
  description
    "NED RPC YANG module for IOS
     Copyright (c) 2016-2020 by Cisco Systems, Inc.
     All rights reserved.";

  revision 2020-07-01 {
    description
      "Added multicast feature RPC";
    cisco-semver:module-version "3.0.0";
  }
  revision 2020-03-01 {
    description
      "Added a container in monitor capture";
    cisco-semver:module-version "2.1.0";
  }
  revision 2019-11-01 {
    description
      "Added new test RPC";
    cisco-semver:module-version "2.0.0";
  }
  revision 2019-07-01 {
    description
      "Establish semantic version baseline";
    cisco-semver:module-version "1.0.0";
  }
  revision 2018-11-25 {
    description
      "Exec command to send AMP file analysis apikey";
  }
  revision 2018-11-07 {
    description
      "Cleanup spelling errors in description statements";
  }
  revision 2018-11-06 {
    description
      "Add UTD database update EXEC command";
  }
  revision 2018-10-29 {
    description
      "Added range-string for debug ipsec command";
  }
  revision 2018-10-12 {
    description
      "Added crypto pki debug and exec commands";
  }
  revision 2018-10-02 {
    description
      "Add unmount command in existing hw-module chain";
  }
  revision 2018-10-01 {
    description
      "Add IPSEC no debug exec commands";
  }
  revision 2018-09-20 {
    description
      "Add IPSEC debug exec commands";
  }
  revision 2018-08-17 {
    description
      "Added cts credential * and clear cts * commands";
  }
  revision 2018-08-05 {
    description
      "Add License Install Commands";
  }
  revision 2018-08-01 {
    description
      "Add UTD clear commands";
  }
  revision 2018-07-30 {
    description
      "Add hw-module commands";
  }
  revision 2018-06-18 {
    description
      "Update UTD signature update EXEC command to include local file support";
  }
  revision 2018-05-21 {
    description
      "Add Umbrella clear commands";
  }
  revision 2018-04-18 {
    description
      "Add ZBFW clear commands";
  }
  revision 2018-03-14 {
    description
      "Add UTD signature update EXEC command";
  }
  revision 2017-12-18 {
    description
      "Add GIR start maintenance and stop maintenance EXEC commands";
  }
  revision 2017-12-06 {
    description
      "Add Viptela clear aaa local user lockout username <> command";
  }
  revision 2017-11-27 {
    description
      "Add Viptela clear and release commands";
  }
  revision 2017-11-21 {
    description
      "Clear flow commands";
  }
  revision 2017-11-14 {
    description
      "Add app-hosting and guestshell EXEC commands";
  }
  revision 2017-11-04 {
    description
      "Add reason to reload";
  }
  revision 2017-10-12 {
    description
      "Added more nodes to the license RPC";
  }
  revision 2017-10-10 {
    description
      "Add copy and delete EXEC commands";
  }
  revision 2017-09-21 {
    description
      "Add virtual-service EXEC commands";
  }
  revision 2017-08-28 {
    description
      "Added the force option to the reload RPC";
  }
  revision 2017-07-13 {
    description
      "Added service sd-avc CLI";
  }
  revision 2017-02-07 {
    description
      "Initial revision";
  }

  grouping cisco-xe-rpc-output {
    description
      "Used to return output from RPCs";
    leaf result {
      type string;
      description
        "Output returned by the network element";
    }
  }

  rpc default {
    description
      "Set a command to its defaults";
    input {
      choice default-choice {
        mandatory true;
        case interface-case {
          leaf interface {
            description
              "Select an interface to configure";
            type string {
              pattern "[A-Za-z]([\\w/.-]+)";
            }
          }
        }
      }
    }
    output {
      uses cisco-xe-rpc-output;
    }
  }
  rpc clear {
    description
      "Clear";
    input {
      choice clear-choice {
        mandatory true;
        case interface-case {
          leaf interface {
            description
              "Select an interface to clear";
            type string {
              pattern "[A-Za-z]([\\w/.-]+)";
            }
          }
        }
        case count-case {
          leaf count {
            description
              "Select an interface to clear";
            type string {
              pattern "[A-Za-z]([\\w/.-]+)";
            }
          }
        }
        case ip-case {
          container ip {
            choice ip-protocol {
              case bgp-case {
                uses clear-choice-ip-case-ip-protocol-bgp-case-grouping;
              }
              case dhcp-case {
                uses clear-choice-ip-case-ip-protocol-dhcp-case-grouping;
              }
              case ospf-case {
                uses clear-choice-ip-case-ip-protocol-ospf-case-grouping;
              }
            }
          }
        }
        case arp-cache-case {
          uses clear-choice-arp-cache-case-grouping;
        }
        case aaa-case {
          uses clear-choice-aaa-case-grouping;
        }
        case platform-case {
          uses clear-choice-platform-case-grouping;
        }
      }
    }
    output {
      uses cisco-xe-rpc-output;
    }
  }
  rpc crypto {
    description
      "Encryption related commands";
    input {
      uses crypto-input-grouping;
    }
    output {
      uses cisco-xe-rpc-output;
    }
  }
  rpc release {
    description
      "Release a resource";
    input {
      leaf dhcp {
        description
          "Release a dhcp lease (an interface)";
        type string;
      }
    }
    output {
      uses cisco-xe-rpc-output;
    }
  }
  rpc reload {
    description
      "Halt and perform a cold restart";
    input {
      leaf force {
        description
          "Force a restart even if there is unsaved config";
        type boolean;
      }
      leaf reason {
        description
          "Reload reason";
        type string;
      }
    }
    output {
      uses cisco-xe-rpc-output;
    }
  }
  rpc factory-reset {
    description
      "Perform a factory reset of the device";
    input {
      container all {
        description
          "Perform a factory reset of the device. This will 
           restore the device to the factory setting and is an
           irreversible operation";
        presence "true";
      }
    }
    output {
      uses cisco-xe-rpc-output;
    }
  }
  rpc license {
    input {
      choice license-command-choice {
        case licese-smart {
          container smart {
            choice smart-choice {
              case register-case {
                container register {
                  leaf idtoken {
                    mandatory true;
                    type string;
                  }
                  leaf force {
                    description
                      "Forcefully register";
                    type empty;
                  }
                }
              }
              case deregister-case {
                leaf deregister {
                  type empty;
                }
              }
              case renew-case {
                container renew {
                  choice renew-choice {
                    mandatory true;
                    leaf ID {
                      type empty;
                    }
                    leaf auth {
                      type empty;
                    }
                  }
                }
              }
            }
          }
        }
        case license-install {
          leaf install {
            description
              "Install license information";
            type string {
              pattern "(((bootflash:)|(flash:)|(ftp:)|(http:)|(https:)|(nvram:)|(param:)|(scp:)|(syslog)|(system:)|(tftp:)|(tmpsys:)).*)";
            }
          }
        }
        case license-clear {
          leaf clear {
            description
              "Clear license information. Feature name to clear";
            type string;
          }
        }
      }
    }
    output {
      uses cisco-xe-rpc-output;
    }
  }
  rpc service {
    description
      "IOS integrated service enablement";
    input {
      choice services-choice {
        case wass-case {
          container waas {
            description
              "WAAS service";
            container wcm {
              description
                "Configure WAAS Central Manager (WCM)";
              choice wcm-choices {
                case ip-case {
                  container ip {
                    description
                      "ipv4";
                    leaf address {
                      type inet:ipv4-address;
                    }
                  }
                }
                case ipv6-case {
                  container ipv6 {
                    description
                      "ipv6 address";
                    leaf address {
                      type inet:ipv6-address;
                    }
                  }
                }
              }
            }
          }
        }
        case sd-avc-case {
          container sd-avc {
            description
              "SD-AVC service management";
            choice sd-avc-choice {
              mandatory true;
              case activate-case {
                leaf activate {
                  type empty;
                }
              }
              case configure-case {
                container configure {
                  container gateway {
                    leaf interface {
                      type string;
                    }
                    leaf service-ip {
                      type inet:ipv4-address;
                    }
                    leaf activate {
                      type empty;
                    }
                  }
                }
              }
              case connect-case {
                leaf connect {
                  type empty;
                }
              }
              case help-case {
                leaf help {
                  type empty;
                }
              }
              case deactivate-case {
                leaf deactivate {
                  type empty;
                }
              }
              case install-case {
                container install {
                  leaf package {
                    type string;
                  }
                }
              }
              case status-case {
                leaf status {
                  type empty;
                }
              }
              case unconfigure-case {
                leaf unconfigure {
                  type empty;
                }
              }
              case uninstall-case {
                leaf uninstall {
                  type empty;
                }
              }
              case upgrade-case {
                container upgrade {
                  leaf package {
                    type string;
                  }
                }
              }
            }
          }
        }
      }
    }
    output {
      uses cisco-xe-rpc-output;
    }
  }
  rpc virtual-service {
    description
      "Virtual-service management";
    input {
      choice operation {
        mandatory true;
        container install {
          leaf name {
            type string;
          }
          leaf package {
            type string;
          }
          leaf media {
            type string;
          }
        }
        container uninstall {
          leaf name {
            type string;
          }
        }
        container upgrade {
          leaf name {
            type string;
          }
          leaf package {
            type string;
          }
        }
        container move {
          leaf name {
            mandatory true;
            type string;
          }
          choice file-choice {
            mandatory true;
            container core {
              leaf to {
                type string {
                  pattern "(((bootflash:)|(flash:)|(harddisk:)).*)";
                }
              }
            }
            container log {
              leaf to {
                type string {
                  pattern "(((bootflash:)|(flash:)|(harddisk:)).*)";
                }
              }
            }
          }
        }
      }
    }
    output {
      uses cisco-xe-rpc-output;
    }
  }
  rpc copy {
    description
      "Copy from one file to another";
    input {
      leaf source-drop-node-name {
        mandatory true;
        type string {
          pattern "((((bootflash:)|(harddisk:)|(flash:)|(nvram:)|(ftp:)|(http:)|(https:)|(scp:)|(tftp:)).*)|((running-config)|(startup-config)))";
        }
      }
      leaf destination-drop-node-name {
        mandatory true;
        type string {
          pattern "((((bootflash:)|(harddisk:)|(flash:)|(nvram:)|(ftp:)|(http:)|(https:)|(scp:)|(tftp:)).*)|((running-config)|(startup-config)))";
        }
      }
    }
    output {
      uses cisco-xe-rpc-output;
    }
  }
  rpc delete {
    description
      "Delete a file";
    input {
      leaf filename-drop-node-name {
        mandatory true;
        type string {
          pattern "(((bootflash:)|(harddisk:)|(flash:)|(nvram:)).*)";
        }
      }
    }
    output {
      uses cisco-xe-rpc-output;
    }
  }
  rpc app-hosting {
    description
      "App-hosting management";
    input {
      choice lifecycle {
        mandatory true;
        container install {
          leaf appid {
            type string;
          }
          leaf package {
            type string;
          }
        }
        container uninstall {
          leaf appid {
            type string;
          }
        }
        container activate {
          leaf appid {
            type string;
          }
        }
        container deactivate {
          leaf appid {
            type string;
          }
        }
        container start {
          leaf appid {
            type string;
          }
        }
        container stop {
          leaf appid {
            type string;
          }
        }
        container upgrade {
          leaf appid {
            type string;
          }
          leaf package {
            type string;
          }
        }
        container verification {
          leaf enable {
            type empty;
          }
          leaf disable {
            type empty;
          }
        }
        container move {
          choice type-choice {
            mandatory true;
            case appid-case {
              leaf appid {
                mandatory true;
                type string;
              }
              choice file-choice {
                mandatory true;
                container core {
                  leaf to {
                    type string {
                      pattern "(((bootflash:)|(flash:)|(harddisk:)).*)";
                    }
                  }
                }
                container log {
                  leaf to {
                    type string {
                      pattern "(((bootflash:)|(flash:)|(harddisk:)).*)";
                    }
                  }
                }
              }
            }
            case system-case {
              container system {
                container techsupport {
                  leaf to {
                    type string {
                      pattern "(((bootflash:)|(flash:)|(harddisk:)).*)";
                    }
                  }
                }
              }
            }
          }
        }
      }
    }
    output {
      uses cisco-xe-rpc-output;
    }
  }
  rpc guestshell {
    description
      "guestshell managementshell";
    input {
      choice action {
        mandatory true;
        case destroy-case {
          leaf destroy {
            description
              "Destroy guestshell";
            type empty;
          }
        }
        case disable-case {
          leaf disable {
            description
              "Disable guestshell";
            type empty;
          }
        }
        case enable-case {
          leaf enable {
            description
              "Enable guestshell";
            type empty;
          }
        }
      }
    }
    output {
      uses cisco-xe-rpc-output;
    }
  }
  rpc start {
    description
      "Start system operations";
    input {
      leaf maintenance {
        description
          "GIR start maintenance mode";
        type empty;
      }
    }
    output {
      uses cisco-xe-rpc-output;
    }
  }
  rpc stop {
    description
      "Stop system operations";
    input {
      leaf maintenance {
        description
          "GIR stop maintenance mode";
        type empty;
      }
    }
    output {
      uses cisco-xe-rpc-output;
    }
  }
  rpc hw-module {
    description
      "Control of individual components in the system";
    input {
      container switch {
        description
          "Switch in the system";
        leaf switch-number-drop-node-name {
          description
            "Switch number in the Stack (Refer to show switch CLI)";
          type uint8 {
            range "1..8";
          }
        }
        container usbflash1 {
          description
            "USB SSD";
          choice umount-sec {
            mandatory true;
            case unmount-case {
              leaf unmount {
                description
                  "unmount on usbflash1";
                type empty;
              }
            }
            case security-case {
              container security {
                description
                  "Security on usbflash1";
                choice security-choice {
                  mandatory true;
                  case enable-case {
                    container enable {
                      description
                        "Enable security on usbflash1";
                      presence "true";
                      leaf password {
                        description
                          "Enter password for enabling security on usbflash1";
                        type string;
                      }
                    }
                  }
                  case disable-case {
                    container disable {
                      description
                        "Disable security on usbflash1";
                      presence "true";
                      leaf password {
                        description
                          "Enter password for Disabling security on usbflash1";
                        type string;
                      }
                    }
                  }
                  case unlock-case {
                    container unlock {
                      description
                        "Unlock security on usbflash1";
                      presence "true";
                      leaf password {
                        description
                          "Enter password for unlock security on usbflash1";
                        type string;
                      }
                    }
                  }
                }
              }
            }
          }
        }
      }
    }
    output {
      uses cisco-xe-rpc-output;
    }
  }
  rpc debug {
    description
      "Debug";
    input {
      choice debug-choice {
        mandatory true;
        case crypto-case {
          uses debug-input-crypto-grouping;
        }
        case platform-case {
          uses debug-choice-platform-case-grouping;
        }
      }
    }
    output {
      uses cisco-xe-rpc-output;
    }
  }
  rpc monitor {
    description
      "monitor";
    input {
      leaf capture {
        description
          "Capture session";
        type string;
      }
      leaf match {
        description
          "Describe filters inline";
        type string;
      }
      leaf interface {
        description
          "Interface";
        type string;
      }
      choice capture-direction-choice {
        case both-case {
          leaf both {
            type empty;
          }
        }
        case in-case {
          leaf in {
            type empty;
          }
        }
        case out-case {
          leaf out {
            type empty;
          }
        }
      }
      container buffer {
        description
          "Buffer options";
        leaf size {
          description
            "Size of buffer in MB";
          type uint8 {
            range "1..100";
          }
        }
        leaf circular {
          description
            "circular buffer";
          type empty;
        }
      }
      container limit {
        description
          "Limit Packets Captured";
        leaf duration {
          description
            "Limit total duration of capture in seconds";
          type uint32 {
            range "1..1000000";
          }
        }
        leaf every {
          description
            "Limit capture to one in every nth packet";
          type uint32 {
            range "2..100000";
          }
        }
        leaf packet-len {
          description
            "Limit the packet length to capture";
          type uint16 {
            range "64..9500";
          }
        }
        leaf packets {
          description
            "Limit number of packets to capture";
          type uint32 {
            range "1..100000";
          }
        }
        leaf pps {
          description
            "Limit number of packets per second to capture";
          type uint32 {
            range "1..1000000";
          }
        }
      }
      choice capture-command-choice {
        case start-case {
          leaf start {
            description
              "Enable session capture points";
            type empty;
          }
        }
        case stop-case {
          leaf stop {
            description
              "Disable session capture points";
            type empty;
          }
        }
        case stop-export-case {
          leaf stop_export {
            description
              "Export session capture buffer";
            type empty;
          }
        }
      }
    }
    output {
      uses cisco-xe-rpc-output;
    }
  }
  rpc pnpa {
    description
      "Plug and play command";
    input {
      container service {
        description
          "Service Name";
        choice service-choice {
          case wakeup-case {
            container wakeup {
              description
                "Wake up Profile";
              leaf profile-drop-node-name {
                description
                  "Profile name";
                type string;
              }
            }
          }
          case reset-case {
            leaf reset {
              description
                "Reset PnP config";
              type empty;
            }
          }
        }
      }
    }
    output {
      uses cisco-xe-rpc-output;
    }
  }
  rpc test {
    description
      "test exec command";
    input {
      choice test-feature;
    }
    output {
      uses cisco-xe-rpc-output;
    }
  }
}
