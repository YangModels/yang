module Cisco-IOS-XE-ha-oper {
  yang-version 1;
  namespace "http://cisco.com/ns/yang/Cisco-IOS-XE-ha-oper";
  prefix ha-ios-xe-oper;
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for High Availability (HA) operational state data.
     Copyright (c) 2017-2019 by Cisco Systems, Inc.
     All rights reserved.";

  revision 2019-11-01 {
    description
      "Modified ha enabled to provide whether system is running in HA";
    reference "1.2.1";
    cisco-semver:module-version "1.2.1";
    cisco-semver-internal:os-version "17.1.1";
  }
  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2018-05-02 {
    description
      "Initial revision";
    reference "1.0.0";
    cisco-semver:module-version "1.0.0";
  }

  typedef rf-states {
    type enumeration {
      enum "db-rf-unknown" {
        value 0;
        description
          "RF HA state is unknown";
        tailf:code-name "ENUM_rf_states_DB_RF_UNKNOWN";
      }
      enum "db-rf-disabled" {
        value 1;
        description
          "RF HA state is disabled";
        tailf:code-name "ENUM_rf_states_DB_RF_DISABLED";
      }
      enum "db-rf-initialization" {
        value 2;
        description
          "RF HA state is initialization";
        tailf:code-name "ENUM_rf_states_DB_RF_INITIALIZATION";
      }
      enum "db-rf-negotiation" {
        value 3;
        description
          "RF HA state is negotiation";
        tailf:code-name "ENUM_rf_states_DB_RF_NEGOTIATION";
      }
      enum "db-rf-standby-cold" {
        value 4;
        description
          "RF HA state is standby cold";
        tailf:code-name "ENUM_rf_states_DB_RF_STANDBY_COLD";
      }
      enum "db-rf-standby-config" {
        value 5;
        description
          "RF HA state is standby config";
        tailf:code-name "ENUM_rf_states_DB_RF_STANDBY_CONFIG";
      }
      enum "db-rf-standby-filesys" {
        value 6;
        description
          "RF HA state is standby filesys";
        tailf:code-name "ENUM_rf_states_DB_RF_STANDBY_FILESYS";
      }
      enum "db-rf-standby-bulk" {
        value 7;
        description
          "RF HA state is standby bulk";
        tailf:code-name "ENUM_rf_states_DB_RF_STANDBY_BULK";
      }
      enum "db-rf-standby-hot" {
        value 8;
        description
          "RF HA state is standby hot";
        tailf:code-name "ENUM_rf_states_DB_RF_STANDBY_HOT";
      }
      enum "db-rf-active-fast" {
        value 9;
        description
          "RF HA state is active fast";
        tailf:code-name "ENUM_rf_states_DB_RF_ACTIVE_FAST";
      }
      enum "db-rf-active-drain" {
        value 10;
        description
          "RF HA state is active drain";
        tailf:code-name "ENUM_rf_states_DB_RF_ACTIVE_DRAIN";
      }
      enum "db-rf-active-preconfig" {
        value 11;
        description
          "RF HA state is active preconfig";
        tailf:code-name "ENUM_rf_states_DB_RF_ACTIVE_PRECONFIG";
      }
      enum "db-rf-active-postconfig" {
        value 12;
        description
          "RF HA state is active postconfig";
        tailf:code-name "ENUM_rf_states_DB_RF_ACTIVE_POSTCONFIG";
      }
      enum "db-rf-active" {
        value 13;
        description
          "RF HA state is active";
        tailf:code-name "ENUM_rf_states_DB_RF_ACTIVE";
      }
      enum "db-rf-active-extraload" {
        value 14;
        description
          "RF HA state is active extraload";
        tailf:code-name "ENUM_rf_states_DB_RF_ACTIVE_EXTRALOAD";
      }
      enum "db-rf-active-handback" {
        value 15;
        description
          "RF HA state is active handback";
        tailf:code-name "ENUM_rf_states_DB_RF_ACTIVE_HANDBACK";
      }
      enum "db-rf-standby-warm" {
        value 16;
        description
          "RF HA state is standby warm";
        tailf:code-name "ENUM_rf_states_DB_RF_STANDBY_WARM";
      }
      enum "db-rf-issu-negotiation" {
        value 17;
        description
          "RF HA state is ISSU negotiation";
        tailf:code-name "ENUM_rf_states_DB_RF_ISSU_NEGOTIATION";
      }
      enum "db-rf-standby-issu-negotiation-late" {
        value 18;
        description
          "RF HA state is standby ISSU negotiation late";
        tailf:code-name "ENUM_rf_states_DB_RF_STANDBY_ISSU_NEGOTIATION_LATE";
      }
      enum "db-rf-platform-sync" {
        value 19;
        description
          "RF HA state is platform sync";
        tailf:code-name "ENUM_rf_states_DB_RF_PLATFORM_SYNC";
      }
    }
    description
      "HA peer states and local peer states";
  }

  grouping ha-infra-content {
    description
      "HA infrastructure status grouping";
    leaf ha-state {
      type ha-ios-xe-oper:rf-states;
      description
        "State for local peer";
    }
    leaf peer-state {
      type ha-ios-xe-oper:rf-states;
      description
        "State for remote peer";
    }
    leaf last-switchover-time {
      type yang:date-and-time;
      description
        "System last switchover time";
    }
    leaf last-switchover-reason {
      type string;
      description
        "System last switchover reason";
    }
    leaf image-version {
      type string;
      description
        "System image version";
    }
    leaf leaf-mode {
      type string;
      description
        "System running redundancy mode";
    }
    leaf ha-enabled {
      type boolean;
      description
        "System ready for switchover";
    }
    leaf has-switchover-occured {
      type boolean;
      description
        "System switchover happened before or not";
    }
  }

  container ha-oper-data {
    config false;
    description
      "HA infrastructure status operational data";
    tailf:callpoint "ios-oper-db";
    tailf:meta-data "callpoint" {
      tailf:meta-value "ios-oper-db";
    }
    tailf:meta-data "greenprefix" {
      tailf:meta-value "/services;serviceName=ios_oper";
    }
    container ha-infra {
      presence "ha-infra";
      description
        "HA infrastructure status";
      uses ha-ios-xe-oper:ha-infra-content;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWaqgeVQAAgdfgEAAEAYQED/v3/q/79/6QAHOBTKGiNU9NRkAMgaBo9RgQeoAGik/VNiEfqNRpoGgAADQ0Aw0NAAABoAAAAASQgppp6Q0EnqZAAep+lNpojTNT86zk+ukLQqEWj2QdX90j1yTS6QtC0ItJmQbW24hVdryA+vubtSBhnQhx2HZ/Z5V7kg7Rt+PRL1VH4KNrvhIe/zhpDzPIEOlsauNkktH12pccuLce5Lv/WR0qvnyvdIXyiLuDwlqGi6gEgRM518NNapqUFN5JqUBF6uUiQWC+ID9vZi6SWj8tEuezba/wbSRNbekwLlJTrlGi00ybW1m7MlqvWONYBGGjS2dRJKOA+6IZgJE4Thglv3ZqlUnrve6ZRKnE+5TYlZG0lGanGrFIsztC4AQURUmyL1LC2GcOqo8gJZPGRNZy83zXJZenLxsdblrkhGowdK2KlrJ25vIB74oCKgOetWFrpNbNypKtAQ1E0nwWdZ5tg5QNQWgIgC6AgiQik6nY9ukiatE0rKje8G6ywrxpUwARkhQh1cEUwe+BADK04Ty4aynVSYV0WzdQscIBBrWPUhKaU+A9Hi8nADaGrNOGpLZ1qdl9MyT5r5pUJ+m0F9G5TMH+M/4u5IpwoSFVQPKoA==";
      }
      tailf:meta-data "uncompressed_size" {
        tailf:meta-value "1055";
      }
    }
  }

  container schema-metadata-Cisco-IOS-XE-ha-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-ha-oper";
    }
    tailf:meta-data "organization" {
      tailf:meta-value "Cisco Systems, Inc.";
    }
    tailf:meta-data "semver" {
      tailf:meta-value "2019-11-01";
    }
  }
}
