module Cisco-IOS-XE-controller-shdsl-common {
  yang-version 1;
  namespace "http://cisco.com/ns/yang/Cisco-IOS-XE-controller-shdsl-common";
  prefix shdsl-ios-xe-common;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring controller SHDSL operational information.
     Copyright (c) 2019 by Cisco Systems, Inc.
     All rights reserved.";

  revision 2020-03-01 {
    description
      "Initial revision";
    reference "1.0.0";
    cisco-semver:module-version "1.0.0";
  }

  typedef controller-state {
    type enumeration {
      enum "admin-down" {
        value 0;
        description
          "SHDSL controller state administrative down";
      }
      enum "up" {
        value 1;
        description
          "SHDSL controller state up";
      }
      enum "down" {
        value 2;
        description
          "SHDSL controller state down";
      }
    }
    description
      "Controller states";
  }

  typedef term-type {
    type enumeration {
      enum "co" {
        value 0;
        description
          "Termination type central office";
      }
      enum "cpe" {
        value 1;
        description
          "Termination type customer premises equipment";
      }
    }
    description
      "SHDSL termination type";
  }

  typedef mode-type {
    type enumeration {
      enum "mode-efm" {
        value 0;
        description
          "Mode is ethernet";
      }
      enum "mode-atm" {
        value 1;
        description
          "Mode is Async Transfer mode";
      }
    }
    description
      "SHDSL mode type";
  }

  typedef group-state {
    type enumeration {
      enum "shdsl-group-up" {
        value 0;
        description
          "SHDSL group is up";
      }
      enum "shdsl-group-down" {
        value 1;
        description
          "SHDSL group is down";
      }
      enum "shdsl-group-shutdown" {
        value 2;
        description
          "SHDSL group is shutdown";
      }
    }
    description
      "Group state";
  }

  typedef group-type {
    type enumeration {
      enum "atm-2wire" {
        value 0;
        description
          "Group type ATM two wire";
      }
      enum "efm-2wire" {
        value 1;
        description
          "Group type Ethernet two wire";
      }
      enum "mpair" {
        value 2;
        description
          "Group type m-pair";
      }
      enum "efm-bond" {
        value 3;
        description
          "Group type Ethernet bonding";
      }
      enum "atm-auto" {
        value 4;
        description
          "Group type ATM auto";
      }
      enum "efm-auto" {
        value 5;
        description
          "Group type Ethernet auto";
      }
    }
    description
      "Group type";
  }

  typedef annex-type {
    type enumeration {
      enum "annex-a" {
        value 0;
        description
          "Annex A";
      }
      enum "annex-b" {
        value 1;
        description
          "Annex B";
      }
      enum "annex-f" {
        value 2;
        description
          "Annex F";
      }
      enum "annex-g" {
        value 3;
        description
          "Annex G";
      }
      enum "annex-a-f" {
        value 4;
        description
          "Annex A-F";
      }
      enum "annex-b-g" {
        value 5;
        description
          "Annex B-G";
      }
      enum "annex-auto" {
        value 6;
        description
          "Annex auto";
      }
    }
    description
      "Annex type";
  }

  typedef pmms-states {
    type enumeration {
      enum "pmms-enabled" {
        value 0;
        description
          "Power measurement modulation session enabled";
      }
      enum "pmms-disabled" {
        value 1;
        description
          "Power measurement modulation session disabled";
      }
    }
    description
      "Power measurement modulation session state";
  }

  typedef line-coding-type {
    type enumeration {
      enum "tcpam-auto" {
        value 0;
        description
          "TCPAM auto";
      }
      enum "tcpam-16" {
        value 1;
        description
          "TCPAM 16";
      }
      enum "tcpam-32" {
        value 2;
        description
          "TCPAM 32";
      }
      enum "tcpam-64" {
        value 3;
        description
          "TCPAM 64";
      }
      enum "tcpam-128" {
        value 4;
        description
          "TCPAM 128";
      }
      enum "tcpam-4" {
        value 5;
        description
          "TCPAM 4";
      }
      enum "tcpam-8" {
        value 6;
        description
          "TCPAM 8";
      }
    }
    description
      "Line coding type";
  }

  typedef link-states {
    type enumeration {
      enum "dsl-up" {
        value 0;
        description
          "Link DSL up";
      }
      enum "dsl-down" {
        value 1;
        description
          "Link DSL down";
      }
      enum "ima-up" {
        value 2;
        description
          "Link inverse multiplexing for ATM up";
      }
      enum "ima-down" {
        value 3;
        description
          "Link inverse multiplexing for ATM down";
      }
      enum "dsl-shutdown" {
        value 4;
        description
          "Link DSL shutdown";
      }
    }
    description
      "Link states";
  }

  typedef alarm-states {
    type enumeration {
      enum "set" {
        value 0;
        description
          "Alarm set";
      }
      enum "none" {
        value 1;
        description
          "Alarm none";
      }
    }
    description
      "Alarm states";
  }

  typedef modem-states {
    type enumeration {
      enum "down-not-ready" {
        value 0;
        description
          "Modem down not ready";
      }
      enum "down-ready" {
        value 1;
        description
          "Modem down ready";
      }
      enum "stop-down-ready" {
        value 2;
        description
          "Modem stop down ready";
      }
      enum "initializing" {
        value 3;
        description
          "Modem initializing";
      }
      enum "up-data-mode" {
        value 4;
        description
          "Modem up data mode";
      }
    }
    description
      "Modem states";
  }

  typedef logs-state {
    type enumeration {
      enum "logs-enabled" {
        value 0;
        description
          "Logs enabled";
      }
      enum "logs-disabled" {
        value 1;
        description
          "Logs disabled";
      }
    }
    description
      "Logs state";
  }

  typedef efm-data-type {
    type enumeration {
      enum "efm-data-type-fragments" {
        value 0;
        description
          "Ethernet data type fragments";
      }
      enum "efm-data-type-frames" {
        value 1;
        description
          "Ethernet data type frames";
      }
    }
    description
      "Ethernet data type";
  }

  typedef shdsl-grp-config-state {
    type enumeration {
      enum "shdsl-group-state-congigured" {
        value 0;
        description
          "SHDSL group state configured";
      }
      enum "shdsl-group-state-not-configured" {
        value 1;
        description
          "SHDSL group state not configured";
      }
    }
    description
      "SHDSL group configuration state";
  }

  grouping shdsl-slot-info-key {
    description
      "SHDSL slot information";
    leaf slot-num {
      type uint32;
      description
        "SHDSL slot number";
    }
    leaf subslot-num {
      type uint32;
      description
        "SHDSL subslot number";
    }
  }

  grouping counter-stats {
    description
      "Counter stats";
    leaf es {
      type uint32;
      description
        "Errored seconds";
    }
    leaf ses {
      type uint32;
      description
        "Severely errored seconds";
    }
    leaf crc {
      type uint32;
      description
        "Cyclic redundancy check";
    }
    leaf losws {
      type uint32;
      description
        "Loss of synchronization word seconds";
    }
    leaf uas {
      type uint32;
      description
        "Unavailable seconds";
    }
  }

  grouping dsl-stats {
    description
      "DSL statistics";
    leaf power-back-off {
      type uint32;
      description
        "Power back off";
    }
    leaf fe-power-back-off {
      type uint32;
      description
        "Forward error power back off";
    }
    leaf loop-attenuation {
      type uint32;
      description
        "Loop attenuation";
    }
    leaf snr-margin {
      type uint32;
      description
        "Signal to noise ratio margin";
    }
    container current-15-minutes {
      description
        "Current 15 minutes reading of the counter";
      uses shdsl-ios-xe-common:counter-stats;
    }
    container previous-15-minutes {
      description
        "Previous 15 minutes reading of the counter";
      uses shdsl-ios-xe-common:counter-stats;
    }
    container current-24-hours {
      description
        "Current 24 hours reading of the counter";
      uses shdsl-ios-xe-common:counter-stats;
    }
    container previous-24-hours {
      description
        "Previous 24 hours reading of the counter";
      uses shdsl-ios-xe-common:counter-stats;
    }
  }

  grouping efm-stats {
    description
      "Ethernet statistics";
    leaf data-type {
      type shdsl-ios-xe-common:efm-data-type;
      description
        "Data type";
    }
    leaf efm-tc-tx {
      type uint32;
      description
        "Total number of Ethernet frames sent";
    }
    leaf efm-tc-rx {
      type uint32;
      description
        "Total number of Ethernet frames received";
    }
  }

  grouping atm-tc-tx-stats {
    description
      "Total number of ATM cells sent statistics";
    leaf data-cells {
      type uint32;
      description
        "Data cells";
    }
    leaf idle-unassigned {
      type uint32;
      description
        "Idle unassigned";
    }
  }

  grouping atm-tc-rx-stats {
    description
      "Total number of ATM cells received statistics";
    leaf data-cells {
      type uint32;
      description
        "Data cells";
    }
    leaf uncorrected-hec {
      type uint32;
      description
        "Uncorrected header error checksum";
    }
    leaf ocd {
      type uint32;
      description
        "Number of Out of Cell Delineation events";
    }
    leaf lcd-start {
      type uint32;
      description
        "Loss of Cell Delineation defects start";
    }
    leaf lcd-end {
      type uint32;
      description
        "Loss of Cell Delineation defects end";
    }
  }

  grouping atm-stats {
    description
      "ATM statistics";
    container atm-tc-tx {
      description
        "Total number of ATM cells sent";
      uses shdsl-ios-xe-common:atm-tc-tx-stats;
    }
    container atm-tc-rx {
      description
        "Total number of ATM cells receive";
      uses shdsl-ios-xe-common:atm-tc-rx-stats;
    }
  }

  grouping shdsl-link-information {
    description
      "shdsl link information";
    leaf link-id {
      type uint32;
      description
        "Link number";
    }
    leaf status {
      type shdsl-ios-xe-common:link-states;
      description
        "Link status";
    }
    leaf losws-defect-alarm {
      type shdsl-ios-xe-common:alarm-states;
      description
        "Loss of synchronization word seconds defect alarm";
    }
    leaf snr-margin-alarm {
      type shdsl-ios-xe-common:alarm-states;
      description
        "Signal to noise ratio margin alarm";
    }
    leaf loop-attenuation-alarm {
      type shdsl-ios-xe-common:alarm-states;
      description
        "Loop attenuation alarm";
    }
    leaf termination {
      type shdsl-ios-xe-common:term-type;
      description
        "Termination";
    }
    leaf line-mode {
      type shdsl-ios-xe-common:group-type;
      description
        "Line mode";
    }
    leaf annex {
      type shdsl-ios-xe-common:annex-type;
      description
        "Annex";
    }
    leaf line-coding {
      type shdsl-ios-xe-common:line-coding-type;
      description
        "Line coding";
    }
    leaf config-auto-rate {
      type boolean;
      description
        "Configured rate auto";
    }
    leaf configured-rate {
      type uint32;
      units "kbps";
      description
        "Configured rate";
    }
    leaf actual-rate {
      type uint32;
      units "kbps";
      description
        "Actual rate";
    }
    leaf modem-status {
      type shdsl-ios-xe-common:modem-states;
      description
        "Modem status";
    }
    leaf link-condition {
      type string;
      description
        "Link condition";
    }
    leaf reason {
      type string;
      description
        "Reason";
    }
    container dsl-statistics {
      description
        "DSL statistics";
      uses shdsl-ios-xe-common:dsl-stats;
    }
    container atm-statistics {
      description
        "ATM statistics";
      uses shdsl-ios-xe-common:atm-stats;
    }
    container efm-statistics {
      description
        "Ethernet statistics";
      uses shdsl-ios-xe-common:efm-stats;
    }
  }

  grouping shdsl-configured-link {
    description
      "SHDSL configured link";
    leaf link-configured {
      type empty;
      description
        "Link configured";
    }
    container linfo {
      when "boolean(../link-configured)";
      description
        "Link information";
      uses shdsl-ios-xe-common:shdsl-link-information;
    }
  }

  grouping shdsl-group-info {
    description
      "SHDSL group information";
    leaf group-id {
      type uint32;
      description
        "Group number";
    }
    leaf gstate {
      type shdsl-ios-xe-common:group-state;
      description
        "Indicated group status up/down/shutdown";
    }
    leaf type {
      type shdsl-ios-xe-common:group-type;
      description
        "Group type";
    }
    leaf ethernet-interface-name {
      type string;
      description
        "Ethernet interface";
    }
    leaf atm-interface-name {
      type string;
      description
        "ATM interface";
    }
    leaf active-links {
      type uint32;
      description
        "Active links";
    }
    leaf bit-map {
      type string;
      description
        "Bit map";
    }
    leaf line-termination {
      type shdsl-ios-xe-common:term-type;
      description
        "Line termination";
    }
    leaf annex {
      type shdsl-ios-xe-common:annex-type;
      description
        "Annex";
    }
    leaf pmms-state {
      type shdsl-ios-xe-common:pmms-states;
      description
        "Power measurement modulation session state";
    }
    leaf line-coding {
      type shdsl-ios-xe-common:line-coding-type;
      description
        "Line coding";
    }
    leaf config-auto-rate {
      type boolean;
      description
        "Configured rate auto";
    }
    leaf configured-rate {
      type uint32;
      units "Kbps";
      description
        "Configured rate";
    }
    leaf actual-rate {
      type uint32;
      units "Kbps";
      description
        "Actual rate";
    }
    leaf dying-gasp {
      type string;
      description
        "Indicates whether dying gasp is present";
    }
    leaf training-logs-state {
      type shdsl-ios-xe-common:logs-state;
      description
        "Indicates training logs state is Enabled/Disabled";
    }
    leaf configured-links {
      type uint32;
      description
        "Configured links";
    }
    list configured-link-information {
      description
        "Configured link information";
      uses shdsl-ios-xe-common:shdsl-configured-link;
    }
  }

  grouping shdsl-configured-group {
    description
      "SHDSL configured group";
    leaf group-configured {
      type empty;
      description
        "Group configured";
    }
    container ginfo {
      when "boolean(../group-configured)";
      description
        "Group information";
      uses shdsl-ios-xe-common:shdsl-group-info;
    }
  }
}
