module Cisco-IOS-XE-switch-dp-mac-learning-oper {
  yang-version 1;
  namespace "http://cisco.com/ns/yang/Cisco-IOS-XE-switch-dp-mac-learning-oper";
  prefix switch-dp-mac-learning-oper;

  import Cisco-IOS-XE-common-types {
    prefix common-types-ios-xe;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for switch device datapath MAC learning statistics
     Copyright (c) 2019-2020 by Cisco Systems, Inc.
     All rights reserved.";

  revision 2020-07-01 {
    description
      "Initial revision";
    reference "1.0.0";
    cisco-semver:module-version "1.0.0";
    cisco-semver-internal:os-version "17.3.1";
  }

  grouping learning-stats {
    description
      "Datapath MAC learning statistics";
    leaf learning-error-count {
      type uint32;
      description
        "Count of learning errors";
    }
    leaf learning-cache-count {
      type uint32;
      description
        "Count of learning cache entries";
    }
    leaf learning-cache-validation-failure {
      type uint32;
      description
        "Count of learning cache validation failures";
    }
  }

  grouping datapath-mac-learning-stats {
    description
      "MAC address learning statistics";
    leaf general-err-count {
      type uint32;
      description
        "Count of general errors";
    }
    leaf ios-notif-count {
      type uint32;
      description
        "Count of notifications sent to IOS process";
    }
    leaf ios-notif-cache-count {
      type uint32;
      description
        "Count of cached notifications sent to IOS process";
    }
    container l2-accumulated {
      description
        "Layer 2 learning counters";
      uses switch-dp-mac-learning-oper:learning-stats;
    }
    container l3-accumulated {
      description
        "Layer 3 learning counters";
      uses switch-dp-mac-learning-oper:learning-stats;
    }
  }

  grouping mac-learning-statistics {
    description
      "This object contains datapath MAC learning statistics";
    container stats {
      description
        "This object contains the counters";
      uses switch-dp-mac-learning-oper:datapath-mac-learning-stats;
    }
  }

  container switch-dp-mac-learning-oper-data {
    config false;
    description
      "Switching device datapath MAC learning operational data";
    tailf:callpoint "fed-emul-oper-db";
    tailf:meta-data "callpoint" {
      tailf:meta-value "fed-emul-oper-db";
    }
    tailf:meta-data "greenprefix" {
      tailf:meta-value "//locations/services;serviceName=fed_emul_oper";
    }
    tailf:meta-data "emulated" {
      tailf:meta-value "true";
    }
    tailf:meta-data "name" {
      tailf:meta-value "Cisco-IOS-XE-switch-dp-mac-learning-oper";
    }
    list location {
      key "fru slot bay chassis node";
      description
        "A list of data provider locations";
      uses common-types-ios-xe:extended-location;
      container mac-learning-stats {
        presence "mac-learning-stats";
        description
          "This object contains MAC learning statistics";
        uses switch-dp-mac-learning-oper:mac-learning-statistics;
      }
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWY2r05EAAM9fgEAAEAYQEDsj2kq/597qMAEGpsJQlMJiYmmIxGjINMTQaKNGQAAAAAAJIqaPRqPSNNAaAHqAaNi0965ZZzFdquMkvih++HZubagFKlRmEZlFVlGVp9dYqgpqVqTAgug0HEqZSDtBVg4vxglCoGCoXc9eBbk6XNHEc6JdUNCdDomBgROBh3q5P3VyLmG6TvWv9q32ssxdiFy5hfvH5HvO7SZHIqylMKd0aNsjGOQS+U2Jm1QJIqDKmCMDkr17sy4opouyYZx7LWU8V4ODQrUrR6CmMTTVoJNJfqytjCFNKH0OkgMuGSZ2C8lQODUmAguojbcnHJgvTMYhr4yWAY/i7kinChIRtXpyIA==";
      }
      tailf:meta-data "uncompressed_size" {
        tailf:meta-value "436";
      }
    }
    container Cisco-IOS-XE-common-types {
      description
        "Hidden internal container used for metadata";
      uses common-types-ios-xe:__yangpp_metadata;
    }
  }

  container schema-metadata-Cisco-IOS-XE-switch-dp-mac-learning-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-switch-dp-mac-learning-oper";
    }
    tailf:meta-data "organization" {
      tailf:meta-value "Cisco Systems, Inc.";
    }
    tailf:meta-data "semver" {
      tailf:meta-value "2020-07-01";
    }
  }
}
