module Cisco-IOS-XE-crypto-pki-oper {
  yang-version 1;
  namespace "http://cisco.com/ns/yang/Cisco-IOS-XE-crypto-pki-oper";
  prefix crypto-pki-ios-xe-oper;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of yang definitions
     for PKI operational data.
     Copyright (c) 2018-2019 by Cisco Systems, Inc.
     All rights reserved.";

  revision 2019-11-01 {
    description
      "Updated trustpoint status flags";
    reference "1.2.0";
    cisco-semver:module-version "1.2.0";
  }
  revision 2019-05-01 {
    description
      "Added semantic version";
    reference "1.1.0";
    cisco-semver:module-version "1.1.0";
  }
  revision 2018-12-03 {
    description
      "Initial revision";
    reference "1.0.0";
    cisco-semver:module-version "1.0.0";
  }

  typedef crypto-pki-tp-mode {
    type enumeration {
      enum "crypto-pki-mode-none" {
        value 0;
        description
          "Normal Trustpoint";
      }
      enum "crypto-pki-mode-ra" {
        value 1;
        description
          "Registration Authority mode Trustpoint";
      }
      enum "crypto-pki-mode-subcs" {
        value 2;
        description
          "Subordinate Certificate Server mode Trustpoint";
      }
    }
    description
      "Trustpoint mode whether it is RA or SUBCS or neither.";
  }

  grouping crypto-pki-data {
    description
      "crypto pki data";
    leaf label {
      type string;
      description
        "Trustpoint label or name";
    }
    leaf mode {
      type crypto-pki-ios-xe-oper:crypto-pki-tp-mode;
      description
        "Trustpoint mode";
    }
    leaf tp-authenticated {
      type boolean;
      description
        "Set to true if trustpoint is authenticated, false otherwise";
    }
    leaf tp-keys-generated {
      type boolean;
      description
        "Set to true if keys are generated, false otherwise";
    }
    leaf tp-enrolled {
      type boolean;
      description
        "Set to true if trustpoint is enrolled, false otherwise";
    }
    leaf tp-scep-enrollment-in-progress {
      type boolean;
      description
        "Set to true if SCEP enrollment is in progress, false otherwise";
    }
  }

  container crypto-pki-oper-data {
    config false;
    description
      "Crypto PKI operational data";
    list crypto-pki-bundle {
      key "label";
      description
        "PKI data list";
      uses crypto-pki-ios-xe-oper:crypto-pki-data;
    }
  }
}
