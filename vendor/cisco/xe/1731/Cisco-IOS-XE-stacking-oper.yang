module Cisco-IOS-XE-stacking-oper {
  yang-version 1;
  namespace "http://cisco.com/ns/yang/Cisco-IOS-XE-stacking-oper";
  prefix stacking-ios-xe-oper;
  import ietf-yang-types {
    prefix yang;
  }
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring all parameters of stack in a Network Element.
     Copyright (c) 2018-2019 by Cisco Systems, Inc.
     All rights reserved.";

  revision 2019-06-06 {
    description
      "- Added semantic version.
       - Model is marked deprecated.";
    reference "1.1.0";
    cisco-semver:module-version "1.1.0";
  }
  revision 2018-09-19 {
    description
      "Initial revision";
    reference "1.0.0";
    cisco-semver:module-version "1.0.0";
  }

  typedef oper-switch-role {
    type enumeration {
      enum "switch-role-unknown" {
        value 0;
        description
          "Switch Role: Unknown";
        tailf:code-name "ENUM_oper_switch_role_SWITCH_ROLE_UNKNOWN";
      }
      enum "switch-state-active" {
        value 1;
        description
          "Switch Role: Active";
        tailf:code-name "ENUM_oper_switch_role_SWITCH_ROLE_ACTIVE";
      }
      enum "switch-state-standby" {
        value 2;
        description
          "Switch Role: Standby";
        tailf:code-name "ENUM_oper_switch_role_SWITCH_ROLE_STANDBY";
      }
      enum "switch-state-member" {
        value 3;
        description
          "Switch Role: Member";
        tailf:code-name "ENUM_oper_switch_role_SWITCH_ROLE_MEMBER";
      }
    }
    description
      "Role of the Switch in Stack or Standalone";
  }

  typedef oper-switch-state {
    type enumeration {
      enum "switch-state-invalid" {
        value 0;
        description
          "Switch is in Invalid state";
        tailf:code-name "ENUM_oper_switch_state_SWITCH_STATE_INVALID";
      }
      enum "switch-state-unknown" {
        value 1;
        description
          "Switch is in Unknown state";
        tailf:code-name "ENUM_oper_switch_state_SWITCH_STATE_UNKNOWN";
      }
      enum "switch-state-waiting" {
        value 2;
        description
          "Switch is in Waiting state";
        tailf:code-name "ENUM_oper_switch_state_SWITCH_STATE_WAITING";
      }
      enum "switch-state-initializing" {
        value 3;
        description
          "Switch is in Initializing state";
        tailf:code-name "ENUM_oper_switch_state_SWITCH_STATE_INIT";
      }
      enum "switch-state-version-mismatch" {
        value 4;
        description
          "Version Mismatch between Switches in Stack";
        tailf:code-name "ENUM_oper_switch_state_SWITCH_STATE_VERSION_MISMATCH";
      }
      enum "switch-state-ready" {
        value 5;
        description
          "Switch is in Ready state";
        tailf:code-name "ENUM_oper_switch_state_SWITCH_STATE_READY";
      }
      enum "switch-state-re-initializing" {
        value 6;
        description
          "Switch is in re-initializing state";
        tailf:code-name "ENUM_oper_switch_state_SWITCH_STATE_RE_INIT";
      }
      enum "switch-state-feature-mismatch" {
        value 7;
        description
          "Feature Mismatch between Active and the switch in stack";
        tailf:code-name "ENUM_oper_switch_state_SWITCH_STATE_FEATURE_MISMATCH";
      }
      enum "switch-state-progressing" {
        value 8;
        description
          "Switch is in Progressing state";
        tailf:code-name "ENUM_oper_switch_state_SWITCH_STATE_PROGRESSING";
      }
      enum "switch-state-configured" {
        value 9;
        description
          "Switch is in Configured state";
        tailf:code-name "ENUM_oper_switch_state_SWITCH_STATE_CONFIGURED";
      }
      enum "switch-state-created" {
        value 10;
        description
          "Switch is in Created state";
        tailf:code-name "ENUM_oper_switch_state_SWITCH_STATE_CREATED";
      }
      enum "switch-state-removed" {
        value 11;
        description
          "Switch is in Removed state";
        tailf:code-name "ENUM_oper_switch_state_SWITCH_STATE_REMOVED";
      }
      enum "switch-state-deleted" {
        value 12;
        description
          "Switch is in Deleted state";
        tailf:code-name "ENUM_oper_switch_state_SWITCH_STATE_DELETED";
      }
      enum "switch-state-license-mismatch" {
        value 13;
        description
          "License Mismatch between Active and the switch in stack";
        tailf:code-name "ENUM_oper_switch_state_SWITCH_STATE_LICENSE_MISMATCH";
      }
      enum "switch-state-platform-mismatch" {
        value 14;
        description
          "Platform Mismatch between Active and the switch in stack";
        tailf:code-name "ENUM_oper_switch_state_SWITCH_STATE_PLATFORM_MISMATCH";
      }
      enum "switch-state-platform-and-license-mismatch" {
        value 15;
        description
          "Both Platform and License Mismatch between Active and the switch in stack";
        tailf:code-name "ENUM_oper_switch_state_SWITCH_STATE_PLAT_PLUS_LIC_MISMATCH";
      }
      enum "switch-state-os-mismatch" {
        value 16;
        description
          "OS Mismatch between Active and the switch in stack";
        tailf:code-name "ENUM_oper_switch_state_SWITCH_STATE_OS_MISMATCH";
      }
    }
    description
      "State of the switch";
  }

  grouping stack-data {
    description
      "Details of the Stack";
    leaf stack-mac-address {
      type yang:mac-address;
      description
        "MAC address for a Stack or Standalone";
    }
    leaf is-local-mac {
      type boolean;
      description
        "Identifies if the stack MAC belongs to the Active switch's MAC(Local) or outside switch's MAC(Foreign)";
    }
    leaf mac-persistent-timer {
      type uint32;
      description
        "Persistent timer for updating the stack MAC address";
    }
  }

  grouping switch-oper-info {
    description
      "Detailed Information of Switch";
    leaf switch-num {
      type uint8;
      description
        "Switch Number";
    }
    leaf role {
      type stacking-ios-xe-oper:oper-switch-role;
      description
        "Switch Role in Stack or Standalone";
    }
    leaf state {
      type stacking-ios-xe-oper:oper-switch-state;
      description
        "Switch State in Stack or Standalone";
    }
    leaf priority {
      type uint8;
      description
        "Switch Priority in Stack or Standalone";
    }
    leaf mac-address {
      type yang:mac-address;
      description
        "MAC Address of the switch";
    }
    leaf hw-version {
      type string;
      description
        "Hardware Version of the switch";
    }
    leaf is-stackport-1-up {
      type boolean;
      description
        "Switch Stack Port link 1 Status";
    }
    leaf stackport-1-nbr-sw {
      type uint8;
      description
        "Switch Number connected to Stack port link 1";
    }
    leaf is-stackport-2-up {
      type boolean;
      description
        "Switch Stack Port link 2 Status";
    }
    leaf stackport-2-nbr-sw {
      type uint8;
      description
        "Switch Number connected to Stack port link 2";
    }
  }

  container stacking-oper-data {
    config false;
    status deprecated;
    description
      "Top-level container for Stack operational data";
    tailf:callpoint "ios-oper-db";
    tailf:meta-data "callpoint" {
      tailf:meta-value "ios-oper-db";
    }
    tailf:meta-data "greenprefix" {
      tailf:meta-value "/services;serviceName=ios_oper";
    }
    container stack-data {
      presence "stack-data";
      description
        "Details of the Stack";
      uses stacking-ios-xe-oper:stack-data;
    }
    list switch-oper-info {
      key "switch-num";
      description
        "Detailed Information of Switch";
      uses stacking-ios-xe-oper:switch-oper-info;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWfqXWjEAAnZfgEAAEAYQED/v3+q/79+6QAHtYKihJFMSZTxDTJNNNBoGmCZDTEEkQmTUxpJpNoAjT1MPVPTQTTAaaVAwmjBNNNqA0MmjRoyDQwAA0AAZNAAAGg6+/Hnw+Vt2u4PCZ4Qjx/TRfes2l382WeHxFp4x+zZVtN5frMwCAgqVCkFAgKx25GAIJgdHRmYjHaoRhTlF9FQ6WjvdwQwW1gBdHfv0bBQdAbHabx1xSFQ7oVKJ27JSrw7TRqkdWEdNJQsTQ7Dv0QSgMq4YwY356khTWV86J9HyFU2IRrnA8jZkFC6NRSik2d5dOwcDgThGaNcM2q1siAUa6r+DPW0AuhO2GoUrhBtQi+hImILCdCGmwgfByhhr2YzrcVQhzZDbt7zcRsBua9k2f4xirMHiDMgGCXK+mnUaZ9xMwW6ent05kZatYwnBGCgav6jLCqDAkKQaFR71JsIjNHCYt7JqDgYsoHwzkvjHKW4hep540VVxGSvxUpCgSVfXC0OCpLmj4GMWVCLC6iorCB/Ry1XFs1hFdpcT4hSkk1hglgHuQdTITkx2YTHQQmrqLxslpZYoKpVM9jUu+eRG2DzVlJbhgKWqbWdCHSRiTQJhXIQyEXUcgscYUM7Jp565FKEOZu6Jz9A6MN642Ybqzf4u5IpwoSH1LrRi";
      }
      tailf:meta-data "uncompressed_size" {
        tailf:meta-value "1277";
      }
    }
  }

  container schema-metadata-Cisco-IOS-XE-stacking-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-stacking-oper";
    }
    tailf:meta-data "organization" {
      tailf:meta-value "Cisco Systems, Inc.";
    }
    tailf:meta-data "semver" {
      tailf:meta-value "2019-06-06";
    }
  }
}
