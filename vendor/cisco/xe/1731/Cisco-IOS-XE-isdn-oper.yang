module Cisco-IOS-XE-isdn-oper {
  yang-version 1;
  namespace "http://cisco.com/ns/yang/Cisco-IOS-XE-isdn-oper";
  prefix isdn-ios-xe-oper;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for ISDN operational data.
     Copyright (c) 2019 by Cisco Systems, Inc.
     All rights reserved.";

  revision 2019-11-01 {
    description
      "Initial revision";
    reference "1.0.0";
    cisco-semver:module-version "1.0.0";
    cisco-semver-internal:os-version "17.1.1";
  }

  typedef isdn-switch-type {
    type enumeration {
      enum "no-isdn-switch-type" {
        value 0;
        description
          "No global ISDN switch type currently configured";
        tailf:code-name "ENUM_isdn_switch_type_TDL_NO_ISDN_STYPE";
      }
      enum "bri-net3-switch-type" {
        value 1;
        description
          "BRI NET3 switch type";
        tailf:code-name "ENUM_isdn_switch_type_TDL_BRI_NET3_STYPE";
      }
      enum "pri-4ess-switch-type" {
        value 2;
        description
          "PRI 4ESS switch type";
        tailf:code-name "ENUM_isdn_switch_type_TDL_PRI_4ESS_STYPE";
      }
      enum "pri-5ess-switch-type" {
        value 3;
        description
          "PRI 5ESS switch type";
        tailf:code-name "ENUM_isdn_switch_type_TDL_PRI_5ESS_STYPE";
      }
      enum "bri-5ess-switch-type" {
        value 4;
        description
          "BRI 5ESS switch type";
        tailf:code-name "ENUM_isdn_switch_type_TDL_BRI_5ESS_STYPE";
      }
      enum "pri-dms100-switch-type" {
        value 5;
        description
          "PRI DMS100 switch type";
        tailf:code-name "ENUM_isdn_switch_type_TDL_PRI_DMS100_STYPE";
      }
      enum "bri-dms100-switch-type" {
        value 6;
        description
          "BRI DMS100 switch type";
        tailf:code-name "ENUM_isdn_switch_type_TDL_BRI_DMS100_STYPE";
      }
      enum "vn2-switch-type" {
        value 7;
        description
          "VN2 switch type";
        tailf:code-name "ENUM_isdn_switch_type_TDL_VN2_STYPE";
      }
      enum "vn3-switch-type" {
        value 8;
        description
          "VN3 switch type";
        tailf:code-name "ENUM_isdn_switch_type_TDL_VN3_STYPE";
      }
      enum "ntt-switch-type" {
        value 9;
        description
          "BRI NTT switch type";
        tailf:code-name "ENUM_isdn_switch_type_TDL_NTT_STYPE";
      }
      enum "bri-1tr6-switch-type" {
        value 10;
        description
          "BRI 1TR6 switch type";
        tailf:code-name "ENUM_isdn_switch_type_TDL_BRI_1TR6_STYPE";
      }
      enum "bri-old-ni1-switch-type" {
        value 11;
        description
          "BRI old national ISDN-1 switch type";
        tailf:code-name "ENUM_isdn_switch_type_TDL_BRI_OLD_NI1_STYPE";
      }
      enum "bri-ni1-switch-type" {
        value 12;
        description
          "BRI generic national ISDN-1 switch type";
        tailf:code-name "ENUM_isdn_switch_type_TDL_BRI_NI1_STYPE";
      }
      enum "pri-ni-switch-type" {
        value 13;
        description
          "PRI generic national ISDN switch type";
        tailf:code-name "ENUM_isdn_switch_type_TDL_PRI_NI_STYPE";
      }
      enum "bri-ts013-switch-type" {
        value 14;
        description
          "BRI Australia switch type";
        tailf:code-name "ENUM_isdn_switch_type_TDL_BRI_TS013_STYPE";
      }
      enum "bri-nznet3-switch-type" {
        value 15;
        description
          "BRI New Zealand NET3 switch type";
        tailf:code-name "ENUM_isdn_switch_type_TDL_BRI_NZNET3_STYPE";
      }
      enum "bri-nwnet3-switch-type" {
        value 16;
        description
          "BRI Norway NET3 switch type";
        tailf:code-name "ENUM_isdn_switch_type_TDL_BRI_NWNET3_STYPE";
      }
      enum "pri-ntt-switch-type" {
        value 17;
        description
          "PRI NTT switch type";
        tailf:code-name "ENUM_isdn_switch_type_TDL_PRI_NTT_STYPE";
      }
      enum "pri-net5-switch-type" {
        value 18;
        description
          "PRI NET5 switch type";
        tailf:code-name "ENUM_isdn_switch_type_TDL_PRI_NET5_STYPE";
      }
      enum "pri-ts014-switch-type" {
        value 19;
        description
          "PRI TS014 switch type";
        tailf:code-name "ENUM_isdn_switch_type_TDL_PRI_TS014_STYPE";
      }
      enum "pri-qsig-master-switch-type" {
        value 20;
        description
          "PRI QSIG Master switch type";
        tailf:code-name "ENUM_isdn_switch_type_TDL_PRI_QSIGMASTER_STYPE";
      }
      enum "pri-qsig-slave-switch-type" {
        value 21;
        description
          "PRI QSIG Slave switch type";
        tailf:code-name "ENUM_isdn_switch_type_TDL_PRI_QSIGSLAVE_STYPE";
      }
      enum "pri-qsig-switch-type" {
        value 22;
        description
          "PRI QSIG switch type";
        tailf:code-name "ENUM_isdn_switch_type_TDL_PRI_QSIG_STYPE";
      }
      enum "bri-qsig-switch-type" {
        value 23;
        description
          "BRI QSIG switch type";
        tailf:code-name "ENUM_isdn_switch_type_TDL_BRI_QSIG_STYPE";
      }
      enum "pri-qsigp-switch-type" {
        value 24;
        description
          "PRI QSIGP switch type";
        tailf:code-name "ENUM_isdn_switch_type_TDL_PRI_QSIGP_STYPE";
      }
      enum "pri-ni2c-switch-type" {
        value 25;
        description
          "PRI NI2C switch type";
        tailf:code-name "ENUM_isdn_switch_type_TDL_PRI_NI2C_STYPE";
      }
      enum "pri-dpnss-switch-type" {
        value 26;
        description
          "PRI DPNSS switch type";
        tailf:code-name "ENUM_isdn_switch_type_TDL_PRI_DPNSS_STYPE";
      }
    }
    description
      "Enumeration for ISDN switch type";
  }

  typedef isdn-protocol-emul-config {
    type enumeration {
      enum "isdn-protocol-emulation-user" {
        value 0;
        description
          "ISDN user protocol emulation";
        tailf:code-name "ENUM_isdn_protocol_emul_config_ISDN_PROTOCOL_USER";
      }
      enum "isdn-protocol-emulation-network" {
        value 1;
        description
          "ISDN network protocol emulation";
        tailf:code-name "ENUM_isdn_protocol_emul_config_ISDN_PROTOCOL_NETWORK";
      }
    }
    description
      "Enumeration for ISDN protocol emulation configuration";
  }

  typedef isdn-l1-status {
    type enumeration {
      enum "l1-deactivated" {
        value 0;
        description
          "ISDN layer 1 is in deactivated status";
        tailf:code-name "ENUM_isdn_l1_status_L1_DEACTIVATED";
      }
      enum "l1-going-down" {
        value 1;
        description
          "ISDN layer 1 is in going down status";
        tailf:code-name "ENUM_isdn_l1_status_L1_GOING_DOWN";
      }
      enum "l1-init" {
        value 2;
        description
          "ISDN layer 1 is in initializing status";
        tailf:code-name "ENUM_isdn_l1_status_L1_INIT";
      }
      enum "l1-testing" {
        value 3;
        description
          "ISDN layer 1 is in in testing status";
        tailf:code-name "ENUM_isdn_l1_status_L1_TESTING";
      }
      enum "l1-active" {
        value 4;
        description
          "ISDN layer 1 is in active status";
        tailf:code-name "ENUM_isdn_l1_status_L1_ACTIVE";
      }
      enum "l1-reset" {
        value 5;
        description
          "ISDN layer 1 is in reset status";
        tailf:code-name "ENUM_isdn_l1_status_L1_RESET";
      }
      enum "l1-shutdown" {
        value 6;
        description
          "ISDN layer 1 is in shut down status";
        tailf:code-name "ENUM_isdn_l1_status_L1_SHUTDOWN";
      }
      enum "l1-deleted" {
        value 7;
        description
          "ISDN layer 1 is in deleted status";
        tailf:code-name "ENUM_isdn_l1_status_L1_DELETED";
      }
      enum "l1-unknown" {
        value 8;
        description
          "ISDN layer 1 is in unknown status";
        tailf:code-name "ENUM_isdn_l1_status_L1_UNKNOWN";
      }
    }
    description
      "ISDN Layer 1 status";
  }

  typedef isdn-l2-status {
    type enumeration {
      enum "l2-not-activated" {
        value 0;
        description
          "ISDN layer 2 is in not activated status";
        tailf:code-name "ENUM_isdn_l2_status_L2_NOT_ACTIVATED";
      }
      enum "l2-tei-unassigned" {
        value 1;
        description
          "ISDN layer 2 is in TEI unassigned status";
        tailf:code-name "ENUM_isdn_l2_status_L2_TEI_UNASSIGNED";
      }
      enum "l2-assign-awaiting-tei" {
        value 2;
        description
          "ISDN layer 2 is in TEI assign awaiting status";
        tailf:code-name "ENUM_isdn_l2_status_L2_ASSIGN_AWAITING_TEI";
      }
      enum "l2-establish-awaiting-tei" {
        value 3;
        description
          "ISDN layer 2 is in TEI establish awaiting status";
        tailf:code-name "ENUM_isdn_l2_status_L2_ESTABLISH_AWAITING_TEI";
      }
      enum "l2-tei-assigned" {
        value 4;
        description
          "ISDN layer 2 is in TEI assigned status";
        tailf:code-name "ENUM_isdn_l2_status_L2_TEI_ASSIGNED";
      }
      enum "l2-awaiting-establishment" {
        value 5;
        description
          "ISDN layer 2 is in awaiting establishment status";
        tailf:code-name "ENUM_isdn_l2_status_L2_AWAITING_ESTABLISHMENT";
      }
      enum "l2-awaiting-release" {
        value 6;
        description
          "ISDN layer 2 is in awaiting release status";
        tailf:code-name "ENUM_isdn_l2_status_L2_AWAITING_RELEASE";
      }
      enum "l2-multiple-frame-established" {
        value 7;
        description
          "ISDN layer 2 is in multiple frame established status";
        tailf:code-name "ENUM_isdn_l2_status_L2_MULTIPLE_FRAME_ESTABLISHED";
      }
      enum "l2-timer-recovery" {
        value 8;
        description
          "ISDN layer 2 is in timer recovery status";
        tailf:code-name "ENUM_isdn_l2_status_L2_TIMER_RECOVERY";
      }
      enum "l2-not-applicable" {
        value 9;
        description
          "ISDN layer 2 is not applicable to NFAS none";
        tailf:code-name "ENUM_isdn_l2_status_L2_NOT_APPLICABLE";
      }
    }
    description
      "ISDN Layer 2 status";
  }

  typedef isdn-active-call-type {
    type enumeration {
      enum "isdn-call-none" {
        value 0;
        description
          "No call type assigned yet";
        tailf:code-name "ENUM_isdn_active_call_type_TDL_ISDN_CALL_NONE";
      }
      enum "isdn-call-data" {
        value 1;
        description
          "ISDN data call";
        tailf:code-name "ENUM_isdn_active_call_type_TDL_ISDN_CALL_DATA";
      }
      enum "isdn-call-voice" {
        value 2;
        description
          "ISDN voice call";
        tailf:code-name "ENUM_isdn_active_call_type_TDL_ISDN_CALL_VOICE";
      }
      enum "isdn-call-v110" {
        value 3;
        description
          "ISDN V110 call";
        tailf:code-name "ENUM_isdn_active_call_type_TDL_ISDN_CALL_V110";
      }
      enum "isdn-call-v120" {
        value 4;
        description
          "ISDN V120 call";
        tailf:code-name "ENUM_isdn_active_call_type_TDL_ISDN_CALL_V120";
      }
      enum "isdn-call-packet" {
        value 5;
        description
          "ISDN packet switched data call";
        tailf:code-name "ENUM_isdn_active_call_type_TDL_ISDN_CALL_PACKET";
      }
      enum "isdn-call-internal" {
        value 6;
        description
          "ISDN call for internal use";
        tailf:code-name "ENUM_isdn_active_call_type_TDL_ISDN_CALL_INTERNAL";
      }
      enum "isdn-call-signaling" {
        value 7;
        description
          "ISDN QSIG signaling call";
        tailf:code-name "ENUM_isdn_active_call_type_TDL_ISDN_CALL_SIGNALING";
      }
      enum "isdn-call-modem" {
        value 8;
        description
          "ISDN modem call";
        tailf:code-name "ENUM_isdn_active_call_type_TDL_ISDN_CALL_MODEM";
      }
      enum "isdn-call-facility" {
        value 9;
        description
          "ISDN facility call";
        tailf:code-name "ENUM_isdn_active_call_type_TDL_ISDN_CALL_FACILITY";
      }
      enum "isdn-call-data-over-voice" {
        value 10;
        description
          "ISDN data over voice call";
        tailf:code-name "ENUM_isdn_active_call_type_TDL_ISDN_CALL_DATA_OVER_VOICE";
      }
      enum "isdn-call-piafs" {
        value 11;
        description
          "ISDN piafs call";
        tailf:code-name "ENUM_isdn_active_call_type_TDL_ISDN_CALL_PIAFS";
      }
      enum "isdn-call-cot" {
        value 12;
        description
          "ISDN call with continuity tone test";
        tailf:code-name "ENUM_isdn_active_call_type_TDL_ISDN_CALL_COT";
      }
      enum "isdn-call-bumped" {
        value 13;
        description
          "ISDN data call being bumped";
        tailf:code-name "ENUM_isdn_active_call_type_TDL_ISDN_CALL_BUMPED";
      }
      enum "isdn-call-woken" {
        value 14;
        description
          "ISDN voice call woken up";
        tailf:code-name "ENUM_isdn_active_call_type_TDL_ISDN_CALL_WOKEN";
      }
      enum "isdn-call-unknown" {
        value 15;
        description
          "Unknown ISDN call type value";
        tailf:code-name "ENUM_isdn_active_call_type_TDL_ISDN_CALL_UNKNOWN";
      }
      enum "isdn-call-voice-over-data" {
        value 16;
        description
          "ISDN clear channel voice over data call";
        tailf:code-name "ENUM_isdn_active_call_type_TDL_ISDN_CALL_VOICE_OVER_DATA";
      }
    }
    description
      "ISDN active call type";
  }

  grouping isdn-active-call-entry {
    description
      "ISDN active call entry";
    leaf key-id {
      type uint32;
      description
        "Key to the entry";
    }
    leaf call-id {
      type uint64;
      description
        "Call ID";
    }
    leaf sapi {
      type uint32;
      description
        "ISDN Service Access Point Identifier";
    }
    leaf ces {
      type uint32;
      description
        "ISDN connection end-point suffix";
    }
    leaf b-channel-num {
      type uint32;
      description
        "ISDN B channel number";
    }
    leaf call-type {
      type isdn-ios-xe-oper:isdn-active-call-type;
      description
        "ISDN call type";
    }
  }

  grouping isdn-intf-entry {
    description
      "ISDN interface entry";
    leaf key-id {
      type uint32;
      description
        "Key to the entry";
    }
    leaf intf-name {
      type string;
      description
        "ISDN interface name";
    }
    leaf proto-emul-config {
      type isdn-ios-xe-oper:isdn-protocol-emul-config;
      description
        "ISDN protocol emulation configuration";
    }
    leaf dsl-number {
      type uint32;
      description
        "ISDN DSL number";
    }
    leaf switch-type {
      type isdn-ios-xe-oper:isdn-switch-type;
      description
        "ISDN switch type configured on this ISDN interface";
    }
    leaf l1-status {
      type isdn-ios-xe-oper:isdn-l1-status;
      description
        "ISDN L1 status on this ISDN interface";
    }
    leaf l2-status {
      type isdn-ios-xe-oper:isdn-l2-status;
      description
        "ISDN L2 status on this ISDN interface";
    }
    leaf l2-tei-config {
      type uint32;
      description
        "ISDN L2 terminal end-point identifier";
    }
    leaf l2-ces-config {
      type uint32;
      description
        "ISDN L2 connection end-point suffix";
    }
    leaf l2-sapi-config {
      type uint32;
      description
        "ISDN L2 service access point identifier";
    }
    leaf free-channel-mask {
      type uint32;
      description
        "Free channel mask on this interface";
    }
    leaf num-active-calls {
      type uint32;
      description
        "Number of ISDN active calls on this interface";
    }
    list isdn-active-call-entry {
      key "key-id";
      description
        "A list of ISDN active call entry";
      uses isdn-ios-xe-oper:isdn-active-call-entry;
    }
  }

  grouping isdn-status {
    description
      "ISDN status";
    leaf global-switch-type {
      type isdn-ios-xe-oper:isdn-switch-type;
      description
        "Global ISDN switch type configuration";
    }
    leaf total-intf {
      type uint32;
      description
        "Total ISDN interface configured";
    }
    list isdn-intf-entry {
      key "key-id";
      description
        "A list of ISDN interface entry";
      uses isdn-ios-xe-oper:isdn-intf-entry;
    }
  }

  container isdn-oper-data {
    config false;
    description
      "ISDN operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    container isdn-status {
      presence "isdn-status";
      description
        "ISDN interface status";
      uses isdn-ios-xe-oper:isdn-status;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWbGl0i8ABavfgEAAEAZ/ED/v//q/7/+6UARGL1GqoZNLTIShGlT2mjVT3qkZoJtIDTPSMm1AJkAc0xMACYAJgABMAATBIkJkmRR+RpTyh6jT0gAABoB6hzTEwAJgAmAAEwABMEiQJkJkKbU9TSaGnoRkaaHqeU0Ygf7P027Tx9Re5fCDs4yn8YQaOcI+XnB/a+/fHnBgDD884hPn7NUc/x0wfZ0ZaB5wy2RwIzFuXXB2cZTFkRKqbz656fc4dPS+sABwIiIEDY2kERA2JOIOPft1gAcx+IOXey8j8tGdX5whAMwHUuObkV1zlFCN+NJXVL2eNzmQEy/ShImjC2BSKerTn6KscmlaRJdfHg+Ht7qddsYDFVmcCIIsLaFKKkJKugYN+jciiWQyhQof54t2D6/cl3DPzwlwazKUS9jWOnSkruhG3lotJQHgb/T8gRAidqpu7/rMt5BUuQDFKub+H5LynZMNfgEJGjQDUHgSxJejiSSmilgSIPqBDh34iN9nralEB8dpcZ4PF4GE6n7c8UzJRFfv9b2VMssBq8Rtntc8ljsRJkJjLhzIWeraqIMNk3NhecXDQGg6K/EIotoYtAUZDviZa6QZ08cjUrJcIQHx6COAmgHk4GNCZDIGrfPha2V9iO7ZrQz1Vxgrd2QYJNN3DXAe+dJBloCOw68FPSvQ6SuS3JkUIwMjwSFiLa7s5pLBo2bOUlvs22NtppptvddA0UlcYGAIxztIw/5jqoDWyqt2odUhVDMlk6sKlE/MCRiJvIK1gdg83NYPTUsXtkkKpsbcsg7WWVVrJDCAxLLzxHlaQp953lLhTZx6VbTkkQgGYdip2PlGVJUI72gNnSxD7WRIZAW4ySVCKFKUH3cGW11Fk07SJL9qcb4Vv1fe2MRiq3pogqE1THdq4tNesyyBtbJ+p5/M2f0JpcgG3zlvKPDxDMxNd4sHijkIhnV7SQDVkhUP3PIU4TTSvIU2UATq85U5COO7hAbzlXeXHB4O5eA/uljQ+WmtjFyvkx26+p3qlr8Q2OhnAbW0xhJ3ZJCa2mgNoCrIhbX5qqC2hOcBg6Qu46ICbBzqsdUhbBLJcMZ2K9bBQaFmkE9s/9NrdeNR2ks4QFaXl+VONZV4liW0I7JoDWxPiRuJ2pBa3Ri9EUFkVgnEWxkO6Lw8K6U5bJWrl0y74QHeJYiSzJlt1P2kLHcpY5X17aFRLJQ0ZcpruWbbGxsaY2N6riB004BY1msQsaVksOgWhkRNZVUKURCQqxPSOBBmSCwXCyQsSm7hS5BFQmdvNZYO7IuWxeaQuC4wtX57QVUYWxNSDZIUwwnbewSl/fiL/HywbH0b/4u5IpwoSFjS6ReA";
      }
      tailf:meta-data "uncompressed_size" {
        tailf:meta-value "2920";
      }
    }
  }

  container schema-metadata-Cisco-IOS-XE-isdn-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-isdn-oper";
    }
    tailf:meta-data "organization" {
      tailf:meta-value "Cisco Systems, Inc.";
    }
    tailf:meta-data "semver" {
      tailf:meta-value "2019-11-01";
    }
  }
}
