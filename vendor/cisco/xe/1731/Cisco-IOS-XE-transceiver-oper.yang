module Cisco-IOS-XE-transceiver-oper {
  yang-version 1;
  namespace "http://cisco.com/ns/yang/Cisco-IOS-XE-transceiver-oper";
  prefix xcvr-ios-xe-oper;

  import Cisco-IOS-XE-ios-common-oper {
    prefix ios-common-ios-xe-oper;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring transceivers in a Network Element.
     Copyright (c) 2017-2019 by Cisco Systems, Inc.
     All rights reserved.";

  revision 2020-03-01 {
    description
      "Update copyright";
    reference "1.3.1";
    cisco-semver:module-version "1.3.1";
    cisco-semver-internal:os-version "17.2.1";
  }
  revision 2019-11-01 {
    description
      "Added fault reason and time of last transceiver event";
    reference "1.3.0";
    cisco-semver:module-version "1.3.0";
    cisco-semver-internal:os-version "17.1.1";
  }
  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2018-01-18 {
    description
      "Initial revision";
    reference "1.0.0";
    cisco-semver:module-version "1.0.0";
  }

  typedef xcvr-sonet-code {
    type enumeration {
      enum "oc-48-short-reach" {
        value 0;
        tailf:code-name "ENUM_xcvr_sonet_code_SONET_OC_48_SHORT_REACH";
      }
      enum "oc-48-intermediate-reach" {
        value 1;
        tailf:code-name "ENUM_xcvr_sonet_code_SONET_OC_48_INTERMEDIATE_REACH";
      }
      enum "oc-48-long-reach" {
        value 2;
        tailf:code-name "ENUM_xcvr_sonet_code_SONET_OC_48_LONG_REACH";
      }
      enum "sonet-sr-compliant" {
        value 3;
        tailf:code-name "ENUM_xcvr_sonet_code_SONET_SR_COMPLIANT";
      }
      enum "sonet-lr-compliant" {
        value 4;
        tailf:code-name "ENUM_xcvr_sonet_code_SONET_LR_COMPLIANT";
      }
      enum "oc-192-short-reach" {
        value 5;
        tailf:code-name "ENUM_xcvr_sonet_code_SONET_OC_192_SHORT_REACH";
      }
      enum "escon-smf-1310-laser" {
        value 6;
        tailf:code-name "ENUM_xcvr_sonet_code_SONET_ESCON_SMF_1310_LASER";
      }
      enum "escon-mmf-1310-led" {
        value 7;
        tailf:code-name "ENUM_xcvr_sonet_code_SONET_ESCON_MMF_1310_LED";
      }
      enum "unknown" {
        value 8;
        tailf:code-name "ENUM_xcvr_sonet_code_SONET_UNKNOWN";
      }
    }
    description
      "SONET/SDH application code supported by the port";
  }

  typedef xcvr-otn-code {
    type enumeration {
      enum "p1l1-2d1" {
        value 0;
        tailf:code-name "ENUM_xcvr_otn_code_OTN_P1L1_2D1";
      }
      enum "p1s1-2d2" {
        value 1;
        tailf:code-name "ENUM_xcvr_otn_code_OTN_P1S1_2D2";
      }
      enum "p1l1-2d2" {
        value 2;
        tailf:code-name "ENUM_xcvr_otn_code_OTN_P1L1_2D2";
      }
      enum "otn-undefined" {
        value 3;
        tailf:code-name "ENUM_xcvr_otn_code_OTN_UNDEFINED";
      }
    }
    description
      "OTN application code supported by the port";
  }

  grouping statistics-values {
    description
      "Statistics values for power and current";
    leaf instant {
      type decimal64 {
        fraction-digits 2;
      }
      description
        "Instant value";
    }
    leaf avg {
      type decimal64 {
        fraction-digits 2;
      }
      description
        "Average value";
    }
    leaf max {
      type decimal64 {
        fraction-digits 2;
      }
      description
        "Maximum value";
    }
    leaf min {
      type decimal64 {
        fraction-digits 2;
      }
      description
        "Minimum value";
    }
  }

  grouping xcvr-physical-channel {
    description
      "List of physical channel for transceiver";
    leaf index {
      type uint16;
      description
        "Index of the physical channel";
    }
    leaf description {
      type string;
      description
        "Text description for the client physical channel";
    }
    leaf tx-laser {
      type boolean;
      description
        "Enable (true) or disable (false) the transmit label for the channel";
    }
    leaf target-output-power {
      type decimal64 {
        fraction-digits 2;
      }
      description
        "Target output optical power level of the optical channel(dBm)";
    }
    leaf output-frequency {
      type uint64;
      description
        "The frequency in MHz of the individual physical channel";
    }
    container output-power {
      description
        "The output optical power of a physical channel(dBm)";
      uses xcvr-ios-xe-oper:statistics-values;
    }
    container input-power {
      description
        "The input optical power of a physical channel(dBm)";
      uses xcvr-ios-xe-oper:statistics-values;
    }
    container laser-bias-current {
      description
        "The current applied by the system to the transmit laser to achieve the output power(mA)";
      uses xcvr-ios-xe-oper:statistics-values;
    }
  }

  grouping xcvr {
    description
      "Attributes of transceiver";
    leaf name {
      type string;
      description
        "Port name";
    }
    leaf enabled {
      type boolean;
      description
        "Turns power on/off to the transceiver";
    }
    leaf present {
      type boolean;
      description
        "Transceiver is present on the port";
    }
    leaf identifier {
      type string;
      description
        "Indicates the type of optical transceiver used on this port";
    }
    leaf connector {
      type string;
      description
        "Connector type used on this port";
    }
    leaf ethernet-pmd {
      type string;
      description
        "Ethernet PMD (physical medium dependent sub layer) that the transceiver supports. The SFF/QSFP MSAs have registers for this and CFP MSA has similar.";
    }
    leaf vendor {
      type string;
      description
        "Full name of transceiver vendor";
    }
    leaf vendor-part {
      type string;
      description
        "Transceiver vendor's part number";
    }
    leaf vendor-rev {
      type string;
      description
        "Transceiver vendor's revision number";
    }
    leaf serial-no {
      type string;
      description
        "Transceiver serial number";
    }
    leaf fault-condition {
      type boolean;
      description
        "Indicates if a fault condition exists in the transceiver";
    }
    leaf date {
      type string;
      description
        "Representation of the transceiver date";
    }
    leaf sonet {
      type xcvr-ios-xe-oper:xcvr-sonet-code;
      description
        "SONET/SDH application code supported by the port";
    }
    leaf otn {
      type xcvr-ios-xe-oper:xcvr-otn-code;
      description
        "OTN application code supported by the port";
    }
    leaf internal-temp {
      type decimal64 {
        fraction-digits 2;
      }
      description
        "Internally measured temperature in degrees Celsius";
    }
    container output-power {
      description
        "The output optical power of overall transceiver(dBm)";
      uses xcvr-ios-xe-oper:statistics-values;
    }
    container input-power {
      description
        "The input optical power of overall transceiver(dBm)";
      uses xcvr-ios-xe-oper:statistics-values;
    }
    container laser-bias-current {
      description
        "The current applied by the system to the transmit laser to achieve the output power(mA)";
      uses xcvr-ios-xe-oper:statistics-values;
    }
    list xcvr-physical-channel {
      key "index";
      description
        "List of physical channel for transceiver";
      uses xcvr-ios-xe-oper:xcvr-physical-channel;
    }
    leaf fault-reason {
      type ios-common-ios-xe-oper:port-err-reason;
      description
        "The error disable on the port is to inform the administrator
         when there is a port problem or error. The port can go into
         error disabled state where the traffic is not allowed in this port.";
    }
    leaf last-event-time {
      type yang:date-and-time;
      description
        "Time of the last transceiver event. 
         Events include module insertion or removal or port error";
    }
  }

  container transceiver-oper-data {
    config false;
    description
      "Top-level container for transceiver operational data";
    tailf:callpoint "ios-oper-db";
    tailf:meta-data "callpoint" {
      tailf:meta-value "ios-oper-db";
    }
    tailf:meta-data "greenprefix" {
      tailf:meta-value "/services;serviceName=ios_oper";
    }
    list transceiver {
      key "name";
      description
        "List of transceiver instance, keyed by name";
      uses xcvr-ios-xe-oper:xcvr;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWUxvg2wACA/fgEAAEAZ8cD/v3+q/79+qUAW092vdnQJFO9gB0LwyU9GjUZA1Ap6mgGh6T1PUBmpkAamVPGiIGgAAAADQ2kNAkRBNAJomUaUeoaH6oAHqMQAZFT0npNMIABkGQDTIAACSSmmj1AAAABoAMgAPzUHDv4Mus5lQXYBsFsWBKRo5q5/bmMQoig83k82NgnWFFfAPJXdwEu8vT8vcBdrqOS9vzHaOXP7jug3cyvS94V6YUi/O5b1SkII9L1WjNKK3Qi8aCg1cT8vDZ18f90T4iQDM4cMhAOc7HDqEgImiJuBMocNXPonFd7vhr9Pf7p+B3vAY2hKghJ5/7g+HMJxph2yoVfwmIp0vuinLmK5xZL5BZ3YIY2wErZBoyyUnEPFRggbikjdWtPe1M4ivHcIJ/dzOd4q/uikms9Wpd+gt+fwLU4E4zBE0FJTMJITgL4fFDparxghAUuGgqhqDOJIKNFJDMhJmFHJcCTcUiB65v4nYpw8uqJg8Nl9/2ypTJZF6e7I9bcfeJJZz3+yvWv41iQzUQnZooP2of4iTKH0Dr3p6Gc1tz8LE6wr3EJe0h4ejVOGEGzeVtloESsHk0BJnoyAz/WCkgmwzFFMkDPMoS6YaPIaSbShhw4savLEKHOscFlz65y6+WDEwQaZW0SydjTN01Hi8nzZi9dG6IgJhZSjo5R9J0EJVRDRbTfeOZgdNuuxjBtupqteZ9oBJRBWvYoiu0Em0Fnqx8bu/VRhlzHFLsWSGtW1xFXe2Wm4hKAyPZp5h5JjaEiHJDZ8409UyHZrET5UPpFwni3HbBPQQjeiAo0QoHD7HjpXAkE6CQoJnzAOHlCucU1ZVyzyKlKJt6sopIVBBO5YAEmzqrIOO/Z58s0TeL2mNGEJdSKsQEWeK2xuRrdISuhJPfmAk4fz8gkqFNsNZNZuyb6QW9qF+DS5Z7u5RRZOYXTCgb+a1M98uwhKC7hhaC0mdzD7Paeb65mK0mAt96xKDilGvoO/vbcI47TcZmCFxbTHjEsgJqEJe7IVe0ZfkdcU+bDda2/ZTd/2Z9jj6zV6OOMp2cv56F9TmpW8JogIOrcYEJUDH0ynETvYKn0K/WFkDFKoqRIYkbpkw3ZRtbr6Md3IOdI40ge3GjVMXgxpUX2VVASOQCSOBLM6QEYNS6yiiDloynKjw9FHaqzTEjU9cBznWH7dKl6UDzATSChJVkIa8lDvAQyz3h5zRUy+qytMItWAN8s+Zk8NZPqpv31rKveOb1bSxQjMtXPOuA0seu01a/9502W4PdWSEpPB/nU3KhPPJsunUDb5YDxQOHco/JFXLpSpbinhGkwbxYpWhsPxneijTYL6pVCAcvriApo18mdzRBtnvF/yjC7DG5pjoJ7NOIrHrUlz7mczxOnC7KcLuunJBOCQ1q4CTM1nJrweEvPWQVPbjmZpWK0zYsge7bWsLmVZz6zcIcdphrwzXMKcUk7EChORuAbHTHqEUY1Vnb25emXKqF+N9+2hOaIE8Dg4qSGuUQWMdQs9rXjRBJ4BJhOBjjOYjEVzimrKuT7a8WkiUMwMjjv8aKBz43PlORmISaM5irPp6RbcPWtJ1aE2EMQMYgfXQYJ1O6Vx0Fw0ViaSWy78mOLJCVwAGM5z8Z+8kgyw1rbbN8tcuzfYtil9WRblqpfTFRCTiAbyWQ2XdC6xjLP2u2NuHjW9t0xXhS0JDGUBvusGKPauROQbOooKkSEQVrhAFaB7p6+Rr60lQY/fxdyRThQkExvg2wA==";
      }
      tailf:meta-data "uncompressed_size" {
        tailf:meta-value "4138";
      }
    }
    container Cisco-IOS-XE-ios-common-oper {
      description
        "Hidden internal container used for metadata";
      uses ios-common-ios-xe-oper:__yangpp_metadata;
    }
  }

  container schema-metadata-Cisco-IOS-XE-transceiver-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-transceiver-oper";
    }
    tailf:meta-data "organization" {
      tailf:meta-value "Cisco Systems, Inc.";
    }
    tailf:meta-data "semver" {
      tailf:meta-value "2020-03-01";
    }
  }
}
