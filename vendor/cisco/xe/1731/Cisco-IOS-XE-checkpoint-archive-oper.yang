module Cisco-IOS-XE-checkpoint-archive-oper {
  yang-version 1;
  namespace "http://cisco.com/ns/yang/Cisco-IOS-XE-checkpoint-archive-oper";
  prefix checkpoint-archive-ios-xe-oper;
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring the checkpoint archives in a Network Element.
     Copyright (c) 2016-2017, 2019 by Cisco Systems, Inc.
     All rights reserved.";

  revision 2019-05-01 {
    description
      "Added semantic version";
    reference "2.2.0";
    cisco-semver:module-version "2.2.0";
  }
  revision 2018-10-29 {
    description
      "Cleaned up spelling errors in descriptions.";
    reference "2.1.0";
    cisco-semver:module-version "2.1.0";
  }
  revision 2017-04-01 {
    description
      "Top level container name change";
    reference "2.0.0";
    cisco-semver:module-version "2.0.0";
  }
  revision 2017-02-07 {
    description
      "Initial revision";
    reference "1.0.0";
    cisco-semver:module-version "1.0.0";
  }

  grouping archive {
    description
      "Archive information";
    leaf number {
      type uint16;
      description
        "The archive number";
    }
    leaf name {
      type string;
      description
        "The name of the archive";
    }
  }

  grouping checkpoint-archive {
    description
      "Checkpoint archive information";
    leaf max {
      type uint8;
      description
        "The maximum number of archives";
    }
    leaf current {
      type uint8;
      description
        "The current number of archives";
    }
    leaf recent {
      type string;
      description
        "The most recent archive";
    }
    container archives {
      description
        "Archive information";
      list archive {
        key "number";
        description
          "List of archives";
        uses checkpoint-archive-ios-xe-oper:archive;
      }
    }
  }

  container checkpoint-archives {
    config false;
    description
      "Contents of the checkpoint archive information base";
    tailf:callpoint "ios-emul-oper-db";
    tailf:meta-data "callpoint" {
      tailf:meta-value "ios-emul-oper-db";
    }
    tailf:meta-data "greenprefix" {
      tailf:meta-value "/services;serviceName=ios_emul_oper/checkpoint_archive;singleton_id=0";
    }
    tailf:meta-data "emulated" {
      tailf:meta-value "true";
    }
    uses checkpoint-archive-ios-xe-oper:checkpoint-archive;
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWQsxPmQAAGnfgFAAEAYAEAogiEoq698KIACIEpNIaDIANDJoJIpqfqahpoepiBp7VKFlUZETYlxJWsbQCDEvVV+dB7zcghqYFaDmIjUsaGo50PA6IRg4+Iqo7kh9RI5E7JFLI9mIqIguJnIRkZVNpRnVril2bmUM0NXAX6yC5oQMEn8XckU4UJALMT5k";
      }
      tailf:meta-data "uncompressed_size" {
        tailf:meta-value "233";
      }
    }
  }

  container schema-metadata-Cisco-IOS-XE-checkpoint-archive-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-checkpoint-archive-oper";
    }
    tailf:meta-data "organization" {
      tailf:meta-value "Cisco Systems, Inc.";
    }
    tailf:meta-data "semver" {
      tailf:meta-value "2019-05-01";
    }
  }
}
