module Cisco-IOS-XE-docsis-oper {
  yang-version 1;
  namespace "http://cisco.com/ns/yang/Cisco-IOS-XE-docsis-oper";
  prefix docsis-ios-xe-oper;
  import ietf-inet-types {
    prefix inet;
  }
  import ietf-yang-types {
    prefix yang;
  }
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for operational data on CMTS.
     Copyright (c) 2018-2019 by Cisco Systems, Inc.
     All rights reserved.";

  revision 2019-05-01 {
    description
      "Added semantic version";
    reference "1.0.1";
    cisco-semver:module-version "1.0.1";
  }
  revision 2019-03-01 {
    description
      "Initial revision";
    reference "1.0.0";
    cisco-semver:module-version "1.0.0";
  }

  typedef cm-state {
    type enumeration {
      enum "shut-down" {
        value 0;
        tailf:code-name "ENUM_cm_state_CM_STATE_SHUT_DOWN";
      }
      enum "offline" {
        value 1;
        tailf:code-name "ENUM_cm_state_CM_STATE_OFFLINE";
      }
      enum "resetting" {
        value 2;
        tailf:code-name "ENUM_cm_state_CM_STATE_RESETTING";
      }
      enum "cc-pending" {
        value 3;
        tailf:code-name "ENUM_cm_state_CM_STATE_CC_PENDING";
      }
      enum "init-r1" {
        value 4;
        tailf:code-name "ENUM_cm_state_CM_STATE_INIT_R1";
      }
      enum "cc-r1" {
        value 5;
        tailf:code-name "ENUM_cm_state_CM_STATE_CC_R1";
      }
      enum "init-r2" {
        value 6;
        tailf:code-name "ENUM_cm_state_CM_STATE_INIT_R2";
      }
      enum "cc-r2" {
        value 7;
        tailf:code-name "ENUM_cm_state_CM_STATE_CC_R2";
      }
      enum "init-rc" {
        value 8;
        tailf:code-name "ENUM_cm_state_CM_STATE_INIT_RC";
      }
      enum "eject-epk" {
        value 9;
        tailf:code-name "ENUM_cm_state_CM_STATE_REJECT_EPK";
      }
      enum "expire-eae" {
        value 10;
        tailf:code-name "ENUM_cm_state_CM_STATE_EXPIRE_EPK";
      }
      enum "assign-epk" {
        value 11;
        tailf:code-name "ENUM_cm_state_CM_STATE_ASSIGN_EPK";
      }
      enum "reject-ept" {
        value 12;
        tailf:code-name "ENUM_cm_state_CM_STATE_REJECT_EPT";
      }
      enum "expire-ept" {
        value 13;
        tailf:code-name "ENUM_cm_state_CM_STATE_EXPIRE_EPT";
      }
      enum "assign-ept" {
        value 14;
        tailf:code-name "ENUM_cm_state_CM_STATE_ASSIGN_EPT";
      }
      enum "init-d" {
        value 15;
        tailf:code-name "ENUM_cm_state_CM_STATE_INIT_D";
      }
      enum "sinit-d" {
        value 16;
        tailf:code-name "ENUM_cm_state_CM_STATE_SINIT_D";
      }
      enum "init6-s" {
        value 17;
        tailf:code-name "ENUM_cm_state_CM_STATE_INIT6_S";
      }
      enum "sinit6-s" {
        value 18;
        tailf:code-name "ENUM_cm_state_CM_STATE_SINIT6_S";
      }
      enum "init-io" {
        value 19;
        tailf:code-name "ENUM_cm_state_CM_STATE_INIT_IO";
      }
      enum "sinit-io" {
        value 20;
        tailf:code-name "ENUM_cm_state_CM_STATE_SINIT_IO";
      }
      enum "init6-a" {
        value 21;
        tailf:code-name "ENUM_cm_state_CM_STATE_INIT6_A";
      }
      enum "sinit6-a" {
        value 22;
        tailf:code-name "ENUM_cm_state_CM_STATE_SINIT6_A";
      }
      enum "init-dr" {
        value 23;
        tailf:code-name "ENUM_cm_state_CM_STATE_INIT_DR";
      }
      enum "sinit-dr" {
        value 24;
        tailf:code-name "ENUM_cm_state_CM_STATE_SINIT_DR";
      }
      enum "init6-r" {
        value 25;
        tailf:code-name "ENUM_cm_state_CM_STATE_INIT6_R";
      }
      enum "sinit6-r" {
        value 26;
        tailf:code-name "ENUM_cm_state_CM_STATE_SINIT6_R";
      }
      enum "init-i" {
        value 27;
        tailf:code-name "ENUM_cm_state_CM_STATE_INIT_I";
      }
      enum "sinit-i" {
        value 28;
        tailf:code-name "ENUM_cm_state_CM_STATE_SINIT_I";
      }
      enum "init6-i" {
        value 29;
        tailf:code-name "ENUM_cm_state_CM_STATE_INIT6_I";
      }
      enum "sinit6-i" {
        value 30;
        tailf:code-name "ENUM_cm_state_CM_STATE_SINIT6_I";
      }
      enum "init-o" {
        value 31;
        tailf:code-name "ENUM_cm_state_CM_STATE_INIT_O";
      }
      enum "sinit-o" {
        value 32;
        tailf:code-name "ENUM_cm_state_CM_STATE_SINIT_O";
      }
      enum "init6-o" {
        value 33;
        tailf:code-name "ENUM_cm_state_CM_STATE_INIT6_O";
      }
      enum "sinit6-o" {
        value 34;
        tailf:code-name "ENUM_cm_state_CM_STATE_SINIT6_O";
      }
      enum "init-tod" {
        value 35;
        tailf:code-name "ENUM_cm_state_CM_STATE_INIT_T";
      }
      enum "eae-time-of-day-start" {
        value 36;
        tailf:code-name "ENUM_cm_state_CM_STATE_SINIT_T";
      }
      enum "init-ipv6-tod" {
        value 37;
        tailf:code-name "ENUM_cm_state_CM_STATE_INIT6_T";
      }
      enum "eae-ipv6-tod" {
        value 38;
        tailf:code-name "ENUM_cm_state_CM_STATE_SINIT6_T";
      }
      enum "reject-m" {
        value 39;
        tailf:code-name "ENUM_cm_state_CM_STATE_REJECT_M";
      }
      enum "sreject-m" {
        value 40;
        tailf:code-name "ENUM_cm_state_CM_STATE_SREJECT_M";
      }
      enum "reject-ts" {
        value 41;
        tailf:code-name "ENUM_cm_state_CM_STATE_REJECT_TS";
      }
      enum "sreject-ts" {
        value 42;
        tailf:code-name "ENUM_cm_state_CM_STATE_SREJECT_TS";
      }
      enum "reject-ip" {
        value 43;
        tailf:code-name "ENUM_cm_state_CM_STATE_REJECT_IP";
      }
      enum "sreject-ip" {
        value 44;
        tailf:code-name "ENUM_cm_state_CM_STATE_SREJECT_IP";
      }
      enum "reject-c" {
        value 45;
        tailf:code-name "ENUM_cm_state_CM_STATE_REJECT_C";
      }
      enum "sreject-c" {
        value 46;
        tailf:code-name "ENUM_cm_state_CM_STATE_SREJECT_C";
      }
      enum "reject-na" {
        value 47;
        tailf:code-name "ENUM_cm_state_CM_STATE_REJECT_NA";
      }
      enum "sreject-na" {
        value 48;
        tailf:code-name "ENUM_cm_state_CM_STATE_SREJECT_NA";
      }
      enum "online" {
        value 49;
        tailf:code-name "ENUM_cm_state_CM_STATE_ONLINE";
      }
      enum "reject-pk" {
        value 50;
        tailf:code-name "ENUM_cm_state_CM_STATE_REJECT_PK";
      }
      enum "expire-pk" {
        value 51;
        tailf:code-name "ENUM_cm_state_CM_STATE_EXPIRE_PK";
      }
      enum "online-pk" {
        value 52;
        tailf:code-name "ENUM_cm_state_CM_STATE_ONLINE_PK";
      }
      enum "reject-pt" {
        value 53;
        tailf:code-name "ENUM_cm_state_CM_STATE_REJECT_PT";
      }
      enum "expire-pt" {
        value 54;
        tailf:code-name "ENUM_cm_state_CM_STATE_EXPIRE_PT";
      }
      enum "online-pt" {
        value 55;
        tailf:code-name "ENUM_cm_state_CM_STATE_ONLINE_PT";
      }
      enum "online-d" {
        value 56;
        tailf:code-name "ENUM_cm_state_CM_STATE_ONLINE_D";
      }
      enum "reject-pkd" {
        value 57;
        tailf:code-name "ENUM_cm_state_CM_STATE_REJECT_PKD";
      }
      enum "expire-pkd" {
        value 58;
        tailf:code-name "ENUM_cm_state_CM_STATE_EXPIRE_PKD";
      }
      enum "online-pkd" {
        value 59;
        tailf:code-name "ENUM_cm_state_CM_STATE_ONLINE_PKD";
      }
      enum "reject-ptd" {
        value 60;
        tailf:code-name "ENUM_cm_state_CM_STATE_REJECT_PTD";
      }
      enum "expire-ptd" {
        value 61;
        tailf:code-name "ENUM_cm_state_CM_STATE_EXPIRE_PTD";
      }
      enum "online-ptd" {
        value 62;
        tailf:code-name "ENUM_cm_state_CM_STATE_ONLINE_PTD";
      }
      enum "w-online" {
        value 63;
        tailf:code-name "ENUM_cm_state_CM_STATE_W_ONLINE";
      }
      enum "w-eject-pk" {
        value 64;
        tailf:code-name "ENUM_cm_state_CM_STATE_W_EJECT_PK";
      }
      enum "w-expire-pk" {
        value 65;
        tailf:code-name "ENUM_cm_state_CM_STATE_W_EXPIRE_PK";
      }
      enum "w-online-pk" {
        value 66;
        tailf:code-name "ENUM_cm_state_CM_STATE_W_ONLINE_PK";
      }
      enum "w-eject-pt" {
        value 67;
        tailf:code-name "ENUM_cm_state_CM_STATE_W_EJECT_PT";
      }
      enum "w-expire-pt" {
        value 68;
        tailf:code-name "ENUM_cm_state_CM_STATE_W_EXPIRE_PT";
      }
      enum "w-online-pt" {
        value 69;
        tailf:code-name "ENUM_cm_state_CM_STATE_W_ONLINE_PT";
      }
      enum "w-online-d" {
        value 70;
        tailf:code-name "ENUM_cm_state_CM_STATE_W_ONLINE_D";
      }
      enum "w-eject-pkd" {
        value 71;
        tailf:code-name "ENUM_cm_state_CM_STATE_W_EJECT_PKD";
      }
      enum "w-expire-pkd" {
        value 72;
        tailf:code-name "ENUM_cm_state_CM_STATE_W_EXPIRE_PKD";
      }
      enum "w-online-pkd" {
        value 73;
        tailf:code-name "ENUM_cm_state_CM_STATE_W_ONLINE_PKD";
      }
      enum "w-eject-ptd" {
        value 74;
        tailf:code-name "ENUM_cm_state_CM_STATE_W_EJECT_PTD";
      }
      enum "w-expire-ptd" {
        value 75;
        tailf:code-name "ENUM_cm_state_CM_STATE_W_EXPIRE_PTD";
      }
      enum "w-online-ptd" {
        value 76;
        tailf:code-name "ENUM_cm_state_CM_STATE_W_ONLINE_PTD";
      }
      enum "p-online" {
        value 77;
        tailf:code-name "ENUM_cm_state_CM_STATE_P_ONLINE";
      }
      enum "p-eject-pk" {
        value 78;
        tailf:code-name "ENUM_cm_state_CM_STATE_P_EJECT_PK";
      }
      enum "p-expire-pk" {
        value 79;
        tailf:code-name "ENUM_cm_state_CM_STATE_P_EXPIRE_PK";
      }
      enum "p-online-pk" {
        value 80;
        tailf:code-name "ENUM_cm_state_CM_STATE_P_ONLINE_PK";
      }
      enum "p-eject-pt" {
        value 81;
        tailf:code-name "ENUM_cm_state_CM_STATE_P_EJECT_PT";
      }
      enum "p-expire-pt" {
        value 82;
        tailf:code-name "ENUM_cm_state_CM_STATE_P_EXPIRE_PT";
      }
      enum "p-online-pt" {
        value 83;
        tailf:code-name "ENUM_cm_state_CM_STATE_P_ONLINE_PT";
      }
      enum "p-online-d" {
        value 84;
        tailf:code-name "ENUM_cm_state_CM_STATE_P_ONLINE_D";
      }
      enum "p-eject-pkd" {
        value 85;
        tailf:code-name "ENUM_cm_state_CM_STATE_P_EJECT_PKD";
      }
      enum "p-expire-pkd" {
        value 86;
        tailf:code-name "ENUM_cm_state_CM_STATE_P_EXPIRE_PKD";
      }
      enum "p-online-pkd" {
        value 87;
        tailf:code-name "ENUM_cm_state_CM_STATE_P_ONLINE_PKD";
      }
      enum "p-eject-ptd" {
        value 88;
        description
          "collection";
        tailf:code-name "ENUM_cm_state_CM_STATE_P_EJECT_PTD";
      }
      enum "p-expire-ptd" {
        value 89;
        description
          "collection";
        tailf:code-name "ENUM_cm_state_CM_STATE_P_EXPIRE_PTD";
      }
      enum "p-online-ptd" {
        value 90;
        description
          "collection";
        tailf:code-name "ENUM_cm_state_CM_STATE_P_ONLINE_PTD";
      }
      enum "w-online-em" {
        value 91;
        tailf:code-name "ENUM_cm_state_CM_STATE_W_ONLINE_EM";
      }
      enum "w-eject-pk-em" {
        value 92;
        tailf:code-name "ENUM_cm_state_CM_STATE_W_EJECT_PK_EM";
      }
      enum "w-expire-pk-em" {
        value 93;
        tailf:code-name "ENUM_cm_state_CM_STATE_W_EXPIRE_PK_EM";
      }
      enum "w-online-pk-em" {
        value 94;
        tailf:code-name "ENUM_cm_state_CM_STATE_W_ONLINE_PK_EM";
      }
      enum "w-eject-pt-em" {
        value 95;
        tailf:code-name "ENUM_cm_state_CM_STATE_W_EJECT_PT_EM";
      }
      enum "w-expire-pt-em" {
        value 96;
        tailf:code-name "ENUM_cm_state_CM_STATE_W_EXPIRE_PT_EM";
      }
      enum "w-online-pt-em" {
        value 97;
        tailf:code-name "ENUM_cm_state_CM_STATE_W_ONLINE_PT_EM";
      }
      enum "w-online-d-em" {
        value 98;
        tailf:code-name "ENUM_cm_state_CM_STATE_W_ONLINE_D_EM";
      }
      enum "w-eject-pkd-em" {
        value 99;
        tailf:code-name "ENUM_cm_state_CM_STATE_W_EJECT_PKD_EM";
      }
      enum "w-expire-pkd-em" {
        value 100;
        tailf:code-name "ENUM_cm_state_CM_STATE_W_EXPIRE_PKD_EM";
      }
      enum "w-online-pkd-em" {
        value 101;
        tailf:code-name "ENUM_cm_state_CM_STATE_W_ONLINE_PKD_EM";
      }
      enum "w-eject-ptd-em" {
        value 102;
        tailf:code-name "ENUM_cm_state_CM_STATE_W_EJECT_PTD_EM";
      }
      enum "w-expire-ptd-em" {
        value 103;
        tailf:code-name "ENUM_cm_state_CM_STATE_W_EXPIRE_PTD_EM";
      }
      enum "w-online-ptd-em" {
        value 104;
        tailf:code-name "ENUM_cm_state_CM_STATE_W_ONLINE_PTD_EM";
      }
      enum "w-online-bm" {
        value 105;
        description
          "collection";
        tailf:code-name "ENUM_cm_state_CM_STATE_W_ONLINE_BM";
      }
      enum "w-eject-pk-bm" {
        value 106;
        description
          "collection";
        tailf:code-name "ENUM_cm_state_CM_STATE_W_EJECT_PK_BM";
      }
      enum "w-expire-pk-bm" {
        value 107;
        tailf:code-name "ENUM_cm_state_CM_STATE_W_EXPIRE_PK_BM";
      }
      enum "w-online-pk-bm" {
        value 108;
        tailf:code-name "ENUM_cm_state_CM_STATE_W_ONLINE_PK_BM";
      }
      enum "w-eject-pt-bm" {
        value 109;
        tailf:code-name "ENUM_cm_state_CM_STATE_W_EJECT_PT_BM";
      }
      enum "w-expire-pt-bm" {
        value 110;
        tailf:code-name "ENUM_cm_state_CM_STATE_W_EXPIRE_PT_BM";
      }
      enum "w-online-pt-bm" {
        value 111;
        tailf:code-name "ENUM_cm_state_CM_STATE_W_ONLINE_PT_BM";
      }
      enum "w-online-d-bm" {
        value 112;
        tailf:code-name "ENUM_cm_state_CM_STATE_W_ONLINE_D_BM";
      }
      enum "w-eject-pkd-bm" {
        value 113;
        tailf:code-name "ENUM_cm_state_CM_STATE_W_EJECT_PKD_BM";
      }
      enum "w-expire-pkd-bm" {
        value 114;
        tailf:code-name "ENUM_cm_state_CM_STATE_W_EXPIRE_PKD_BM";
      }
      enum "w-online-pkd-bm" {
        value 115;
        tailf:code-name "ENUM_cm_state_CM_STATE_W_ONLINE_PKD_BM";
      }
      enum "w-eject-ptd-bm" {
        value 116;
        tailf:code-name "ENUM_cm_state_CM_STATE_W_EJECT_PTD_BM";
      }
      enum "w-expire-ptd-bm" {
        value 117;
        tailf:code-name "ENUM_cm_state_CM_STATE_W_EXPIRE_PTD_BM";
      }
      enum "w-online-ptd-bm" {
        value 118;
        tailf:code-name "ENUM_cm_state_CM_STATE_W_ONLINE_PTD_BM";
      }
    }
    description
      "Cable modem state";
  }

  typedef docsis-version-type {
    type enumeration {
      enum "docsis1-0" {
        value 0;
        tailf:code-name "ENUM_docsis_version_type_DOCSIS_VERSION_1_O";
      }
      enum "docsis1-1" {
        value 1;
        tailf:code-name "ENUM_docsis_version_type_DOCSIS_VERSION_1_1";
      }
      enum "docsis2-0" {
        value 2;
        tailf:code-name "ENUM_docsis_version_type_DOCSIS_VERSION_2_O";
      }
      enum "docsis3-0" {
        value 3;
        tailf:code-name "ENUM_docsis_version_type_DOCSIS_VERSION_3_O";
      }
      enum "docsis3-1" {
        value 4;
        tailf:code-name "ENUM_docsis_version_type_DOCSIS_VERSION_3_1";
      }
    }
    description
      "Cable modem DOCSIS version";
  }

  typedef rpd-state-type {
    type enumeration {
      enum "shutdown" {
        value 0;
        tailf:code-name "ENUM_rpd_state_type_RPD_STATE_SHUTDOWN";
      }
      enum "rpd-offline" {
        value 1;
        tailf:code-name "ENUM_rpd_state_type_RPD_STATE_OFFLINE";
      }
      enum "init-auth" {
        value 2;
        tailf:code-name "ENUM_rpd_state_type_RPD_STATE_INIT_AUTH";
      }
      enum "init-gcp" {
        value 3;
        tailf:code-name "ENUM_rpd_state_type_RPD_STATE_INIT_GCP";
      }
      enum "init-clock" {
        value 4;
        tailf:code-name "ENUM_rpd_state_type_RPD_STATE_INIT_CLOCK";
      }
      enum "init-l2tp" {
        value 5;
        tailf:code-name "ENUM_rpd_state_type_RPD_STATE_INIT_L2TP";
      }
      enum "rpd-online" {
        value 6;
        tailf:code-name "ENUM_rpd_state_type_RPD_STATE_ONLINE";
      }
    }
    description
      "RPD state";
  }

  typedef rpd-core-role-type {
    type enumeration {
      enum "core-unknown" {
        value 0;
        tailf:code-name "ENUM_rpd_core_role_type_RPD_CORE_ROLE_UNKNOWN";
      }
      enum "principal" {
        value 1;
        tailf:code-name "ENUM_rpd_core_role_type_RPD_CORE_ROLE_PRINCIPAL";
      }
      enum "auxiliary" {
        value 2;
        tailf:code-name "ENUM_rpd_core_role_type_RPD_CORE_ROLE_AUXILIARY";
      }
    }
    description
      "RPD core role";
  }

  typedef rpd-ha-role-type {
    type enumeration {
      enum "active" {
        value 0;
        tailf:code-name "ENUM_rpd_ha_role_type_RPD_HA_ROLE_ACTIVE";
      }
      enum "standby" {
        value 1;
        tailf:code-name "ENUM_rpd_ha_role_type_RPD_HA_ROLE_STANDBY";
      }
      enum "ha-unknown" {
        value 2;
        tailf:code-name "ENUM_rpd_ha_role_type_RPD_HA_ROLE_UNKNOWN";
      }
    }
    description
      "RPD HA role";
  }

  typedef rpd-auth-method-type {
    type enumeration {
      enum "auth-bypass" {
        value 0;
        tailf:code-name "ENUM_rpd_auth_method_type_RPD_AUTH_METHOD_BYPASS";
      }
      enum "auth-disabled" {
        value 1;
        tailf:code-name "ENUM_rpd_auth_method_type_RPD_AUTH_METHOD_DISABLED";
      }
      enum "auth-enbaled" {
        value 2;
        tailf:code-name "ENUM_rpd_auth_method_type_RPD_AUTH_METHOD_ENABLED";
      }
    }
    description
      "RPD authentication method";
  }

  typedef rpd-conf-type {
    type enumeration {
      enum "rpd-node" {
        value 0;
        description
          "RPD's configuration type is node";
        tailf:code-name "ENUM_rpd_conf_type_RPD_CFG_NODE";
      }
      enum "rpd-shelf" {
        value 1;
        description
          "RPD's configuration type is shelf";
        tailf:code-name "ENUM_rpd_conf_type_RPD_CFG_SHELF";
      }
    }
    description
      "RPD type";
  }

  typedef sbfd-conf-type {
    type enumeration {
      enum "sbfd-not-configured" {
        value 0;
        description
          "Seamless bidirectional forwarding detection is not enabled";
        tailf:code-name "ENUM_sbfd_conf_type_SBFD_NOT_SET";
      }
      enum "sbfd-configured" {
        value 1;
        description
          "Seamless bidirectional forwarding detection is enabled";
        tailf:code-name "ENUM_sbfd_conf_type_SBFD_SET";
      }
    }
    description
      "Seamless bidirectional forwarding detection configuration";
  }

  typedef nw-delay-static-conf-type {
    type enumeration {
      enum "netork-delay-static-not-cfg" {
        value 0;
        description
          "Network delay static is not set";
        tailf:code-name "ENUM_nw_delay_static_conf_type_NETORK_DELAY_STATIC_NOT_SET";
      }
      enum "netork-delay-static" {
        value 1;
        description
          "Network delay static is set";
        tailf:code-name "ENUM_nw_delay_static_conf_type_NETORK_DELAY_STATIC_SET";
      }
    }
    description
      "Network delay static status";
  }

  typedef ptp-clk-prof-conf-type {
    type enumeration {
      enum "ptp-clock-profile-not-cfg" {
        value 0;
        description
          "No precision time protocol profile configured";
        tailf:code-name "ENUM_ptp_clk_prof_conf_type_PTP_CLK_PROF_NOT_SET";
      }
      enum "ptp-clock-profile" {
        value 1;
        description
          "Precision time protocol profile is configured";
        tailf:code-name "ENUM_ptp_clk_prof_conf_type_PTP_CLK_PROF_SET";
      }
    }
    description
      "Precision time protocol profile configuration";
  }

  typedef ssf-prof-conf-type {
    type enumeration {
      enum "ssd-profile-not-cfg" {
        value 0;
        description
          "Secure software download profile is not configured";
        tailf:code-name "ENUM_ssf_prof_conf_type_SSD_PROF_NOT_SET";
      }
      enum "ssd-profile" {
        value 1;
        description
          "Secure software download profile configured";
        tailf:code-name "ENUM_ssf_prof_conf_type_SSD_PROF_SET";
      }
    }
    description
      "Secure software download profile configuration";
  }

  typedef oob-us-evt-conf-type {
    type enumeration {
      enum "oob-551-us-event-profile-not-cfg" {
        value 0;
        description
          "Out of bind 55-1 upstream event profile id is not configured";
        tailf:code-name "ENUM_oob_us_evt_conf_type_OOB_551_US_EVENT_PROF_NOT_SET";
      }
      enum "oob-551-us-event-profile" {
        value 1;
        description
          "Out of bind 55-1 upstream event profile id is configured";
        tailf:code-name "ENUM_oob_us_evt_conf_type_OOB_551_US_EVENT_PROF_SET";
      }
    }
    description
      "Out of bind 55-1 upstream event profile id configuration";
  }

  typedef rpd-event-prof-conf-type {
    type enumeration {
      enum "rpd-event-profile-not-cfg" {
        value 0;
        description
          "RPD event profile is not configured";
        tailf:code-name "ENUM_rpd_event_prof_conf_type_RPD_EVENT_PROF_NOT_SET";
      }
      enum "rpd-event-profile" {
        value 1;
        description
          "RPD event profile is configured";
        tailf:code-name "ENUM_rpd_event_prof_conf_type_RPD_EVENT_PROF_SET";
      }
    }
    description
      "RPD event profile configuration";
  }

  typedef pt-prof-conf-type {
    type enumeration {
      enum "ds-pilot-tone-not-configured" {
        value 0;
        description
          "Downstream pilot tone profile is not configured";
        tailf:code-name "ENUM_pt_prof_conf_type_DS_PILOT_TONE_NOT_SET";
      }
      enum "ds-pilot-tone" {
        value 1;
        description
          "Downstream pilot tone profile is configured";
        tailf:code-name "ENUM_pt_prof_conf_type_DS_PILOT_TONE_SET";
      }
    }
    description
      "Downstream pilot tone configuration";
  }

  typedef nw-delay-conf-type {
    type enumeration {
      enum "netork-delay-sampling-interval-not-cfg" {
        value 0;
        description
          "Network delay sampling interval is not set";
        tailf:code-name "ENUM_nw_delay_conf_type_NETORK_DELAY_SAMPLING_INTERVAL_NOT_SET";
      }
      enum "netork-delay-sampling-interval" {
        value 1;
        description
          "Network delay sampling interval is set";
        tailf:code-name "ENUM_nw_delay_conf_type_NETORK_DELAY_SAMPLING_INTERVAL_SET";
      }
    }
    description
      "Network delay sampling interval status";
  }

  typedef cbr-lic-conf-type {
    type enumeration {
      enum "downstream-license" {
        value 0;
        description
          "DOCSIS down stream";
        tailf:code-name "ENUM_cbr_lic_conf_type_DS_LICENSE";
      }
      enum "upstream-license" {
        value 1;
        description
          "DOCSIS upstream";
        tailf:code-name "ENUM_cbr_lic_conf_type_US_LICENSE";
      }
      enum "wan-license" {
        value 2;
        description
          "WAN port";
        tailf:code-name "ENUM_cbr_lic_conf_type_WAN_LICENSE";
      }
      enum "subscriber-license" {
        value 3;
        description
          "Subscriber";
        tailf:code-name "ENUM_cbr_lic_conf_type_SUBS_LICENSE";
      }
      enum "lcha-license" {
        value 4;
        description
          "Lice card high available";
        tailf:code-name "ENUM_cbr_lic_conf_type_LCHA_LICENSE";
      }
      enum "video-narrowcast-license" {
        value 5;
        description
          "Video narrow cast";
        tailf:code-name "ENUM_cbr_lic_conf_type_NC_LICENSE";
      }
      enum "video-narrowcast-replicate-license" {
        value 6;
        description
          "Video narrow cast replicate";
        tailf:code-name "ENUM_cbr_lic_conf_type_NC_RPL_LICENSE";
      }
      enum "video-narrowcast-pkey-license" {
        value 7;
        description
          "Video narrow cast power key";
        tailf:code-name "ENUM_cbr_lic_conf_type_NC_PKY_LICENSE";
      }
      enum "video-narrowcast-pme-license" {
        value 8;
        description
          "Video narrow cast privacy mode encryption";
        tailf:code-name "ENUM_cbr_lic_conf_type_NC_PME_LICENSE";
      }
      enum "video-narrowcast-dvb-license" {
        value 9;
        description
          "Video narrow cast video digital video broadcasting";
        tailf:code-name "ENUM_cbr_lic_conf_type_NC_DVB_LICENSE";
      }
      enum "video-broadcast-license" {
        value 10;
        description
          "Video broadcast";
        tailf:code-name "ENUM_cbr_lic_conf_type_BC_LICENSE";
      }
      enum "video-broadcast-enc-license" {
        value 11;
        description
          "Video broadcast power key";
        tailf:code-name "ENUM_cbr_lic_conf_type_BC_ENC_LICENSE";
      }
      enum "docsis31-downstream-channel-license" {
        value 12;
        description
          "DOCSIS 3.1 downstream";
        tailf:code-name "ENUM_cbr_lic_conf_type_DS_D31_LICENSE";
      }
      enum "docsis31-downstream-channel-2-kqam-license" {
        value 13;
        description
          "DOCSIS 3.1 downstream 2 kilo hertz QAM";
        tailf:code-name "ENUM_cbr_lic_conf_type_DS_D31_2KQAM_LICENSE";
      }
      enum "docsis31-downstream-channel-4-kqam-license" {
        value 14;
        description
          "DOCSIS 3.1 downstream 4 kilo hertz QAM";
        tailf:code-name "ENUM_cbr_lic_conf_type_DS_D31_4KQAM_LICENSE";
      }
      enum "rphy-video-broadcast-license" {
        value 15;
        description
          "RPD video broadcast";
        tailf:code-name "ENUM_cbr_lic_conf_type_RPHY_BC_LICENSE";
      }
      enum "docsis31-upstream-channel-exclusive-license" {
        value 16;
        description
          "DOCSIS 3.1 upstream exclusive";
        tailf:code-name "ENUM_cbr_lic_conf_type_US_D31_LICENSE";
      }
      enum "docsis31-upstream-channel-overlap-license" {
        value 17;
        description
          "DOCSIS 3.1 upstream overlap";
        tailf:code-name "ENUM_cbr_lic_conf_type_US_D31_OVERLAP_LICENSE";
      }
      enum "wan-100-g-license" {
        value 18;
        description
          "100 Gigabit Ethernet";
        tailf:code-name "ENUM_cbr_lic_conf_type_WAN_100G_LICENSE";
      }
      enum "cpb-license" {
        value 19;
        description
          "Core Peak Bandwidth";
        tailf:code-name "ENUM_cbr_lic_conf_type_CPB_LICENSE";
      }
    }
    description
      "Cable license type";
  }

  typedef lic-enforced-state-type {
    type enumeration {
      enum "not-enforced" {
        value 0;
        description
          "No enforcement";
        tailf:code-name "ENUM_lic_enforced_state_type_LICENSE_NOT_ENFORCED";
      }
      enum "capped-enforced" {
        value 1;
        description
          "Capped enforcement";
        tailf:code-name "ENUM_lic_enforced_state_type_LICENSE_CAPPED_ENFORCED";
      }
      enum "deact-enforced" {
        value 2;
        description
          "Deactivated enforcement";
        tailf:code-name "ENUM_lic_enforced_state_type_LICENSE_DEACT_ENFORCED";
      }
    }
    description
      "Enforcement state";
  }

  typedef sup250-100g-conf-type {
    type enumeration {
      enum "sup250-100-g-not-cfg" {
        value 0;
        description
          "100 Gigabit Ethernet backhaul interface does not consume WAN License";
        tailf:code-name "ENUM_sup250_100g_conf_type_SUP250_100G_LICENSE_NOT_CONSUMED";
      }
      enum "sup250-100-g-enabled" {
        value 1;
        description
          "100 Gigabit Ethernet backhaul interface consumes WAN License";
        tailf:code-name "ENUM_sup250_100g_conf_type_SUP250_100G_LICENSE_CONSUMED";
      }
    }
    description
      "100 Gigabit Ethernet backhaul interface";
  }

  typedef license-quarter-type {
    type enumeration {
      enum "first-quarter" {
        value 0;
        tailf:code-name "ENUM_license_quarter_type_FIRST_QUARTER";
      }
      enum "second-quarter" {
        value 1;
        tailf:code-name "ENUM_license_quarter_type_SECOND_QUARTER";
      }
      enum "third-quarter" {
        value 2;
        tailf:code-name "ENUM_license_quarter_type_THIRD_QUARTER";
      }
      enum "fourth-quarter" {
        value 3;
        tailf:code-name "ENUM_license_quarter_type_FOURTH_QUARTER";
      }
    }
    description
      "License quarter type";
  }

  grouping upstream-chan-type {
    description
      "Operational data for upstream channel";
    leaf chan-index {
      type uint8;
      description
        "Upstream channel index used by the CM";
    }
    leaf rx-power {
      type decimal64 {
        fraction-digits 2;
      }
      units "dBmV";
      description
        "Rx power of the upstream channel";
    }
    leaf timing-offset {
      type uint32;
      description
        "Timing offset of the upstream channel";
    }
  }

  grouping cable-modem {
    description
      "Operational data for a CM";
    leaf mac-address {
      type yang:mac-address;
      description
        "MAC address of the CM";
    }
    leaf ipv4-addr {
      type inet:ipv4-address;
      description
        "IPv4 address of the CM";
    }
    leaf ipv6-addr {
      type inet:ipv6-address;
      description
        "IPv6 address of the CM";
    }
    leaf interface {
      type string;
      description
        "Upstream interface name of the CM";
    }
    leaf state {
      type docsis-ios-xe-oper:cm-state;
      description
        "State of the CM";
    }
    leaf docsis-version {
      type docsis-ios-xe-oper:docsis-version-type;
      description
        "The maximum supported version of DOCSIS that the CM supports";
    }
    leaf primary-sid {
      type uint32;
      description
        "Primary SID of the CM";
    }
    list us-chan {
      description
        "Upstream channel list of the CM";
      uses docsis-ios-xe-oper:upstream-chan-type;
    }
    leaf cpe-number {
      type uint32;
      description
        "CPE MAC address number attached to the CM";
    }
    leaf dual-ip {
      type boolean;
      description
        "Dual IP status, TRUE indicates the CM has both IPv4 and IPv6 address, 
         FALSE indicates the CM only has an IPV4 address";
    }
  }

  grouping cm-if-summary-totals {
    description
      "Summary information of CMs on one cable interface";
    leaf interface {
      type string;
      description
        "Upstream interface name";
    }
    leaf total {
      type uint32;
      description
        "Number of CMs";
    }
    leaf registered {
      type uint32;
      description
        "Number of registered CMs";
    }
    leaf operational {
      type uint32;
      description
        "Number of operational CMs";
    }
    leaf unregistered {
      type uint32;
      description
        "Number of CMs that are either offline or attempting to come online but are not yet registered";
    }
    leaf offline {
      type uint32;
      description
        "Number of CMs in offline state";
    }
    leaf wideband {
      type uint32;
      description
        "Number of wideband CMs";
    }
    leaf initrc {
      type uint32;
      description
        "Number of CMs in init(rc) state";
    }
    leaf initd {
      type uint32;
      description
        "Number of CMs in init(d) state";
    }
    leaf initio {
      type uint32;
      description
        "Number of CMs in init(io) state";
    }
    leaf inito {
      type uint32;
      description
        "Number of CMs in init(o) state";
    }
  }

  grouping cm-summary-total {
    description
      "Total modems information on CMTS";
    leaf total {
      type uint32;
      description
        "Total number of CMs on the CMTS";
    }
    leaf registered {
      type uint32;
      description
        "Total number of registered CMs on CMTS";
    }
    leaf operational {
      type uint32;
      description
        "Total number of operational CMs on CMTS";
    }
    leaf unregistered {
      type uint32;
      description
        "Total number of CMs that are either offline or attempting to come online but are not yet registered on the CMTS";
    }
    leaf offline {
      type uint32;
      description
        "Total number of CMs in offline state on CMTS";
    }
    leaf wideband {
      type uint32;
      description
        "Total number of wideband CMs on the CMTS";
    }
    leaf initrc {
      type uint32;
      description
        "Total number of CMs in init(rc) state on the CMTS";
    }
    leaf initd {
      type uint32;
      description
        "Total number of CMs in init(d) state on the CMTS";
    }
    leaf initio {
      type uint32;
      description
        "Total number of CMs in init(io) state on the CMTS";
    }
    leaf inito {
      type uint32;
      description
        "Total number of CMs in init(o) state on the CMTS";
    }
    list cm-if-summary-totals {
      key "interface";
      description
        "The list of summary information of CMs per cable interface";
      uses docsis-ios-xe-oper:cm-if-summary-totals;
    }
  }

  grouping cm-dc-summary {
    description
      "Total modems DOCSIS device class information on the CMTS";
    leaf online {
      type uint32;
      description
        "Total number of CMs currently online";
    }
    leaf unrep {
      type uint32;
      description
        "Total number of CMs for which the device class information is unreported or unavailable";
    }
    leaf cm {
      type uint32;
      description
        "Total number of CMs that have reported the device class as an embedded cable modem";
    }
    leaf e-rtr {
      type uint32;
      description
        "Total number of CMs that  have reported the device class as an embedded router";
    }
    leaf e-mta {
      type uint32;
      description
        "Total number of CMs that have reported the device class as an embedded multimedia terminal adapter";
    }
    leaf e-stb {
      type uint32;
      description
        "Total number of CMs that have reported the device class as an embedded set-top box";
    }
    leaf e-ps {
      type uint32;
      description
        "Total number of CMs that have reported the device class as embedded portal services";
    }
    leaf e-dva {
      type uint32;
      description
        "Total number of CMs that have reported the device class as embedded digital voice adapter";
    }
  }

  grouping cable-rpd-state-key {
    description
      "RPD state key";
    leaf id {
      type yang:mac-address;
      description
        "MAC address of the RPD";
    }
    leaf local-if {
      type string;
      description
        "Local ethernet interface that the RPD connected to";
    }
  }

  grouping cable-rpd-state {
    description
      "Operational state of RPD";
    leaf ip-addr {
      type inet:ip-address;
      description
        "RPD's IP address";
    }
    leaf clock-synced {
      type boolean;
      description
        "RPD's state";
    }
    leaf state {
      type docsis-ios-xe-oper:rpd-state-type;
      description
        "RPD's state";
    }
    leaf core-role {
      type docsis-ios-xe-oper:rpd-core-role-type;
      description
        "Primary or auxiliary role";
    }
    leaf ha-role {
      type docsis-ios-xe-oper:rpd-ha-role-type;
      description
        "Active or standby role";
    }
    leaf auth {
      type docsis-ios-xe-oper:rpd-auth-method-type;
      description
        "Authentication result";
    }
    leaf name {
      type string;
      description
        "Configuration name of RPD";
    }
  }

  grouping ds-chan-shutdown-conf-type {
    description
      "Downstream channel mute configuration group";
    leaf start-chan {
      type uint32;
      description
        "Start channel of this group";
    }
    leaf end-chan {
      type uint32;
      description
        "End channel number of this group";
    }
    leaf shutdown {
      type boolean;
      description
        "Shutdown configuration of the channels in this group";
    }
  }

  grouping ds-chan-power-adjust-conf-type {
    description
      "Downstream channel power adjust configuration group";
    leaf start-chan {
      type uint32;
      description
        "Start channel of this group";
    }
    leaf end-chan {
      type uint32;
      description
        "End channel number of this group";
    }
    leaf power-adjust {
      type decimal64 {
        fraction-digits 2;
      }
      description
        "Power adjust configuration parameters for the channels in this group";
    }
  }

  grouping ds-chan-mute-conf-type {
    description
      "Downstream channel mute configuration group";
    leaf start-chan {
      type uint32;
      description
        "Start channel of this group";
    }
    leaf end-chan {
      type uint32;
      description
        "End channel number of this group";
    }
    leaf mute {
      type boolean;
      description
        "Mute is enabled or disabled for the channels in this group";
    }
  }

  grouping sbfd-para-conf-type {
    description
      "Seamless bidirectional forwarding detection configuration parameters";
    leaf sbfd-interval {
      type uint32;
      description
        "Transmit interval between Seamless bidirectional forwarding detection PDUs";
    }
    leaf sbfd-multiplier {
      type uint32;
      description
        "Multiplier value used to compute holddown";
    }
  }

  grouping us-description-conf-type {
    description
      "Upstream description configuration";
    leaf us-index {
      type uint8;
      description
        "Upstream index";
    }
    leaf us-description {
      type string;
      description
        "Upstream description";
    }
  }

  grouping analog-power-conf {
    description
      "Analog power configuration parameters";
    leaf power-major-lo-th {
      type uint16;
      description
        "Power major low alarm threshold";
    }
    leaf power-minor-lo-th {
      type uint16;
      description
        "Power minor low alarm threshold";
    }
    leaf power-normal-th {
      type uint16;
      description
        "Power normal threshold";
    }
    leaf power-minor-hi-th {
      type uint16;
      description
        "Power minor high threshold";
    }
  }

  grouping rpd-shelf-ds-conf-type {
    description
      "Downstream configuration specific for RPD shelf";
    leaf max-carrier {
      type uint32;
      description
        "Max carrier";
    }
    leaf base-power {
      type decimal64 {
        fraction-digits 2;
      }
      description
        "Base power";
    }
  }

  grouping rpd-node-ds-conf-type {
    description
      "Downstream configuration specific for RPD node";
    leaf base-power {
      type decimal64 {
        fraction-digits 2;
      }
      description
        "Base power";
    }
  }

  grouping ds-port-conf {
    description
      "RPD downstream RF port configuration";
    leaf index {
      type uint32;
      description
        "Index of the downstream port";
    }
    leaf pt-prof-conf {
      type docsis-ios-xe-oper:pt-prof-conf-type;
      config false;
      description
        "DO NOT USE!  -- hidden internal";
      tailf:hidden "full";
      tailf:meta-data "hidden" {
        tailf:meta-value "true";
      }
    }
    leaf rpd-type {
      type docsis-ios-xe-oper:rpd-conf-type;
      config false;
      description
        "DO NOT USE!  -- hidden internal";
      tailf:hidden "full";
      tailf:meta-data "hidden" {
        tailf:meta-value "true";
      }
    }
    list ds-chan-power-adjust {
      description
        "List of channel power adjust";
      uses docsis-ios-xe-oper:ds-chan-power-adjust-conf-type;
    }
    list ds-chan-mute {
      description
        "List of channel mute";
      uses docsis-ios-xe-oper:ds-chan-mute-conf-type;
    }
    list ds-chan-shutdown {
      description
        "List of channel shutdown";
      uses docsis-ios-xe-oper:ds-chan-shutdown-conf-type;
    }
    leaf tilt-slope {
      type decimal64 {
        fraction-digits 2;
      }
      description
        "Tilt slope";
    }
    leaf tilt-pivot-freq {
      type uint32;
      description
        "Tilt pivot frequency";
    }
    leaf mute {
      type boolean;
      description
        "Mute configuration";
    }
    leaf shutdown {
      type boolean;
      description
        "Shutdown";
    }
    choice pt-prof-conf-choice {
      description
        "Downstream pilot tone configuration";
      case ds-pilot-tone {
        leaf pt-prof-id {
          type uint32;
          description
            "Profile id";
        }
      }
    }
    choice rpd-type-choice {
      description
        "Configuration in downstream port based on RPD's type";
      case rpd-node {
        description
          "Node specific downstream port configuration";
        container node-ds-conf {
          description
            "Node specific downstream port configuration";
          uses docsis-ios-xe-oper:rpd-node-ds-conf-type;
        }
      }
      case rpd-shelf {
        description
          "Shelf specific configuration";
        container shelf-ds-conf {
          description
            "Shelf specific downstream port configuration";
          uses docsis-ios-xe-oper:rpd-shelf-ds-conf-type;
        }
      }
    }
  }

  grouping ds-oob-vom-conf-type {
    description
      "Downstream oob virtual OM configuration parameters";
    leaf ds-index {
      type uint8;
      description
        "Downstream index";
    }
    leaf vom-id {
      type uint32;
      description
        "Downstream oob virtual OM value";
    }
    leaf profile {
      type uint32;
      description
        "Profile id";
    }
  }

  grouping core-ds-ctlr-conf {
    description
      "Downstream controller configuration";
    leaf ds-ctrlr-index {
      type uint8;
      description
        "Downstream controller index";
    }
    leaf downstream-if {
      type string;
      description
        "Downstream interface name";
    }
    leaf profile {
      type uint32;
      description
        "Profile id";
    }
  }

  grouping core-ds-port-conf {
    description
      "Core downstream port configuration";
    leaf ds-index {
      type uint8;
      description
        "Downstream port index";
    }
    list ds-ctlr {
      description
        "List of downstream controllers";
      uses docsis-ios-xe-oper:core-ds-ctlr-conf;
    }
  }

  grouping us-oob-varpd-conf {
    description
      "Oob varpd configuration for core upstream port";
    leaf us-index {
      type uint8;
      description
        "Upstream port index of the core";
    }
    leaf varpd-id {
      type uint32;
      description
        "Varpd id";
    }
    leaf profile {
      type uint32;
      description
        "Profile id";
    }
  }

  grouping core-us-port-conf {
    description
      "Upstream port configuration for core";
    leaf us-index {
      type uint8;
      description
        "Upstream port's index";
    }
    leaf us-intf {
      type string;
      description
        "Interface name";
    }
    leaf profile-id {
      type uint32;
      description
        "Profile id";
    }
  }

  grouping pw-conf {
    description
      "Static-pseudowire configuration";
    leaf index {
      type uint8;
      description
        "Index";
    }
    leaf static-pw-name {
      type string;
      description
        "Static-pseudowire name";
    }
    leaf profile {
      type uint32;
      description
        "Profile id";
    }
  }

  grouping nw-delay-dlm-conf {
    description
      "Network delay sampling interval configuration";
    leaf sampling-interval {
      type uint32;
      description
        "Network delay sampling interval";
    }
    leaf measure-only {
      type boolean;
      description
        "Measure only is enabled or not";
    }
  }

  grouping core-conf {
    description
      "RPD core configuration";
    leaf index {
      type uint32;
      description
        "Core index";
    }
    leaf core-if {
      type string;
      description
        "Interface name";
    }
    leaf principal {
      type boolean;
      description
        "Principal role";
    }
    list core-ds-port {
      description
        "List of downstream ports";
      uses docsis-ios-xe-oper:core-ds-port-conf;
    }
    list core-ds-oob-vom {
      description
        "List of oob virtual OM for downstream ports";
      uses docsis-ios-xe-oper:ds-oob-vom-conf-type;
    }
    list core-us-port {
      description
        "List of upstream ports that belong to the core";
      uses docsis-ios-xe-oper:core-us-port-conf;
    }
    list core-us-port-varpd {
      description
        "List of oob varpd for upstream ports that belong to the core";
      uses docsis-ios-xe-oper:us-oob-varpd-conf;
    }
    list ds-pw {
      description
        "List of downstream static pseudowires that belong to the core";
      uses docsis-ios-xe-oper:pw-conf;
    }
    list us-pw {
      description
        "List of upstream static pseudowires that belong to the core";
      uses docsis-ios-xe-oper:pw-conf;
    }
    leaf depi {
      type string;
      description
        "Downstream External PHY Interface";
    }
    leaf uepi {
      type string;
      description
        "Upstream External PHY Interface";
    }
    leaf nw-delay-sampling-en {
      type docsis-ios-xe-oper:nw-delay-conf-type;
      config false;
      description
        "DO NOT USE!  -- hidden internal";
      tailf:hidden "full";
      tailf:meta-data "hidden" {
        tailf:meta-value "true";
      }
    }
    leaf nw-delay-static-en {
      type docsis-ios-xe-oper:nw-delay-static-conf-type;
      config false;
      description
        "DO NOT USE!  -- hidden internal";
      tailf:hidden "full";
      tailf:meta-data "hidden" {
        tailf:meta-value "true";
      }
    }
    choice nw-delay-sampling-en-choice {
      description
        "The configuration status of network delay sampling interval";
      case netork-delay-sampling-interval {
        container network-delay-dlm {
          description
            "Network delay settings";
          uses docsis-ios-xe-oper:nw-delay-dlm-conf;
        }
      }
    }
    choice nw-delay-static-en-choice {
      description
        "The configuration status of network delay static";
      case netork-delay-static {
        leaf network-delay-static {
          type uint32;
          description
            "Network delay static value";
        }
      }
    }
  }

  grouping cable-rpd-conf {
    description
      "RPD configuration";
    leaf name {
      type string;
      description
        "Configuration name";
    }
    leaf description {
      type string;
      description
        "Description name";
    }
    leaf identifier {
      type yang:mac-address;
      description
        "MAC address";
    }
    leaf type {
      type docsis-ios-xe-oper:rpd-conf-type;
      description
        "Node or shelf";
    }
    leaf sbfd-enable {
      type docsis-ios-xe-oper:sbfd-conf-type;
      config false;
      description
        "DO NOT USE!  -- hidden internal";
      tailf:hidden "full";
      tailf:meta-data "hidden" {
        tailf:meta-value "true";
      }
    }
    leaf auth-type {
      type docsis-ios-xe-oper:rpd-auth-method-type;
      description
        "Authentication type";
    }
    list ds-port-conf {
      key "index";
      description
        "List of downstream port configurations that belong to the RPD";
      uses docsis-ios-xe-oper:ds-port-conf;
    }
    list core-conf {
      key "index";
      description
        "List of core configurations that belong to the RPD";
      uses docsis-ios-xe-oper:core-conf;
    }
    list us-description {
      description
        "List of upstream descriptions that belong to the RPD";
      uses docsis-ios-xe-oper:us-description-conf-type;
    }
    container analog-power-rx {
      description
        "Analog power rx";
      uses docsis-ios-xe-oper:analog-power-conf;
    }
    container analog-power-tx {
      description
        "Analog power tx";
      uses docsis-ios-xe-oper:analog-power-conf;
    }
    leaf ptp-clk-prof-en {
      type docsis-ios-xe-oper:ptp-clk-prof-conf-type;
      config false;
      description
        "DO NOT USE!  -- hidden internal";
      tailf:hidden "full";
      tailf:meta-data "hidden" {
        tailf:meta-value "true";
      }
    }
    leaf rpd-event-prof-en {
      type docsis-ios-xe-oper:rpd-event-prof-conf-type;
      config false;
      description
        "DO NOT USE!  -- hidden internal";
      tailf:hidden "full";
      tailf:meta-data "hidden" {
        tailf:meta-value "true";
      }
    }
    leaf ssd-prof-en {
      type docsis-ios-xe-oper:ssf-prof-conf-type;
      config false;
      description
        "DO NOT USE!  -- hidden internal";
      tailf:hidden "full";
      tailf:meta-data "hidden" {
        tailf:meta-value "true";
      }
    }
    leaf oob-us-evt-prof-en {
      type docsis-ios-xe-oper:oob-us-evt-conf-type;
      config false;
      description
        "DO NOT USE!  -- hidden internal";
      tailf:hidden "full";
      tailf:meta-data "hidden" {
        tailf:meta-value "true";
      }
    }
    choice rpd-event-prof-en-choice {
      description
        "The configuration status of rpd event profile";
      case rpd-event-profile {
        leaf rpd-event-profile {
          type uint8;
          description
            "Rpd event profile";
        }
      }
    }
    choice ssd-prof-en-choice {
      description
        "The configuration status of secure software download";
      case ssd-profile {
        leaf ssd-profile-id {
          type uint8;
          description
            "Secure software download profile id";
        }
      }
    }
    choice oob-us-evt-prof-en-choice {
      description
        "The configuration status of out of bind 55-1 upstream event profile";
      case oob-551-us-event-profile {
        leaf oob-55d1-us-event-prof-id {
          type uint8;
          description
            "Out of bind 55-1 upstream event profile";
        }
      }
    }
    choice sbfd-enable-choice {
      description
        "Seamless bidirectional forwarding detection configuration";
      case sbfd-configured {
        description
          "Seamless bidirectional forwarding detection enabled";
        container sbfd-parameter {
          description
            "Seamless bidirectional forwarding detection parameter";
          uses docsis-ios-xe-oper:sbfd-para-conf-type;
        }
      }
    }
    choice ptp-clk-prof-en-choice {
      description
        "The configuration status of dti profile";
      case ptp-clock-profile {
        leaf r-dti {
          type uint8;
          description
            "Dti profile id";
        }
      }
    }
  }

  grouping lic-with-conf-lock {
    description
      "Operational state of license type with config enforcement setting";
    leaf entitlement {
      type string;
      description
        "Entitlement";
    }
    leaf c-cnt {
      type uint32;
      description
        "Consumed count";
    }
    leaf reported-to-sm {
      type uint32;
      description
        "Count reported to smart agent";
    }
    leaf enforced-state {
      type docsis-ios-xe-oper:lic-enforced-state-type;
      config false;
      description
        "DO NOT USE!  -- hidden internal";
      tailf:hidden "full";
      tailf:meta-data "hidden" {
        tailf:meta-value "true";
      }
    }
    leaf cfg-lock-enforced {
      type boolean;
      description
        "Configuration lock enforced status";
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
  }

  grouping lic-without-conf-lock {
    description
      "Operational state of license type without config enforcement setting";
    leaf entitlement {
      type string;
      description
        "Entitlement";
    }
    leaf c-cnt {
      type uint32;
      description
        "Consumed count";
    }
    leaf reported-to-sm {
      type uint32;
      description
        "Count reported to smart agent";
    }
    leaf enforced-state {
      type docsis-ios-xe-oper:lic-enforced-state-type;
      config false;
      description
        "DO NOT USE!  -- hidden internal";
      tailf:hidden "full";
      tailf:meta-data "hidden" {
        tailf:meta-value "true";
      }
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
  }

  grouping wan-lic-state-type {
    description
      "Operational state of WAN license";
    leaf entitlement {
      type string;
      description
        "Entitlement";
    }
    leaf c-cnt {
      type uint32;
      description
        "Consumed count";
    }
    leaf reported-to-sm {
      type uint32;
      description
        "Count reported to smart agent";
    }
    leaf enforced-state {
      type docsis-ios-xe-oper:lic-enforced-state-type;
      config false;
      description
        "DO NOT USE!  -- hidden internal";
      tailf:hidden "full";
      tailf:meta-data "hidden" {
        tailf:meta-value "true";
      }
    }
    leaf cfg-lock-enforced {
      type boolean;
      description
        "Configuration lock enforced status";
    }
    leaf sup250-100g-en {
      type docsis-ios-xe-oper:sup250-100g-conf-type;
      config false;
      description
        "DO NOT USE!  -- hidden internal";
      tailf:hidden "full";
      tailf:meta-data "hidden" {
        tailf:meta-value "true";
      }
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
    choice sup250-100g-en-choice {
      description
        "Wan license for 100 gigabit backhaul interface status";
      case sup250-100-g-enabled {
        leaf backhaul-consumes-wan-lic {
          type boolean;
          description
            "100 gigabit backhaul interface consumes WAN License";
        }
      }
    }
  }

  grouping us-d31-lic-state {
    description
      "Operational state of DOCSIS 3.1 downstream license";
    leaf entitlement {
      type string;
      description
        "Entitlement";
    }
    leaf total-licensed-spectrum {
      type uint32;
      description
        "Total licensed spectrum";
    }
    leaf c-cnt {
      type uint32;
      description
        "Consumed count";
    }
    leaf reported-to-sm {
      type uint32;
      description
        "Count reported to smart agent";
    }
    leaf enforced-state {
      type docsis-ios-xe-oper:lic-enforced-state-type;
      config false;
      description
        "DO NOT USE!  -- hidden internal";
      tailf:hidden "full";
      tailf:meta-data "hidden" {
        tailf:meta-value "true";
      }
    }
    leaf forced-shut-down-chan {
      type string;
      description
        "Forced shut down channel";
    }
    choice enforced-state-choice {
      description
        "Operational status of license enforcement";
      case deact-enforced {
        leaf deact-enforcement {
          type string;
          description
            "Deactivated enforcement";
        }
      }
      case capped-enforced {
        leaf capped-enforcement {
          type uint32;
          description
            "Capped enforcement";
        }
      }
      case not-enforced {
        leaf no-enforcement-state {
          type boolean;
          description
            "No enforcement";
        }
      }
    }
  }

  grouping cpb-lic-state {
    description
      "Operational state of Core Peak Bandwidth smart license feature";
    leaf entitlement {
      type string;
      description
        "Entitlement";
    }
    leaf c-cnt {
      type uint32;
      description
        "Consumed count";
    }
    leaf reported-to-sm {
      type uint32;
      description
        "Count reported to smart agent";
    }
    leaf enforced-state {
      type boolean;
      description
        "Enforced state";
    }
    leaf cfg-lock-enforced {
      type boolean;
      description
        "Configuration lock enforced status";
    }
    leaf quarterly-cpb-rate {
      type uint32;
      description
        "Quarterly Core Peak Bandwidth";
    }
    leaf quarter {
      type docsis-ios-xe-oper:license-quarter-type;
      description
        "Quarter";
    }
    leaf year {
      type uint32;
      description
        "Year of the Core Peak Bandwidth";
    }
    leaf first-monthly-cpb-bps {
      type uint32;
      description
        "bps for first monthly Core Peak Bandwidth";
    }
    leaf first-monthly-cpb-100mbps {
      type uint32;
      description
        "100 Mbps for first monthly Core Peak Bandwidth";
    }
    leaf second-monthly-cpb-bps {
      type uint32;
      description
        "bps for second monthly Core Peak Bandwidth";
    }
    leaf second-monthly-cpb-100mbps {
      type uint32;
      description
        "100 Mbps for second monthly Core Peak Bandwidth";
    }
    leaf third-monthly-cpb-bps {
      type uint32;
      description
        "bps for third monthly Core Peak Bandwidth";
    }
    leaf third-monthly-cpb-100mbps {
      type uint32;
      description
        "100 Mbps for third monthly Core Peak Bandwidth";
    }
  }

  grouping cable-license {
    description
      "Operational state of cable license";
    leaf license-type {
      type docsis-ios-xe-oper:cbr-lic-conf-type;
      description
        "Type of cable license";
    }
    leaf license-state {
      type docsis-ios-xe-oper:cbr-lic-conf-type;
      config false;
      description
        "DO NOT USE!  -- hidden internal";
      tailf:hidden "full";
      tailf:meta-data "hidden" {
        tailf:meta-value "true";
      }
    }
    choice license-state-choice {
      description
        "Operational state of specific type of cable license";
      case downstream-license {
        container ds-lic {
          description
            "DOCSIS down stream";
          uses docsis-ios-xe-oper:lic-with-conf-lock;
        }
      }
      case upstream-license {
        container us-lic {
          description
            "DOCSIS upstream";
          uses docsis-ios-xe-oper:lic-with-conf-lock;
        }
      }
      case wan-license {
        container wan-lic {
          description
            "WAN port";
          uses docsis-ios-xe-oper:wan-lic-state-type;
        }
      }
      case lcha-license {
        container lcha-lic {
          description
            "Lice card high available";
          uses docsis-ios-xe-oper:lic-with-conf-lock;
        }
      }
      case video-narrowcast-license {
        container nc-lic {
          description
            "Narrow cast video";
          uses docsis-ios-xe-oper:lic-without-conf-lock;
        }
      }
      case video-narrowcast-replicate-license {
        container nc-rpl-lic {
          description
            "Narrow cast video replicate";
          uses docsis-ios-xe-oper:lic-without-conf-lock;
        }
      }
      case video-narrowcast-pkey-license {
        container nc-pky-lic {
          description
            "Narrow cast video power key";
          uses docsis-ios-xe-oper:lic-without-conf-lock;
        }
      }
      case video-narrowcast-pme-license {
        container nc-pme-lic {
          description
            "Narrow cast video privacy mode encryption";
          uses docsis-ios-xe-oper:lic-without-conf-lock;
        }
      }
      case video-narrowcast-dvb-license {
        container nc-dvb-lic {
          description
            "Narrow cast video digital video broadcasting";
          uses docsis-ios-xe-oper:lic-without-conf-lock;
        }
      }
      case video-broadcast-license {
        container bc-lic {
          description
            "Broadcast video";
          uses docsis-ios-xe-oper:lic-without-conf-lock;
        }
      }
      case video-broadcast-enc-license {
        container bc-enc-lic {
          description
            "Broadcast video power key";
          uses docsis-ios-xe-oper:lic-without-conf-lock;
        }
      }
      case docsis31-downstream-channel-license {
        container ds-31-lic {
          description
            "DOCSIS 3.1 downstream";
          uses docsis-ios-xe-oper:lic-with-conf-lock;
        }
      }
      case rphy-video-broadcast-license {
        container rphy-bc-lic {
          description
            "RPD broadcast video";
          uses docsis-ios-xe-oper:lic-without-conf-lock;
        }
      }
      case docsis31-upstream-channel-exclusive-license {
        container us-d31-lic {
          description
            "DOCSIS 3.1 upstream exclusive";
          uses docsis-ios-xe-oper:us-d31-lic-state;
        }
      }
      case docsis31-upstream-channel-overlap-license {
        container us-d31-overlap-lic {
          description
            "DOCSIS 3.1 upstream overlap";
          uses docsis-ios-xe-oper:us-d31-lic-state;
        }
      }
      case wan-100-g-license {
        container wan-100g-lic {
          description
            "100 Gigabit Ethernet";
          uses docsis-ios-xe-oper:lic-with-conf-lock;
        }
      }
      case cpb-license {
        container cpb-lic {
          description
            "Core Peak Bandwidth";
          uses docsis-ios-xe-oper:cpb-lic-state;
        }
      }
    }
  }

  container docsis-oper-data {
    config false;
    description
      "Operational data on Cisco Cable Modem Termination System";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    container cm-summary-total {
      presence "cm-summary-total";
      description
        "A summary of all the modem information";
      uses docsis-ios-xe-oper:cm-summary-total;
    }
    list cable-modem {
      key "mac-address";
      description
        "List of cable modems";
      uses docsis-ios-xe-oper:cable-modem;
    }
    list cable-license {
      key "license-type";
      description
        "Operational state of Cable license";
      uses docsis-ios-xe-oper:cable-license;
    }
    container cm-dc-summary {
      presence "cm-dc-summary";
      description
        "A summary of DOCSIS device class information";
      uses docsis-ios-xe-oper:cm-dc-summary;
    }
    list cable-rpd-state {
      key "id local-if";
      description
        "Operational state of RPD";
      uses docsis-ios-xe-oper:cable-rpd-state-key;
      uses docsis-ios-xe-oper:cable-rpd-state;
    }
    list cable-rpd-conf {
      key "name";
      description
        "Configuration data of RPD";
      uses docsis-ios-xe-oper:cable-rpd-conf;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWU7TJREADkFfgEAAEAZ/ED///+q////qYAlztrfNqG17mlUhRXbtYzt0YqShRhKaSaAE0xSfqnqaNkg0e1NQeJqeUeoAGqp/5ERPFNQNMgaAA0ekHogekAGm1KnpMJGnqZAGgAAAAAASakEEKeTRqTJ6QAAAAaZBkOYBNMAmQwABMEwAAARJEATJU9ommmoNJsgNIwjDQEP60XavKU4PDxRz3e1+qATuJS0RmDMzKKKKLFixdmv+MLxgcNl8bLNeNQTuK6UpgwUk4FSQDJAMkByaZeqC9UF+fYWgu8hqMOfqeTZeGCvT7NOs0SSHXRpIkioK54EHhAFf7NvDh4HPIfbl2/OmP0ihQNaQEwTBG4VWwd/PwlWylPPC2qNezZECaBoWJCSTp1BQUFvc01Pbwsnniqb4FTb05ZgTPdcVO8KbbbdL7nhx4G1Ac9S6ZSkslJZKS7TLpSXSoXPY+/0/P7T/Hzf+9yCs/CkAKpZVDVU1EUqikkVAhVIj67mf2iKnuZ6/X/qp7vomZ+Dw7eJ7tvinTp7nIKErbnYNTC3CIqYSbD4y0BP6NOsZrv7IsWLOGrhppw2bfftVk71zX4XXv3pZJkmSbFpb0lUJijzcYdyywK1rhJroHyfRNXfKHmh148tg0b9NFtbfrTSCxYsWd5ttRk0REUUFERRRnZ1aasUiIooKIiij2sbml1lHQuy/PTGVMJbr5Qv+k/U80uRlHYufR8g9x78MmJgLAtjJkznsfWa/k9T0ZL9CXM58YbhYsdhP+n1A+xBBv90ntlezr7yJ9ifqb8eoeVFRMAAJiIcwtgqjyIDNR2PyNefO4x6ING/dlZ3VF7qT87XTpgSCuPvJHZoiaZhVEvLJdLmW2wGyVMtyBCqtIQ8wbpRHnM3W1Vm8G1lvVW0xD+e826WvJ3YAxOqUQU9dq9YAeB3T0m3Ah0UUiiwTMPGwBeOKDuFD1ChhlsAaPQKxEdsRve0aizJaBM3L2gXpVVVVVXFUqqqqqrYhKlVIFokIcq8DuOB39xm1cCjfvKPa4m2eL0sEOtBYNxGi50wOMEA65o00VVUQVRVFiwYe9U279iJtpknRV18AAxDOKlz5P92DgI8HlxfQO/wOxLdshDCr3chYScDyTJXA0N9lVVVVRFVV8S0xgNJISegLmdeFIZrjclwi1ASWaUDQsq4qeZgg2MCgysnwlYuEJC518E59DgdwvPgWVaNE5OzZwC5mJqYZWNTLLI6k999gTtpUPIU7mlXzL13RC5EkUOpB3IBeD3kDA4qqqonZ4ryjIqwWiQtOSGKAuTeEG0MbB0sVrjgu2VjMwPgBKsAZ2Sm5AeidUpNciFIAF7YkOjuE8ao2TfjoalEKCoRhCDG4PRAApDKDsGxuKrffNpwuccbGIeWpYtxtMFck3S8vdLQRQRIcQSHK0uAkLHxhd0IX4LE8eAk5OuvAZ5pmUFCJ5zREZie8qwrDo3RqM88dgiCZUnyLG1Ys/pthInTqRs2RLBR5y1m0aF9yDgL3nnuZ+FYKsKqqmMapJLVTFidBleBuYrrAhAAQqYIdKUWYNhA5JrO40FNXZa4iVXVd9dyKzJkPFozd7XvP3NOzI3ZF7ypgkABCAAhYbb1RYWmmkoiKKWqhSmuzxaasUiIKIiiiigDzsbmbqYCd6K2udS+Ojh6Krq092Qh4QDAiikVZJFCSam2VhgtLWHGGF469UnnzM9n1Sz4kYyb6Z2dt1dDy84sfwRQcyativlwpYj/Q/MS24mA6KYvkbFVEqMCfCzpZpKNkDnWvzhjuZ1y43e6iSN7OTQJkvETPiVPbocjwvLepvmEwc0kj6vC+q2sq1VLa1rLApCQNyHwDchgyxRqtYsc1qXbFt0pY0lSi0h2riyyI7muQqCk6HV7XL2SUTkufLvpoGb5pVVVVVVVVVVVVc1rtuWk39oAV5ZuUPSjLJooKCgsTeHu6h5YIGUdATgMALGceQxc8bOGgdMk2YEgSBIHh07akOi5tAZd5ZqFLnRHvTdMsYm1ocYht0wKROAMTZTxzMcskA62o2dVRViwVVV7cCcU67khxzCb/MdIScb+IAZKax4CNEAMTY9D9pkFS1VxnQc9gO2W9t9Qh04RQkscZgcGmiqqqqoiqq7TaGEHh5jbbxMniD4jxOHOoUaefFrBaISAnKcBZu3QDUsq4pkJj6jIE2CBm4SEmHNwJ37up6XxRu8aaTIDPAje4LBQUFBQTrR4S+A0IbFXxrDbIw3M8nUDmD1Kw/jHQe23Laj1CnwUkgjPArXegN3ApJEGxud5ZOZMBwhZNnFUnK5uPphJJIkxrnnINDxbAdUxXhN4m2RTrvJvgYnQgOBmUbYncCX1xouQThHSk2hEOLWZqclW1hKgYZU4VNTySWRNk3xHGIXSELNBRBKNAoSrMlyxQmtrhirlfQM2wVpc142xsm4T06my2L/EFmxCGvk8WPHzOB1OTt3HQNNjWIDSNuYKZdpWqVtf8fxqP2PG7+CGN/4u5IpwoSCdpkoiA";
      }
      tailf:meta-data "uncompressed_size" {
        tailf:meta-value "7318";
      }
    }
  }

  container schema-metadata-Cisco-IOS-XE-docsis-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-docsis-oper";
    }
    tailf:meta-data "organization" {
      tailf:meta-value "Cisco Systems, Inc.";
    }
    tailf:meta-data "semver" {
      tailf:meta-value "2019-05-01";
    }
  }
}
