module Cisco-IOS-XE-trustsec-oper {
  yang-version 1;
  namespace "http://cisco.com/ns/yang/Cisco-IOS-XE-trustsec-oper";
  prefix trustsec-ios-xe-oper;
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of Cisco Trustsec operational information on
     Role based permissions, IP-SGT bindings and SXP connections.
     Copyright (c) 2016-2017, 2019-2020 by Cisco Systems, Inc.
     All rights reserved.";

  revision 2020-07-01 {
    description
      "Modified trustsec oper model to support CTS manual.";
    reference "0.0.0";
    cisco-semver:module-version "0.0.0";
    cisco-semver-internal:os-version "17.3.1";
  }
  revision 2019-11-01 {
    description
      "Added model for IPv6 CTS role based policy.";
    reference "1.3.0";
    cisco-semver:module-version "1.3.0";
    cisco-semver-internal:os-version "17.1.1";
  }
  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2017-02-07 {
    description
      "Initial revision";
    reference "1.0.0";
    cisco-semver:module-version "1.0.0";
  }

  typedef cts-odm-binding-source {
    type enumeration {
      enum "default" {
        value 0;
        description
          "Default Security Group Tag binding value in this device
           for the given IP-Address";
        tailf:code-name "ENUM_cts_odm_binding_source_CTS_SGT_BINDING_DEFAULT";
      }
      enum "from-vlan" {
        value 1;
        description
          "Security Group Tag binding value in this device for the given
           IP-Address is learned from a VLAN";
        tailf:code-name "ENUM_cts_odm_binding_source_CTS_SGT_BINDING_FROM_VLAN";
      }
      enum "from-cli" {
        value 2;
        description
          "Security Group Tag binding value in this device
           for the given
           IP-Address is configure from CLI (Command Line Interface)";
        tailf:code-name "ENUM_cts_odm_binding_source_CTS_SGT_BINDING_FROM_CLI";
      }
      enum "from-l3if" {
        value 3;
        description
          "Security Group Tag binding value in this device
           for the given IP-Address is learned from a L3 (Layer 3) interface";
        tailf:code-name "ENUM_cts_odm_binding_source_CTS_SGT_BINDING_FROM_L3IF";
      }
      enum "from-cfp" {
        value 4;
        description
          "Security Group Tag binding value in this device
           for the given IP-Address is learned via SXP
           binding exchange protocol";
        tailf:code-name "ENUM_cts_odm_binding_source_CTS_SGT_BINDING_FROM_SXP";
      }
      enum "from-ip-arp" {
        value 5;
        description
          "Security Group Tag binding value in this
           device for the given
           IP-Address is learned via IP-ARP protocol";
        tailf:code-name "ENUM_cts_odm_binding_source_CTS_SGT_BINDING_FROM_IP_ARP";
      }
      enum "from-local" {
        value 6;
        description
          "Security Group Tag binding value in this device
           for the given IP-Address is learned locally";
        tailf:code-name "ENUM_cts_odm_binding_source_CTS_SGT_BINDING_FROM_LOCAL";
      }
      enum "from-sgt-caching" {
        value 7;
        description
          "Security Group Tag binding value in this device
           for the given IP-Address is learned via Security Group Tag
           caching from data path.";
        tailf:code-name "ENUM_cts_odm_binding_source_CTS_SGT_BINDING_FROM_SGT_CACHING";
      }
      enum "from-cli-hi" {
        value 8;
        description
          "Security Group Tag binding value in this device
           for the given IP-Address is configured from CLI-high priority.";
        tailf:code-name "ENUM_cts_odm_binding_source_CTS_SGT_BINDING_FROM_CLI_HI";
      }
    }
    description
      "Binding Source enumeration";
  }

  typedef sxp-con-state {
    type enumeration {
      enum "state-off" {
        value 0;
        description
          "SXP Connection state is OFF";
        tailf:code-name "ENUM_sxp_con_state_CTS_SXP_CON_STATE_OFF";
      }
      enum "state-pending-on" {
        value 1;
        description
          "SXP Connection state is Pending-On";
        tailf:code-name "ENUM_sxp_con_state_CTS_SXP_CON_STATE_PENDING_ON";
      }
      enum "state-on" {
        value 2;
        description
          "SXP Connection state is ON";
        tailf:code-name "ENUM_sxp_con_state_CTS_SXP_CON_STATE_ON";
      }
      enum "state-delete-hold-down" {
        value 3;
        description
          "SXP Connection state is Delete-Hold-Down";
        tailf:code-name "ENUM_sxp_con_state_CTS_SXP_CON_STATE_DELETE_HOLD_DOWN";
      }
      enum "state-not-applicable" {
        value 4;
        description
          "SXP Connection state is Not-Applicable";
        tailf:code-name "ENUM_sxp_con_state_CTS_SXP_CON_STATE_NOT_APPLICABLE";
      }
    }
    description
      "SXP Connection state";
  }

  typedef sxp-con-mode {
    type enumeration {
      enum "con-mode-invalid" {
        value 0;
        description
          "SXP Connection mode is Invalid";
        tailf:code-name "ENUM_sxp_con_mode_CTS_SXP_CON_MODE_INVALID";
      }
      enum "con-mode-speaker" {
        value 1;
        description
          "SXP Connection mode is Speaker";
        tailf:code-name "ENUM_sxp_con_mode_CTS_SXP_CON_MODE_SPEAKER";
      }
      enum "con-mode-listener" {
        value 2;
        description
          "SXP Connection mode is Listener";
        tailf:code-name "ENUM_sxp_con_mode_CTS_SXP_CON_MODE_LISTENER";
      }
      enum "con-mode-both" {
        value 3;
        description
          "SXP Connection mode is Both (Speaker and Listener)";
        tailf:code-name "ENUM_sxp_con_mode_CTS_SXP_CON_MODE_BOTH";
      }
    }
    description
      "SXP Connection mode";
  }

  typedef cts-ndac-mode {
    type enumeration {
      enum "cts-ndac-mode-invalid" {
        value 0;
        description
          "CTS Interface Connection mode is Invalid";
        tailf:code-name "ENUM_cts_ndac_mode_CTS_NDAC_MODE_INVALID";
      }
      enum "cts-ndac-mode-manual" {
        value 1;
        description
          "CTS Interface Connection mode is MANUAL";
        tailf:code-name "ENUM_cts_ndac_mode_CTS_NDAC_MODE_MANUAL";
      }
    }
    description
      "CTS Interface Connection mode";
  }

  typedef cts-manual-ifc-state {
    type enumeration {
      enum "cts-manual-mode-init" {
        value 0;
        description
          "CTS IFC state is Init";
        tailf:code-name "ENUM_cts_manual_ifc_state_CTS_MANUAL_MODE_INIT";
      }
      enum "cts-manual-mode-authenticating" {
        value 1;
        description
          "CTS IFC state is in authentication. 
           This is bypassed in MANUAL mode.";
        tailf:code-name "ENUM_cts_manual_ifc_state_CTS_MANUAL_MODE_AUTHENTICATING";
      }
      enum "cts-manual-mode-authorizing" {
        value 2;
        description
          "CTS IFC state is in authorization.
           This is bypassed in MANUAL mode.";
        tailf:code-name "ENUM_cts_manual_ifc_state_CTS_MANUAL_MODE_AUTHORIZING";
      }
      enum "cts-manual-mode-sap-ne" {
        value 3;
        description
          "CTS IFC state is in SAP negotiation";
        tailf:code-name "ENUM_cts_manual_ifc_state_CTS_MANUAL_MODE_SAP_NE";
      }
      enum "cts-manual-mode-open" {
        value 4;
        description
          "CTS IFC state is in OPEN state";
        tailf:code-name "ENUM_cts_manual_ifc_state_CTS_MANUAL_MODE_OPEN";
      }
      enum "cts-manual-mode-held" {
        value 5;
        description
          "CTS IFC state is in HELD state";
        tailf:code-name "ENUM_cts_manual_ifc_state_CTS_MANUAL_MODE_HELD";
      }
      enum "cts-manual-mode-disconnecting" {
        value 6;
        description
          "CTS IFC state is in disconnecting state";
        tailf:code-name "ENUM_cts_manual_ifc_state_CTS_MANUAL_MODE_DISCONNECTING";
      }
      enum "cts-manual-mode-invalid" {
        value 7;
        description
          "CTS IFC state is invalid indicating 
           some error condition";
        tailf:code-name "ENUM_cts_manual_ifc_state_CTS_MANUAL_MODE_INVALID";
      }
      enum "cts-manual-mode-license-err" {
        value 8;
        description
          "CTS IFC state is in license error state
           indicating that current license level does
           not permit usage of CTS MANUAL";
        tailf:code-name "ENUM_cts_manual_ifc_state_CTS_MANUAL_MODE_LICENSE_ERR";
      }
      enum "cts-manual-mode-ignore" {
        value 9;
        description
          "Ignore CTS IFC state value as the
           interface is not configured with
           CTS MANUAL";
        tailf:code-name "ENUM_cts_manual_ifc_state_CTS_MANUAL_MODE_IGNORE";
      }
    }
    description
      "CTS Manual IFC State Machine status";
  }

  typedef cts-manual-trust-status {
    type enumeration {
      enum "cts-manual-trusted" {
        value 0;
        description
          "CTS MANUAL connection on the interface is trusted";
        tailf:code-name "ENUM_cts_manual_trust_status_CTS_MANUAL_TRUSTED";
      }
      enum "cts-manual-untrusted" {
        value 1;
        description
          "CTS Interface connection on the interface is untrusted";
        tailf:code-name "ENUM_cts_manual_trust_status_CTS_MANUAL_UNTRUSTED";
      }
      enum "cts-manual-trust-status-ignore" {
        value 2;
        description
          "Ignore the trust status as CTS MANUAL is not 
           configured on the interface";
        tailf:code-name "ENUM_cts_manual_trust_status_CTS_MANUAL_TRUST_STATUS_IGNORE";
      }
    }
    description
      "CTS Interface trust status";
  }

  typedef cts-manual-sgt-propagate-status {
    type enumeration {
      enum "cts-sgt-propagate-enabled" {
        value 0;
        description
          "Inline SGT propagation is enabled on the interface";
        tailf:code-name "ENUM_cts_manual_sgt_propagate_status_CTS_SGT_PROPAGATE_ENABLED";
      }
      enum "cts-sgt-propagate-disabled" {
        value 1;
        description
          "Inline SGT propagation is not enabled on the interface";
        tailf:code-name "ENUM_cts_manual_sgt_propagate_status_CTS_SGT_PROPAGATE_DISABLED";
      }
      enum "cts-sgt-propagate-ignore" {
        value 2;
        description
          "Ignore the SGT propagation status as CTS 
           MANUAL is not configured on the interface";
        tailf:code-name "ENUM_cts_manual_sgt_propagate_status_CTS_SGT_PROPAGATE_IGNORE";
      }
    }
    description
      "CTS Interface SGT propagation status";
  }

  typedef cts-sap-status {
    type enumeration {
      enum "cts-sap-unknown" {
        value 0;
        description
          "SAP negotiation is unknown indicating some error condition";
        tailf:code-name "ENUM_cts_sap_status_CTS_SAP_UNKNOWN";
      }
      enum "cts-sap-in-progress" {
        value 1;
        description
          "SAP negotiation is in progress";
        tailf:code-name "ENUM_cts_sap_status_CTS_SAP_IN_PROGRESS";
      }
      enum "cts-sap-success" {
        value 2;
        description
          "SAP negotiation is successful";
        tailf:code-name "ENUM_cts_sap_status_CTS_SAP_SUCCESS";
      }
      enum "cts-sap-failed" {
        value 3;
        description
          "SAP negotiation failed on the interface";
        tailf:code-name "ENUM_cts_sap_status_CTS_SAP_FAILED";
      }
      enum "cts-sap-license-err" {
        value 4;
        description
          "Current license level does not support SAP";
        tailf:code-name "ENUM_cts_sap_status_CTS_SAP_LICENSE_ERR";
      }
      enum "cts-sap-not-applicable" {
        value 5;
        description
          "SAP status is not applicable on this interface";
        tailf:code-name "ENUM_cts_sap_status_CTS_SAP_NOT_APPLICABLE";
      }
      enum "cts-sap-status-ignore" {
        value 6;
        description
          "SAP status is not applicable on this interface";
        tailf:code-name "ENUM_cts_sap_status_CTS_SAP_STATUS_IGNORE";
      }
    }
    description
      "CTS SAP negotiation status";
  }

  grouping cts-ip-sgt-map-key {
    description
      "IP-Address information to find corresponding CTS Security Group Tag binding";
    leaf ip {
      type inet:ip-prefix;
      description
        "IP-Prefix information to find its corresponding
         Secure Group Tag. Only IPv4 prefix information is
         supported currently to get the Security Group Tag
         binding in this device";
    }
    leaf vrf-name {
      type string;
      description
        "VRF-Name to find the Security Group Tag for the
         corresponding IP-Address in
         this VRF instance. Only default VRF is supported
         currently which is indicated by (empty string)";
    }
  }

  grouping cts-ip-sgt-map {
    description
      "Trustsec Security Group Tag binding information";
    leaf sgt {
      type int32;
      description
        "Security Group Tag value corresponding to the
         given IP-Address";
    }
    leaf source {
      type trustsec-ios-xe-oper:cts-odm-binding-source;
      description
        "Source information via which the Security
         Group Tag binding was learned in this device";
    }
  }

  grouping cts-role-based-policy-key {
    description
      "Source Security Group Tag and Destination Security
       Group Tag information to find the list of Security
       Group Access Control List that are currently
       applied between two security groups in the device";
    leaf src-sgt {
      type int32;
      description
        "Source Security Group Tag number.
         This value must be in the inclusive range of -1 to 65519";
    }
    leaf dst-sgt {
      type int32;
      description
        "Destination Security Tag number.
         This value must be in the inclusive range of -1 to 65519";
    }
  }

  grouping cts-role-based-policy {
    description
      "Trustsec Role based permissions between a Source
       Security Group and the Destination Security Group";
    leaf sgacl-name {
      type string;
      description
        "List of Security Group Access Control List names
         separated by semi-colon(;)";
    }
    leaf num-of-sgacl {
      type uint32;
      description
        "Number of Security Group Access Control Lists that
         are currently applied between
         the Source Security Group and the Destination
         Security Group. This should match
         the number of Security Group Access Control List
         names in sgacl-name";
    }
    leaf monitor-mode {
      type boolean;
      description
        "Indicates the monitor mode status between the Source
         Security Group and Destination
         Security Group is currently enabled or disabled.
         This will be TRUE if monitor
         mode is enabled and FALSE if it is disabled";
    }
    leaf policy-life-time {
      type uint64;
      description
        "Duration of the Role based permissions that are
         applied between a Source Security Group
         and a Destination Security Group. The duration
         is represented in seconds";
    }
    leaf last-updated-time {
      type yang:date-and-time;
      description
        "Indicates the time when the Role based permissions
         between a Source Security Group and a Destination
         Security Group was modified or updated last. The
         value will be represented as date and time 
         corresponding to the local time zone of the
         Identify Services Engine when the Role based 
         permissions was modified or updated last";
    }
    leaf total-deny-count {
      type uint64;
      description
        "Total number of packets that have been denied by
         the Role based permissions
         between a Source Security Group and a Destination
         Security Group. This corresponds to
         total packets denied in both hardware and software
         forwarding paths of the device";
    }
    leaf total-permit-count {
      type uint64;
      description
        "Total number of packets that have been permitted
         by the Role based permissions
         between a Source Security Group and a Destination
         Security Group. This corresponds to
         total packets allowed in both hardware and software
         forwarding paths of the device";
    }
    leaf software-deny-count {
      type uint64;
      description
        "Number of packets that have been denied in the 
         software forwarding path of the device
         by the Role based permissions between a Source
         Security Group and a Destination
         Security Group";
    }
    leaf software-permit-count {
      type uint64;
      description
        "Number of packets that have been permitted in the
         software forwarding path of the device
         by the Role based permissions between a Source
         Security Group and a Destination Security Group";
    }
    leaf hardware-deny-count {
      type uint64;
      description
        "Number of packets that have been denied in the
         hardware forwarding path of the device by
         the Role based permissions between a Source
         Security Group and a Destination Security Group";
    }
    leaf hardware-permit-count {
      type uint64;
      description
        "Number of packets that have been permitted in the
         hardware forwarding path of the device
         by the Role based permissions between a Source
         Security Group and a Destination Security Group.";
    }
    leaf software-monitor-count {
      type uint64;
      description
        "Number of packets that have been monitored in the
         software forwarding path of the device
         by the Role based permissions between a Source
         Security Group and a Destination Security Group";
    }
    leaf hardware-monitor-count {
      type uint64;
      description
        "Number of packets that have been monitored in the
         hardware forwarding path of the device
         by the Role based permissions between a Source
         Security Group and a Destination Security Group";
    }
  }

  grouping cts-sxp-con-key {
    description
      "The peer IP-Address of a CTS SXP connection and
       vrf-name of the VRF instance
       in this device to which this IP-Address is configured.
       This information is used
       to get additional details of the SXP connection";
    leaf peer-ip {
      type inet:ip-address;
      description
        "IP-Address information of the peer of an SXP
         connection in this device. Only IPv4
         address is currently supported.";
    }
    leaf vrf-name {
      type string;
      description
        "vrf-name string of the VRF instance in this device,
         to which the peer of an SXP connection
         belongs to. Only default VRF is supported currently
         which is indicated by empty string";
    }
  }

  grouping cts-sxp-con {
    description
      "SXP connection information";
    leaf source-ip {
      type inet:ip-address;
      description
        "Source IP-Address of the SXP connection in this
         device for the given peer IP-Address.";
    }
    leaf speaker-state {
      type trustsec-ios-xe-oper:sxp-con-state;
      description
        "SXP speaker state information of the SXP
         connection in this device. This information is
         valid only if the local mode of the SXP
         connection in this device is Speaker";
    }
    leaf speaker-duration {
      type uint64;
      description
        "Duration of the SXP speaker of the SXP connection
         in this device. This information is valid
         only if the local mode of the SXP connection is Speaker";
    }
    leaf listener-state {
      type trustsec-ios-xe-oper:sxp-con-state;
      description
        "SXP listener state information of the SXP 
         connection in this device. This information is
         valid only if the local mode of the SXP
         connection in the device is Listener";
    }
    leaf listener-duration {
      type uint64;
      description
        "Duration of the SXP listener of the SXP connection
         in this device. This information is valid
         Only if the local mode of the SXP connection is Listener";
    }
    leaf local-mode {
      type trustsec-ios-xe-oper:sxp-con-mode;
      description
        "SXP connection mode of this device for the SXP
         connection with the given peer";
    }
  }

  grouping cts-manual-record {
    description
      "CTS Manual connection information";
    leaf if-name {
      type string;
      description
        "Interface name";
    }
    leaf mode {
      type trustsec-ios-xe-oper:cts-ndac-mode;
      description
        "Indicates the configured mode of CTS on the interface.";
    }
    leaf ifc-state {
      type trustsec-ios-xe-oper:cts-manual-ifc-state;
      description
        "State of the IFC state machine that controls the
         interface when CTS manual is configured.";
    }
    leaf trusted {
      type trustsec-ios-xe-oper:cts-manual-trust-status;
      description
        "Indicates whether incoming inline SGT on this interface
         can be trusted and used for further classification.";
    }
    leaf sgt-propagate {
      type trustsec-ios-xe-oper:cts-manual-sgt-propagate-status;
      description
        "Status of SGT propagation on the interface. SGT is 
         inserted inline for further propagation only if this is enabled.";
    }
    leaf sap-status {
      type trustsec-ios-xe-oper:cts-sap-status;
      description
        "The status of SAP negotiation on the given interface";
    }
    leaf peer-sgt {
      type uint16;
      description
        "Statically configured peer SGT value that is used
         to classify the incoming traffic on the interface";
    }
  }

  container trustsec-state {
    config false;
    description
      "This is top level container for Cisco Trusted Security
       solution operational data.
       It can have Security Group Tag binding information for
       the given IP-Address, Role based permissions between a
       Source Security Group Tag and a Destination Security
       Group, SXP Connection information for a given peer
       IP-Address in this device";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    container cts-rolebased-sgtmaps {
      description
        "Security Group Tag value corresponding to an IP-Address 
         in the given VRF instance in this device";
      list cts-rolebased-sgtmap {
        key "ip vrf-name";
        description
          "Security Group Tag is assigned for an IP-Address
           based on the user permissions and authorization 
           level as configured by the network administrator
           in Identity Service Engine server or in the device locally";
        uses trustsec-ios-xe-oper:cts-ip-sgt-map-key;
        uses trustsec-ios-xe-oper:cts-ip-sgt-map;
      }
    }
    container cts-rolebased-policies {
      description
        "Role based permissions between a Source Security Group
         and a Destination Security Group are configured by the
         administrator in the Identity Services Engine or in the Device";
      list cts-rolebased-policy {
        key "src-sgt dst-sgt";
        description
          "Role based permissions between a Source Security Group
           and a Destination Security Group can be retrieved from
           the device using a Security Group Tag and Destination
           Group Tag value";
        uses trustsec-ios-xe-oper:cts-role-based-policy-key;
        uses trustsec-ios-xe-oper:cts-role-based-policy;
      }
    }
    list cts-rolebased-ipv6-policy {
      key "src-sgt dst-sgt";
      description
        "Role based permissions ifor ipv6 between a Source Security Group
         and a Destination Security Group can be retrieved from
         the device using a Security Group Tag and Destination
         Group Tag value";
      uses trustsec-ios-xe-oper:cts-role-based-policy-key;
      uses trustsec-ios-xe-oper:cts-role-based-policy;
    }
    container cts-sxp-connections {
      description
        "Trustsec SXP connection is used between Cisco devices
         to propagate Security Group Tags from one device to 
         another device. One of the device will be in Speaker 
         mode or Listener mode or both the devices can be in
         both the connection modes";
      list cts-sxp-connection {
        key "peer-ip vrf-name";
        description
          "Trustsec SXP connection information from a device
           can be retrieved with the SXP connection peer IP
           address. Only IPv4 address as Peer IP and default
           VRF instance in device is supported currently";
        uses trustsec-ios-xe-oper:cts-sxp-con-key;
        uses trustsec-ios-xe-oper:cts-sxp-con;
      }
    }
    list cts-manual-con {
      key "if-name";
      description
        "A TrustSec link between two devices can be configured 
         manually to propagate the Scalable Group Tag (SGT) inline.
         MACSec can also be enabled on the link using SAP and a static SGT
         assignment is also possible to classify the incoming traffic. The
         link can be either configured as trusted or untrusted. There is no
         authentication in this mode. The status of CTS manual connection 
         between two devices can be retrieved with the interface name.";
      uses trustsec-ios-xe-oper:cts-manual-record;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWfFlpNoABKPfgEAAEAYIED/v39q/79/aUAPGLzVBbaSCEpMmkaJHqANNqaD0nkjQ9I/VNAMAANAAGTQAABoBIUTU2pqnmJJ+qepoD0gAPUANDAADQABk0AAAaASJAQE0yRGQADRpoAD+km1McqL874tCBnCjxFeWZTOdjSsJ71tIxrW40QegX6dh2ot+KxwiMnjDF4ivEadWOBDCy2fYhCbqUQ66bdn4GbTv7hCH6WpEgkgiSCIQYoIiJXcjxiEdENG3PU8/BTNUKLzNR9GaDowwHHHRC6HBo1kchKFjBdHZ3tvW5FWF2sKSescmdTLXpW4EAyLutdZemq3c/qioJbuETWWgP0+hMLsxmkdwP1D74yZalDBoNOaQiYyujmNrmVMQCBEKnsk4Y/DefImuPc6XdORS3zqb8L3WI3oSNtJptmXHlfPOAcA1VgrvQqiMat5uM+TIaO+YY/NBT6O2wiqPBkGGW8YyZTt104GrKabG4xTo+dEKCSxAt1q6FKl0EmUkkrU7AqeOqpgJWVgbRr2gF9uGBBqIhRoE7m0lv2WyXjeHBqQGNkEgNi5YN3fsAarU8SyK45APQgSqNLgm4SGWSEVnxcRgrtFLGEt8ZOEhEihohXqJOdTVZkiinY8UWEad6O5E8DbkQgb6ySDWa6NSkBGDMRon3WKUcdULsM2DfJyQlCxgrsrksFRoWLUqiMh3QKhoM3h3ca6O82YcTMNlkNUntt4RggkvtJ+YixAfkG/0fI70wxZnQ56H6RLhQSXgT6RzZjOsocTEHLu4VElnag2nIamQBhajXWOzHx6JjeRENtJptnSZNVChJSKb/eLYO2xTD90KVOWd85cU22rsBmjdXCnNGeDd3GXJqGKf2oGDw73u5V8LVU6dw9/HlvjSVnrftmniGcoU1Ni5a6hz2RUCgllrAC/+xdkvBXOxHmEqLKwdoWOyRUq64iUlojkab9oBlr1s3YEsHcCCSlu+YWZw+qvbf/GyB8LyPJmpFBg7nQOEVDrcrWMgIV5nQWJqSp1FBJa4ANVJK5MVisZoZBZqFvLqojQ1DRBiGLRCzpkRPoFp5lHhnUSWCuVEoipobCkqKeRVa/D+MD+ofx1/xBCHBv/i7kinChIeLLSbQA==";
      }
      tailf:meta-data "uncompressed_size" {
        tailf:meta-value "2405";
      }
    }
  }

  container schema-metadata-Cisco-IOS-XE-trustsec-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-trustsec-oper";
    }
    tailf:meta-data "organization" {
      tailf:meta-value "Cisco Systems, Inc.";
    }
    tailf:meta-data "semver" {
      tailf:meta-value "2020-07-01";
    }
  }
}
