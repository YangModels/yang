module Cisco-IOS-XE-mdt-oper-v2 {
  yang-version 1;
  namespace "http://cisco.com/ns/yang/Cisco-IOS-XE-mdt-oper-v2";
  prefix mdt-oper-v2;

  import Cisco-IOS-XE-mdt-common-defs {
    prefix mdt-common-defs;
  }
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for operational data of streaming telemetry.
     Copyright (c) 2016-2020 by Cisco Systems, Inc.
     All rights reserved.";

  revision 2020-07-01 {
    description
      "Initial revision";
    reference "1.0.0";
    cisco-semver:module-version "1.0.0";
    cisco-semver-internal:os-version "17.3.1";
  }

  typedef mdt-sub-type {
    type enumeration {
      enum "sub-type-dynamic" {
        value 1;
        description
          "Dynamic subscriptions
           -do not survive reboot
           -existence tied to connection they are created on
           -send updates only to peer that creates them";
        tailf:code-name "ENUM_mdt_sub_type_SUB_TYPE_DYNAMIC";
      }
      enum "sub-type-static" {
        value 2;
        description
          "Static subscriptions
           -created, (modified), and deleted by management operations
           -survive reboot
           -receivers are configured ";
        tailf:code-name "ENUM_mdt_sub_type_SUB_TYPE_STATIC";
      }
      enum "sub-type-permanent" {
        value 3;
        description
          "Permanent subscriptions
           -created during system startup, can not be modified";
        tailf:code-name "ENUM_mdt_sub_type_SUB_TYPE_PERMANENT";
      }
    }
    description
      "Subscription types";
  }

  typedef mdt-sub-state {
    type enumeration {
      enum "sub-state-valid" {
        value 0;
        description
          "The subscription is valid and may be sending updates.";
        tailf:code-name "ENUM_mdt_sub_state_SUB_STATE_VALID";
      }
      enum "sub-state-suspended" {
        value 1;
        description
          "The subscription has been suspended and is not
           sending notifications even if there are updates.";
        tailf:code-name "ENUM_mdt_sub_state_SUB_STATE_SUSPENDED";
      }
      enum "sub-state-terminated" {
        value 2;
        description
          "The subscription is terminated. This state is valid
           only for static subscriptions.";
        tailf:code-name "ENUM_mdt_sub_state_SUB_STATE_TERMINATED";
      }
      enum "sub-state-invalid" {
        value 3;
        description
          "The subscription is invalid. This state is valid
           only for static subscriptions.";
        tailf:code-name "ENUM_mdt_sub_state_SUB_STATE_INVALID";
      }
    }
    description
      "Subscription states";
  }

  typedef mdt-receiver-state {
    type enumeration {
      enum "rcvr-state-invalid" {
        value 1;
        description
          "The receiver configuration is invalid and
           cannot be used.";
        tailf:code-name "ENUM_mdt_receiver_state_RCVR_STATE_INVALID";
      }
      enum "rcvr-state-disconnected" {
        value 2;
        description
          "The receiver is disconnected and there is no
           attempt being made to connect to it.";
        tailf:code-name "ENUM_mdt_receiver_state_RCVR_STATE_DISCONNECTED";
      }
      enum "rcvr-state-connecting" {
        value 3;
        description
          "An attempt is being made to connect to the receiver.";
        tailf:code-name "ENUM_mdt_receiver_state_RCVR_STATE_CONNECTING";
      }
      enum "rcvr-state-connected" {
        value 4;
        description
          "The receiver is connected, and update notifications
           are being sent to the receiver when they occur";
        tailf:code-name "ENUM_mdt_receiver_state_RCVR_STATE_CONNECTED";
      }
      enum "rcvr-state-disconnecting" {
        value 5;
        description
          "The receiver is in the process of being disconnected.";
        tailf:code-name "ENUM_mdt_receiver_state_RCVR_STATE_DISCONNECTING";
      }
    }
    description
      "Receiver states.";
  }

  typedef mdt-connection-type {
    type enumeration {
      enum "conn-type-protocol" {
        value 0;
        description
          "The connection type is protocol";
        tailf:code-name "ENUM_mdt_connection_type_CONN_TYPE_PROTOCOL";
      }
    }
    description
      "Connection Types";
  }

  typedef mdt-con-state {
    type enumeration {
      enum "con-state-active" {
        value 0;
        description
          "The connection is active and usable.";
        tailf:code-name "ENUM_mdt_con_state_CON_STATE_ACTIVE";
      }
      enum "con-state-connecting" {
        value 1;
        description
          "An attempt is being made to set the connection up.";
        tailf:code-name "ENUM_mdt_con_state_CON_STATE_CONNECTING";
      }
      enum "con-state-pending" {
        value 2;
        description
          "The connection is down, but between connection
           attempts. It is in this state, for example, during
           the idle time between retries. No longer used - use
           con-state-connecting instead.";
        tailf:code-name "ENUM_mdt_con_state_CON_STATE_PENDING";
      }
      enum "con-state-disconnecting" {
        value 3;
        description
          "The connection is the process of being disconnected.";
        tailf:code-name "ENUM_mdt_con_state_CON_STATE_DISCONNECTING";
      }
    }
    description
      "Connection states.";
  }

  grouping mdt-stream {
    description
      "MDT stream table element.";
    leaf-list stream {
      type string;
      ordered-by user;
      description
        "Name of a supported stream.";
    }
  }

  grouping mdt-subscription-oper {
    description
      "Subscription operational data.";
    leaf subscription-id {
      type uint32;
      description
        "Unique subscription identifier.";
    }
    container base {
      description
        "Common subscription information.";
      uses mdt-common-defs:mdt-subscription-base;
    }
    leaf type {
      type mdt-oper-v2:mdt-sub-type;
      description
        "Subscription type.";
    }
    leaf state {
      type mdt-oper-v2:mdt-sub-state;
      description
        "Subscription state.";
    }
    leaf state-explanation {
      type string;
      description
        "Comments related to subscription state.";
    }
    list mdt-receivers {
      key "address port";
      description
        "List of MDT receivers.";
      uses mdt-oper-v2:mdt-receiver-oper;
      uses mdt-common-defs:mdt-receiver-id;
    }
    leaf last-state-change-time {
      type yang:date-and-time;
      description
        "Time of last state change of this subscription.";
    }
  }

  grouping mdt-receiver-oper {
    description
      "MDT receiver operational information.";
    leaf protocol {
      type string;
      description
        "Receiver transport protocol.";
    }
    leaf state {
      type mdt-oper-v2:mdt-receiver-state;
      description
        "Receiver state.";
    }
    leaf state-explanation {
      type string;
      description
        "Comments related to receiver state.";
    }
    leaf profile {
      type string;
      description
        "Receiver's protocol profile name.";
    }
    leaf last-state-change-time {
      type yang:date-and-time;
      description
        "Time of last state change of this receiver.";
    }
    leaf con-index {
      type uint16;
      description
        "Receiver connection index";
    }
  }

  grouping mdt-connection-id {
    description
      "MDT connection type identifier";
    leaf type {
      type mdt-oper-v2:mdt-connection-type;
      config false;
      description
        "DO NOT USE!  -- hidden internal";
      tailf:hidden "full";
      tailf:meta-data "hidden" {
        tailf:meta-value "true";
      }
    }
    choice type-choice {
      description
        "Type of Connection Type Choice";
      case conn-type-protocol {
        leaf address {
          type inet:ip-address;
          description
            "address";
        }
        leaf port {
          type uint16;
          description
            "Connection port";
        }
        leaf vrf-table-id {
          type uint32;
          description
            "VRF table id";
        }
        leaf source-address {
          type inet:ip-address;
          description
            "source address";
        }
      }
    }
  }

  grouping mdt-connection {
    description
      "MDT receiver operational information.";
    leaf index {
      type uint16;
      description
        "Connection Tables Index";
    }
    container conn-id {
      description
        "Connection Type Index";
      uses mdt-oper-v2:mdt-connection-id;
    }
    leaf peer-id {
      type string;
      description
        "Peer ID";
    }
    leaf state {
      type mdt-oper-v2:mdt-con-state;
      description
        "Connection state.";
    }
    leaf last-state-change-time {
      type yang:date-and-time;
      description
        "Time of last state change of this connection.";
    }
  }

  container mdt-oper-v2-data {
    config false;
    description
      "MDT operational data.";
    tailf:callpoint "mdt-oper-db";
    tailf:meta-data "callpoint" {
      tailf:meta-value "mdt-oper-db";
    }
    tailf:meta-data "greenprefix" {
      tailf:meta-value "/services;serviceName=mdt_oper";
    }
    container mdt-streams {
      description
        "MDT streams table. The list of supported streams.";
      uses mdt-oper-v2:mdt-stream;
    }
    list mdt-subscriptions {
      key "subscription-id";
      description
        "MDT subscription operational data.";
      uses mdt-oper-v2:mdt-subscription-oper;
    }
    list mdt-connections {
      key "index";
      description
        "MDT subscription connection operational data.";
      uses mdt-oper-v2:mdt-connection;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWQu1kRcAAx7fgEQAEAYQED/n32q/599qQALOAGgART9UyBNMAmmT0RpgNBMI0IapmqNHogyMmIBjQCaaDGGhpoAaAA0AAMhoEiISYj0RpCn6oaep6hmSbyFHqepySbb1LgAEmxVxORJ2C5PaHklUQaUwAQtOrOciRUFye5cUffRXfvq/frEztUp8/QGHjAIgTcCghDY3CEOGoVPzw/1eIC+h+zI/QPQL/4cyFykgPdGcHgDPIqYKZZBNWxstDVKIYX5qlh2cJqaSqnwHG4IO44QIPDsvv+/j1nxQur7JL+Vj2fRtvejoL8ZolEmAx57nuWQ81a9T7eoQLA82YEsgUNKGMbTYx03IvUWat53OU5eiovVFalWZFewRRU47LNFDAl+1NixcVsaoiiUkVoURXGbyNLBhwojLXuXHBcEDy7kVIXDgzbuRCJDetMMRKuKSi1cxKTQ1meaJSVEWohVSTQ7EZVRsEm2iDzR9UUvi0vZDPszoNglxgEASOA1GW9hqQggcMGpabR9hYzySNnCoGzm/67eu6PQ9MkLDSL/hJa8PWQ9igm7lf7RtBRDlttFBYaIgwGMzUW3sxiFvNEKONDrvLJYsY2mxjzVRSasZ1OVirMbIgTInJGPAlF09XhlvLzw5rOq+EWsWZfngYUBh5IspubdqHdTGFxRjxQ6ZqX5QNtzauRcmBHKnzlmVKitnVEOiUjmtFlsjQmE8MyCQxGlFEb+XAz+ei0Qd+7UTKPINTV+CGg4yh1LEKmgboXf0jTltTkXA6BsW4XEsnokmikI70K3ISqQhajnoimFCoag8uNtzBZKEghSyMO+ViO6xRG/ZB4L4aS/5H1Ls+YRBDTX/i7kinChIBdrIi4A=";
      }
      tailf:meta-data "uncompressed_size" {
        tailf:meta-value "1640";
      }
    }
    container Cisco-IOS-XE-mdt-common-defs {
      description
        "Hidden internal container used for metadata";
      uses mdt-common-defs:__yangpp_metadata;
    }
  }

  container schema-metadata-Cisco-IOS-XE-mdt-oper-v2 {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-mdt-oper-v2";
    }
    tailf:meta-data "organization" {
      tailf:meta-value "Cisco Systems, Inc.";
    }
    tailf:meta-data "semver" {
      tailf:meta-value "2020-07-01";
    }
  }
}
