module Cisco-IOS-XE-install-events {
  yang-version 1;
  namespace "http://cisco.com/ns/yang/Cisco-IOS-XE-install-events";
  prefix install-ios-xe-events;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for install status notification for image install events.
     Copyright (c) 2019-2020 by Cisco Systems, Inc.
     All rights reserved.";

  revision 2020-07-01 {
    description
      "- Added enum values for installation sub-states
       - Remove unused empty container install-events";
    reference "0.0.0";
    cisco-semver:module-version "0.0.0";
    cisco-semver-internal:os-version "17.3.1";
  }
  revision 2020-03-01 {
    description
      "Initial revision";
    reference "1.0.0";
    cisco-semver:module-version "1.0.0";
    cisco-semver-internal:os-version "17.2.1";
  }

  typedef installation-status {
    type enumeration {
      enum "download-start" {
        value 0;
        description
          "Download Start";
        tailf:code-name "ENUM_installation_status_DOWNLOAD_START";
      }
      enum "download-complete" {
        value 1;
        description
          "Download Complete";
        tailf:code-name "ENUM_installation_status_DOWNLOAD_COMPLETE";
      }
      enum "verification-complete" {
        value 2;
        description
          "Verification Complete";
        tailf:code-name "ENUM_installation_status_VERIFICATION_COMPLETE";
      }
      enum "upgrade-apply-complete" {
        value 3;
        description
          "Upgrade Apply Complete";
        tailf:code-name "ENUM_installation_status_UPGRADE_APPLY_COMPLETE";
      }
      enum "sync-partition-start" {
        value 4;
        description
          "Sync Partition Start";
        tailf:code-name "ENUM_installation_status_SYNC_PARTITION_START";
      }
      enum "sync-partition-complete" {
        value 5;
        description
          "Sync Partition Start";
        tailf:code-name "ENUM_installation_status_SYNC_PARTITION_COMPLETE";
      }
      enum "install-complete" {
        value 6;
        description
          "Install Complete";
        tailf:code-name "ENUM_installation_status_INSTALL_COMPLETE";
      }
      enum "install-fail" {
        value 7;
        description
          "Install Fail";
        tailf:code-name "ENUM_installation_status_INSTALL_FAIL";
      }
      enum "reboot" {
        value 8;
        description
          "Reboot";
        tailf:code-name "ENUM_installation_status_REBOOT";
      }
      enum "install-start" {
        value 9;
        description
          "Install Start";
        tailf:code-name "ENUM_installation_status_INSTALL_START";
      }
      enum "uninstall-complete" {
        value 10;
        description
          "Uninstall Complete";
        tailf:code-name "ENUM_installation_status_UNINSTALL_COMPLETE";
      }
      enum "uninstall-fail" {
        value 11;
        description
          "Uninstall Fail";
        tailf:code-name "ENUM_installation_status_UNINSTALL_FAIL";
      }
      enum "reset-complete" {
        value 12;
        description
          "Reset Complete";
        tailf:code-name "ENUM_installation_status_RESET_COMPLETE";
      }
      enum "reset-fail" {
        value 13;
        description
          "Reset Fail";
        tailf:code-name "ENUM_installation_status_RESET_FAIL";
      }
      enum "config-commit-confirm-complete" {
        value 14;
        description
          "Confirmation for configuration commit complete";
        tailf:code-name "ENUM_installation_status_CONFIG_COMMIT_CONFIRM_COMPLETE";
      }
      enum "config-commit-confirm-fail" {
        value 15;
        description
          "Confirmation for configuration commit fail";
        tailf:code-name "ENUM_installation_status_CONFIG_COMMIT_CONFIRM_FAIL";
      }
      enum "rollback-complete" {
        value 16;
        description
          "Rollback Complete";
        tailf:code-name "ENUM_installation_status_ROLLBACK_COMPLETE";
      }
      enum "rollback-fail" {
        value 17;
        description
          "Rollback Fail";
        tailf:code-name "ENUM_installation_status_ROLLBACK_FAIL";
      }
      enum "download-fail" {
        value 18;
        description
          "Download Fail";
        tailf:code-name "ENUM_installation_status_DOWNLOAD_FAIL";
      }
      enum "download-success" {
        value 19;
        description
          "Download Success";
        tailf:code-name "ENUM_installation_status_DOWNLOAD_SUCCESS";
      }
    }
    description
      "Installation Status";
  }

  typedef install-sub-state {
    type enumeration {
      enum "none" {
        value 0;
        description
          "None or not applicable";
        tailf:code-name "ENUM_install_sub_state_INSTALL_NONE";
      }
      enum "install-adding-pkg" {
        value 1;
        description
          "Install add package in progress";
        tailf:code-name "ENUM_install_sub_state_INSTALL_ADDING_PKG";
      }
      enum "install-expanding-pkg" {
        value 2;
        description
          "Install expand package in progress";
        tailf:code-name "ENUM_install_sub_state_INSTALL_EXPANDING_PKG";
      }
      enum "install-expand-pkg-done" {
        value 3;
        description
          "Install completes successful expand package";
        tailf:code-name "ENUM_install_sub_state_INSTALL_EXPAND_PKG_DONE";
      }
      enum "install-activating-pkg" {
        value 4;
        description
          "Activating package in progress";
        tailf:code-name "ENUM_install_sub_state_INSTALL_ACTIVATING_PKG";
      }
      enum "install-activate-dev-boot" {
        value 5;
        description
          "Activate or deactivate complete and starting device boot";
        tailf:code-name "ENUM_install_sub_state_INSTALL_ACTIVATE_DEV_BOOT";
      }
      enum "install-error-msg" {
        value 6;
        description
          "Action failed error";
        tailf:code-name "ENUM_install_sub_state_INSTALL_ERROR_MSG";
      }
      enum "install-oper-invoked" {
        value 7;
        description
          "Operation is invoked in install infra for the action";
        tailf:code-name "ENUM_install_sub_state_INSTALL_OPER_INVOKED";
      }
      enum "install-inprogress" {
        value 8;
        description
          "Operation is in progress";
        tailf:code-name "ENUM_install_sub_state_INSTALL_INPROGRESS";
      }
      enum "install-ewc-predwnld-none" {
        value 9;
        description
          "Predownload for Embedded Wireless Controller not started";
        tailf:code-name "ENUM_install_sub_state_INSTALL_EWC_PRE_DWNLD_NONE";
      }
      enum "install-ewc-ctrl-img-dwnld-initiated" {
        value 10;
        description
          "Embedded Wireless Controller - Controller image download initiated";
        tailf:code-name "ENUM_install_sub_state_INSTALL_EWC_CONTROLLER_DWNLD_INITIATED";
      }
      enum "install-ewc-ctrl-img-dwnld-in-progress" {
        value 11;
        description
          "Embedded Wireless Controller - Controller image download in progress";
        tailf:code-name "ENUM_install_sub_state_INSTALL_EWC_CONTROLLER_DWNLD_IN_PROGRESS";
      }
      enum "install-ewc-ctrl-img-dwnld-completed" {
        value 12;
        description
          "Embedded Wireless Controller - Controller image download completed";
        tailf:code-name "ENUM_install_sub_state_INSTALL_EWC_CONTROLLER_DWNLD_COMPLETE";
      }
      enum "install-ewc-ctrl-img-dwnld-failed" {
        value 13;
        description
          "Embedded Wireless Controller - Controller image download failed";
        tailf:code-name "ENUM_install_sub_state_INSTALL_EWC_CONTROLLER_DWNLD_FAILED";
      }
      enum "install-ewc-ap-img-predwnld-initiated" {
        value 14;
        description
          "Embedded Wireless Controller - AP image predownload initiated";
        tailf:code-name "ENUM_install_sub_state_INSTALL_EWC_AP_PRE_DWNLD_INITIATED";
      }
      enum "install-ewc-ap-img-predwnld-in-progress" {
        value 15;
        description
          "Embedded Wireless Controller - AP image predownload in progress";
        tailf:code-name "ENUM_install_sub_state_INSTALL_EWC_AP_PRE_DWNLD_IN_PROGRESS";
      }
      enum "install-ewc-ap-img-predwnld-completed" {
        value 16;
        description
          "Embedded Wireless Controller - AP image predownload completed";
        tailf:code-name "ENUM_install_sub_state_INSTALL_EWC_AP_PRE_DWNLD_COMPLETE";
      }
      enum "install-ewc-ap-img-predwnld-not-supported" {
        value 17;
        description
          "Embedded Wireless Controller - AP image predownload not supported";
        tailf:code-name "ENUM_install_sub_state_INSTALL_EWC_AP_PRE_DWNLD_UNSUPPORTED";
      }
      enum "install-ewc-ap-img-predwnld-failed" {
        value 18;
        description
          "Embedded Wireless Controller - AP image predownload failed";
        tailf:code-name "ENUM_install_sub_state_INSTALL_EWC_AP_PRE_DWNLD_FAILED";
      }
      enum "install-ewc-ctrl-img-predwnld-in-progress" {
        value 19;
        description
          "Embedded Wireless Controller - Controller image predownload in progress";
        tailf:code-name "ENUM_install_sub_state_INSTALL_EWC_CONTROLLER_PRE_DWNLD_IN_PROGRESS";
      }
      enum "install-ewc-ctrl-img-predwnld-completed" {
        value 20;
        description
          "Embedded Wireless Controller - Controller image predownload completed";
        tailf:code-name "ENUM_install_sub_state_INSTALL_EWC_CONTROLLER_PRE_DWNLD_COMPLETE";
      }
      enum "install-ewc-ctrl-img-predwnld-failed" {
        value 21;
        description
          "Embedded Wireless Controller - Controller image predownload failed";
        tailf:code-name "ENUM_install_sub_state_INSTALL_EWC_CONTROLLER_PRE_DWNLD_FAILED";
      }
      enum "install-ewc-activated" {
        value 22;
        description
          "Embedded Wireless Controller - install activate successful";
        tailf:code-name "ENUM_install_sub_state_INSTALL_EWC_ACTIVATED";
      }
      enum "install-ewc-activate-failed" {
        value 23;
        description
          "Embedded Wireless Controller - install activate failed";
        tailf:code-name "ENUM_install_sub_state_INSTALL_EWC_ACTIVATION_FAILED";
      }
      enum "install-status-bundle-boot-error" {
        value 24;
        description
          "Install is not allowed in bundle boot use one shot install";
        tailf:code-name "ENUM_install_sub_state_INSTALL_STATUS_BUNDLE_BOOT_ERROR";
      }
      enum "install-status-invalid-image-file" {
        value 25;
        description
          "RPC action failed because either image file specified is not present or invalid";
        tailf:code-name "ENUM_install_sub_state_INSTALL_STATUS_INVALID_IMAGE_FILE_ERROR";
      }
      enum "install-earlier-added-image-present" {
        value 26;
        description
          "Install action detected image already installed on device with same version waiting for
           activation. Either remove this earlier installed image to install new image or use
           activate RPC action to proceed image activation";
        tailf:code-name "ENUM_install_sub_state_INSTALL_STATUS_EARLIER_ADDED_IMAGE_PRESENT";
      }
      enum "install-activate-trigg-without-add" {
        value 27;
        description
          "Activate image is triggered before image is installed on device.
           Use install RPC to install image and trigger activate on device";
        tailf:code-name "ENUM_install_sub_state_INSTALL_ACTIVATE_TRIGGERED_WITHOUT_ADD";
      }
      enum "install-status-no-trans-to-commit" {
        value 28;
        description
          "Commit action could not find any activate transaction to commit. Either activate
           installed image first or remove installed image to start fresh Workflow";
        tailf:code-name "ENUM_install_sub_state_INSTALL_STATUS_NO_TRANSACTION_TO_COMMIT";
      }
      enum "install-status-activate-pend-commit" {
        value 29;
        description
          "Rollback to base is not allowed while image is pending commit. Either use abort action to abort
           activated image transaction or use install rollback action to commit to go back to previous image";
        tailf:code-name "ENUM_install_sub_state_INSTALL_STATUS_ACTIVATE_PENDING_COMMIT";
      }
      enum "install-status-nothing-to-rollback" {
        value 30;
        description
          "No Rollback points present from the current image to rollback";
        tailf:code-name "ENUM_install_sub_state_INSTALL_STATUS_NOTHING_TO_ROLLBACK";
      }
      enum "install-status-already-at-base" {
        value 31;
        description
          "Rollback to base is not required as device is already at the base image";
        tailf:code-name "ENUM_install_sub_state_INSTALL_STATUS_ALREADY_AT_BASE";
      }
      enum "install-remove-rejected-by-platform" {
        value 32;
        description
          "Remove of the file is not allowed currently. The file is likely in use at this moment. Retry again";
        tailf:code-name "ENUM_install_sub_state_INSTALL_STATUS_REMOVE_REJECTED_BY_PLATFORM";
      }
      enum "install-status-no-trans-to-abort" {
        value 33;
        description
          "There is no activate or deactivate operation detected on device that needs to be aborted.";
        tailf:code-name "ENUM_install_sub_state_INSTALL_STATUS_NO_TRANSACTION_TO_ABORT";
      }
      enum "install-status-no-platform-response" {
        value 34;
        description
          "Action failed due to no response from other platform or access device.
           Please check device operation status";
        tailf:code-name "ENUM_install_sub_state_INSTALL_STATUS_NO_PLATFORM_RESPONSE";
      }
      enum "install-rem-of-activated-img-reject" {
        value 35;
        description
          "Install remove can not remove activated image. Please use install commit
           to commit activated image.";
        tailf:code-name "ENUM_install_sub_state_INSTALL_REMOVE_OF_ACTIVATED_IMAGE_REJECTED";
      }
    }
    description
      "Install sub state provides the intermediate sub state status during
       install and activate operations. This helps to see the progress during 
       long waiting install action operation.";
  }

  typedef install-action {
    type enumeration {
      enum "install" {
        value 0;
        description
          "Install action type";
        tailf:code-name "ENUM_install_action_INSTALL_INSTALL";
      }
      enum "activate" {
        value 1;
        description
          "Activate action type";
        tailf:code-name "ENUM_install_action_INSTALL_ACTIVATE";
      }
      enum "install-commit" {
        value 2;
        description
          "Commit action type";
        tailf:code-name "ENUM_install_action_INSTALL_COMMIT";
      }
      enum "rollback" {
        value 3;
        description
          "Rollback action type";
        tailf:code-name "ENUM_install_action_INSTALL_ROLLBACK";
      }
      enum "deactivate" {
        value 4;
        description
          "Deactivate action type";
        tailf:code-name "ENUM_install_action_INSTALL_DEACTIAVTE";
      }
      enum "remove" {
        value 5;
        description
          "Remove action type";
        tailf:code-name "ENUM_install_action_INSTALL_REMOVE";
      }
      enum "auto-abort-timer" {
        value 6;
        description
          "Auto abort timer action type";
        tailf:code-name "ENUM_install_action_INSTALL_AUTO_ABORT_TIMER";
      }
      enum "abort" {
        value 7;
        description
          "Abort action type";
        tailf:code-name "ENUM_install_action_INSTALL_ABORT";
      }
    }
    description
      "Install action type";
  }

  grouping common-notification-header {
    description
      "Install notification header";
    leaf host-name {
      type string;
      description
        "Host name";
    }
  }

  grouping install-notification-fields {
    description
      "Install operation state";
    leaf status {
      type install-ios-xe-events:installation-status;
      description
        "Installation status";
    }
    leaf action-type {
      type install-ios-xe-events:install-action;
      description
        "Action type";
    }
    leaf sub-state {
      type install-ios-xe-events:install-sub-state;
      description
        "Intermediate sub state of install status";
    }
    leaf uuid {
      type string;
      description
        "Universally unique identifier 128-bit number UUID is received from action rpc";
    }
    leaf percentage-completed {
      type int8;
      units "percent";
      description
        "Percent of completion for in-progress installations.
         If the value is -1, the field is not applicable";
    }
  }

  notification install-status {
    description
      "install status notification";
    uses install-ios-xe-events:common-notification-header;
    uses install-ios-xe-events:install-notification-fields;
  }
  container Cisco-IOS-XE-install-events {
    config false;
    tailf:callpoint "ios-eventq-db";
    tailf:meta-data "callpoint" {
      tailf:meta-value "ios-eventq-db";
    }
    tailf:meta-data "greenprefix" {
      tailf:meta-value "/services;serviceName=iosevent";
    }
    tailf:meta-data "name" {
      tailf:meta-value "Cisco-IOS-XE-install-events";
    }
    tailf:hidden "full";
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWUhrM5AABvEfgBAGABA//9/gv//f6lAE+K8UAS2aIGswyJlNM0pDaepDaQAAANNBgNAaAADTQaAaANAkJBGUSTM0kaYQAGT0h6QYDQGgAA00GgGgDQJEgahMRpNT0SBo0eU2KDQH3/s35eTp/l+h5VYqyLsGx1TxTlnf+WTMlOHxcw244/h6ve/Yx18JO3rJdyindkccchV6se3BjI4e2RmakdOM/P0/Ts2JJP1gAd3ikkvnhQafSir6rfkV3Ipvw3SfOaV2jOTY7fuUK5cWJihGbNIOcSuZiybIH+NttkFPHr6Bqw+b7ONq+u1ErO2yiME3ml2BGxmTcmOBAHwXyDfwKJH2U9A+5fMR6/eIFj6EkCmqqZ3PQYfIfm7iJLWCCX5plfWahVAcxoLlEj2EvYdvSwi6xTmKZVwaFa70m1qiCxYlbAsd4+tC99Omj9zO7Y2/pBd2F107evLRc9Aw1IdWEAsjTCAdNLIIzzrBEXEZ7kMod9jRzwp2uE0LwEo78jUgyEPkrbNnvQOyDJghsQQiwvfB1XfBYoMDudjpwEHB0YUICUKgQlQFvTn0cpDQCwDvhAK1w0RhGaYLey/Yrl5O6UooM3QEiixaBArXolQaaazC+Qd2kboDbdwG7SyF8VODgoXdLaEvtwtA6qzZ8TksdIFgFy8n1tZCmiOsnloeHjaUZ0IuFEFbzPMdgwSXS6KVeRtscCbWqI5FXVbMUEC5Enydwjk46XqN1NJJLXPZpELPsMWMqt2pjouMC2mjSWBFPjJxONeHQ067hGU6ZgRdlK5gE9UKweNTMr15YjA9/hGGU23k1XI5WwyfCz64QXZkOOzJoVhYloomhAiBERDbEuIN7ltzVlhoozxSbqgtNE0r76W8eW2PM0rHJrrxWnhiJ1o6XOLn69vV7/wVeJ5BPupK4NfrTzPYR6e3okIxqSQjDmysaVwl9R6j9cAbb3DPze3EzzEvQPfnvAfHKA2M5LIIl8qQtW2m1qxErWFnGXYlBiMbGxsv1Rdd2uXYXNQ+Td5bv0/MtltpsfzmHdI72vDeu3ptWehkOGEnIFpYQd2Iz5kMyNiXYeoWTQPn0Lb5hkHfU2geBQw1LMAex/lF2S1ZDEENC8aF1J8+aPKSyR4nYOfQOFw00JcJNC4xvcqGaFjhhUFiWkIyC4RWqydzJiWqJRYYLmyqd/qWyPjZK4QM5oCQ6spcvCQjDbOfRbtj6BOoeLC6AwscOgceSnB2KKupmOO4qBxA7xBndQcADTNJu5BrqxQJsuL66kDFQ4giwYuBnPgOshMs6lTF22xmqMtQNTd5ldzFEhG0LZs3x4VMSWmtc3Lx36CQqLtsTQ3Uj4nDMZWqjeTCC3LG1Es4ApqgroAEOLTsQGEpspJrkQXAkF0xA3fyIK/4u5IpwoSCQ1mcgA==";
      }
      tailf:meta-data "uncompressed_size" {
        tailf:meta-value "3559";
      }
    }
  }

  container schema-metadata-Cisco-IOS-XE-install-events {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-install-events";
    }
    tailf:meta-data "organization" {
      tailf:meta-value "Cisco Systems, Inc.";
    }
    tailf:meta-data "semver" {
      tailf:meta-value "2020-07-01";
    }
  }
}
