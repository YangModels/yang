/*
 * Generated by confdc --mib2yang-std
 * Source: mgmt/dmi/model/mib/src/OLD-CISCO-INTERFACES-MIB.mib
 */
/*
 * This YANG module has been generated by smidump 0.5.0:
 *
 *      smidump -f yang OLD-CISCO-INTERFACES-MIB
 *
 * Do not edit. Edit the source file instead!
 */

module OLD-CISCO-INTERFACES-MIB {

  namespace "urn:ietf:params:xml:ns:yang:smiv2:OLD-CISCO-INTERFACES-MIB";
  prefix OLD-CISCO-INTERFACES-MIB;

  import RFC1213-MIB {
    prefix "rfc1213-mib";
  }

  import ietf-yang-smiv2 {
    prefix "smiv2";
  }

  import ietf-yang-types {
    prefix "yang";
  }


  container OLD-CISCO-INTERFACES-MIB {
    config false;

    container lifTable {
      status obsolete;
      description
       "A list of interface entries.";
      smiv2:oid "1.3.6.1.4.1.9.2.2.1";

      list lifEntry {
        key "ifIndex";
        status obsolete;
        description
         "A collection of additional objects in the
          cisco interface.";
        smiv2:oid "1.3.6.1.4.1.9.2.2.1.1";

        leaf ifIndex {
          type leafref {
            path "/rfc1213-mib:RFC1213-MIB/rfc1213-mib:ifTable/rfc1213-mib:ifEntry/rfc1213-mib:ifIndex";
          }
        }

        leaf locIfHardType {
          type rfc1213-mib:DisplayString;
          status obsolete;
          description
           "Returns the type of interface.";
          smiv2:max-access "read-only";
          smiv2:oid "1.3.6.1.4.1.9.2.2.1.1.1";
        }

        leaf locIfLineProt {
          type int32;
          status obsolete;
          description
           "Boolean whether interface line protocol is
            up or not.";
          smiv2:max-access "read-only";
          smiv2:oid "1.3.6.1.4.1.9.2.2.1.1.2";
        }

        leaf locIfLastIn {
          type int32;
          status obsolete;
          description
           "Elapsed time in milliseconds since last line
            protocol input packet was received.";
          smiv2:max-access "read-only";
          smiv2:oid "1.3.6.1.4.1.9.2.2.1.1.3";
        }

        leaf locIfLastOut {
          type int32;
          status obsolete;
          description
           "Elapsed time in milliseconds since last line
            protocol output packet was transmitted.";
          smiv2:max-access "read-only";
          smiv2:oid "1.3.6.1.4.1.9.2.2.1.1.4";
        }

        leaf locIfLastOutHang {
          type int32;
          status obsolete;
          description
           "Elapsed time in milliseconds since last line
            protocol output packet could not be
            successfully transmitted.";
          smiv2:max-access "read-only";
          smiv2:oid "1.3.6.1.4.1.9.2.2.1.1.5";
        }

        leaf locIfInBitsSec {
          type int32;
          status obsolete;
          description
           "Five minute exponentially-decayed moving
            average of input bits per second.";
          smiv2:max-access "read-only";
          smiv2:oid "1.3.6.1.4.1.9.2.2.1.1.6";
        }

        leaf locIfInPktsSec {
          type int32;
          status obsolete;
          description
           "Five minute exponentially-decayed moving
            average of input packets per second.";
          smiv2:max-access "read-only";
          smiv2:oid "1.3.6.1.4.1.9.2.2.1.1.7";
        }

        leaf locIfOutBitsSec {
          type int32;
          status obsolete;
          description
           "Five minute exponentially-decayed moving
            average of output bits per second.";
          smiv2:max-access "read-only";
          smiv2:oid "1.3.6.1.4.1.9.2.2.1.1.8";
        }

        leaf locIfOutPktsSec {
          type int32;
          status obsolete;
          description
           "Five minute exponentially-decayed moving
            average of output packets per second.";
          smiv2:max-access "read-only";
          smiv2:oid "1.3.6.1.4.1.9.2.2.1.1.9";
        }

        leaf locIfInRunts {
          type int32;
          status obsolete;
          description
           "Number of packets input which were smaller
            then the allowable physical media permitted.";
          smiv2:max-access "read-only";
          smiv2:oid "1.3.6.1.4.1.9.2.2.1.1.10";
        }

        leaf locIfInGiants {
          type int32;
          status obsolete;
          description
           "Number of input packets which were larger
            then the physical media permitted.";
          smiv2:max-access "read-only";
          smiv2:oid "1.3.6.1.4.1.9.2.2.1.1.11";
        }

        leaf locIfInCRC {
          type int32;
          status obsolete;
          description
           "Number of input packets which had cyclic
            redundancy checksum errors.";
          smiv2:max-access "read-only";
          smiv2:oid "1.3.6.1.4.1.9.2.2.1.1.12";
        }

        leaf locIfInFrame {
          type int32;
          status obsolete;
          description
           "Number of input packet which were
            misaligned.";
          smiv2:max-access "read-only";
          smiv2:oid "1.3.6.1.4.1.9.2.2.1.1.13";
        }

        leaf locIfInOverrun {
          type int32;
          status obsolete;
          description
           "Count of input which arrived too quickly for
            the to hardware receive.";
          smiv2:max-access "read-only";
          smiv2:oid "1.3.6.1.4.1.9.2.2.1.1.14";
        }

        leaf locIfInIgnored {
          type int32;
          status obsolete;
          description
           "Number of input packets which were simply
            ignored by this interface.";
          smiv2:max-access "read-only";
          smiv2:oid "1.3.6.1.4.1.9.2.2.1.1.15";
        }

        leaf locIfInAbort {
          type int32;
          status obsolete;
          description
           "Number of input packets which were aborted.";
          smiv2:max-access "read-only";
          smiv2:oid "1.3.6.1.4.1.9.2.2.1.1.16";
        }

        leaf locIfResets {
          type int32;
          status obsolete;
          description
           "Number of times the interface internally
            reset.";
          smiv2:max-access "read-only";
          smiv2:oid "1.3.6.1.4.1.9.2.2.1.1.17";
        }

        leaf locIfRestarts {
          type int32;
          status obsolete;
          description
           "Number of times interface needed to be
            completely restarted.";
          smiv2:max-access "read-only";
          smiv2:oid "1.3.6.1.4.1.9.2.2.1.1.18";
        }

        leaf locIfKeep {
          type int32;
          status obsolete;
          description
           "Boolean whether keepalives are enabled on
            this interface.";
          smiv2:max-access "read-only";
          smiv2:oid "1.3.6.1.4.1.9.2.2.1.1.19";
        }

        leaf locIfReason {
          type rfc1213-mib:DisplayString;
          status obsolete;
          description
           "Reason for interface last status change.";
          smiv2:max-access "read-only";
          smiv2:oid "1.3.6.1.4.1.9.2.2.1.1.20";
        }

        leaf locIfCarTrans {
          type int32;
          status obsolete;
          description
           "Number of times interface saw the carrier
            signal transition.";
          smiv2:max-access "read-only";
          smiv2:oid "1.3.6.1.4.1.9.2.2.1.1.21";
        }

        leaf locIfReliab {
          type int32;
          status obsolete;
          description
           "The reliability of the interface. Used by
            IGRP.";
          smiv2:max-access "read-only";
          smiv2:oid "1.3.6.1.4.1.9.2.2.1.1.22";
        }

        leaf locIfDelay {
          type int32;
          status obsolete;
          description
           "The amount of delay in microseconds of the
            interface. Used by IGRP.";
          smiv2:max-access "read-only";
          smiv2:oid "1.3.6.1.4.1.9.2.2.1.1.23";
        }

        leaf locIfLoad {
          type int32;
          status obsolete;
          description
           "The loading factor of the interface. Used by
            IGRP.";
          smiv2:max-access "read-only";
          smiv2:oid "1.3.6.1.4.1.9.2.2.1.1.24";
        }

        leaf locIfCollisions {
          type int32;
          status obsolete;
          description
           "The number of output collisions detected on
            this interface.";
          smiv2:max-access "read-only";
          smiv2:oid "1.3.6.1.4.1.9.2.2.1.1.25";
        }

        leaf locIfInputQueueDrops {
          type int32;
          status obsolete;
          description
           "The number of packets dropped because the
            input queue was full.";
          smiv2:max-access "read-only";
          smiv2:oid "1.3.6.1.4.1.9.2.2.1.1.26";
        }

        leaf locIfOutputQueueDrops {
          type int32;
          status obsolete;
          description
           "The number of packets dropped because the
            output queue was full.";
          smiv2:max-access "read-only";
          smiv2:oid "1.3.6.1.4.1.9.2.2.1.1.27";
        }

        leaf locIfDescr {
          type rfc1213-mib:DisplayString;
          status obsolete;
          description
           "User configurable interface description.";
          smiv2:max-access "read-write";
          smiv2:oid "1.3.6.1.4.1.9.2.2.1.1.28";
        }

        leaf locIfSlowInPkts {
          type yang:counter32;
          status obsolete;
          description
           "Packet count for Inbound traffic routed with
            slow switching";
          smiv2:max-access "read-only";
          smiv2:oid "1.3.6.1.4.1.9.2.2.1.1.30";
        }

        leaf locIfSlowOutPkts {
          type yang:counter32;
          status obsolete;
          description
           "Packet count for Outbound traffic routed
            with slow switching";
          smiv2:max-access "read-only";
          smiv2:oid "1.3.6.1.4.1.9.2.2.1.1.31";
        }

        leaf locIfSlowInOctets {
          type yang:counter32;
          status obsolete;
          description
           "Octet count for Inbound traffic routed with
            slow switching";
          smiv2:max-access "read-only";
          smiv2:oid "1.3.6.1.4.1.9.2.2.1.1.32";
        }

        leaf locIfSlowOutOctets {
          type yang:counter32;
          status obsolete;
          description
           "Octet count for Outbound traffic routed with
            slow switching";
          smiv2:max-access "read-only";
          smiv2:oid "1.3.6.1.4.1.9.2.2.1.1.33";
        }

        leaf locIfFastInPkts {
          type yang:counter32;
          status obsolete;
          description
           "Packet count for Inbound traffic routed with
            fast switching";
          smiv2:max-access "read-only";
          smiv2:oid "1.3.6.1.4.1.9.2.2.1.1.34";
        }

        leaf locIfFastOutPkts {
          type yang:counter32;
          status obsolete;
          description
           "Packet count for Outbound traffic routed
            with fast switching";
          smiv2:max-access "read-only";
          smiv2:oid "1.3.6.1.4.1.9.2.2.1.1.35";
        }

        leaf locIfFastInOctets {
          type yang:counter32;
          status obsolete;
          description
           "Octet count for Inbound traffic routed with
            fast switching";
          smiv2:max-access "read-only";
          smiv2:oid "1.3.6.1.4.1.9.2.2.1.1.36";
        }

        leaf locIfFastOutOctets {
          type yang:counter32;
          status obsolete;
          description
           "Octet count for Outbound traffic routed with
            fast switching";
          smiv2:max-access "read-only";
          smiv2:oid "1.3.6.1.4.1.9.2.2.1.1.37";
        }

        leaf locIfotherInPkts {
          type yang:counter32;
          status obsolete;
          description
           "Other protocol input packet count";
          smiv2:max-access "read-only";
          smiv2:oid "1.3.6.1.4.1.9.2.2.1.1.38";
        }

        leaf locIfotherOutPkts {
          type yang:counter32;
          status obsolete;
          description
           "Other protocol output packet count";
          smiv2:max-access "read-only";
          smiv2:oid "1.3.6.1.4.1.9.2.2.1.1.39";
        }

        leaf locIfotherInOctets {
          type yang:counter32;
          status obsolete;
          description
           "Other protocol input octet count";
          smiv2:max-access "read-only";
          smiv2:oid "1.3.6.1.4.1.9.2.2.1.1.40";
        }

        leaf locIfotherOutOctets {
          type yang:counter32;
          status obsolete;
          description
           "Other protocol output octet count";
          smiv2:max-access "read-only";
          smiv2:oid "1.3.6.1.4.1.9.2.2.1.1.41";
        }

        leaf locIfipInPkts {
          type yang:counter32;
          status obsolete;
          description
           "ip protocol input packet count";
          smiv2:max-access "read-only";
          smiv2:oid "1.3.6.1.4.1.9.2.2.1.1.42";
        }

        leaf locIfipOutPkts {
          type yang:counter32;
          status obsolete;
          description
           "ip protocol output packet count";
          smiv2:max-access "read-only";
          smiv2:oid "1.3.6.1.4.1.9.2.2.1.1.43";
        }

        leaf locIfipInOctets {
          type yang:counter32;
          status obsolete;
          description
           "ip protocol input octet count";
          smiv2:max-access "read-only";
          smiv2:oid "1.3.6.1.4.1.9.2.2.1.1.44";
        }

        leaf locIfipOutOctets {
          type yang:counter32;
          status obsolete;
          description
           "ip protocol output octet count";
          smiv2:max-access "read-only";
          smiv2:oid "1.3.6.1.4.1.9.2.2.1.1.45";
        }

        leaf locIfdecnetInPkts {
          type yang:counter32;
          status obsolete;
          description
           "Decnet protocol input packet count";
          smiv2:max-access "read-only";
          smiv2:oid "1.3.6.1.4.1.9.2.2.1.1.46";
        }

        leaf locIfdecnetOutPkts {
          type yang:counter32;
          status obsolete;
          description
           "Decnet protocol output packet count";
          smiv2:max-access "read-only";
          smiv2:oid "1.3.6.1.4.1.9.2.2.1.1.47";
        }

        leaf locIfdecnetInOctets {
          type yang:counter32;
          status obsolete;
          description
           "Decnet protocol input byte count";
          smiv2:max-access "read-only";
          smiv2:oid "1.3.6.1.4.1.9.2.2.1.1.48";
        }

        leaf locIfdecnetOutOctets {
          type yang:counter32;
          status obsolete;
          description
           "Decnet protocol output byte count";
          smiv2:max-access "read-only";
          smiv2:oid "1.3.6.1.4.1.9.2.2.1.1.49";
        }

        leaf locIfxnsInPkts {
          type yang:counter32;
          status obsolete;
          description
           "XNS protocol input packet count";
          smiv2:max-access "read-only";
          smiv2:oid "1.3.6.1.4.1.9.2.2.1.1.50";
        }

        leaf locIfxnsOutPkts {
          type yang:counter32;
          status obsolete;
          description
           "XNS protocol output packet count";
          smiv2:max-access "read-only";
          smiv2:oid "1.3.6.1.4.1.9.2.2.1.1.51";
        }

        leaf locIfxnsInOctets {
          type yang:counter32;
          status obsolete;
          description
           "XNS protocol input byte count";
          smiv2:max-access "read-only";
          smiv2:oid "1.3.6.1.4.1.9.2.2.1.1.52";
        }

        leaf locIfxnsOutOctets {
          type yang:counter32;
          status obsolete;
          description
           "XNS protocol output byte count";
          smiv2:max-access "read-only";
          smiv2:oid "1.3.6.1.4.1.9.2.2.1.1.53";
        }

        leaf locIfclnsInPkts {
          type yang:counter32;
          status obsolete;
          description
           "CLNS protocol input packet count";
          smiv2:max-access "read-only";
          smiv2:oid "1.3.6.1.4.1.9.2.2.1.1.54";
        }

        leaf locIfclnsOutPkts {
          type yang:counter32;
          status obsolete;
          description
           "CLNS protocol output packet count";
          smiv2:max-access "read-only";
          smiv2:oid "1.3.6.1.4.1.9.2.2.1.1.55";
        }

        leaf locIfclnsInOctets {
          type yang:counter32;
          status obsolete;
          description
           "CLNS protocol input byte count";
          smiv2:max-access "read-only";
          smiv2:oid "1.3.6.1.4.1.9.2.2.1.1.56";
        }

        leaf locIfclnsOutOctets {
          type yang:counter32;
          status obsolete;
          description
           "CLNS protocol output byte count";
          smiv2:max-access "read-only";
          smiv2:oid "1.3.6.1.4.1.9.2.2.1.1.57";
        }

        leaf locIfappletalkInPkts {
          type yang:counter32;
          status obsolete;
          description
           "Appletalk protocol input packet count";
          smiv2:max-access "read-only";
          smiv2:oid "1.3.6.1.4.1.9.2.2.1.1.58";
        }

        leaf locIfappletalkOutPkts {
          type yang:counter32;
          status obsolete;
          description
           "Appletalk protocol output packet count";
          smiv2:max-access "read-only";
          smiv2:oid "1.3.6.1.4.1.9.2.2.1.1.59";
        }

        leaf locIfappletalkInOctets {
          type yang:counter32;
          status obsolete;
          description
           "Appletalk protocol input octet count";
          smiv2:max-access "read-only";
          smiv2:oid "1.3.6.1.4.1.9.2.2.1.1.60";
        }

        leaf locIfappletalkOutOctets {
          type yang:counter32;
          status obsolete;
          description
           "Appletalk protocol output octet count";
          smiv2:max-access "read-only";
          smiv2:oid "1.3.6.1.4.1.9.2.2.1.1.61";
        }

        leaf locIfnovellInPkts {
          type yang:counter32;
          status obsolete;
          description
           "Novell protocol input packet count";
          smiv2:max-access "read-only";
          smiv2:oid "1.3.6.1.4.1.9.2.2.1.1.62";
        }

        leaf locIfnovellOutPkts {
          type yang:counter32;
          status obsolete;
          description
           "Novell protocol output packet count";
          smiv2:max-access "read-only";
          smiv2:oid "1.3.6.1.4.1.9.2.2.1.1.63";
        }

        leaf locIfnovellInOctets {
          type yang:counter32;
          status obsolete;
          description
           "Novell protocol input octet count";
          smiv2:max-access "read-only";
          smiv2:oid "1.3.6.1.4.1.9.2.2.1.1.64";
        }

        leaf locIfnovellOutOctets {
          type yang:counter32;
          status obsolete;
          description
           "Novell protocol output octet count";
          smiv2:max-access "read-only";
          smiv2:oid "1.3.6.1.4.1.9.2.2.1.1.65";
        }

        leaf locIfapolloInPkts {
          type yang:counter32;
          status obsolete;
          description
           "Apollo protocol input packet count";
          smiv2:max-access "read-only";
          smiv2:oid "1.3.6.1.4.1.9.2.2.1.1.66";
        }

        leaf locIfapolloOutPkts {
          type yang:counter32;
          status obsolete;
          description
           "Apollo protocol output packet count";
          smiv2:max-access "read-only";
          smiv2:oid "1.3.6.1.4.1.9.2.2.1.1.67";
        }

        leaf locIfapolloInOctets {
          type yang:counter32;
          status obsolete;
          description
           "Apollo protocol input octet count";
          smiv2:max-access "read-only";
          smiv2:oid "1.3.6.1.4.1.9.2.2.1.1.68";
        }

        leaf locIfapolloOutOctets {
          type yang:counter32;
          status obsolete;
          description
           "Apollo protocol output octet count";
          smiv2:max-access "read-only";
          smiv2:oid "1.3.6.1.4.1.9.2.2.1.1.69";
        }

        leaf locIfvinesInPkts {
          type yang:counter32;
          status obsolete;
          description
           "Vines protocol input packet count";
          smiv2:max-access "read-only";
          smiv2:oid "1.3.6.1.4.1.9.2.2.1.1.70";
        }

        leaf locIfvinesOutPkts {
          type yang:counter32;
          status obsolete;
          description
           "Vines protocol output packet count";
          smiv2:max-access "read-only";
          smiv2:oid "1.3.6.1.4.1.9.2.2.1.1.71";
        }

        leaf locIfvinesInOctets {
          type yang:counter32;
          status obsolete;
          description
           "Vines protocol input octet count";
          smiv2:max-access "read-only";
          smiv2:oid "1.3.6.1.4.1.9.2.2.1.1.72";
        }

        leaf locIfvinesOutOctets {
          type yang:counter32;
          status obsolete;
          description
           "Vines protocol output octet count";
          smiv2:max-access "read-only";
          smiv2:oid "1.3.6.1.4.1.9.2.2.1.1.73";
        }

        leaf locIfbridgedInPkts {
          type yang:counter32;
          status obsolete;
          description
           "Bridged protocol input packet count";
          smiv2:max-access "read-only";
          smiv2:oid "1.3.6.1.4.1.9.2.2.1.1.74";
        }

        leaf locIfbridgedOutPkts {
          type yang:counter32;
          status obsolete;
          description
           "Bridged protocol output packet count";
          smiv2:max-access "read-only";
          smiv2:oid "1.3.6.1.4.1.9.2.2.1.1.75";
        }

        leaf locIfbridgedInOctets {
          type yang:counter32;
          status obsolete;
          description
           "Bridged protocol input octet count";
          smiv2:max-access "read-only";
          smiv2:oid "1.3.6.1.4.1.9.2.2.1.1.76";
        }

        leaf locIfbridgedOutOctets {
          type yang:counter32;
          status obsolete;
          description
           "Bridged protocol output octet count";
          smiv2:max-access "read-only";
          smiv2:oid "1.3.6.1.4.1.9.2.2.1.1.77";
        }

        leaf locIfsrbInPkts {
          type yang:counter32;
          status obsolete;
          description
           "SRB protocol input packet count";
          smiv2:max-access "read-only";
          smiv2:oid "1.3.6.1.4.1.9.2.2.1.1.78";
        }

        leaf locIfsrbOutPkts {
          type yang:counter32;
          status obsolete;
          description
           "SRB protocol output packet count";
          smiv2:max-access "read-only";
          smiv2:oid "1.3.6.1.4.1.9.2.2.1.1.79";
        }

        leaf locIfsrbInOctets {
          type yang:counter32;
          status obsolete;
          description
           "SRB protocol input octet count";
          smiv2:max-access "read-only";
          smiv2:oid "1.3.6.1.4.1.9.2.2.1.1.80";
        }

        leaf locIfsrbOutOctets {
          type yang:counter32;
          status obsolete;
          description
           "SRB protocol output octet count";
          smiv2:max-access "read-only";
          smiv2:oid "1.3.6.1.4.1.9.2.2.1.1.81";
        }

        leaf locIfchaosInPkts {
          type yang:counter32;
          status obsolete;
          description
           "Choas protocol input packet count";
          smiv2:max-access "read-only";
          smiv2:oid "1.3.6.1.4.1.9.2.2.1.1.82";
        }

        leaf locIfchaosOutPkts {
          type yang:counter32;
          status obsolete;
          description
           "Choas protocol output packet count";
          smiv2:max-access "read-only";
          smiv2:oid "1.3.6.1.4.1.9.2.2.1.1.83";
        }

        leaf locIfchaosInOctets {
          type yang:counter32;
          status obsolete;
          description
           "Choas protocol input octet count";
          smiv2:max-access "read-only";
          smiv2:oid "1.3.6.1.4.1.9.2.2.1.1.84";
        }

        leaf locIfchaosOutOctets {
          type yang:counter32;
          status obsolete;
          description
           "Choas protocol output octet count";
          smiv2:max-access "read-only";
          smiv2:oid "1.3.6.1.4.1.9.2.2.1.1.85";
        }

        leaf locIfpupInPkts {
          type yang:counter32;
          status obsolete;
          description
           "PUP protocol input packet count";
          smiv2:max-access "read-only";
          smiv2:oid "1.3.6.1.4.1.9.2.2.1.1.86";
        }

        leaf locIfpupOutPkts {
          type yang:counter32;
          status obsolete;
          description
           "PUP protocol output packet count";
          smiv2:max-access "read-only";
          smiv2:oid "1.3.6.1.4.1.9.2.2.1.1.87";
        }

        leaf locIfpupInOctets {
          type yang:counter32;
          status obsolete;
          description
           "PUP protocol input octet count";
          smiv2:max-access "read-only";
          smiv2:oid "1.3.6.1.4.1.9.2.2.1.1.88";
        }

        leaf locIfpupOutOctets {
          type yang:counter32;
          status obsolete;
          description
           "PUP protocol output octet count";
          smiv2:max-access "read-only";
          smiv2:oid "1.3.6.1.4.1.9.2.2.1.1.89";
        }

        leaf locIfmopInPkts {
          type yang:counter32;
          status obsolete;
          description
           "MOP protocol input packet count";
          smiv2:max-access "read-only";
          smiv2:oid "1.3.6.1.4.1.9.2.2.1.1.90";
        }

        leaf locIfmopOutPkts {
          type yang:counter32;
          status obsolete;
          description
           "MOP protocol output packet count";
          smiv2:max-access "read-only";
          smiv2:oid "1.3.6.1.4.1.9.2.2.1.1.91";
        }

        leaf locIfmopInOctets {
          type yang:counter32;
          status obsolete;
          description
           "MOP protocol input octet count";
          smiv2:max-access "read-only";
          smiv2:oid "1.3.6.1.4.1.9.2.2.1.1.92";
        }

        leaf locIfmopOutOctets {
          type yang:counter32;
          status obsolete;
          description
           "MOP protocol output octet count";
          smiv2:max-access "read-only";
          smiv2:oid "1.3.6.1.4.1.9.2.2.1.1.93";
        }

        leaf locIflanmanInPkts {
          type yang:counter32;
          status obsolete;
          description
           "LanMan protocol input packet count";
          smiv2:max-access "read-only";
          smiv2:oid "1.3.6.1.4.1.9.2.2.1.1.94";
        }

        leaf locIflanmanOutPkts {
          type yang:counter32;
          status obsolete;
          description
           "LanMan protocol output packet count";
          smiv2:max-access "read-only";
          smiv2:oid "1.3.6.1.4.1.9.2.2.1.1.95";
        }

        leaf locIflanmanInOctets {
          type yang:counter32;
          status obsolete;
          description
           "LanMan protocol input octet count";
          smiv2:max-access "read-only";
          smiv2:oid "1.3.6.1.4.1.9.2.2.1.1.96";
        }

        leaf locIflanmanOutOctets {
          type yang:counter32;
          status obsolete;
          description
           "LanMan protocol output octet count";
          smiv2:max-access "read-only";
          smiv2:oid "1.3.6.1.4.1.9.2.2.1.1.97";
        }

        leaf locIfstunInPkts {
          type yang:counter32;
          status obsolete;
          description
           "STUN protocol input packet count";
          smiv2:max-access "read-only";
          smiv2:oid "1.3.6.1.4.1.9.2.2.1.1.98";
        }

        leaf locIfstunOutPkts {
          type yang:counter32;
          status obsolete;
          description
           "STUN protocol output packet count";
          smiv2:max-access "read-only";
          smiv2:oid "1.3.6.1.4.1.9.2.2.1.1.99";
        }

        leaf locIfstunInOctets {
          type yang:counter32;
          status obsolete;
          description
           "STUN protocol input octet count";
          smiv2:max-access "read-only";
          smiv2:oid "1.3.6.1.4.1.9.2.2.1.1.100";
        }

        leaf locIfstunOutOctets {
          type yang:counter32;
          status obsolete;
          description
           "STUN protocol output octet count";
          smiv2:max-access "read-only";
          smiv2:oid "1.3.6.1.4.1.9.2.2.1.1.101";
        }

        leaf locIfspanInPkts {
          type yang:counter32;
          status obsolete;
          description
           "Spanning tree input protocol packet count";
          smiv2:max-access "read-only";
          smiv2:oid "1.3.6.1.4.1.9.2.2.1.1.102";
        }

        leaf locIfspanOutPkts {
          type yang:counter32;
          status obsolete;
          description
           "Spanning tree output protocol packet count";
          smiv2:max-access "read-only";
          smiv2:oid "1.3.6.1.4.1.9.2.2.1.1.103";
        }

        leaf locIfspanInOctets {
          type yang:counter32;
          status obsolete;
          description
           "Spanning tree input octet packet count";
          smiv2:max-access "read-only";
          smiv2:oid "1.3.6.1.4.1.9.2.2.1.1.104";
        }

        leaf locIfspanOutOctets {
          type yang:counter32;
          status obsolete;
          description
           "Spanning tree output octet packet count";
          smiv2:max-access "read-only";
          smiv2:oid "1.3.6.1.4.1.9.2.2.1.1.105";
        }

        leaf locIfarpInPkts {
          type yang:counter32;
          status obsolete;
          description
           "Arp protocol input packet count";
          smiv2:max-access "read-only";
          smiv2:oid "1.3.6.1.4.1.9.2.2.1.1.106";
        }

        leaf locIfarpOutPkts {
          type yang:counter32;
          status obsolete;
          description
           "Arp protocol output packet count";
          smiv2:max-access "read-only";
          smiv2:oid "1.3.6.1.4.1.9.2.2.1.1.107";
        }

        leaf locIfarpInOctets {
          type yang:counter32;
          status obsolete;
          description
           "Arp protocol input octet count";
          smiv2:max-access "read-only";
          smiv2:oid "1.3.6.1.4.1.9.2.2.1.1.108";
        }

        leaf locIfarpOutOctets {
          type yang:counter32;
          status obsolete;
          description
           "Arp protocol output octet count";
          smiv2:max-access "read-only";
          smiv2:oid "1.3.6.1.4.1.9.2.2.1.1.109";
        }

        leaf locIfprobeInPkts {
          type yang:counter32;
          status obsolete;
          description
           "Probe protocol input packet count";
          smiv2:max-access "read-only";
          smiv2:oid "1.3.6.1.4.1.9.2.2.1.1.110";
        }

        leaf locIfprobeOutPkts {
          type yang:counter32;
          status obsolete;
          description
           "Probe protocol output packet count";
          smiv2:max-access "read-only";
          smiv2:oid "1.3.6.1.4.1.9.2.2.1.1.111";
        }

        leaf locIfprobeInOctets {
          type yang:counter32;
          status obsolete;
          description
           "Probe protocol input octet count";
          smiv2:max-access "read-only";
          smiv2:oid "1.3.6.1.4.1.9.2.2.1.1.112";
        }

        leaf locIfprobeOutOctets {
          type yang:counter32;
          status obsolete;
          description
           "Probe protocol output octet count";
          smiv2:max-access "read-only";
          smiv2:oid "1.3.6.1.4.1.9.2.2.1.1.113";
        }

        leaf locIfDribbleInputs {
          type yang:counter32;
          status obsolete;
          description
           "The number of good packets received with the
            dribble condition present";
          smiv2:max-access "read-only";
          smiv2:oid "1.3.6.1.4.1.9.2.2.1.1.114";
        }
      }
    }

    container lFSIPTable {
      status obsolete;
      description
       "A list of card entries for 4T, HSSI,
        Mx serial or FSIP.";
      smiv2:oid "1.3.6.1.4.1.9.2.2.2";

      list lFSIPEntry {
        key "locIfFSIPIndex";
        status obsolete;
        description
         "A collection of objects specific to 4T,
          HSSI, Mx serial or FSIP.";
        smiv2:oid "1.3.6.1.4.1.9.2.2.2.1";

        leaf locIfFSIPIndex {
          type int32;
          status obsolete;
          description
           "Interface index of this card corresponding
            to its ifIndex";
          smiv2:max-access "read-only";
          smiv2:oid "1.3.6.1.4.1.9.2.2.2.1.1";
        }

        leaf locIfFSIPtype {
          type enumeration {
            enum "notAvailable" {
              value "1";
            }
            enum "dte" {
              value "2";
            }
            enum "dce" {
              value "3";
            }
          }
          status obsolete;
          description
           "Is this FSIP line DCE or DTE";
          smiv2:max-access "read-only";
          smiv2:oid "1.3.6.1.4.1.9.2.2.2.1.2";
        }

        leaf locIfFSIPrts {
          type enumeration {
            enum "notAvailable" {
              value "1";
            }
            enum "up" {
              value "2";
            }
            enum "down" {
              value "3";
            }
          }
          status obsolete;
          description
           "Is the RTS signal up or down";
          smiv2:max-access "read-only";
          smiv2:oid "1.3.6.1.4.1.9.2.2.2.1.3";
        }

        leaf locIfFSIPcts {
          type enumeration {
            enum "notAvailable" {
              value "1";
            }
            enum "up" {
              value "2";
            }
            enum "down" {
              value "3";
            }
          }
          status obsolete;
          description
           "Is the CTS signal up or down";
          smiv2:max-access "read-only";
          smiv2:oid "1.3.6.1.4.1.9.2.2.2.1.4";
        }

        leaf locIfFSIPdtr {
          type enumeration {
            enum "notAvailable" {
              value "1";
            }
            enum "up" {
              value "2";
            }
            enum "down" {
              value "3";
            }
          }
          status obsolete;
          description
           "Is the DTR signal up or down";
          smiv2:max-access "read-only";
          smiv2:oid "1.3.6.1.4.1.9.2.2.2.1.5";
        }

        leaf locIfFSIPdcd {
          type enumeration {
            enum "notAvailable" {
              value "1";
            }
            enum "up" {
              value "2";
            }
            enum "down" {
              value "3";
            }
          }
          status obsolete;
          description
           "Is the DCD signal up or down";
          smiv2:max-access "read-only";
          smiv2:oid "1.3.6.1.4.1.9.2.2.2.1.6";
        }

        leaf locIfFSIPdsr {
          type enumeration {
            enum "notAvailable" {
              value "1";
            }
            enum "up" {
              value "2";
            }
            enum "down" {
              value "3";
            }
          }
          status obsolete;
          description
           "Is the DSR signal up or down";
          smiv2:max-access "read-only";
          smiv2:oid "1.3.6.1.4.1.9.2.2.2.1.7";
        }

        leaf locIfFSIPrxClockrate {
          type int32;
          status obsolete;
          description
           "Received clock rate";
          smiv2:max-access "read-only";
          smiv2:oid "1.3.6.1.4.1.9.2.2.2.1.8";
        }

        leaf locIfFSIPrxClockrateHi {
          type int32;
          status obsolete;
          description
           "Use when received clock rate 
            is greater than 2^32 (gigabits).";
          smiv2:max-access "read-only";
          smiv2:oid "1.3.6.1.4.1.9.2.2.2.1.9";
        }

        leaf locIfFSIPportType {
          type enumeration {
            enum "noCable" {
              value "1";
            }
            enum "rs232" {
              value "2";
            }
            enum "rs422" {
              value "3";
            }
            enum "rs423" {
              value "4";
            }
            enum "v35" {
              value "5";
            }
            enum "x21" {
              value "6";
            }
            enum "rs449" {
              value "7";
            }
            enum "rs530" {
              value "8";
            }
            enum "hssi" {
              value "9";
            }
            enum "g703unbal" {
              value "10";
            }
            enum "g703bal" {
              value "11";
            }
            enum "jt2unbal" {
              value "12";
            }
          }
          status obsolete;
          description
           "Cable Type of 4T, HSSI, Mx serial or FSIP";
          smiv2:max-access "read-only";
          smiv2:oid "1.3.6.1.4.1.9.2.2.2.1.10";
        }
      }
    }
  }

  smiv2:alias "linterfaces" {
    smiv2:oid "1.3.6.1.4.1.9.2.2";
  }

}
