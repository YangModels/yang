/*
 * Generated by confdc --mib2yang-std
 * Source: mgmt/dmi/model/mib/src/patched/CISCO-RTTMON-MIB.mib
 */
/*
 * This YANG module has been generated by smidump 0.5.0:
 *
 *      smidump -f yang CISCO-RTTMON-MIB
 *
 * Do not edit. Edit the source file instead!
 */

module CISCO-RTTMON-MIB {

  namespace "urn:ietf:params:xml:ns:yang:smiv2:CISCO-RTTMON-MIB";
  prefix CISCO-RTTMON-MIB;

  import CISCO-ETHER-CFM-MIB {
    prefix "cisco-ether";
  }

  import CISCO-QOS-PIB-MIB {
    prefix "cisco-qos";
  }

  import CISCO-RTTMON-TC-MIB {
    prefix "cisco-rttmon";
  }

  import IF-MIB {
    prefix "if-mib";
  }

  import INET-ADDRESS-MIB {
    prefix "inet-address";
  }

  import Q-BRIDGE-MIB {
    prefix "q-bridge";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "Cisco IOS";

  contact
   "Cisco Systems, Inc.
    Customer Service 
    
    Postal: 170 W Tasman Drive
    San Jose, CA 95134
    
    Tel: +1 800 553 NETS
    
    cs-ipsla@cisco.com";

  description
   "This module defines a MIB for Round Trip Time
    (RTT) monitoring of a list of targets, using a 
    variety of protocols.
    
    The table structure overview is a follows (t: 
     indicates a table, at:  indicates an augmented 
     table, and it:  indicates table with the same 
     indices/control as parent table):
    
    RTTMON MIB
    |--- Application Group
    |    |--- Application Identity
    |    |--- Application Capabilities
    |    |--- Application Reset
    |    |t-- Supported RTT Types
    |         |--- Truth Value
    |    |t-- Supported Protocols
    |         |--- Truth Value
    |    |t-- Application Preconfigured
    |         |--- Script Names
    |         |--- File Paths
    |    |--- Responder control
    |    |t-- Control Protocol Authentication
    |
    |--- Overall Control Group
    |    |t-- Master Definitions Table
    |    |    |--- Global Configuration Definitions
    |    |         |--- Config for a single RTT Life
    |    |    |it- Echo Specific Configuration
    |    |    |it- Echo Path Hop Address Configuration
    |    |    |it- File I/O Specific Configuration
    |    |    |it- Script Specific Configuration
    |    |    |at- Schedule Configuration
    |    |    |at- Reaction Specific Config
    |    |    |at- Statistics Capture Configuration
    |    |    |at- History Collection Configuration
    |    |    |at- Monitoring Operational State
    |    |    |at- Last RTT operation
    |    |
    |    |t-- Reaction Trigger Table
    |         |at- Reaction Trigger Operational State
    |
    |--- Statistics Collection Group
    |    |t-- Statistics Capture Table
    |         |--- Captured Statistics
    |              |--- Path Information
    |              |--- Distribution Capture 
    |              |--- Mean and Deviation Capture
    |         |it- Statistics Collection Table
    |    |it- Statistics Totals Table
    |    |t-- HTTP Stats Table
    |    |t-- Jitter Stats Table
    |
    |--- History Collection Group
    |    |t-- History Collection Table
    |         |-- Path Information
    |         |-- Completion Information per operation
    |
    |--- Latest Operation Group
    |    |t-- Latest HTTP Oper Table
    |    |t-- Latest Jitter Oper Table
    
    DEFINITIONS:
      conceptual RTT control row - 
              This is a row in the 'Overall Control 
              Group'.  This row is indexed via the 
              rttMonCtrlAdminIndex object.  This row 
              is spread across multiple real tables 
              in the 'Overall Control Group'.
      probe -
              This is the entity that executes via a 
              conceptual RTT control row and populates
              a conceptual statistics row and a 
              conceptual history row.
      Rtt operation -
              This is a single operation performed by
              a probe.  This operation can be a single
              Rtt attempt/completion or a group of Rtt
              attempts/completions that produce one
              operation table entry.
    
    ARR Protocol Definition:
    
    The format of the RTT Asymmetric Request/Responses 
     (ARR) protocol is as follows:
    
      The ARR Header (total of 12 octets): 
    
      4 octet -> eyecatcher: 'WxYz'
      1 octet -> version   : 0x01 - protocol version
      1 octet -> command   : 0x01 - logoff request
                             0x02 - echo request
                             0x03 - echo response
                             0x04 - software version request
                             0x05 - software version response
      2 octet -> sequence number (Network Byte Order)
      4 octet -> response data size (Network Byte Order)
    
      The ARR Data:
    
      n octets -> request/response data
                            : 'AB..ZAB..ZAB..' 
    
      For software version request/response the 
       protocol version octet will contain the version
       number of the responder.  Thus the sequence 
       number, etc will not be included.
    
      For snaLU0EchoAppl and snaLU2EchoAppl all character 
       fields will be in EBCDIC.
    
      The response data should be appended to the 
       origin request data.  This allows data  
       verification to check the data that flows in 
       both directions.  If the response data size is
       smaller than the request data size the original
       request data will be truncated.  
    
      An example would be:
        Request:        /       Response:
        'WxYz'          /       'WxYz'
        0x01            /       0x01
        0x02            /       0x03
        0x0001          /       0x0001
        0x00000008      /       0x00000008
        'ABCDEF'        /       'ABCDEFGH'
    
      NOTE: We requested 8 bytes in the response and 
            the response had 8 bytes.  The size of the
            request data has no correlation to the
            size of the response data.
    
    NOTE:  For native RTT request/response (i.e. 
           ipIcmpecho) operations both the 'Header' 
           and 'Data' will be included.  Only the 
           'sequence number' in the Header will be 
           valid.
    
    NOTE:  For non-connection oriented protocol the 
           initial RTT request/response operation will
           be preceded with an RTT request/response 
           operation to the target address to force 
           path exploration and to prove 
           connectivity.  The History collection table
           will contain these responses, but the 
           Statistics capture table will omit them to
           prevent skewed results.";

  revision 2012-08-16 {
    description
     "Added following objects to support Y1731 Synthetic Loss
      Measurement
          rttMonEchoAdminEnableBurst,
          rttMonEchoAdminAggBurstCycles,
          rttMonEchoAdminLossRatioNumFrames,
          rttMonEchoAdminAvailNumFrames
      Added following object to support improving accuracy for jitter
      probes measurement. 
          rttMonEchoAdminTstampOptimization        
      Deprecated rttMonScheduleAdminConceptRowAgeout and replace
      with  rttMonScheduleAdminConceptRowAgeoutV2.
      Deprecated rttMonControlEnableErrors, rttMonStatsRetrieveErrors
      and replace with rttMonStatsCollectCtrlEnErrors,
      rttMonStatsCollectRetrieveErrors.
      Modified the descriptions for 
          rttMonLatestJitterOperMOS
          rttMonLatestJitterOperICPIF,
          rttMonJitterStatsMinOfMOS
          rttMonJitterStatsMinOfICPIF,
          rttMonJitterStatsMaxOfMOS
          rttMonJitterStatsMaxOfICPIF
      Added new compliance
          ciscoRttMonMibComplianceRev21.";
  }

  revision 2011-09-15 {
    description
     "Added following objects to rttMonEchoAdmin to support
      Y1731 extensions.
      - rttMonEchoAdminTargetMacAddress,
      - rttMonEchoAdminSourceMacAddress and 
      - rttMonEchoAdminSourceMPID";
  }

  revision 2011-02-21 {
    description
     "Added four new objects rttMonEchoAdminEmulateSourceAddress,
      rttMonEchoAdminEmulateSourcePort,
      rttMonEchoAdminEmulateTargetAddress,
      rttMonEchoAdminEmulateTargetPort to RttMonEchoAdminEntry.";
  }

  revision 2010-10-18 {
    description
     "Added three new objects rttMonEchoAdminDscp,
      rttMonEchoAdminReserveDsp, rttMonEchoAdminInputInterface";
  }

  revision 2010-06-04 {
    description
     "Changes added for video operation:
      -Added new MIB object rttMonEchoAdminVideoTrafficProfile
      -Changed the maximum range of rttMonEchoAdminCallDuration to 600
      -Changed the minimum range of rttMonEchoAdminCallDuration to 1
      from 10";
  }

  revision 2009-04-07 {
    description
     "- Added rttMonEchoAdminTargetMEPPort object in
      rttMonEchoAdminEntry.";
  }

  revision 2008-03-24 {
    description
     "- Added nine new objects rttMonLatestJitterOperRTTSumHigh,
      rttMonLatestJitterOperRTTSum2High,
      rttMonLatestJitterOperOWSumSDHigh,
      rttMonLatestJitterOperOWSum2SDHigh,
      rttMonLatestJitterOperOWSumDSHigh,
      rttMonLatestJitterOperOWSum2DSHigh,
      rttMonJitterStatsRTTSumHigh, rttMonJitterStatsOWSumSDHigh,
      rttMonJitterStatsOWSumDSHigh.
      - Modified the unit and the description of
      rttMonLatestRttOperCompletionTime,
      rttMonJitterStatsRTTSum, rttMonJitterStatsOWSumSD,
      rttMonJitterStatsOWSumDS, rttMonLatestJitterOperRTTSum, 
      rttMonLatestJitterOperRTTSum2, rttMonLatestJitterOperOWSumSD,
      rttMonLatestJitterOperOWSumDS, rttMonLatestJitterOperOWSum2SD,
      rttMonLatestJitterOperOWSum2DS.";
  }

  revision 2008-01-06 {
    description
     "Added a new object rttMonEchoAdminTargetEVC.";
  }

  revision 2006-12-08 {
    description
     "Added a new object rttMonCtrlAdminGroupName to support the
      auto measure project. Group Name will be shown for auto 
      generated operations.";
  }

  revision 2006-06-08 {
    description
     "Added a new rttMonRttType named as lspPingPseudowire.
      Added an object rttMonEchoAdminLSPVccvID to support 
      lspPingPseudowire.
      Change the default value of rttMplsVpnMonTypeLpdScanPeriod
      from 1 to 240.";
  }

  revision 2006-03-02 {
    description
     "Added two new rttMonRttType's ethernetPing and ethernetJitter.
      Added four objects rttMonEchoAdminTargetMPID, 
      rttMonEchoAdminTargetVLAN, rttMonEchoAdminTargetDomainName
      and rttMonEchoAdminEthernetCOS in rttMonEchoAdminEntry to 
      support ethernetPing and ethernetJitter.
      Change the default value of rttMplsVpnMonTypeLpdScanPeriod
      from 0 to 1.
      Modified the range of rttMonApplProbeCapacity and 
      rttMonApplNumCtrlAdminEntry to 1 .. 2147483647. 
      Modified the range of rttMonLatestJitterOperMOS, 
      rttMonJitterStatsMinOfMOS and rttMonJitterStatsMaxOfMOS to 
      (0|100 .. 500).
      Modified the SYNTAX of rttMonCtrlAdminOwner to OCTET STRING 
      because OwnerString is deprecated.";
  }

  revision 2005-08-11 {
    description
     "- TEXTUAL Conventions previously defined in the MIB are defined
      in CISCO-RTTMON-TC-MIB.";
  }

  revision 2005-04-21 {
    description
     "- Added new objects given in ciscoCtrlGroupRev4 to
      rttMonGrpScheduleAdminTable.
      - Changed description of object rttMonHTTPStatsRTTMax.";
  }

  revision 2005-01-04 {
    description
     "Added two new rttMonRttType's rtp and lspGroup. Added a new
      object rttMonApplLpdGrpStatsReset to reset the LPD Group Stats.
      Added rttMonLpdGrpStatsTable for supporting LSP Path Discovery.
      Added two new notifications rttMonLpdDiscoveryNotification
      and rttMonLpdGrpStatusNotification.
      Added and modified descriptions of some objects in
      rttMplsVpnMonCtrlTable, rttMplsVpnMonTypeTable and
      rttMplsVpnMonReactTable for LSP Path Discovery.
      Added 6 options in the rttMonReactVar.
      Added rttMonEchoAdminSourceVoicePort and
      rttMonEchoAdminCallDuration in rttMonEchoAdminTable.";
  }

  revision 2004-08-26 {
    description
     "Added a table rttMonReactTable, which defines the
      the reaction configurations for the probes.
      Deprecated the old reaction table rttMonReactAdminTable.
      This is replaced by the new table (rttMonReactTable).
      Depreacted the notification types
        rttMonConnectionChangeNotification
        rttMonTimeoutNotification
        rttMonThresholdNotification
        rttMonVerifyErrorNotification
      Added new notification type rttMonNotification.
      Added two objects, rttMonGrpScheduleAdminFreqMax 
      and rttMonGrpScheduleAdminFreqMin to table 
      rttMonGrpScheduleAdminTable.";
  }

  revision 2004-05-18 {
    description
     "- Add the following fields for VoIP GK registration delay:
      RttMonEchoAdminEntry:
       rttMonEchoAdminGKRegistration
      - Add the following fields for VoIP Post dial delay:
      RttMonOperation:
       voipDTAlertRinging(6),
       voipDTConnectOK(7)
      RttMonRttType:
       voip(13)
      RttMonProtocol:
       voipAppl(31)
      RttMonEchoAdminEntry:
       rttMonEchoAdminCalledNumber
       rttMonEchoAdminDetectPoint
      - Add HTTP code 301, 302 as non-error scenario.
      - Modify description for rttMonEchoAdminNameServer:
       it is applicable for DNS and HTTP probe.
      - Modify rttMonCtrlAdminFrequency range 
       from Integer32 (0..604800) to (1..604800)
      - Added following new objects for jitter probe precision
      and other improvements:
      rttMonEchoAdminPrecision, rttMonEchoAdminProbePakPriority, 
      rttMonJitterStatsIAJOut, rttMonJitterStatsIAJIn, 
      rttMonJitterStatsAvgJitter, rttMonJitterStatsAvgJitterSD, 
      rttMonJitterStatsAvgJitterDS, rttMonJitterStatsUnSyncRTs,
      rttMonLatestJitterOperIAJIn, rttMonLatestJitterOperAvgJitter,
      rttMonLatestJitterOperAvgSDJ, rttMonLatestJitterOperAvgDSJ,
      rttMonLatestJitterOperOWAvgSD, rttMonLatestJitterOperOWAvgDS,
      rttMonLatestJitterOperIAJOut, rttMonLatestJitterOperNTPState, 
      rttMonEchoAdminOWNTPSyncTolAbs,
      rttMonEchoAdminOWNTPSyncTolPct,
      rttMonEchoAdminOWNTPSyncTolType,
      rttMonLatestJitterOperUNSyncRTs";
  }

  revision 2004-01-20 {
    description
     "Created new tables for Auto SAA L3 MPLS VPN.
      rttMplsVpnMonCtrlTable
      rttMplsVpnMonTypeTable
      rttMplsVpnMonScheduleTable
      rttMplsVpnMonReactTable.
      Modified MIB for creation of echo and pathecho operations based
      on MPLS LSP Ping.";
  }

  revision 2003-08-11 {
    description
     "Added 1 object rttMonScheduleAdminRttRecurring to the
      rttMonScheduleAdminTable. Added a new table 
      rttMonGrpScheduleAdminTable for group scheduling. This table
      contains the following objects
      rttMonGrpScheduleAdminIndex
      rttMonGrpScheduleAdminProbes
      rttMonGrpScheduleAdminPeriod
      rttMonGrpScheduleAdminFrequency
      rttMonGrpScheduleAdminLife
      rttMonGrpScheduleAdminAgeout
      rttMonGrpScheduleAdminStatus.
      Modified the default value of rttMonReactTriggerAdminStatus
      from createAndGo to no default value. Corrected the Revision
      clause specified for the existing and all the earlier
      submissions.";
  }

  revision 2003-05-21 {
    description
     "Range for rttMonLatestJitterOperMOS, rttMonJitterStatsMinOfMOS
      and rttMonJitterStatsMaxOfMOS to be changed to 100..500
      instead of 1..5. Modifying the range of rttMonApplProbeCapacity 
      and rttMonApplNumCtrlAdminEntry to 1..10000.Added value other(0)
      for RttResponseSense and changed the range of objects
      rttMonLatestRttOperApplSpecificSense and
      rttMonHistoryCollectionApplSpecificSense to 0..2147483647.
      Added range for rttMonApplAuthIndex.";
  }

  revision 2003-04-15 {
    description
     "Removed default values from
      rttMonEchoAdminCodecInterval
      rttMonEchoAdminCodecPayload
      rttMonEchoAdminCodecNumPackets.
      Corrected some typos in the earliar revision.";
  }

  revision 2003-03-12 {
    description
     "Added 5 objects in the rttMonEchoAdminTable to support
      codec configuration.
      Added few objects in rttMonLatestJitterOperTable and
      rttMonJitterStatsTable for ICPIF (Calculated Planning
      Impairment Factor) and MOS (Mean Opinion Score) scores.";
  }

  revision 2000-11-03 {
    description
     "deprecated 4 objects in the rttMonJitterStatsTable
      and added the same objects with a SYNTAX of Gauge32.
      Also added the capability to specify a VrfName.";
  }

  revision 1999-06-15 {
    description
     "created rttMonAuthTable.";
  }


  container CISCO-RTTMON-MIB {
    config false;

    container rttMonAppl {
      smiv2:oid "1.3.6.1.4.1.9.9.42.1.1";

      leaf rttMonApplVersion {
        type snmpv2-tc:DisplayString;
        description
         "Round Trip Time monitoring application version
          string.
          
          The format will be:
          
          'Version.Release.Patch-Level: Textual-Description'
          
          For example:  '1.0.0: Initial RTT Application'";
        smiv2:max-access "read-only";
        smiv2:oid "1.3.6.1.4.1.9.9.42.1.1.1";
      }

      leaf rttMonApplMaxPacketDataSize {
        type int32 {
          range "0..16384";
        }
        units "octets";
        description
         "The maximum size of the data portion an echo
          packet supported by this RTT application.  This is
          the maximum value that can be specified by
          (rttMonEchoAdminPktDataRequestSize + ARR Header)
          or 
          (rttMonEchoAdminPktDataResponseSize + ARR Header)
          in the rttMonCtrlAdminTable.
          
          This object is undefined for conceptual RTT 
          control rows when the RttMonRttType object is set
          to 'fileIO' or 'script'.";
        smiv2:max-access "read-only";
        smiv2:oid "1.3.6.1.4.1.9.9.42.1.1.2";
      }

      leaf rttMonApplTimeOfLastSet {
        type yang:timestamp;
        description
         "The last time at which a set operation occurred
          on any of the objects in this MIB.  The managing 
          application can inspect this value in order to 
          determine whether changes have been made without 
          retrieving the entire Administration portion of
          this MIB.
          
          This object applies to all settable objects in this
          MIB, including the 'Reset' objects that could clear
          saved history/statistics.";
        smiv2:max-access "read-only";
        smiv2:oid "1.3.6.1.4.1.9.9.42.1.1.3";
      }

      leaf rttMonApplNumCtrlAdminEntry {
        type int32 {
          range "1..2147483647";
        }
        description
         "This object defines the maximum number of entries
          that can be added to the rttMonCtrlAdminTable. It
          is calculated at the system init time. The value
          is impacted when rttMonApplFreeMemLowWaterMark is changed.";
        smiv2:max-access "read-only";
        smiv2:oid "1.3.6.1.4.1.9.9.42.1.1.4";
      }

      leaf rttMonApplReset {
        type cisco-rttmon:RttReset;
        description
         "When set to 'reset' the entire RTT application
          goes through a reset sequence, making a best 
          effort to revert to its startup condition.  Any 
          and all rows in the Overall Control Group will be
          immediately deleted, together with any associated
          rows in the Statistics Collection Group, and 
          History Collection Group.  All open connections 
          will also be closed.  Finally the 
          rttMonApplPreConfigedTable will reset (see 
          rttMonApplPreConfigedReset).";
        smiv2:max-access "read-write";
        smiv2:oid "1.3.6.1.4.1.9.9.42.1.1.5";
      }

      leaf rttMonApplPreConfigedReset {
        type cisco-rttmon:RttReset;
        status obsolete;
        description
         "When set to 'reset' the RTT application will
          reset the Application Preconfigured MIB section.
          
          This will force the RTT application to delete all
          entries in the rttMonApplPreConfigedTable and then
          to repopulate the table with the current configuration.
          
          This provides a mechanism to load and unload user
          scripts and file paths.";
        smiv2:max-access "read-write";
        smiv2:oid "1.3.6.1.4.1.9.9.42.1.1.6";
      }

      leaf rttMonApplProbeCapacity {
        type int32 {
          range "1..2147483647";
        }
        description
         "This object defines the number of new probes that can be
          configured on a router. The number depends on the value 
          of rttMonApplFreeMemLowWaterMark, free bytes
          available on the router and the system configured
          rttMonCtrlAdminEntry number.
          Equation:
          rttMonApplProbeCapacity = 
          MIN(((Free_Bytes_on_the_Router - rttMonApplFreeMemLowWaterMark)/
          Memory_required_by_each_probe),
          rttMonApplNumCtrlAdminEntry - 
          Num_of_Probes_already_configured))";
        smiv2:max-access "read-only";
        smiv2:oid "1.3.6.1.4.1.9.9.42.1.1.10";
      }

      leaf rttMonApplFreeMemLowWaterMark {
        type int32 {
          range "0..2147483647";
        }
        description
         "This object defines the amount of free memory a router must
          have in order to configure RTR. If RTR found out that the
          memory is falling below this mark, it will not allow new
          probes to be configured.
          
          This value should not be set higher (or very close to) than 
          the free bytes available on the router.";
        smiv2:max-access "read-write";
        smiv2:oid "1.3.6.1.4.1.9.9.42.1.1.11";
      }

      leaf rttMonApplLatestSetError {
        type snmpv2-tc:DisplayString;
        description
         "An error description for the last error message caused
          by set.
          
          Currently, it includes set error caused due to setting
          rttMonApplFreeMemLowWaterMark greater than the available
          free memory on the router or not enough memory left to
          create new probes.";
        smiv2:max-access "read-only";
        smiv2:oid "1.3.6.1.4.1.9.9.42.1.1.12";
      }

      leaf rttMonApplResponder {
        type boolean;
        description
         "Enable or disable RTR responder on the router.";
        smiv2:max-access "read-write";
        smiv2:oid "1.3.6.1.4.1.9.9.42.1.1.13";
      }

      leaf rttMonApplLpdGrpStatsReset {
        type int32 {
          range "0..2147483647";
        }
        description
         "This object is used to reset certain objects within the
          rttMonLpdGrpStatsTable.  When the object is set to value of
          an active LPD Group identifier the associated objects will be
          reset. The reset objects will be set to a value as specified
          in the object's description.
          
          The following objects will not be reset.
          - rttMonLpdGrpStatsTargetPE
          - rttMonLpdGrpStatsGroupProbeIndex
          - rttMonLpdGrpStatsGroupIndex
          - rttMonLpdGrpStatsStartTimeIndex.";
        smiv2:max-access "read-write";
        smiv2:oid "1.3.6.1.4.1.9.9.42.1.1.15";
      }
    }

    container rttMonApplSupportedRttTypesTable {
      description
       "A table of which contains the supported Rtt
        Monitor Types.
        
        See the RttMonRttType textual convention for
        the definition of each type.";
      smiv2:oid "1.3.6.1.4.1.9.9.42.1.1.7";

      list rttMonApplSupportedRttTypesEntry {
        key "rttMonApplSupportedRttTypes";
        description
         "A list that presents the valid Rtt Monitor
          Types.";
        smiv2:oid "1.3.6.1.4.1.9.9.42.1.1.7.1";

        leaf rttMonApplSupportedRttTypes {
          type cisco-rttmon:RttMonRttType;
          description
           "This object indexes the supported
            'RttMonRttType' types.";
          smiv2:max-access "not-accessible";
          smiv2:oid "1.3.6.1.4.1.9.9.42.1.1.7.1.1";
        }

        leaf rttMonApplSupportedRttTypesValid {
          type boolean;
          description
           "This object defines the supported
            'RttMonRttType' types.";
          smiv2:max-access "read-only";
          smiv2:oid "1.3.6.1.4.1.9.9.42.1.1.7.1.2";
        }
      }
    }

    container rttMonApplSupportedProtocolsTable {
      description
       "A table of which contains the supported Rtt
        Monitor Protocols.
        
        See the RttMonProtocol textual convention 
        for the definition of each protocol.";
      smiv2:oid "1.3.6.1.4.1.9.9.42.1.1.8";

      list rttMonApplSupportedProtocolsEntry {
        key "rttMonApplSupportedProtocols";
        description
         "A list that presents the valid Rtt Monitor
          Protocols.";
        smiv2:oid "1.3.6.1.4.1.9.9.42.1.1.8.1";

        leaf rttMonApplSupportedProtocols {
          type cisco-rttmon:RttMonProtocol;
          description
           "This object indexes the supported
            'RttMonProtocol' protocols.";
          smiv2:max-access "not-accessible";
          smiv2:oid "1.3.6.1.4.1.9.9.42.1.1.8.1.1";
        }

        leaf rttMonApplSupportedProtocolsValid {
          type boolean;
          description
           "This object defines the supported
            'RttMonProtocol' protocols.";
          smiv2:max-access "read-only";
          smiv2:oid "1.3.6.1.4.1.9.9.42.1.1.8.1.2";
        }
      }
    }

    container rttMonApplPreConfigedTable {
      status obsolete;
      description
       "A table of which contains the previously
        configured Script Names and File IO targets.
        
        These Script Names and File IO targets are installed
        via a different mechanism than this application, and
        are specific to each platform.";
      smiv2:oid "1.3.6.1.4.1.9.9.42.1.1.9";

      list rttMonApplPreConfigedEntry {
        key "rttMonApplPreConfigedType rttMonApplPreConfigedName";
        status obsolete;
        description
         "A list of objects that describe the previously
          configured Script Names and File IO targets.";
        smiv2:oid "1.3.6.1.4.1.9.9.42.1.1.9.1";

        leaf rttMonApplPreConfigedType {
          type enumeration {
            enum "filePath" {
              value "1";
            }
            enum "scriptName" {
              value "2";
            }
          }
          status obsolete;
          description
           "This is the type of value being stored in the
            rttMonApplPreConfigedName object.";
          smiv2:max-access "not-accessible";
          smiv2:oid "1.3.6.1.4.1.9.9.42.1.1.9.1.2";
        }

        leaf rttMonApplPreConfigedName {
          type snmpv2-tc:DisplayString;
          status obsolete;
          description
           "This is either one of the following depending on the
            value of the rttMonApplPreConfigedType object:
            
             - The file path to a server.  One of these file paths 
               must be used when defining an entry in the 
               rttMonFileIOAdminTable table with 'fileIO' as the 
               value of the rttMonCtrlAdminRttType object.
            
             - The script name to be used when generating RTT 
               operations.  One of these script names must be used 
               when defining an entry in the rttMonScriptAdminTable 
               table with 'script' as the value of the 
               rttMonCtrlAdminRttType object.
            
            NOTE:  For script names, command line parameters 
                   can follow these names in the 
                   rttMonScriptAdminTable table.";
          smiv2:max-access "not-accessible";
          smiv2:oid "1.3.6.1.4.1.9.9.42.1.1.9.1.3";
        }

        leaf rttMonApplPreConfigedValid {
          type boolean;
          status obsolete;
          description
           "When this row exists, this value will be 'true'.
            This object exists only to create a valid row in this 
            table.";
          smiv2:max-access "read-only";
          smiv2:oid "1.3.6.1.4.1.9.9.42.1.1.9.1.4";
        }
      }
    }

    container rttMonApplAuthTable {
      description
       "A table which contains the definitions for key-strings
        that will be used in authenticating RTR Control Protocol.";
      smiv2:oid "1.3.6.1.4.1.9.9.42.1.1.14";

      list rttMonApplAuthEntry {
        key "rttMonApplAuthIndex";
        description
         "A list that presents the valid parameters for Authenticating
          RTR Control Protocol.";
        smiv2:oid "1.3.6.1.4.1.9.9.42.1.1.14.1";

        leaf rttMonApplAuthIndex {
          type int32 {
            range "0..2147483647";
          }
          description
           "Uniquely identifies a row in the rttMonApplAuthTable.
            This is a pseudo-random number selected by the management
            station when creating a row via the rttMonApplAuthStatus 
            object. If the pseudo-random number is already in use, an 
            'inconsistentValue' is returned. Currently, only one row 
            can be created.";
          smiv2:max-access "not-accessible";
          smiv2:oid "1.3.6.1.4.1.9.9.42.1.1.14.1.1";
        }

        leaf rttMonApplAuthKeyChain {
          type snmpv2-tc:DisplayString {
            length "1..48";
          }
          description
           "A string which represents the key-chain name. If multiple
            key-strings are specified, then the authenticator will 
            alternate between the specified strings.";
          smiv2:max-access "read-write";
          smiv2:oid "1.3.6.1.4.1.9.9.42.1.1.14.1.2";
        }

        leaf rttMonApplAuthKeyString1 {
          type snmpv2-tc:DisplayString {
            length "1..48";
          }
          description
           "A string which represents a key-string name whose id is 1.";
          smiv2:max-access "read-write";
          smiv2:oid "1.3.6.1.4.1.9.9.42.1.1.14.1.3";
        }

        leaf rttMonApplAuthKeyString2 {
          type snmpv2-tc:DisplayString {
            length "1..48";
          }
          description
           "A string which represents a key-string name whose id is 2.";
          smiv2:max-access "read-write";
          smiv2:oid "1.3.6.1.4.1.9.9.42.1.1.14.1.4";
        }

        leaf rttMonApplAuthKeyString3 {
          type snmpv2-tc:DisplayString {
            length "1..48";
          }
          description
           "A string which represents a key-string name whose id is 3.";
          smiv2:max-access "read-write";
          smiv2:oid "1.3.6.1.4.1.9.9.42.1.1.14.1.5";
        }

        leaf rttMonApplAuthKeyString4 {
          type snmpv2-tc:DisplayString {
            length "1..48";
          }
          description
           "A string which represents a key-string name whose id is 4.";
          smiv2:max-access "read-write";
          smiv2:oid "1.3.6.1.4.1.9.9.42.1.1.14.1.6";
        }

        leaf rttMonApplAuthKeyString5 {
          type snmpv2-tc:DisplayString {
            length "1..48";
          }
          description
           "A string which represents a key-string name whose id is 5.";
          smiv2:max-access "read-write";
          smiv2:oid "1.3.6.1.4.1.9.9.42.1.1.14.1.7";
        }

        leaf rttMonApplAuthStatus {
          type snmpv2-tc:RowStatus;
          description
           "The status of the Authentication row.";
          smiv2:max-access "read-write";
          smiv2:oid "1.3.6.1.4.1.9.9.42.1.1.14.1.8";
        }
      }
    }

    container rttMonCtrlAdminTable {
      description
       "A table of Round Trip Time (RTT) monitoring definitions.
        
        The RTT administration control is in multiple tables.  
        This first table, is used to create a conceptual RTT 
        control row.  The following tables contain objects which 
        configure scheduling, information gathering, and 
        notification/trigger generation.  All of these tables 
        will create the same conceptual RTT control row as this 
        table using this tables' index as their own index. 
        
        This table is limited in size by the agent 
        implementation.  The object rttMonApplNumCtrlAdminEntry
        will reflect this tables maximum number of entries.";
      smiv2:oid "1.3.6.1.4.1.9.9.42.1.2.1";

      list rttMonCtrlAdminEntry {
        key "rttMonCtrlAdminIndex";
        description
         "A base list of objects that define a conceptual RTT
          control row.";
        smiv2:oid "1.3.6.1.4.1.9.9.42.1.2.1.1";

        leaf rttMonCtrlAdminIndex {
          type int32 {
            range "1..2147483647";
          }
          description
           "Uniquely identifies a row in the rttMonCtrlAdminTable.
            This is a pseudo-random number, selected by the management 
            station or auto-generated based on  operation started by the 
            management station,when creating a row via
             the rttMonCtrlAdminStatus object.  If the pseudo-random 
             number is already in use an 'inconsistentValue' return code 
             will be returned when
            set operation is attempted.";
          smiv2:max-access "not-accessible";
          smiv2:oid "1.3.6.1.4.1.9.9.42.1.2.1.1.1";
        }

        leaf rttMonCtrlAdminOwner {
          type binary {
            length "0..255";
          }
          description
           "Identifies the entity that created this table row.";
          smiv2:defval "";
          smiv2:max-access "read-write";
          smiv2:oid "1.3.6.1.4.1.9.9.42.1.2.1.1.2";
        }

        leaf rttMonCtrlAdminTag {
          type snmpv2-tc:DisplayString {
            length "0..16";
          }
          description
           "A string which is used by a managing application to
            identify the RTT target.  This string is inserted into trap
            notifications, but has no other significance to the 
            agent.";
          smiv2:defval "";
          smiv2:max-access "read-write";
          smiv2:oid "1.3.6.1.4.1.9.9.42.1.2.1.1.3";
        }

        leaf rttMonCtrlAdminRttType {
          type cisco-rttmon:RttMonRttType;
          description
           "The type of RTT operation to be performed.  This value
            must be set in the same PDU or before setting any type
            specific configuration.
            
            Note: The RTT operation 'lspGroup' cannot be created via this
            control row. It will be created automatically by Auto SAA L3
            MPLS VPN when rttMplsVpnMonCtrlLpd is 'true'.";
          smiv2:defval "echo";
          smiv2:max-access "read-write";
          smiv2:oid "1.3.6.1.4.1.9.9.42.1.2.1.1.4";
        }

        leaf rttMonCtrlAdminThreshold {
          type int32 {
            range "0..2147483647";
          }
          units "milliseconds";
          description
           "This object defines an administrative threshold limit.
            If the RTT operation time exceeds this limit and if the 
            conditions specified in rttMonReactAdminThresholdType or 
            rttMonHistoryAdminFilter are satisfied, a
            threshold is generated.";
          smiv2:defval "5000";
          smiv2:max-access "read-write";
          smiv2:oid "1.3.6.1.4.1.9.9.42.1.2.1.1.5";
        }

        leaf rttMonCtrlAdminFrequency {
          type int32 {
            range "0..604800";
          }
          units "seconds";
          description
           "Specifies the duration between initiating each RTT
            operation. 
            
            This object cannot be set to a value which would be a 
            shorter duration than rttMonCtrlAdminTimeout.
            
            When the RttMonRttType specifies an operation that is
            synchronous in nature, it may happen that the next RTT 
            operation is blocked by a RTT operation which has not
            yet completed.  In this case, the value of a counter
            (rttMonStatsCollectBusies) in rttMonStatsCaptureTable is
            incremented in lieu of initiating a RTT operation, and 
            the next attempt will occur at the next
            rttMonCtrlAdminFrequency expiration. 
            
            NOTE:  When the rttMonCtrlAdminRttType object is defined 
                   to be 'pathEcho', setting this value to a small
                   value for your network size may cause an operation
                   attempt (or multiple attempts) to be started 
                   before the previous operation has finished.  In 
                   this situation the rttMonStatsCollectBusies object
                   will be incremented in lieu of initiating a new 
                   RTT operation, and the next attempt will occur at
                   the next rttMonCtrlAdminFrequency expiration.
            
            When the rttMonCtrlAdminRttType object is defined
            to be 'pathEcho', the suggested value for this object 
            is greater than rttMonCtrlAdminTimeout times the 
            maximum number of expected hops to the target.
            
            NOTE:  When the rttMonCtrlAdminRttType object is defined 
                   to be 'dhcp', the minimum allowed value for this
                   object is 10 seconds.  This restriction is due to
                   protocol limitations described in RFC 2131.";
          smiv2:defval "60";
          smiv2:max-access "read-write";
          smiv2:oid "1.3.6.1.4.1.9.9.42.1.2.1.1.6";
        }

        leaf rttMonCtrlAdminTimeout {
          type int32 {
            range "0..604800000";
          }
          units "milliseconds";
          description
           "Specifies the duration to wait for a RTT operation
            completion.  The value of this object cannot be set to 
            a value which would specify a duration exceeding 
            rttMonCtrlAdminFrequency.
            
            For connection oriented protocols, this may cause the
            connection to be closed by the probe.  Once closed, it
            will be assumed that the connection reestablishment
            will be performed.  To prevent unwanted closure of
            connections, be sure to set this value to a realistic
            connection timeout.";
          smiv2:defval "5000";
          smiv2:max-access "read-write";
          smiv2:oid "1.3.6.1.4.1.9.9.42.1.2.1.1.7";
        }

        leaf rttMonCtrlAdminVerifyData {
          type boolean;
          description
           "When set to true, the resulting data in each RTT
            operation is compared with the expected data.  This
            includes checking header information (if possible) and
            exact packet size.  Any mismatch will be recorded in the
            rttMonStatsCollectVerifyErrors object.
            
            Some RttMonRttTypes may not support this option.  When
            a type does not support this option, the agent will 
            transition this object to false.  It is the management
            applications responsibility to check for this 
            transition.";
          smiv2:defval "false";
          smiv2:max-access "read-write";
          smiv2:oid "1.3.6.1.4.1.9.9.42.1.2.1.1.8";
        }

        leaf rttMonCtrlAdminStatus {
          type snmpv2-tc:RowStatus;
          description
           "The status of the conceptual RTT control row.
            
            In order for this object to become active, the following 
            row objects must be defined:  
             - rttMonCtrlAdminRttType
            Additionally:
             - for echo, pathEcho based on 'ipIcmpEcho' and dlsw probes
                rttMonEchoAdminProtocol and 
                rttMonEchoAdminTargetAddress;
             - for echo, pathEcho based on 'mplsLspPingAppl'
                rttMonEchoAdminProtocol, rttMonEchoAdminTargetAddress 
                and rttMonEchoAdminLSPFECType
             - for udpEcho, tcpConnect and jitter probes
                rttMonEchoAdminTargetAddress and
                rttMonEchoAdminTargetPort
             - for http and ftp probe
                rttMonEchoAdminURL 
             - for dns probe
                rttMonEchoAdminTargetAddressString 
                rttMonEchoAdminNameServer 
             - dhcp probe doesn't require any additional objects
            
            All other objects can assume default values. The 
            conceptual Rtt control row will be placed into a 
            'pending' state (via the rttMonCtrlOperState object)
            if rttMonScheduleAdminRttStartTime is not specified.
            
            Most conceptual Rtt control row objects cannot be 
            modified once this conceptual Rtt control row has been 
            created.  The objects that can change are the following:
            
             - Objects in the rttMonReactAdminTable can be modified
               as needed without setting this object to 
               'notInService'.
             - Objects in the rttMonScheduleAdminTable can be 
               modified only when this object has the value of
               'notInService'.
             - The rttMonCtrlOperState can be modified to control
               the state of the probe.
            
            Once this object is in 'active' status, it cannot be 
            set to 'notInService' while the rttMonCtrlOperState
            is in 'active' state.  Thus the rttMonCtrlOperState 
            object must be transitioned first. 
            
            This object can be set to 'destroy' from any value
            at any time.";
          smiv2:max-access "read-write";
          smiv2:oid "1.3.6.1.4.1.9.9.42.1.2.1.1.9";
        }

        leaf rttMonCtrlAdminNvgen {
          type boolean;
          description
           "When set to true, this entry will be shown in
            'show running' command and can be saved into
            Non-volatile memory.";
          smiv2:defval "false";
          smiv2:max-access "read-write";
          smiv2:oid "1.3.6.1.4.1.9.9.42.1.2.1.1.10";
        }

        leaf rttMonCtrlAdminGroupName {
          type snmp-framework:SnmpAdminString {
            length "0..64";
          }
          description
           "If the operation is created through auto measure group
            creation, then this string will specify the group name
            to which this operation is associated.";
          smiv2:defval "";
          smiv2:max-access "read-only";
          smiv2:oid "1.3.6.1.4.1.9.9.42.1.2.1.1.11";
        }
      }
    }

    container rttMonEchoAdminTable {
      description
       "A table that contains Round Trip Time (RTT) specific
        definitions.
        
        This table is controlled via the 
        rttMonCtrlAdminTable.  Entries in this table are
        created via the rttMonCtrlAdminStatus object.";
      smiv2:oid "1.3.6.1.4.1.9.9.42.1.2.2";

      list rttMonEchoAdminEntry {
        key "rttMonCtrlAdminIndex";
        description
         "A list of objects that define specific configuration for
          RttMonRttType conceptual Rtt control rows.";
        smiv2:oid "1.3.6.1.4.1.9.9.42.1.2.2.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonEchoAdminProtocol {
          type cisco-rttmon:RttMonProtocol;
          description
           "Specifies the protocol to be used to perform the RTT
            operation. The following list defines what protocol 
            should be used for each probe type:
            
            echo, pathEcho   - ipIcmpEcho / mplsLspPingAppl
            udpEcho          - ipUdpEchoAppl
            tcpConnect       - ipTcpConn
            http             - httpAppl
            jitter           - jitterAppl
            dlsw             - dlswAppl
            dhcp             - dhcpAppl
            ftp              - ftpAppl
            mplsLspPing      - mplsLspPingAppl
            voip             - voipAppl
            video            - videoAppl
            
            When this protocol does not support the type, a 'badValue'
            error will be returned.";
          smiv2:defval "notApplicable";
          smiv2:max-access "read-write";
          smiv2:oid "1.3.6.1.4.1.9.9.42.1.2.2.1.1";
        }

        leaf rttMonEchoAdminTargetAddress {
          type cisco-rttmon:RttMonTargetAddress;
          description
           "A string which specifies the address of the target.";
          smiv2:defval "";
          smiv2:max-access "read-write";
          smiv2:oid "1.3.6.1.4.1.9.9.42.1.2.2.1.2";
        }

        leaf rttMonEchoAdminPktDataRequestSize {
          type int32 {
            range "0..16384";
          }
          units "octets";
          description
           "This object represents the number of octets to be
            placed into the ARR Data portion of the request 
            message, when using SNA protocols.
            
            For non-ARR protocols' RTT request/responses, 
            this value represents the native payload size.
            
            REMEMBER:  The ARR Header overhead is not included 
                       in this value.
            
            For echo probes the total packet size = (IP header(20) + 
            ICMP header(8) + 8 (internal timestamps) + request size).
            
            For echo and pathEcho default request size is 28.
            For udp probe, default request size is 16 and for jitter 
            probe it is 32. For dlsw probes default request size is 0.
            
            The minimum request size for echo and pathEcho is 28 bytes,
            for udp it is 4 and for jitter it is 16.
            For udp and jitter probes the maximum request size is 1500.
            
            For ethernetPing the default request size is 66.
            For ethernetJitter the default request size is 51.";
          smiv2:defval "1";
          smiv2:max-access "read-write";
          smiv2:oid "1.3.6.1.4.1.9.9.42.1.2.2.1.3";
        }

        leaf rttMonEchoAdminPktDataResponseSize {
          type int32 {
            range "0..16384";
          }
          description
           "This object represents the number of octets to be
            placed into the ARR Data portion of the response message.
            This value is passed to the RTT Echo Server via a
            field in the ARR Header.
            
            For non-ARR RTT request/response (i.e. ipIcmpecho)
            this value will be set by the agent to match the
            size of rttMonEchoAdminPktDataRequestSize, when
            native payloads are supported.
            
            REMEMBER:  The ARR Header overhead is not included 
                       in this value.
            
            This object is only supported by SNA protocols.";
          smiv2:defval "0";
          smiv2:max-access "read-write";
          smiv2:oid "1.3.6.1.4.1.9.9.42.1.2.2.1.4";
        }

        leaf rttMonEchoAdminTargetPort {
          type int32 {
            range "0..65536";
          }
          description
           "This object represents the target's port number. This
            object is applicable to udpEcho, tcpConnect and jitter probes.";
          smiv2:defval "0";
          smiv2:max-access "read-write";
          smiv2:oid "1.3.6.1.4.1.9.9.42.1.2.2.1.5";
        }

        leaf rttMonEchoAdminSourceAddress {
          type cisco-rttmon:RttMonTargetAddress;
          description
           "A string which specifies the IP address of the source.
            This object is applicable to all probes except dns, dlsw 
            and sna.";
          smiv2:defval "";
          smiv2:max-access "read-write";
          smiv2:oid "1.3.6.1.4.1.9.9.42.1.2.2.1.6";
        }

        leaf rttMonEchoAdminSourcePort {
          type int32 {
            range "0..65536";
          }
          description
           "This object represents the source's port number. If this
            object is not specified, the application will get a 
            port allocated by the system. This object is applicable 
            to all probes except dns, dlsw and sna.";
          smiv2:defval "0";
          smiv2:max-access "read-write";
          smiv2:oid "1.3.6.1.4.1.9.9.42.1.2.2.1.7";
        }

        leaf rttMonEchoAdminControlEnable {
          type boolean;
          description
           "If this object is enabled, then the RTR application
            will send control messages to a responder, residing on the 
            target router to respond to the data request packets being 
            sent by the source router. This object is not applicable to 
            echo, pathEcho, dns and http probes.";
          smiv2:defval "true";
          smiv2:max-access "read-write";
          smiv2:oid "1.3.6.1.4.1.9.9.42.1.2.2.1.8";
        }

        leaf rttMonEchoAdminTOS {
          type int32 {
            range "0..255";
          }
          description
           "This object represents the type of service octet in an
            IP header. This object is not applicable to dhcp, dns, 
            ethernetPing and ethernetJitter.";
          reference
           "Refer to the following documents for TOS definition.
            RFC791/1349  for IPv4, IPv6, 
            draft-ietf-diffserv-header-02.txt";
          smiv2:defval "0";
          smiv2:max-access "read-write";
          smiv2:oid "1.3.6.1.4.1.9.9.42.1.2.2.1.9";
        }

        leaf rttMonEchoAdminLSREnable {
          type boolean;
          description
           "If this object is enabled then it means that the application
            calculates response time for a specific path, defined in
            rttMonEchoPathAdminEntry. This object is applicable to echo 
            probe only.";
          smiv2:defval "false";
          smiv2:max-access "read-only";
          smiv2:oid "1.3.6.1.4.1.9.9.42.1.2.2.1.10";
        }

        leaf rttMonEchoAdminTargetAddressString {
          type snmpv2-tc:DisplayString;
          description
           "A string which specifies the address of the target. This string
            can be in IP address format or a hostname. This object
            is applicable to dns probe only.";
          smiv2:defval "";
          smiv2:max-access "read-write";
          smiv2:oid "1.3.6.1.4.1.9.9.42.1.2.2.1.11";
        }

        leaf rttMonEchoAdminNameServer {
          type cisco-rttmon:RttMonTargetAddress;
          description
           "A string which specifies the ip address of the name-server.
            This object is applicable to dns probe only.";
          smiv2:defval "";
          smiv2:max-access "read-write";
          smiv2:oid "1.3.6.1.4.1.9.9.42.1.2.2.1.12";
        }

        leaf rttMonEchoAdminOperation {
          type cisco-rttmon:RttMonOperation;
          description
           "A code that represents the specific type of RTT operation.
            This object is applicable to http and ftp probe only.";
          smiv2:max-access "read-write";
          smiv2:oid "1.3.6.1.4.1.9.9.42.1.2.2.1.13";
        }

        leaf rttMonEchoAdminHTTPVersion {
          type snmpv2-tc:DisplayString {
            length "3..10";
          }
          description
           "A string which specifies the version number of the HTTP
            Server.  The syntax for the version string is 
            <major number>.<minor number> An example would be 1.0, 
            1.1 etc.,.  This object is applicable to http probe only.";
          smiv2:defval "1.0";
          smiv2:max-access "read-write";
          smiv2:oid "1.3.6.1.4.1.9.9.42.1.2.2.1.14";
        }

        leaf rttMonEchoAdminURL {
          type snmpv2-tc:DisplayString;
          description
           "A string which represents the URL to which a HTTP probe should
            communicate with. This object is applicable to http probe only.";
          smiv2:defval "";
          smiv2:max-access "read-write";
          smiv2:oid "1.3.6.1.4.1.9.9.42.1.2.2.1.15";
        }

        leaf rttMonEchoAdminCache {
          type boolean;
          description
           "If this object is false then it means that HTTP request should
            not download cached pages. This means that the request should 
            be forwarded to the origin server. This object is applicable
            to http probe only.";
          smiv2:defval "true";
          smiv2:max-access "read-write";
          smiv2:oid "1.3.6.1.4.1.9.9.42.1.2.2.1.16";
        }

        leaf rttMonEchoAdminInterval {
          type int32 {
            range "0..60000";
          }
          units "milliseconds";
          description
           "This value represents the inter-packet delay between packets
            and is in milliseconds. This value is currently used for 
            Jitter probe. This object is applicable to jitter probe only.";
          smiv2:defval "20";
          smiv2:max-access "read-write";
          smiv2:oid "1.3.6.1.4.1.9.9.42.1.2.2.1.17";
        }

        leaf rttMonEchoAdminNumPackets {
          type int32;
          description
           "This value represents the number of packets that need to be
            transmitted. This value is currently used for Jitter probe. 
            This object is applicable to jitter probe only.";
          smiv2:defval "10";
          smiv2:max-access "read-write";
          smiv2:oid "1.3.6.1.4.1.9.9.42.1.2.2.1.18";
        }

        leaf rttMonEchoAdminProxy {
          type snmpv2-tc:DisplayString;
          description
           "This string represents the proxy server information.
            This object is applicable to http probe only.";
          smiv2:defval "";
          smiv2:max-access "read-write";
          smiv2:oid "1.3.6.1.4.1.9.9.42.1.2.2.1.19";
        }

        leaf rttMonEchoAdminString1 {
          type snmpv2-tc:DisplayString;
          description
           "This string stores the content of HTTP raw request.
            If the request cannot fit into String1 then it should 
            be split and put in Strings 1 through 5.
            
            This string stores the content of the DHCP raw option
            data.  The raw DHCP option data must be in HEX.
            If an odd number of characters are specified, a 0
            will be appended to the end of the string.  Only
            DHCP option 82 (decimal) is allowed.
            Here is an example of a valid string:
            5208010610005A6F1234
            Only rttMonEchoAdminString1 is used for dhcp, Strings
            1 through 5 are not used.
            
            This object is applicable to http and dhcp probe 
            types only.";
          smiv2:defval "";
          smiv2:max-access "read-write";
          smiv2:oid "1.3.6.1.4.1.9.9.42.1.2.2.1.20";
        }

        leaf rttMonEchoAdminString2 {
          type snmpv2-tc:DisplayString;
          description
           "This string stores the content of HTTP raw request.
            rttMonEchoAdminString1-5 are concatenated to 
            form the HTTP raw request used in the RTT operation.
            This object is applicable to http probe only.";
          smiv2:defval "";
          smiv2:max-access "read-write";
          smiv2:oid "1.3.6.1.4.1.9.9.42.1.2.2.1.21";
        }

        leaf rttMonEchoAdminString3 {
          type snmpv2-tc:DisplayString;
          description
           "This string stores the content of HTTP raw request.
            rttMonEchoAdminString1-5 are concatenated to 
            form the HTTP raw request used in the RTT operation.
            This object is applicable to http probe only.";
          smiv2:defval "";
          smiv2:max-access "read-write";
          smiv2:oid "1.3.6.1.4.1.9.9.42.1.2.2.1.22";
        }

        leaf rttMonEchoAdminString4 {
          type snmpv2-tc:DisplayString;
          description
           "This string stores the content of HTTP raw request.
            rttMonEchoAdminString1-5 are concatenated to 
            form the HTTP raw request used in the RTT operation.
            This object is applicable to http probe only.";
          smiv2:defval "";
          smiv2:max-access "read-write";
          smiv2:oid "1.3.6.1.4.1.9.9.42.1.2.2.1.23";
        }

        leaf rttMonEchoAdminString5 {
          type snmpv2-tc:DisplayString;
          description
           "This string stores the content of HTTP raw request.
            rttMonEchoAdminString1-5 are concatenated to 
            form the HTTP raw request used in the RTT operation.
            This object is applicable to http probe only.";
          smiv2:defval "";
          smiv2:max-access "read-write";
          smiv2:oid "1.3.6.1.4.1.9.9.42.1.2.2.1.24";
        }

        leaf rttMonEchoAdminMode {
          type cisco-rttmon:RttMonOperation;
          description
           "A code that represents the specific type of RTT operation.
            This object is applicable to ftp probe only.";
          smiv2:defval "ftpPassive";
          smiv2:max-access "read-write";
          smiv2:oid "1.3.6.1.4.1.9.9.42.1.2.2.1.25";
        }

        leaf rttMonEchoAdminVrfName {
          type binary {
            length "0..32";
          }
          description
           "This field is used to specify the VPN name in
            which the RTT operation will be used. For regular RTT
            operation this field should not be configured. The agent 
            will use this field to identify the VPN routing Table for
            this operation.";
          smiv2:defval "";
          smiv2:max-access "read-write";
          smiv2:oid "1.3.6.1.4.1.9.9.42.1.2.2.1.26";
        }

        leaf rttMonEchoAdminCodecType {
          type cisco-rttmon:RttMonCodecType;
          description
           "Specifies the codec type to be used with jitter probe. This is
            applicable only for the jitter probe.
            
            If codec-type is configured the following parameters cannot be 
            configured.
            rttMonEchoAdminPktDataRequestSize
            rttMonEchoAdminInterval
            rttMonEchoAdminNumPackets";
          smiv2:max-access "read-write";
          smiv2:oid "1.3.6.1.4.1.9.9.42.1.2.2.1.27";
        }

        leaf rttMonEchoAdminCodecInterval {
          type int32 {
            range "0..60000";
          }
          units "milliseconds";
          description
           "This field represents the inter-packet delay between
            packets and is in milliseconds. This object is applicable
            only to jitter probe which uses codec type.";
          smiv2:max-access "read-write";
          smiv2:oid "1.3.6.1.4.1.9.9.42.1.2.2.1.28";
        }

        leaf rttMonEchoAdminCodecPayload {
          type int32 {
            range "0..16384";
          }
          units "octets";
          description
           "This object represents the number of octets that needs to be
            placed into the Data portion of the message. This value is
            used only for jitter probe which uses codec type.";
          smiv2:max-access "read-write";
          smiv2:oid "1.3.6.1.4.1.9.9.42.1.2.2.1.29";
        }

        leaf rttMonEchoAdminCodecNumPackets {
          type int32 {
            range "0..60000";
          }
          description
           "This value represents the number of packets that need to be
            transmitted. This value is used only for jitter probe which
            uses codec type.";
          smiv2:max-access "read-write";
          smiv2:oid "1.3.6.1.4.1.9.9.42.1.2.2.1.30";
        }

        leaf rttMonEchoAdminICPIFAdvFactor {
          type int32 {
            range "0..20";
          }
          description
           "The advantage factor is dependant on the type of access and
            how the service is to be used.
            Conventional Wire-line     0
            Mobility within Building    5
            Mobility within geographic area  10
            Access to hard-to-reach location   20
            
            This will be used while calculating the ICPIF values
            This valid only for Jitter while calculating the ICPIF value";
          smiv2:defval "0";
          smiv2:max-access "read-write";
          smiv2:oid "1.3.6.1.4.1.9.9.42.1.2.2.1.31";
        }

        leaf rttMonEchoAdminLSPFECType {
          type enumeration {
            enum "ldpIpv4Prefix" {
              value "1";
            }
          }
          description
           "The type of the target FEC for the RTT 'echo' and 'pathEcho'
            operations based on 'mplsLspPingAppl' RttMonProtocol.
            
            ldpIpv4Prefix   - LDP IPv4 prefix.";
          smiv2:max-access "read-write";
          smiv2:oid "1.3.6.1.4.1.9.9.42.1.2.2.1.32";
        }

        leaf rttMonEchoAdminLSPSelector {
          type cisco-rttmon:RttMonTargetAddress;
          description
           "A string which specifies a valid 127/8 address. This address
            is of the form 127.x.y.z.
            This address is not used to route the MPLS echo packet to the
            destination but is used for load balancing in cases where the
            IP payload's destination address is used for load balancing.";
          smiv2:defval "7F 00 00 01";
          smiv2:max-access "read-write";
          smiv2:oid "1.3.6.1.4.1.9.9.42.1.2.2.1.33";
        }

        leaf rttMonEchoAdminLSPReplyMode {
          type cisco-rttmon:RttMonLSPPingReplyMode;
          description
           "This object specifies the reply mode for the LSP Echo
            requests.";
          smiv2:defval "replyIpv4Udp";
          smiv2:max-access "read-write";
          smiv2:oid "1.3.6.1.4.1.9.9.42.1.2.2.1.34";
        }

        leaf rttMonEchoAdminLSPTTL {
          type int32 {
            range "0..255";
          }
          description
           "This object represents the TTL setting for MPLS echo request
            packets. For ping operation this represents the TTL value to
            be set in the echo request packet. For trace operation it
            represent the maximum ttl value that can be set in the echo
            request packets starting with TTL=1.
            
            For 'echo' based on mplsLspPingAppl the default TTL will be
            set to 255, and for 'pathEcho' based on mplsLspPingAppl the
            default will be set to 30.
            
            Note: This object cannot be set to the value of 0. The
            default value of 0 signifies the default TTL values to be
            used for 'echo' and 'pathEcho' based on 'mplsLspPingAppl'.";
          smiv2:defval "0";
          smiv2:max-access "read-write";
          smiv2:oid "1.3.6.1.4.1.9.9.42.1.2.2.1.35";
        }

        leaf rttMonEchoAdminLSPExp {
          type int32 {
            range "0..7";
          }
          description
           "This object represents the EXP value that needs to be
            put as precedence bit in the MPLS echo request IP header.";
          smiv2:defval "0";
          smiv2:max-access "read-write";
          smiv2:oid "1.3.6.1.4.1.9.9.42.1.2.2.1.36";
        }

        leaf rttMonEchoAdminPrecision {
          type enumeration {
            enum "milliseconds" {
              value "1";
            }
            enum "microseconds" {
              value "2";
            }
          }
          description
           "This object specifies the accuracy of statistics that
            needs to be calculated
            milliseconds - The accuracy of stats will be of milliseconds
            microseconds - The accuracy of stats will be in microseconds.
            This value can be set only for jitter operation";
          smiv2:defval "milliseconds";
          smiv2:max-access "read-write";
          smiv2:oid "1.3.6.1.4.1.9.9.42.1.2.2.1.37";
        }

        leaf rttMonEchoAdminProbePakPriority {
          type enumeration {
            enum "normal" {
              value "1";
            }
            enum "high" {
              value "2";
            }
          }
          description
           "This object specifies the priority that will be assigned
            to probe packet.  This value can be set only for jitter 
            operation";
          smiv2:defval "normal";
          smiv2:max-access "read-write";
          smiv2:oid "1.3.6.1.4.1.9.9.42.1.2.2.1.38";
        }

        leaf rttMonEchoAdminOWNTPSyncTolAbs {
          type int32;
          units "microseconds";
          description
           "This object specifies the total clock synchronization error
            on source and responder that is considered acceptable for 
            oneway measurement when NTP is used as clock synchronization 
            mechanism.  The total clock synchronization error is sum of
            NTP offsets on source and responder. The value specified is 
            microseconds. This value can be set only for jitter operation 
            with precision of microsecond.";
          smiv2:defval "0";
          smiv2:max-access "read-write";
          smiv2:oid "1.3.6.1.4.1.9.9.42.1.2.2.1.39";
        }

        leaf rttMonEchoAdminOWNTPSyncTolPct {
          type int32 {
            range "0..100";
          }
          description
           "This object specifies the total clock synchronization error
            on source and responder that is considered acceptable for 
            oneway measurement when NTP is used as clock synchronization 
            mechanism.  The total clock synchronization error is sum of 
            NTP offsets on source and responder. The value is expressed 
            as the percentage of actual oneway latency that is measured. 
            This value can be set only for jitter operation with precision 
            of microsecond.";
          smiv2:defval "0";
          smiv2:max-access "read-write";
          smiv2:oid "1.3.6.1.4.1.9.9.42.1.2.2.1.40";
        }

        leaf rttMonEchoAdminOWNTPSyncTolType {
          type enumeration {
            enum "percent" {
              value "1";
            }
            enum "absolute" {
              value "2";
            }
          }
          description
           "This object specifies whether the value in specified for oneway
            NTP sync tolerance is absolute value or percent value";
          smiv2:defval "percent";
          smiv2:max-access "read-write";
          smiv2:oid "1.3.6.1.4.1.9.9.42.1.2.2.1.41";
        }

        leaf rttMonEchoAdminCalledNumber {
          type snmp-framework:SnmpAdminString {
            length "0..24";
          }
          description
           "This string stores the called number of post dial delay.
            This object is applicable to voip post dial delay probe only.
            The number will be like the one actualy the user could dial.
            It has the number required by the local country dial plan, plus
            E.164 number. The maximum length is 24 digits. Only digit (0-9)
            is allowed.";
          smiv2:defval "";
          smiv2:max-access "read-write";
          smiv2:oid "1.3.6.1.4.1.9.9.42.1.2.2.1.42";
        }

        leaf rttMonEchoAdminDetectPoint {
          type cisco-rttmon:RttMonOperation;
          description
           "A code that represents the detect point of post dial delay.
            This object is applicable to SAA post dial delay probe only.";
          smiv2:defval "voipDTAlertRinging";
          smiv2:max-access "read-write";
          smiv2:oid "1.3.6.1.4.1.9.9.42.1.2.2.1.43";
        }

        leaf rttMonEchoAdminGKRegistration {
          type boolean;
          description
           "A boolean that represents VoIP GK registration delay.
            This object is applicable to SAA GK registration delay 
            probe only.";
          smiv2:defval "false";
          smiv2:max-access "read-write";
          smiv2:oid "1.3.6.1.4.1.9.9.42.1.2.2.1.44";
        }

        leaf rttMonEchoAdminSourceVoicePort {
          type snmpv2-tc:DisplayString;
          description
           "A string which specifies the voice-port on the source gateway.
            This object is applicable to RTP probe only.";
          smiv2:defval "";
          smiv2:max-access "read-write";
          smiv2:oid "1.3.6.1.4.1.9.9.42.1.2.2.1.45";
        }

        leaf rttMonEchoAdminCallDuration {
          type int32 {
            range "1..600";
          }
          description
           "Duration of RTP/Video Probe session.
            This object is applicable to RTP and Video probe.";
          smiv2:defval "60";
          smiv2:max-access "read-write";
          smiv2:oid "1.3.6.1.4.1.9.9.42.1.2.2.1.46";
        }

        leaf rttMonEchoAdminLSPReplyDscp {
          type int32 {
            range "0..63|255";
          }
          description
           "This object specifies the DSCP value to be set in the IP header
            of the LSP echo reply packet.
            The value of this object will be in range of DiffServ codepoint
            values between 0 to 63.
            
            Note: This object cannot be set to value of 255. This default
            value specifies that DSCP is not set for this row.";
          smiv2:defval "255";
          smiv2:max-access "read-write";
          smiv2:oid "1.3.6.1.4.1.9.9.42.1.2.2.1.47";
        }

        leaf rttMonEchoAdminLSPNullShim {
          type boolean;
          description
           "This object specifies if the explicit-null label is to be added
            to LSP echo requests which are sent while performing RTT
            operation.";
          smiv2:defval "false";
          smiv2:max-access "read-write";
          smiv2:oid "1.3.6.1.4.1.9.9.42.1.2.2.1.48";
        }

        leaf rttMonEchoAdminTargetMPID {
          type cisco-ether:CfmMepid;
          description
           "This object specifies the destination maintenance point ID.
            It is only applicable to ethernetPing and ethernetJitter 
            operation. It will be set to 0 for other types of 
            operations.";
          smiv2:max-access "read-write";
          smiv2:oid "1.3.6.1.4.1.9.9.42.1.2.2.1.49";
        }

        leaf rttMonEchoAdminTargetDomainName {
          type snmp-framework:SnmpAdminString;
          description
           "This object specifies the name of the domain in which the
            destination maintenance point lies. It is only applicable to 
            ethernetPing and ethernetJitter operation.";
          smiv2:defval "";
          smiv2:max-access "read-write";
          smiv2:oid "1.3.6.1.4.1.9.9.42.1.2.2.1.50";
        }

        leaf rttMonEchoAdminTargetVLAN {
          type q-bridge:VlanId;
          description
           "This object specifies the ID of the VLAN in which the
            destination maintenance point lies. It is only applicable to 
            ethernetPing and ethernetJitter operation. 
            It will be set to 0 for other types of operations.";
          smiv2:max-access "read-write";
          smiv2:oid "1.3.6.1.4.1.9.9.42.1.2.2.1.51";
        }

        leaf rttMonEchoAdminEthernetCOS {
          type cisco-qos:QosLayer2Cos {
            range "0..7";
          }
          description
           "This object specifies the class of service in an Ethernet
            packet header. It is only applicable to ethernetPing and 
            ethernetJitter operation.";
          smiv2:defval "0";
          smiv2:max-access "read-write";
          smiv2:oid "1.3.6.1.4.1.9.9.42.1.2.2.1.52";
        }

        leaf rttMonEchoAdminLSPVccvID {
          type int32 {
            range "0..2147483647";
          }
          description
           "This object specifies MPLS LSP pseudowire VCCV ID
            values between 1 to 2147483647.
            
            Note: This object cannot be set to value of 0. This default
            value specifies that VCCV is not set for this row.";
          smiv2:defval "0";
          smiv2:max-access "read-write";
          smiv2:oid "1.3.6.1.4.1.9.9.42.1.2.2.1.53";
        }

        leaf rttMonEchoAdminTargetEVC {
          type snmp-framework:SnmpAdminString {
            length "0..100";
          }
          description
           "This object specifies the Ethernet Virtual Connection in
            which the destination maintenance point lies. It is only 
            applicable to ethernetPing and ethernetJitter operation. 
            It will be set to NULL for other types of operations.";
          smiv2:defval "";
          smiv2:max-access "read-write";
          smiv2:oid "1.3.6.1.4.1.9.9.42.1.2.2.1.54";
        }

        leaf rttMonEchoAdminTargetMEPPort {
          type boolean;
          description
           "This object specifies that Port Level CFM testing towards an
            Outward/Down MEP will be used. It is only applicable to 
            ethernetPing and ethernetJitter operation. 
            It will be set to NULL for other types of operations.";
          smiv2:defval "false";
          smiv2:max-access "read-write";
          smiv2:oid "1.3.6.1.4.1.9.9.42.1.2.2.1.55";
        }

        leaf rttMonEchoAdminVideoTrafficProfile {
          type snmp-framework:SnmpAdminString {
            length "0..255";
          }
          description
           "A string which represents the profile name to which a video
            probe should use. This object is applicable to video probe
            only.";
          smiv2:defval "";
          smiv2:max-access "read-write";
          smiv2:oid "1.3.6.1.4.1.9.9.42.1.2.2.1.56";
        }

        leaf rttMonEchoAdminDscp {
          type inet:dscp;
          description
           "This object represents the Differentiated Service Code Point
            (DSCP) QoS marking in the generated synthetic packets.
            
            Value - DiffServ Class
                0 - BE (default)
               10 - AF11
               12 - AF12
               14 - AF13
               18 - AF21
               20 - AF22
               22 - AF23
               26 - AF31
               28 - AF32
               30 - AF33
               34 - AF41
               36 - AF42
               38 - AF43
                8 - CS1
               16 - CS2
               24 - CS3
               32 - CS4
               40 - CS5
               48 - CS6
               56 - CS7
               46 - EF";
          reference
           "RFC 2474, RFC 2780";
          smiv2:defval "0";
          smiv2:max-access "read-write";
          smiv2:oid "1.3.6.1.4.1.9.9.42.1.2.2.1.57";
        }

        leaf rttMonEchoAdminReserveDsp {
          type enumeration {
            enum "be" {
              value "1";
            }
            enum "gs" {
              value "2";
            }
            enum "na" {
              value "3";
            }
          }
          description
           "This object represents the video traffic generation source.
            
            be : best effort using DSP but without reservation
            gs : guaranteed service using DSP with reservation
            na : not applicable for not using DSP";
          smiv2:defval "na";
          smiv2:max-access "read-write";
          smiv2:oid "1.3.6.1.4.1.9.9.42.1.2.2.1.58";
        }

        leaf rttMonEchoAdminInputInterface {
          type if-mib:InterfaceIndexOrZero;
          description
           "This object represents the network input interface on the
            sender router where the synthetic packets are received from the
            emulated endpoint source. This is used for path congruence with
            correct feature processing at the sender router.
            
            The user can get the InterfaceIndex number from ifIndex object
            by looking up in ifTable. In fact, it should be useful to first
            get the entry by the augmented table ifXTable which has ifName
            object which matches the interface name used on the router or
            switch equipment console.";
          smiv2:defval "36991728";
          smiv2:max-access "read-write";
          smiv2:oid "1.3.6.1.4.1.9.9.42.1.2.2.1.59";
        }

        leaf rttMonEchoAdminEmulateSourceAddress {
          type cisco-rttmon:RttMonTargetAddress;
          description
           "This object specifies the IP address of the emulated source
            from which the synthetic packets would be generated. If this
            object is not specified, the emulated source IP address will by
            default be the same as rttMonEchoAdminSourceAddress. This object
            is applicable to video probes.";
          smiv2:max-access "read-write";
          smiv2:oid "1.3.6.1.4.1.9.9.42.1.2.2.1.60";
        }

        leaf rttMonEchoAdminEmulateSourcePort {
          type int32 {
            range "0..65536";
          }
          description
           "This object represents the port number of the emulated source
            from which the synthetic packets would be generated. If this
            object is not specified, the emulated source port number will by
            default be the same as rttMonEchoAdminSourcePort. This object is
            applicable to video probes.";
          smiv2:max-access "read-write";
          smiv2:oid "1.3.6.1.4.1.9.9.42.1.2.2.1.61";
        }

        leaf rttMonEchoAdminEmulateTargetAddress {
          type cisco-rttmon:RttMonTargetAddress;
          description
           "This object specifies the IP address of the emulated target by
            which the synthetic packets would be received. If this object is
            not specified, the emulated target IP address will by default be
            the same as rttMonEchoAdminTargetAddress. This object is
            applicable to video probes.";
          smiv2:max-access "read-write";
          smiv2:oid "1.3.6.1.4.1.9.9.42.1.2.2.1.62";
        }

        leaf rttMonEchoAdminEmulateTargetPort {
          type int32 {
            range "0..65536";
          }
          description
           "This object represents the port number of the emulated target
            by which the synthetic packets would be received. If this object
            is not specified, the emulated target port number will by
            default be the same as rttMonEchoAdminTargetPort. This object is
            applicable to video probes.";
          smiv2:max-access "read-write";
          smiv2:oid "1.3.6.1.4.1.9.9.42.1.2.2.1.63";
        }

        leaf rttMonEchoAdminTargetMacAddress {
          type yang:mac-address;
          description
           "This object indicates the MAC address of the target device.
            This object is only applicable for Y.1731 operations. 
            rttMonEchoAdminTargetMacAddress and rttMonEchoAdminTargetMPID
            may not be used in conjunction.";
          smiv2:max-access "read-only";
          smiv2:oid "1.3.6.1.4.1.9.9.42.1.2.2.1.64";
        }

        leaf rttMonEchoAdminSourceMacAddress {
          type yang:mac-address;
          description
           "This object indicates the MAC address of the source device.
            This object is only applicable for Y.1731 operations. 
            rttMonEchoAdminSourceMacAddress and rttMonEchoAdminSourceMPID
            may not be used in conjunction.";
          smiv2:max-access "read-only";
          smiv2:oid "1.3.6.1.4.1.9.9.42.1.2.2.1.65";
        }

        leaf rttMonEchoAdminSourceMPID {
          type cisco-ether:CfmMepid;
          description
           "This object indicates the source maintenance point ID.  It is
            only applicable to Y.1731 operation.  It will be set to zero for
            other types of opearations.  rttMonEchoAdminSourceMPID and
            rttMonEchoAdminSourceMacAddress may not be used in conjunction.";
          smiv2:max-access "read-only";
          smiv2:oid "1.3.6.1.4.1.9.9.42.1.2.2.1.66";
        }

        leaf rttMonEchoAdminEndPointListName {
          type snmp-framework:SnmpAdminString {
            length "1..64";
          }
          description
           "This object specifies the name of endpoint list which a probe
            uses to generate operations.";
          smiv2:defval "";
          smiv2:max-access "read-write";
          smiv2:oid "1.3.6.1.4.1.9.9.42.1.2.2.1.67";
        }

        leaf rttMonEchoAdminSSM {
          type boolean;
          description
           "This object specifies if Source Specific Multicast is to be
            added. This object is applicable to multicast probe only.";
          smiv2:defval "false";
          smiv2:max-access "read-write";
          smiv2:oid "1.3.6.1.4.1.9.9.42.1.2.2.1.68";
        }

        leaf rttMonEchoAdminControlRetry {
          type uint32 {
            range "1..5";
          }
          description
           "This object specifies the maximum number of retries for control message.";
          smiv2:defval "3";
          smiv2:max-access "read-write";
          smiv2:oid "1.3.6.1.4.1.9.9.42.1.2.2.1.69";
        }

        leaf rttMonEchoAdminControlTimeout {
          type uint32 {
            range "1..10000";
          }
          units "milliseconds";
          description
           "This object specifies the wait duration before control message
            timeout.";
          smiv2:defval "5000";
          smiv2:max-access "read-write";
          smiv2:oid "1.3.6.1.4.1.9.9.42.1.2.2.1.70";
        }

        leaf rttMonEchoAdminIgmpTreeInit {
          type uint32 {
            range "0..10";
          }
          description
           "This object specifies number of packets to be sent for
            multicast tree setup. This object is applicable to multicast
            probe only.";
          smiv2:defval "0";
          smiv2:max-access "read-write";
          smiv2:oid "1.3.6.1.4.1.9.9.42.1.2.2.1.71";
        }

        leaf rttMonEchoAdminEnableBurst {
          type boolean;
          description
           "This object indicates that packets will be sent in burst.";
          smiv2:defval "false";
          smiv2:max-access "read-only";
          smiv2:oid "1.3.6.1.4.1.9.9.42.1.2.2.1.72";
        }

        leaf rttMonEchoAdminAggBurstCycles {
          type int32;
          description
           "This object indicates the number of burst cycles to be sent
            during the aggregate interval. This value is currently used
            for Y1731 SLM(Synthetic Loss Measurment) probe.
            This object is applicable to Y1731 SLM probe only.";
          smiv2:defval "0";
          smiv2:max-access "read-only";
          smiv2:oid "1.3.6.1.4.1.9.9.42.1.2.2.1.73";
        }

        leaf rttMonEchoAdminLossRatioNumFrames {
          type int32;
          description
           "This object indicates the number of frames over which to
            calculate the frame loss ratio. This object is applicable 
            to Y1731 SLM probe only.";
          smiv2:defval "10";
          smiv2:max-access "read-only";
          smiv2:oid "1.3.6.1.4.1.9.9.42.1.2.2.1.74";
        }

        leaf rttMonEchoAdminAvailNumFrames {
          type int32;
          description
           "This object indicates the number of frames over which to
            calculate the availability. This object is applicable to
            Y1731 SLM probe only.";
          smiv2:defval "10";
          smiv2:max-access "read-only";
          smiv2:oid "1.3.6.1.4.1.9.9.42.1.2.2.1.75";
        }

        leaf rttMonEchoAdminTstampOptimization {
          type boolean;
          description
           "This object specifies whether timestamp optimization is
            enabled.
            
            When the value is 'true' then timestamp optimization is
            enabled.  The probe will utilize lower layer (Hardware/Packet
            Processor) timestamping values to improve accuracy of
            statistics.
            
            This value can be set only for udp jitter operation with
            precision of microsecond.";
          smiv2:defval "false";
          smiv2:max-access "read-write";
          smiv2:oid "1.3.6.1.4.1.9.9.42.1.2.2.1.76";
        }
      }
    }

    container rttMonFileIOAdminTable {
      status obsolete;
      description
       "A table of Round Trip Time (RTT) monitoring 'fileIO'
        specific definitions.
        
        When the RttMonRttType is not 'fileIO' this table is
        not valid.
        
        This table is controlled via the 
        rttMonCtrlAdminTable.  Entries in this table are
        created via the rttMonCtrlAdminStatus object.";
      smiv2:oid "1.3.6.1.4.1.9.9.42.1.2.3";

      list rttMonFileIOAdminEntry {
        key "rttMonCtrlAdminIndex";
        status obsolete;
        description
         "A list of objects that define specific configuration for
          'fileIO' RttMonRttType conceptual Rtt control rows.";
        smiv2:oid "1.3.6.1.4.1.9.9.42.1.2.3.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonFileIOAdminFilePath {
          type snmpv2-tc:DisplayString;
          status obsolete;
          description
           "The fully qualified file path that will be the target
            of the RTT operation.
            
            This value must match one of the rttMonApplPreConfigedName
            entries.";
          smiv2:defval "";
          smiv2:max-access "read-write";
          smiv2:oid "1.3.6.1.4.1.9.9.42.1.2.3.1.1";
        }

        leaf rttMonFileIOAdminSize {
          type enumeration {
            enum "n256" {
              value "1";
            }
            enum "n1k" {
              value "2";
            }
            enum "n64k" {
              value "3";
            }
            enum "n128k" {
              value "4";
            }
            enum "n256k" {
              value "5";
            }
          }
          units "bytes";
          status obsolete;
          description
           "The size of the file to write/read from the File
            Server.";
          smiv2:defval "n256";
          smiv2:max-access "read-write";
          smiv2:oid "1.3.6.1.4.1.9.9.42.1.2.3.1.2";
        }

        leaf rttMonFileIOAdminAction {
          type enumeration {
            enum "write" {
              value "1";
            }
            enum "read" {
              value "2";
            }
            enum "writeRead" {
              value "3";
            }
          }
          status obsolete;
          description
           "The File I/O action to be performed.";
          smiv2:defval "read";
          smiv2:max-access "read-write";
          smiv2:oid "1.3.6.1.4.1.9.9.42.1.2.3.1.3";
        }
      }
    }

    container rttMonScriptAdminTable {
      status obsolete;
      description
       "A table of Round Trip Time (RTT) monitoring 'script'
        specific definitions.
        
        When the RttMonRttType is not 'script' this table is
        not valid.
        
        This table is controlled via the
        rttMonCtrlAdminTable.  Entries in this table are
        created via the rttMonCtrlAdminStatus object.";
      smiv2:oid "1.3.6.1.4.1.9.9.42.1.2.4";

      list rttMonScriptAdminEntry {
        key "rttMonCtrlAdminIndex";
        status obsolete;
        description
         "A list of objects that define specific configuration for
          'script' RttMonRttType conceptual Rtt control rows.";
        smiv2:oid "1.3.6.1.4.1.9.9.42.1.2.4.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonScriptAdminName {
          type snmpv2-tc:DisplayString;
          status obsolete;
          description
           "This will be the Name of the Script that will be used to
            generate RTT operations.  
            
            This object must match one of the 
            rttMonApplPreConfigedName entries.";
          smiv2:defval "";
          smiv2:max-access "read-write";
          smiv2:oid "1.3.6.1.4.1.9.9.42.1.2.4.1.1";
        }

        leaf rttMonScriptAdminCmdLineParams {
          type snmpv2-tc:DisplayString;
          status obsolete;
          description
           "This will be the actual command line parameters
            passed to the rttMonScriptAdminName when being
            executed.";
          smiv2:defval "";
          smiv2:max-access "read-write";
          smiv2:oid "1.3.6.1.4.1.9.9.42.1.2.4.1.2";
        }
      }
    }

    container rttMonReactTriggerAdminTable {
      description
       "A table of which contains the list of conceptual RTT
        control rows that will start to collect data when a 
        reaction condition is violated and when 
        rttMonReactAdminActionType is set to one of the 
        following:
          -  triggerOnly
          -  trapAndTrigger
          -  nmvtAndTrigger
          -  trapNmvtAndTrigger
        or when a reaction condition is violated and when any of the
        row in rttMonReactTable has rttMonReactActionType as one of
        the following:
          - triggerOnly
          - trapAndTrigger
        
        The goal of this table is to define one or more 
        additional conceptual RTT control rows that will become
        active and start to collect additional history and
        statistics (depending on the rows configuration values),
        when a problem has been detected.
        
        If the conceptual RTT control row is undefined, and a 
        trigger occurs, no action will take place.  
        
        If the conceptual RTT control row is scheduled to start 
        at a later time, triggering that row will have no effect.
        
        If the conceptual RTT control row is currently active, 
        triggering that row will have no effect on that row, but 
        the rttMonReactTriggerOperState object will transition to 
        'active'.
        
        An entry in this table can only be triggered when
        it is not currently in a triggered state.  The
        object rttMonReactTriggerOperState will 
        reflect the state of each entry in this table.";
      smiv2:oid "1.3.6.1.4.1.9.9.42.1.2.11";

      list rttMonReactTriggerAdminEntry {
        key "rttMonCtrlAdminIndex rttMonReactTriggerAdminRttMonCtrlAdminIndex";
        description
         "A list of objects that will be triggered when
          a reaction condition is violated.";
        smiv2:oid "1.3.6.1.4.1.9.9.42.1.2.11.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonReactTriggerAdminRttMonCtrlAdminIndex {
          type int32 {
            range "1..2147483647";
          }
          description
           "This object points to a single conceptual Rtt control
            row.  If this row does not exist and this value is 
            triggered no action will result.
            
            The conceptual Rtt control row will be triggered for the 
            rttMonCtrlOperRttLife length.  If this conceptual Rtt
            control row is already active, rttMonCtrlOperRttLife will
            not be updated, and its life will continue as previously 
            defined.";
          smiv2:max-access "not-accessible";
          smiv2:oid "1.3.6.1.4.1.9.9.42.1.2.11.1.1";
        }

        leaf rttMonReactTriggerAdminStatus {
          type snmpv2-tc:RowStatus;
          description
           "This object is used to create Trigger entries.";
          smiv2:max-access "read-write";
          smiv2:oid "1.3.6.1.4.1.9.9.42.1.2.11.1.2";
        }
      }
    }

    container rttMonEchoPathAdminTable {
      description
       "A table to store the hop addresses in a Loose Source Routing
        path. Response times are computed along the specified path
        using ping.
        
        This maximum table size is limited by the size of the 
        maximum number of hop addresses that can fit in an IP header,
        which is 8. The object rttMonEchoPathAdminEntry will reflect 
        this tables maximum number of entries.
        
        This table is coupled with rttMonCtrlAdminStatus.";
      smiv2:oid "1.3.6.1.4.1.9.9.42.1.2.13";

      list rttMonEchoPathAdminEntry {
        key "rttMonCtrlAdminIndex rttMonEchoPathAdminHopIndex";
        description
         "A list of objects that define intermediate hop's IP Address.
          
          This entry can be added only if the rttMonCtrlAdminRttType is
          'echo'. The entry gets deleted when the corresponding RTR entry,
          which has an index of rttMonCtrlAdminIndex, is deleted.";
        smiv2:oid "1.3.6.1.4.1.9.9.42.1.2.13.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonEchoPathAdminHopIndex {
          type int32 {
            range "1..8";
          }
          description
           "Uniquely identifies a row in the rttMonEchoPathAdminTable.
            This number represents the hop address number in a specific 
            ping path. All the indicies should start from 1 and must be 
            contiguous ie., entries should be 
            (say rttMonCtrlAdminIndex = 1) 
            1.1, 1.2, 1.3, they cannot be 1.1, 1.2, 1.4";
          smiv2:max-access "not-accessible";
          smiv2:oid "1.3.6.1.4.1.9.9.42.1.2.13.1.1";
        }

        leaf rttMonEchoPathAdminHopAddress {
          type cisco-rttmon:RttMonTargetAddress;
          description
           "A string which specifies the address of an intermediate hop's
            IP Address for a RTT 'echo' operation";
          smiv2:max-access "read-write";
          smiv2:oid "1.3.6.1.4.1.9.9.42.1.2.13.1.2";
        }
      }
    }

    container rttMonGrpScheduleAdminTable {
      description
       "A table of Round Trip Time (RTT) monitoring group scheduling
        specific definitions.
        This table is used to create a conceptual group scheduling
        control row. The entries in this control row contain objects
        used to define group schedule configuration parameters.
        
        The objects of this table will be used to schedule a group of
        probes identified by the conceptual rows of the
        rttMonCtrlAdminTable.";
      smiv2:oid "1.3.6.1.4.1.9.9.42.1.2.14";

      list rttMonGrpScheduleAdminEntry {
        key "rttMonGrpScheduleAdminIndex";
        description
         "A list of objects that define a conceptual group scheduling
          control row.";
        smiv2:oid "1.3.6.1.4.1.9.9.42.1.2.14.1";

        leaf rttMonGrpScheduleAdminIndex {
          type int32 {
            range "1..2147483647";
          }
          description
           "Uniquely identifies a row in the
            rttMonGrpScheduleAdminTable.
            
            This is a pseudo-random number selected by the management
            station when creating a row via the
            rttMonGrpScheduleAdminStatus object. If the pseudo-random
            number is already in use an 'inconsistentValue' return code
            will be returned when set operation is attempted.";
          smiv2:max-access "not-accessible";
          smiv2:oid "1.3.6.1.4.1.9.9.42.1.2.14.1.1";
        }

        leaf rttMonGrpScheduleAdminProbes {
          type snmpv2-tc:DisplayString {
            length "0..200";
          }
          description
           "A string which holds the different probes which are to be
            group scheduled. The probes can be specified in the following
            forms.
            (a) Individual ID's with comma separated as 23,45,34.
            (b) Range form including hyphens with multiple ranges being
                separated by a comma as 1-10,12-34.
            (c) Mix of the above two forms as 1,2,4-10,12,15,19-25.
            
            Any whitespace in the string is considered an error. Duplicates
            and overlapping ranges as an example 1,2,3,2-10 are considered
            fine. For a single range like 1-20 the upper value (in this
            example 20) must be greater than lower value (1), otherwise it's
            treated as an error. The agent will not normalize the list e.g.,
            it will not change 1,2,1-10 or even 1,2,3,4,5,6.. to 1-10.";
          smiv2:defval "";
          smiv2:max-access "read-write";
          smiv2:oid "1.3.6.1.4.1.9.9.42.1.2.14.1.2";
        }

        leaf rttMonGrpScheduleAdminPeriod {
          type int32 {
            range "0..604800";
          }
          units "seconds";
          description
           "Specifies the time duration over which all the probes have to
            be scheduled.";
          smiv2:defval "0";
          smiv2:max-access "read-write";
          smiv2:oid "1.3.6.1.4.1.9.9.42.1.2.14.1.3";
        }

        leaf rttMonGrpScheduleAdminFrequency {
          type int32 {
            range "0..604800";
          }
          units "seconds";
          description
           "Specifies the duration between initiating each RTT
            operation for all the probes specified in the group.
            
            The value of this object is only effective when both
            rttMonGrpScheduleAdminFreqMax and rttMonGrpScheduleAdminFreqMin 
            have zero values.";
          smiv2:defval "0";
          smiv2:max-access "read-write";
          smiv2:oid "1.3.6.1.4.1.9.9.42.1.2.14.1.4";
        }

        leaf rttMonGrpScheduleAdminLife {
          type int32 {
            range "0..2147483647";
          }
          units "seconds";
          description
           "This object specifies the life of all the probes included in
            the object rttMonGrpScheduleAdminProbes, that are getting group
            scheduled. This value will be placed into
            rttMonScheduleAdminRttLife object for each of the probes listed
            in rttMonGrpScheduleAdminProbes when this conceptual control
            row becomes 'active'.
            
            The value 2147483647 has a special meaning. When this object is
            set to 2147483647, the rttMonCtrlOperRttLife object for all the
            probes listed in rttMonGrpScheduleAdminProbes,  will not
            decrement. And thus the life time of the probes will never end.";
          smiv2:defval "3600";
          smiv2:max-access "read-write";
          smiv2:oid "1.3.6.1.4.1.9.9.42.1.2.14.1.5";
        }

        leaf rttMonGrpScheduleAdminAgeout {
          type int32 {
            range "0..2073600";
          }
          units "seconds";
          description
           "This object specifies the ageout value of all the probes
            included in the object rttMonGrpScheduleAdminProbes, that are
            getting group scheduled. This value will be placed into
            rttMonScheduleAdminConceptRowAgeout object for each of the
            probes listed in rttMonGrpScheduleAdminProbes when this
            conceptual control row becomes 'active'.
            
            When this value is set to zero, the probes listed in
            rttMonGrpScheduleAdminProbes, will never ageout.";
          smiv2:defval "3600";
          smiv2:max-access "read-write";
          smiv2:oid "1.3.6.1.4.1.9.9.42.1.2.14.1.6";
        }

        leaf rttMonGrpScheduleAdminStatus {
          type snmpv2-tc:RowStatus;
          description
           "The status of the conceptual RTT group schedule control row.
            
            In order for this object to become active, the following
            row objects must be defined:
             - rttMonGrpScheduleAdminProbes
             - rttMonGrpScheduleAdminPeriod
            All other objects can assume default values.
            
            The conceptual RTT group schedule control row objects cannot be
            modified once this conceptual RTT group schedule control row
            has been created.
            Once this object is in 'active' status, it cannot be set to
            'notInService'.
            When this object moves to 'active' state it will schedule the
            probes of the rttMonCtrlAdminTable which had been created using
            'createAndWait'.
            
            This object can be set to 'destroy' from any value at any time.
            When this object is set to 'destroy' it will stop all the probes
            of the rttMonCtrlAdminTable, which had been group scheduled
            by it earlier, before destroying the RTT group schedule
            control row.";
          smiv2:max-access "read-write";
          smiv2:oid "1.3.6.1.4.1.9.9.42.1.2.14.1.7";
        }

        leaf rttMonGrpScheduleAdminFreqMax {
          type int32 {
            range "0..604800";
          }
          units "seconds";
          description
           "Specifies the max duration between initiating each RTT
            operation for all the probes specified in the group.
            
            If this is 0 and rttMonGrpScheduleAdminFreqMin is also 0
            then rttMonGrpScheduleAdminFrequency becomes the fixed
            frequency.";
          smiv2:defval "0";
          smiv2:max-access "read-write";
          smiv2:oid "1.3.6.1.4.1.9.9.42.1.2.14.1.8";
        }

        leaf rttMonGrpScheduleAdminFreqMin {
          type int32 {
            range "0..604800";
          }
          units "seconds";
          description
           "Specifies the min duration between initiating each RTT
            operation for all the probes specified in the group.
            
            The value of this object cannot be greater than the value of
            rttMonGrpScheduleAdminFreqMax.
            
            If this is 0 and rttMonGrpScheduleAdminFreqMax is 0 then
            rttMonGrpScheduleAdminFrequency becomes the fixed frequency.";
          smiv2:defval "0";
          smiv2:max-access "read-write";
          smiv2:oid "1.3.6.1.4.1.9.9.42.1.2.14.1.9";
        }

        leaf rttMonGrpScheduleAdminStartTime {
          type int32 {
            range "0..604800";
          }
          units "seconds";
          description
           "This is the time in seconds after which the member probes of
            this group specified in rttMonGrpScheduleAdminProbes will
            transition to active state";
          smiv2:defval "0";
          smiv2:max-access "read-write";
          smiv2:oid "1.3.6.1.4.1.9.9.42.1.2.14.1.10";
        }

        leaf rttMonGrpScheduleAdminAdd {
          type boolean;
          description
           "Addition of members to an existing group will be allowed
            if this object is set to TRUE (1). The members, IDs of
            which are mentioned in rttMonGrpScheduleAdminProbes object
            are added to the existing group";
          smiv2:max-access "read-write";
          smiv2:oid "1.3.6.1.4.1.9.9.42.1.2.14.1.11";
        }

        leaf rttMonGrpScheduleAdminDelete {
          type boolean;
          description
           "Removal of members from an existing group will be allowed
            if this object is set to TRUE (1). The members, IDs of
            which are mentioned in rttMonGrpScheduleAdminProbes object
            are removed from the existing group";
          smiv2:max-access "read-write";
          smiv2:oid "1.3.6.1.4.1.9.9.42.1.2.14.1.12";
        }

        leaf rttMonGrpScheduleAdminReset {
          type boolean;
          description
           "When this is set to true then all members
            of this group will be stopped and rescheduled using the
            previously set values of this group.";
          smiv2:max-access "read-write";
          smiv2:oid "1.3.6.1.4.1.9.9.42.1.2.14.1.13";
        }
      }
    }

    container rttMplsVpnMonCtrlTable {
      description
       "A table of Auto SAA L3 MPLS VPN definitions.
        
        The Auto SAA L3 MPLS VPN administration control is in multiple
        tables.
        
        This first table, is used to create a conceptual Auto SAA L3
        MPLS VPN control row.  The following tables contain objects
        which used in type specific configurations, scheduling and
        reaction configurations. All of these tables will create the
        same conceptual control row as this table using this table's
        index as their own index.
        
        In order to a row in this table to become active the following
        objects must be defined.
          rttMplsVpnMonCtrlRttType,
          rttMplsVpnMonCtrlVrfName and
          rttMplsVpnMonSchedulePeriod.";
      smiv2:oid "1.3.6.1.4.1.9.9.42.1.2.15";

      list rttMplsVpnMonCtrlEntry {
        key "rttMplsVpnMonCtrlIndex";
        description
         "A base list of objects that define a conceptual Auto SAA L3
          MPLS VPN control row.";
        smiv2:oid "1.3.6.1.4.1.9.9.42.1.2.15.1";

        leaf rttMplsVpnMonCtrlIndex {
          type int32 {
            range "1..2147483647";
          }
          description
           "Uniquely identifies a row in the rttMplsVpnMonCtrlTable.
            
            This is a pseudo-random number selected by the management
            station when creating a row via the
            rttMplsVpnMonCtrlStatus object.
            
            If the pseudo-random number is already in use an
            'inconsistentValue' return code will be returned when set
            operation is attempted.";
          smiv2:max-access "not-accessible";
          smiv2:oid "1.3.6.1.4.1.9.9.42.1.2.15.1.1";
        }

        leaf rttMplsVpnMonCtrlRttType {
          type cisco-rttmon:RttMplsVpnMonRttType;
          description
           "The type of RTT operation to be performed for Auto SAA L3
            MPLS VPN.
            
            This value must be set in the same PDU of
            rttMplsVpnMonCtrlStatus.
            
            This value must be set before setting
            any other parameter configuration of an Auto SAA L3 MPLS VPN.";
          smiv2:max-access "read-write";
          smiv2:oid "1.3.6.1.4.1.9.9.42.1.2.15.1.2";
        }

        leaf rttMplsVpnMonCtrlVrfName {
          type binary {
            length "0..32";
          }
          description
           "This field is used to specify the VPN name for which
            the Auto SAA L3 MPLS VPN RTT operation will be used.
            
            This value must be set in the same PDU of
            rttMplsVpnMonCtrlStatus.
            
            The Auto SAA L3 MPLS VPN will find the PEs participating in
            this VPN and configure RTT operation corresponding to value
            specified in rttMplsVpnMonCtrlRttType.
            
            If the VPN corresponds to the value configured for this object
            doesn't exist 'inconsistentValue' error will be returned.
            
            The value 'saa-vrf-all' has a special meaning. When this
            object is set to 'saa-vrf-all', all the VPNs in the PE will be
            discovered and Auto SAA L3 MPLS VPN will configure RTT
            operations corresponding to all these PEs with the value
            specified in rttMplsVpnMonCtrlRttType as type for those
            operations.
            
            So, the user should avoid using this string for a particular
            VPN name when using this feature in order to avoid ambiguity.";
          smiv2:max-access "read-write";
          smiv2:oid "1.3.6.1.4.1.9.9.42.1.2.15.1.3";
        }

        leaf rttMplsVpnMonCtrlTag {
          type snmpv2-tc:DisplayString {
            length "0..255";
          }
          description
           "A string which is used by a managing application to
            identify the RTT target.
            
            This string will be configured as rttMonCtrlAdminTag for all
            the operations configured by this Auto SAA L3 MPLS VPN.
            
            The usage of this value in Auto SAA L3 MPLS VPN is same as
            rttMonCtrlAdminTag in RTT operation.";
          smiv2:defval "";
          smiv2:max-access "read-write";
          smiv2:oid "1.3.6.1.4.1.9.9.42.1.2.15.1.4";
        }

        leaf rttMplsVpnMonCtrlThreshold {
          type int32 {
            range "0..2147483647";
          }
          units "milliseconds";
          description
           "This object defines an administrative threshold limit.
            
            This value will be configured as rttMonCtrlAdminThreshold for
            all the operations that will be configured by the current
            Auto SAA L3 MPLS VPN.
            
            The usage of this value in Auto SAA L3 MPLS VPN is same as
            rttMonCtrlAdminThreshold.";
          smiv2:defval "5000";
          smiv2:max-access "read-write";
          smiv2:oid "1.3.6.1.4.1.9.9.42.1.2.15.1.5";
        }

        leaf rttMplsVpnMonCtrlTimeout {
          type int32 {
            range "0..604800000";
          }
          units "milliseconds";
          description
           "Specifies the duration to wait for a RTT operation configured
            automatically by the Auto SAA L3 MPLS VPN to complete. 
            
            The value of this object cannot be set to a value which would
            specify a duration exceeding rttMplsVpnMonScheduleFrequency.
            
            The usage of this value in Auto SAA L3 MPLS VPN is similar to
            rttMonCtrlAdminTimeout.";
          smiv2:defval "5000";
          smiv2:max-access "read-write";
          smiv2:oid "1.3.6.1.4.1.9.9.42.1.2.15.1.6";
        }

        leaf rttMplsVpnMonCtrlScanInterval {
          type int32 {
            range "1..70560";
          }
          units "minutes";
          description
           "Specifies the frequency at which the automatic PE addition
            should take place if there is any for an Auto SAA L3 MPLS VPN.
            
            New RTT operations corresponding to the new PEs discovered will
            be created and scheduled.
            
            The default value for this object is 4 hours. The maximum value
            supported is 49 days.";
          smiv2:defval "240";
          smiv2:max-access "read-write";
          smiv2:oid "1.3.6.1.4.1.9.9.42.1.2.15.1.7";
        }

        leaf rttMplsVpnMonCtrlDelScanFactor {
          type int32 {
            range "0..2147483647";
          }
          description
           "Specifies the frequency at which the automatic PE deletion
            should take place.
            
            This object specifies the number of times of
            rttMonMplslmCtrlScanInterval (rttMplsVpnMonCtrlDelScanFactor *
            rttMplsVpnMonCtrlScanInterval) to wait before removing the PEs.
            This object doesn't directly specify the explicit value to
            wait before removing the PEs that were down.
            
            If this object set 0 the entries will never removed.";
          smiv2:defval "1";
          smiv2:max-access "read-write";
          smiv2:oid "1.3.6.1.4.1.9.9.42.1.2.15.1.8";
        }

        leaf rttMplsVpnMonCtrlEXP {
          type int32 {
            range "0..7";
          }
          description
           "This object represents the EXP value that needs to be
            put as precedence bit of an IP header.";
          smiv2:defval "0";
          smiv2:max-access "read-write";
          smiv2:oid "1.3.6.1.4.1.9.9.42.1.2.15.1.9";
        }

        leaf rttMplsVpnMonCtrlRequestSize {
          type int32 {
            range "0..16384";
          }
          units "octets";
          description
           "This object represents the native payload size that needs to
            be put on the packet.
            
            This value will be configured as
            rttMonEchoAdminPktDataRequestSize for all the RTT operations
            configured by the current Auto SAA L3 MPLS VPN.
            
            The minimum request size for jitter probe is 16. The maximum
            for jitter probe is 1500. The default request size is 32 for
            jitter probe.
            
            For echo and pathEcho default request size is 28.
            The minimum request size for echo and pathEcho is 28 bytes.";
          smiv2:defval "1";
          smiv2:max-access "read-write";
          smiv2:oid "1.3.6.1.4.1.9.9.42.1.2.15.1.10";
        }

        leaf rttMplsVpnMonCtrlVerifyData {
          type boolean;
          description
           "When set to true, the resulting data in each RTT operation
            created by the current Auto SAA L3 MPLS VPN is compared with
            the expected data. This includes checking header information
            (if possible) and exact packet size.  Any mismatch will be
            recorded in the rttMonStatsCollectVerifyErrors object of each
            RTT operation created by the current Auto SAA L3 MPLS VPN.";
          smiv2:defval "false";
          smiv2:max-access "read-write";
          smiv2:oid "1.3.6.1.4.1.9.9.42.1.2.15.1.11";
        }

        leaf rttMplsVpnMonCtrlStorageType {
          type snmpv2-tc:StorageType;
          description
           "The storage type of this conceptual row. When set to
            'nonVolatile', this entry will be shown in 'show running'
            command and can be saved into Non-volatile memory.
            
            By Default the entry will not be saved into Non-volatile
            memory.
            
            This object can be set to either 'volatile' or 'nonVolatile'.
            Other values are not applicable for this conceptual row and
            are not supported.";
          smiv2:defval "volatile";
          smiv2:max-access "read-write";
          smiv2:oid "1.3.6.1.4.1.9.9.42.1.2.15.1.12";
        }

        leaf rttMplsVpnMonCtrlProbeList {
          type snmpv2-tc:DisplayString;
          description
           "This object holds the list of probes ID's that are created by
            the Auto SAA L3 MPLS VPN.
            
            The probes will be specified in the following form.
            (a) Individual ID's with comma separated as 1,5,3.
            (b) Range form including hyphens with multiple ranges being
                separated by comma as 1-10,12-34.
            (c) Mix of the above two forms as 1,2,4-10,12,15,19-25.";
          smiv2:max-access "read-only";
          smiv2:oid "1.3.6.1.4.1.9.9.42.1.2.15.1.13";
        }

        leaf rttMplsVpnMonCtrlStatus {
          type snmpv2-tc:RowStatus;
          description
           "The status of the conceptual Auto SAA L3 MPLS VPN control row.
            
            In order for this object to become active
            rttMplsVpnMonCtrlRttType,  rttMplsVpnMonCtrlVrfName and 
            rttMplsVpnMonSchedulePeriod objects must be defined.
            All other objects can assume default values.
            
            If the object is set to 'createAndGo' rttMplsVpnMonCtrlRttType,
            rttMplsVpnMonCtrlVrfName and rttMplsVpnMonSchedulePeriod needs
            to be set along with rttMplsVpnMonCtrlStatus.
            
            If the object is set to 'createAndWait' rttMplsVpnMonCtrlRttType
            and rttMplsVpnMonCtrlVrfName needs to be set along with
            rttMplsVpnMonCtrlStatus. rttMplsVpnMonSchedulePeriod needs to be
            specified before setting rttMplsVpnMonCtrlStatus to 'active'.
            
            The following objects cannot be modified after creating the
            Auto SAA L3 MPLS VPN conceptual row.
            
             - rttMplsVpnMonCtrlRttType
             - rttMplsVpnMonCtrlVrfName
            
            The following objects can be modified even after creating the
            Auto SAA L3 MPLS VPN conceptual row by setting this object to
            'notInService'
            
             - All other writable objects in rttMplsVpnMonCtrlTable except
               rttMplsVpnMonCtrlRttType and rttMplsVpnMonCtrlVrfName.
             - Objects in the rttMplsVpnMonTypeTable.
             - Objects in the rttMplsVpnMonScheduleTable.
            
            The following objects can be modified as needed without setting
            this object to 'notInService' even after creating the
            Auto SAA L3 MPLS VPN conceptual row.
            
             - Objects in rttMplsVpnMonReactTable.
            
            This object can be set to 'destroy' from any value
            at any time. When this object is set to 'destroy' it will stop
            and destroy all the probes created by this Auto SAA L3 MPLS VPN
            before destroying Auto SAA L3 MPLS VPN control row.";
          smiv2:max-access "read-write";
          smiv2:oid "1.3.6.1.4.1.9.9.42.1.2.15.1.14";
        }

        leaf rttMplsVpnMonCtrlLpd {
          type boolean;
          description
           "When set to true, this implies that LPD (LSP Path Discovery)
            is enabled for this row.
            
            The Auto SAA L3 MPLS VPN will find all the paths to each of the
            PE's and configure RTT operation with rttMonCtrlAdminRttType
            value as 'lspGroup'. The 'lspGroup' probe will walk through
            the list of set of information that uniquely identifies a path
            and send the LSP echo requests across them. All these LSP echo
            requests sent for 1st path, 2nd path etc. can be thought of as
            'single probes' sent as a part of 'lspGroup'. These single
            probes will of type 'rttMplsVpnMonCtrlRttType'.
            
            'lspGroup' probe is a superset of individual probes that will
            test multiple paths. For example Suppose there are 10 paths to
            the target. One 'lspGroup' probe will be created which will
            store all the information related to uniquely identify the 10
            paths. When the 'lspGroup' probe will run it will sweep through
            the set of information for 1st path, 2nd path, 3rd path and so
            on till it has tested all the paths.";
          smiv2:defval "false";
          smiv2:max-access "read-write";
          smiv2:oid "1.3.6.1.4.1.9.9.42.1.2.15.1.15";
        }

        leaf rttMplsVpnMonCtrlLpdGrpList {
          type snmpv2-tc:DisplayString;
          description
           "This object holds the list of LPD Group IDs that are created
            for this Auto SAA L3 MPLS VPN row.
            
            This object will be applicable only when LSP Path Discovery is
            enabled for this row.
            
            The LPD Groups will be specified in the following form.
            (a) Individual ID's with comma separated as 1,5,3.
            (b) Range form including hyphens with multiple ranges being
                separated by comma as 1-10,12-34.
            (c) Mix of the above two forms as 1,2,4-10,12,15,19-25.";
          smiv2:max-access "read-only";
          smiv2:oid "1.3.6.1.4.1.9.9.42.1.2.15.1.16";
        }

        leaf rttMplsVpnMonCtrlLpdCompTime {
          type int32 {
            range "1..65535";
          }
          units "minutes";
          description
           "The completion time of the LSP Path Discovery for the entire
            set of PEs which are discovered for this Auto SAA.
            
            This object will be applicable only when LSP Path Discovery is
            enabled for this row.";
          smiv2:max-access "read-only";
          smiv2:oid "1.3.6.1.4.1.9.9.42.1.2.15.1.17";
        }
      }
    }

    container rttMonReactTable {
      description
       "A table that contains the reaction configurations. Each
        conceptual row in rttMonReactTable corresponds to a reaction
        configured for the probe defined in rttMonCtrlAdminTable.
        
        For each reaction configured for a probe there is an entry in
        the table.
        
        Each Probe can have multiple reactions and hence there can be
        multiple rows for a particular probe.
        
        This table is coupled with rttMonCtrlAdminTable.";
      smiv2:oid "1.3.6.1.4.1.9.9.42.1.2.19";

      list rttMonReactEntry {
        key "rttMonCtrlAdminIndex rttMonReactConfigIndex";
        description
         "A base list of objects that define a conceptual reaction
          configuration control row.";
        smiv2:oid "1.3.6.1.4.1.9.9.42.1.2.19.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonReactConfigIndex {
          type int32 {
            range "1..2147483647";
          }
          description
           "This object along with rttMonCtrlAdminIndex identifies
            a particular reaction-configuration for a particular probe.
            This is a pseudo-random number selected by the management
            station when creating a row via the rttMonReactStatus.
            If the pseudo-random number is already in use an
            'inconsistentValue' return code will be returned when
            set operation is attempted.";
          smiv2:max-access "not-accessible";
          smiv2:oid "1.3.6.1.4.1.9.9.42.1.2.19.1.1";
        }

        leaf rttMonReactVar {
          type cisco-rttmon:RttMonReactVar;
          description
           "This object specifies the type of reaction configured for a
            probe.
            
            The reaction types 'rtt', 'timeout', and 'connectionLoss' 
            can be configured for all probe types.
            
            The reaction type 'verifyError' can be configured for all 
            probe types except RTP probe type.
            
            The reaction types 'jitterSDAvg', 'jitterDSAvg', 'jitterAvg', 
            'packetLateArrival', 'packetOutOfSequence', 
            'maxOfPositiveSD', 'maxOfNegativeSD', 'maxOfPositiveDS'
            and 'maxOfNegativeDS' can be configured for UDP jitter 
            and ICMP jitter probe types only.
            
            The reaction types 'mos' and 'icpif' can be configured 
            for UDP jitter and ICMP jitter probe types only.
            
            The reaction types 'packetLossDS', 'packetLossSD' and 
            'packetMIA' can be configured for UDP jitter, and 
            RTP probe types only.
            
            The reaction types 'iaJitterDS', 'frameLossDS', 'mosLQDS', 
            'mosCQDS', 'rFactorDS', 'iaJitterSD', 'rFactorSD', 'mosCQSD' 
            can be configured for RTP probe type only.
            
            The reaction types 'successivePacketLoss', 'maxOfLatencyDS', 
            'maxOfLatencySD', 'latencyDSAvg', 'latencySDAvg' and 
            'packetLoss' can be configured for ICMP jitter probe 
            type only.";
          smiv2:max-access "read-write";
          smiv2:oid "1.3.6.1.4.1.9.9.42.1.2.19.1.2";
        }

        leaf rttMonReactThresholdType {
          type enumeration {
            enum "never" {
              value "1";
            }
            enum "immediate" {
              value "2";
            }
            enum "consecutive" {
              value "3";
            }
            enum "xOfy" {
              value "4";
            }
            enum "average" {
              value "5";
            }
          }
          description
           "This object specifies the conditions under which
            the notification ( trap ) is sent.
            
            never       - rttMonReactOccurred is never set
            
            immediate   - rttMonReactOccurred is set to 'true' when the
                          value of parameter for which reaction is
                          configured ( e.g rtt, jitterAvg, packetLossSD,
                          mos etc ) violates the threshold.
                          Conversely, rttMonReactOccurred is set to 'false'
                          when the parameter ( e.g rtt, jitterAvg,
                          packetLossSD, mos etc ) is below the threshold
                          limits.
            
            consecutive - rttMonReactOccurred is set to true when the value
                          of parameter for which reaction is configured
                          ( e.g rtt, jitterAvg, packetLossSD, mos etc )
                          violates the threshold for configured consecutive
                          times.
                          Conversely, rttMonReactOccurred is set to false
                          when the value of parameter ( e.g rtt, jitterAvg
                          packetLossSD, mos etc ) is below the threshold
                          limits for the same number of consecutive
                          operations.
            
            xOfy        - rttMonReactOccurred is set to true when x
                          ( as specified by rttMonReactThresholdCountX )
                          out of the last y ( as specified by
                          rttMonReacthresholdCountY ) times the value of
                          parameter for which the reaction is configured
                          ( e.g rtt, jitterAvg, packetLossSD, mos etc )
                          violates the threshold.
                          Conversely, it is set to false when x, out of the
                          last y times the value of parameter
                          ( e.g rtt, jitterAvg, packetLossSD, mos ) is
                          below the threshold limits.
                          NOTE: When x > y, the probe will never
                                generate a reaction.
            
            average    - rttMonReactOccurred is set to true when the
                         average ( rttMonReactThresholdCountX times )
                         value of parameter for which reaction is 
                         configured ( e.g rtt, jitterAvg, packetLossSD,
                         mos etc ) violates the threshold condition.
                         Conversely, it is set to false when the
                         average value of parameter ( e.g rtt, jitterAvg,
                         packetLossSD, mos etc ) is below the threshold
                         limits.
            
            If this value is changed by a management station,
            rttMonReactOccurred is set to false, but
            no reaction is generated if the prior value of
            rttMonReactOccurred was true.";
          smiv2:defval "never";
          smiv2:max-access "read-write";
          smiv2:oid "1.3.6.1.4.1.9.9.42.1.2.19.1.3";
        }

        leaf rttMonReactActionType {
          type enumeration {
            enum "none" {
              value "1";
            }
            enum "trapOnly" {
              value "2";
            }
            enum "triggerOnly" {
              value "3";
            }
            enum "trapAndTrigger" {
              value "4";
            }
          }
          description
           "Specifies what type(s), if any, of reaction(s) to
            generate if an operation violates one of the watched
            ( reaction-configuration ) conditions:
            
            none               - no reaction is generated
            trapOnly           - a trap is generated
            triggerOnly        - all trigger actions defined for this
                                 entry are initiated
            trapAndTrigger     - both a trap and all trigger actions
                                 are initiated
            A trigger action is defined via the
            rttMonReactTriggerAdminTable.";
          smiv2:defval "none";
          smiv2:max-access "read-write";
          smiv2:oid "1.3.6.1.4.1.9.9.42.1.2.19.1.4";
        }

        leaf rttMonReactThresholdRising {
          type int32 {
            range "0..2147483647";
          }
          description
           "This object defines the higher threshold limit.
            If the value ( e.g rtt, jitterAvg, packetLossSD etc ) rises
            above this limit and if the condition specified in
            rttMonReactThresholdType are satisfied, a trap is generated.
            
            Default value of rttMonReactThresholdRising for
               'rtt' is 5000
               'jitterAvg' is 100.
               'jitterSDAvg' is 100.
               'jitterDSAvg' 100.
               'packetLossSD' is 10000.
               'packetLossDS' is 10000.
               'mos' is 500.
               'icpif' is 93.
               'packetMIA' is 10000.
               'packetLateArrival' is 10000.
               'packetOutOfSequence' is 10000.
               'maxOfPositiveSD' is 10000.
               'maxOfNegativeSD' is 10000.
               'maxOfPositiveDS' is 10000.
               'maxOfNegativeDS' is 10000.
               'iaJitterDS' is 20.
               'frameLossDS' is 10000.
               'mosLQDS' is 400.
               'mosCQDS' is 400.
               'rFactorDS' is 80.
               'successivePacketLoss' is 1000.
               'maxOfLatencyDS' is 5000.
               'maxOfLatencySD' is 5000.
               'latencyDSAvg' is 5000.
               'latencySDAvg' is 5000.
               'packetLoss' is 10000.
            
            This object is not applicable if the rttMonReactVar is
            'timeout', 'connectionLoss' or 'verifyError'. For 'timeout',
            'connectionLoss' and 'verifyError' default value of 
            rttMonReactThresholdRising will be 0.";
          smiv2:max-access "read-write";
          smiv2:oid "1.3.6.1.4.1.9.9.42.1.2.19.1.5";
        }

        leaf rttMonReactThresholdFalling {
          type int32 {
            range "0..2147483647";
          }
          description
           "This object defines a lower threshold limit. If the
            value ( e.g rtt, jitterAvg, packetLossSD etc ) falls
            below this limit and if the conditions specified in
            rttMonReactThresholdType are satisfied, a trap is generated.
            
            Default value of rttMonReactThresholdFalling
               'rtt' is 3000
               'jitterAvg' is 100.
               'jitterSDAvg' is 100.
               'jitterDSAvg' 100.
               'packetLossSD' is 10000.
               'packetLossDS' is 10000.
               'mos' is 500.
               'icpif' is 93.
               'packetMIA' is 10000.
               'packetLateArrival' is 10000.
               'packetOutOfSequence' is 10000.
               'maxOfPositiveSD' is 10000.
               'maxOfNegativeSD' is 10000.
               'maxOfPositiveDS' is 10000.
               'maxOfNegativeDS' is 10000.
               'iaJitterDS' is 20.
               'frameLossDS' is 10000.
               'mosLQDS' is 310.
               'mosCQDS' is 310.
               'rFactorDS' is 60.
               'successivePacketLoss' is 1000.
               'maxOfLatencyDS' is 3000.
               'maxOfLatencySD' is 3000.
               'latencyDSAvg' is 3000.
               'latencySDAvg' is 3000.
               'packetLoss' is 10000.
               'iaJitterSD' is 20.
               'mosCQSD' is 310.
               'rFactorSD' is 60.
            
            This object is not applicable if the rttMonReactVar is
            'timeout', 'connectionLoss' or 'verifyError'. For 'timeout',
            'connectionLoss' and 'verifyError' default value of
            rttMonReactThresholdFalling will be 0.";
          smiv2:max-access "read-write";
          smiv2:oid "1.3.6.1.4.1.9.9.42.1.2.19.1.6";
        }

        leaf rttMonReactThresholdCountX {
          type int32 {
            range "1..16";
          }
          description
           "If rttMonReactThresholdType value is 'xOfy', this object
            defines the 'x' value.
            
            If rttMonReactThresholdType value is 'consecutive'
            this object defines the number of consecutive occurrences
            that needs threshold violation before setting 
            rttMonReactOccurred as true.
            
            If rttMonReactThresholdType value is 'average' this object
            defines the number of samples that needs be considered for
            calculating average.
            
            This object has no meaning if rttMonReactThresholdType has
            value of 'never' and 'immediate'.";
          smiv2:defval "5";
          smiv2:max-access "read-write";
          smiv2:oid "1.3.6.1.4.1.9.9.42.1.2.19.1.7";
        }

        leaf rttMonReactThresholdCountY {
          type int32 {
            range "1..16";
          }
          description
           "This object defines the 'y' value of the xOfy condition
            if rttMonReactThresholdType is 'xOfy'.
            
            For other values of rttMonReactThresholdType, this object
            is not applicable.";
          smiv2:defval "5";
          smiv2:max-access "read-write";
          smiv2:oid "1.3.6.1.4.1.9.9.42.1.2.19.1.8";
        }

        leaf rttMonReactValue {
          type int32 {
            range "0..2147483647";
          }
          description
           "This object will be set when the configured threshold condition
            is violated as defined by rttMonReactThresholdType and holds the
            actual value that violated the configured threshold values.
            
            This object is not valid for the following values of
            rttMonReactVar and It will be always 0:
              - timeout
              - connectionLoss
              - verifyError.";
          smiv2:defval "0";
          smiv2:max-access "read-only";
          smiv2:oid "1.3.6.1.4.1.9.9.42.1.2.19.1.9";
        }

        leaf rttMonReactOccurred {
          type boolean;
          description
           "This object is set to true when the configured threshold
            condition is violated as defined by rttMonReactThresholdType.
            It will be again set to 'false' if the condition reverses.
            
            This object is set to true in the following conditions:
             - rttMonReactVar is set to timeout and
               rttMonCtrlOperTimeoutOccurred set to true.
             - rttMonReactVar is set to connectionLoss and
               rttMonCtrlOperConnectionLostOccurred set to true.
             - rttMonReactVar is set to verifyError and
               rttMonCtrlOperVerifyErrorOccurred is set to true.
             - For all other values of rttMonReactVar, if the
               corresponding value exceeds the configured
               rttMonReactThresholdRising.
            
             This object is set to false in the following conditions:
             - rttMonReactVar is set to timeout and
               rttMonCtrlOperTimeoutOccurred set to false.
             - rttMonReactVar is set to connectionLoss and 
               rttMonCtrlOperConnectionLostOccurred set to false.
             - rttMonReactVar is set to verifyError and
               rttMonCtrlOperVerifyErrorOccurred is set to false.
             - For all other values of rttMonReactVar, if the
               corresponding value fall below the configured 
               rttMonReactThresholdFalling.
            
            When the RttMonRttType is 'pathEcho' or 'pathJitter',
            this object is applied only to the 
            rttMonEchoAdminTargetAddress and not to intermediate
            hops to the Target.";
          smiv2:defval "false";
          smiv2:max-access "read-only";
          smiv2:oid "1.3.6.1.4.1.9.9.42.1.2.19.1.10";
        }

        leaf rttMonReactStatus {
          type snmpv2-tc:RowStatus;
          description
           "This objects indicates the status of the conceptual RTT
            Reaction Control Row.Only CreateAndGo and destroy 
            operations are permitted on the row.
            
            When this object moves to active state, the conceptual row
            having the Reaction configuration for the probe is monitored
            and the notifications are generated when the threshold violation
            takes place.
            
            In order for this object to become active rttMonReactVar must
            be defined. All other objects assume the default value.
            
            This object can be set to 'destroy' from any value at any time.
            When this object is set to 'destroy' no reaction configuration
            for the probes would exist. The reaction configuration for the
            probe is removed.";
          smiv2:max-access "read-write";
          smiv2:oid "1.3.6.1.4.1.9.9.42.1.2.19.1.11";
        }
      }
    }

    container rttMonGeneratedOperTable {
      description
       "This table contains information about the generated
        operation id as part of a parent IP SLA operation. The parent
        operation id is pseudo-random number, selected by the management 
        station based on an operation started by the management 
        station,when creating a row via the rttMonCtrlAdminStatus
        object in the rttMonCtrlAdminTable table.";
      smiv2:oid "1.3.6.1.4.1.9.9.42.1.2.20";

      list rttMonGeneratedOperEntry {
        key "rttMonCtrlAdminIndex rttMonGeneratedOperRespIpAddrType rttMonGeneratedOperRespIpAddr";
        description
         "An entry in the Generated Oper table corresponding to
          a child or generated operation as part of a parent
          IP SLA operation.";
        smiv2:oid "1.3.6.1.4.1.9.9.42.1.2.20.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonGeneratedOperRespIpAddrType {
          type inet-address:InetAddressType;
          description
           "The type of Internet address, IPv4 or IPv6, of a responder
            for an IP SLA operation.";
          smiv2:max-access "not-accessible";
          smiv2:oid "1.3.6.1.4.1.9.9.42.1.2.20.1.1";
        }

        leaf rttMonGeneratedOperRespIpAddr {
          type inet-address:InetAddress;
          description
           "The internet address of a responder for IP SLA
            operation. The type of this address is determined
            by the value of rttMonGeneratedOperRespIpAddrType.";
          smiv2:max-access "not-accessible";
          smiv2:oid "1.3.6.1.4.1.9.9.42.1.2.20.1.2";
        }

        leaf rttMonGeneratedOperCtrlAdminIndex {
          type uint32 {
            range "1..2147483647";
          }
          description
           "This is a pseudo-random number, auto-generated based
            to identify a child operation based on a parent 
            operation started by the management station,when 
            creating a row via the rttMonCtrlAdminStatus
            object.";
          smiv2:max-access "read-only";
          smiv2:oid "1.3.6.1.4.1.9.9.42.1.2.20.1.3";
        }
      }
    }

    container rttMonStatsCaptureTable {
      description
       "The statistics capture database.
        
        The statistics capture table contains summarized 
        information of the results for a conceptual RTT control 
        row.  A rolling accumulated history of this information 
        is maintained in a series of hourly 'group(s)'.  Each 
        'group' contains a series of 'path(s)', each 'path' 
        contains a series of 'hop(s)', each 'hop' contains a 
        series of 'statistics distribution bucket(s)'.
        
        Each conceptual statistics row has a current hourly 
        group, into which RTT results are accumulated.  At the 
        end of each hour a new hourly group is created which 
        then becomes current.  The counters and accumulators in 
        the new group are initialized to zero.  The previous 
        group(s) is kept in the table until the table contains 
        rttMonStatisticsAdminNumHourGroups groups for the 
        conceptual statistics row;  at this point, the oldest 
        group is discarded and is replaced by the newly created 
        one.  The hourly group is uniquely identified by the 
        rttMonStatsCaptureStartTimeIndex object.
        
        If the activity for a conceptual RTT control row ceases 
        because the rttMonCtrlOperState object transitions to 
        'inactive', the corresponding current hourly group in 
        this table is 'frozen', and a new hourly group is 
        created when activity is resumed.
        
        If the activity for a conceptual RTT control row ceases 
        because the rttMonCtrlOperState object transitions to 
        'pending' this whole table will be cleared and reset to 
        its initial state.
        
        When the RttMonRttType is 'pathEcho', the path 
        exploration RTT requests' statistics will not be 
        accumulated in this table.
        
        NOTE: When the RttMonRttType is 'pathEcho', a source to 
              target rttMonStatsCapturePathIndex path will be 
              created for each rttMonStatsCaptureStartTimeIndex 
              to hold all errors that occur when a specific path
              had not been found or connection has not be setup.
        
        Using this rttMonStatsCaptureTable, a managing 
        application can retrieve summarized data from accurately 
        measured periods, which is synchronized across multiple 
        conceptual RTT control rows.  With the new hourly group
        creation being performed on a 60 minute period, the 
        managing station has plenty of time to collect the data, 
        and need not be concerned with the vagaries of network 
        delays and lost PDU's when trying to get matching data.  
        Also, the managing station can spread the data gathering 
        over a longer period, which removes the need for a flood 
        of get requests in a short period which otherwise would 
        occur.";
      smiv2:oid "1.3.6.1.4.1.9.9.42.1.3.1";

      list rttMonStatsCaptureEntry {
        key "rttMonCtrlAdminIndex rttMonStatsCaptureStartTimeIndex rttMonStatsCapturePathIndex rttMonStatsCaptureHopIndex rttMonStatsCaptureDistIndex";
        description
         "A list of objects which accumulate the results of a
          series of RTT operations over a 60 minute time period.
          
          The statistics capture table is a rollover table.  When
          rttMonStatsCaptureStartTimeIndex groups exceeds the 
          rttMonStatisticsAdminNumHourGroups value, the oldest 
          corresponding hourly group will be deleted and will be 
          replaced with the new rttMonStatsCaptureStartTimeIndex
          hourly group.  
          
          All other indices will fill to there maximum size. 
          
          The statistics capture table has five indices.  Each
          described as follows:
          
            -  The first index correlates its entries to a
                conceptual RTT control row via the 
                rttMonCtrlAdminIndex object.
            -  The second index is a rollover group and it 
                uniquely identifies a 60 minute group. (The 
                rttMonStatsCaptureStartTimeIndex object
                is used to make this value unique.)
            -  When the RttMonRttType is 'pathEcho', the third 
                index uniquely identifies the paths in a 
                statistics period.  (The period is 60
                minutes.)  A path will be created for each
                unique path through the network.  Note:  A
                path that does not contain the target is
                considered a different path than one which
                uses the exact same path, but does contain the
                target.  For all other values of RttMonRttType
                this index will be one.
            -  When the RttMonRttType is 'pathEcho', the fourth 
                index uniquely identifies the hops in each path, 
                as grouped by the third index.  This index does 
                imply the order of the hops along the path to a 
                target.  For all other values of RttMonRttType
                this index will be one.
            -  The fifth index uniquely creates a statistical
                distribution bucket.";
        smiv2:oid "1.3.6.1.4.1.9.9.42.1.3.1.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonStatsCaptureStartTimeIndex {
          type yang:timestamp;
          description
           "The time when this row was created.
            
            This object is the second index of the 
            rttMonStatsCaptureTable Table.
            
            The the number of rttMonStatsCaptureStartTimeIndex  
            groups exceeds the rttMonStatisticsAdminNumHourGroups
            value, the oldest rttMonStatsCaptureStartTimeIndex 
            group will be removed and replaced with the new entry.
            
            When the RttMonRttType is 'pathEcho', this object also 
            uniquely defines a group of paths.  See the 
            rttMonStatsCaptureEntry object.";
          smiv2:max-access "not-accessible";
          smiv2:oid "1.3.6.1.4.1.9.9.42.1.3.1.1.1";
        }

        leaf rttMonStatsCapturePathIndex {
          type int32 {
            range "1..128";
          }
          description
           "When the RttMonRttType is 'pathEcho', this object
            uniquely defines a path for a given value of 
            rttMonStatsCaptureStartTimeIndex.  For all other values
            of RttMonRttType, this object will be one.
            
            For a particular value of 
            rttMonStatsCaptureStartTimeIndex, the agent assigns the
            first instance of a path a value of 1, then second 
            instance a value of 2, and so on.  The sequence keeps 
            incrementing until the number of paths equals 
            rttMonStatisticsAdminNumPaths value, then no new paths 
            are kept for the current rttMonStatsCaptureStartTimeIndex 
            group.
            
            NOTE: A source to target rttMonStatsCapturePathIndex
                  path will be created for each 
                  rttMonStatsCaptureStartTimeIndex to hold all 
                  errors that occur when a specific path or 
                  connection has not be setup.
            
            This value directly represents the path to
            a target. We can only support 128 paths.";
          smiv2:max-access "not-accessible";
          smiv2:oid "1.3.6.1.4.1.9.9.42.1.3.1.1.2";
        }

        leaf rttMonStatsCaptureHopIndex {
          type int32 {
            range "1..30";
          }
          description
           "When the RttMonRttType is 'pathEcho', this object
            uniquely defines a hop for a given value of 
            rttMonStatsCapturePathIndex.  For all other values of
            RttMonRttType, this object will be one.
            
            For a particular value of rttMonStatsCapturePathIndex,
            the agent assigns the first instance of a hop
            a value of 1, then second instance a value of 2, and so
            on.  The sequence keeps incrementing until the number of 
            hops equals rttMonStatisticsAdminNumHops value, then
            no new hops are kept for the current
            rttMonStatsCapturePathIndex.
            
            This value directly represents a hop along the path to
            a target, thus we can only support 30 hops.
            
            This value shows the order along the path to a target.";
          smiv2:max-access "not-accessible";
          smiv2:oid "1.3.6.1.4.1.9.9.42.1.3.1.1.3";
        }

        leaf rttMonStatsCaptureDistIndex {
          type int32 {
            range "1..20";
          }
          description
           "This object uniquely defines a statistical distribution
            bucket for a given value of rttMonStatsCaptureHopIndex.
            
            For a particular value of rttMonStatsCaptureHopIndex,
            the agent assigns the first instance of a distribution
            a value of 1, then second instance a value of 2, and so
            on.  The sequence keeps incrementing until the number of 
            statistics distribution intervals equals 
            rttMonStatisticsAdminNumDistBuckets value, then
            all values that fall above the last interval will
            be placed into the last interval.
            
            Each of these Statistics Distribution Buckets contain 
            the results of each completion as defined by 
            rttMonStatisticsAdminDistInterval object.";
          smiv2:max-access "not-accessible";
          smiv2:oid "1.3.6.1.4.1.9.9.42.1.3.1.1.4";
        }

        leaf rttMonStatsCaptureCompletions {
          type int32 {
            range "0..2147483647";
          }
          description
           "The number of RTT operations that have completed without
            an error and without timing out.
            
            This object has the special behavior as defined by the
            ROLLOVER NOTE in the DESCRIPTION of the ciscoRttMonMIB
            object.";
          smiv2:max-access "read-only";
          smiv2:oid "1.3.6.1.4.1.9.9.42.1.3.1.1.5";
        }

        leaf rttMonStatsCaptureOverThresholds {
          type int32 {
            range "0..2147483647";
          }
          description
           "The number of RTT operations successfully completed, but
            in excess of rttMonCtrlAdminThreshold.  This number is a
            subset of the accumulation of all 
            rttMonStatsCaptureCompletions.  The operation time 
            of these completed operations will be accumulated.
            
            This object has the special behavior as defined by the
            ROLLOVER NOTE in the DESCRIPTION of the ciscoRttMonMIB
            object.";
          smiv2:max-access "read-only";
          smiv2:oid "1.3.6.1.4.1.9.9.42.1.3.1.1.6";
        }

        leaf rttMonStatsCaptureSumCompletionTime {
          type yang:gauge32;
          units "milliseconds";
          description
           "The accumulated completion time of RTT operations which
            complete successfully.";
          smiv2:max-access "read-only";
          smiv2:oid "1.3.6.1.4.1.9.9.42.1.3.1.1.7";
        }

        leaf rttMonStatsCaptureSumCompletionTime2Low {
          type yang:gauge32;
          description
           "The low order 32 bits of the accumulated squares
            of completion times (in milliseconds) of RTT 
            operations which complete successfully.
            
            Low/High order is defined where the binary number
            will look as follows:
            -------------------------------------------------
            | High order 32 bits    | Low order 32 bits     |
            -------------------------------------------------
            For example the number 4294967296 would have all
            Low order bits as '0' and the rightmost High
            order bit will be 1 (zeros,1).";
          smiv2:max-access "read-only";
          smiv2:oid "1.3.6.1.4.1.9.9.42.1.3.1.1.8";
        }

        leaf rttMonStatsCaptureSumCompletionTime2High {
          type yang:gauge32;
          description
           "The high order 32 bits of the accumulated squares
            of completion times (in milliseconds) of RTT 
            operations which complete successfully.
            
            See the rttMonStatsCaptureSumCompletionTime2Low object
            for a definition of Low/High Order.";
          smiv2:max-access "read-only";
          smiv2:oid "1.3.6.1.4.1.9.9.42.1.3.1.1.9";
        }

        leaf rttMonStatsCaptureCompletionTimeMax {
          type yang:gauge32;
          units "milliseconds";
          description
           "The maximum completion time of any RTT operation which
            completes successfully.";
          smiv2:max-access "read-only";
          smiv2:oid "1.3.6.1.4.1.9.9.42.1.3.1.1.10";
        }

        leaf rttMonStatsCaptureCompletionTimeMin {
          type yang:gauge32;
          units "milliseconds";
          description
           "The minimum completion time of any RTT operation which
            completes successfully.";
          smiv2:max-access "read-only";
          smiv2:oid "1.3.6.1.4.1.9.9.42.1.3.1.1.11";
        }
      }
    }

    container rttMonStatsCollectTable {
      description
       "The statistics collection database.
        
        This table has the exact same behavior as the
        rttMonStatsCaptureTable, except it does not keep
        statistical distribution information.
        
        For a complete table description see
        the rttMonStatsCaptureTable object.";
      smiv2:oid "1.3.6.1.4.1.9.9.42.1.3.2";

      list rttMonStatsCollectEntry {
        key "rttMonCtrlAdminIndex rttMonStatsCaptureStartTimeIndex rttMonStatsCapturePathIndex rttMonStatsCaptureHopIndex";
        description
         "A list of objects which accumulate the results of a
          series of RTT operations over a 60 minute time period.
          
          This entry has the exact same behavior as the 
          rttMonStatsCaptureEntry, except it does not keep
          statistical distribution information.
          
          For a complete entry description see
          the rttMonStatsCaptureEntry object.";
        smiv2:oid "1.3.6.1.4.1.9.9.42.1.3.2.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonStatsCaptureStartTimeIndex {
          type leafref {
            path "/CISCO-RTTMON-MIB:CISCO-RTTMON-MIB/CISCO-RTTMON-MIB:rttMonStatsCaptureTable/CISCO-RTTMON-MIB:rttMonStatsCaptureEntry/CISCO-RTTMON-MIB:rttMonStatsCaptureStartTimeIndex";
          }
        }

        leaf rttMonStatsCapturePathIndex {
          type leafref {
            path "/CISCO-RTTMON-MIB:CISCO-RTTMON-MIB/CISCO-RTTMON-MIB:rttMonStatsCaptureTable/CISCO-RTTMON-MIB:rttMonStatsCaptureEntry/CISCO-RTTMON-MIB:rttMonStatsCapturePathIndex";
          }
        }

        leaf rttMonStatsCaptureHopIndex {
          type leafref {
            path "/CISCO-RTTMON-MIB:CISCO-RTTMON-MIB/CISCO-RTTMON-MIB:rttMonStatsCaptureTable/CISCO-RTTMON-MIB:rttMonStatsCaptureEntry/CISCO-RTTMON-MIB:rttMonStatsCaptureHopIndex";
          }
        }

        leaf rttMonStatsCollectNumDisconnects {
          type int32 {
            range "0..2147483647";
          }
          description
           "When the RttMonRttType is 'echo' or pathEcho', this
            object represents the number of times that the target or 
            hop along the path to a target became disconnected.  For
            all other values of RttMonRttType, this object will
            remain zero.
            
            For connectionless protocols this has no meaning,
            and will consequently remain 0.  When
            rttMonEchoAdminProtocol is one of snaRUEcho, this is
            the number of times that an LU-SSCP session was lost, 
            for snaLU0EchoAppl, snaLU2EchoAppl, snaLu62Echo, and for 
            snaLU62EchoAppl, this is the number of times that LU-LU 
            session was lost.
            
            Since this error does not indicate any information about
            the failure of an RTT operation, no response time 
            information for this instance will be recorded in the 
            appropriate objects.
            
            If this error occurs and the rttMonStatsCapturePathIndex 
            cannot be determined, this error will be accumulated in 
            the source to target path, that will always exist.
            
            This object has the special behavior as defined by the
            ROLLOVER NOTE in the DESCRIPTION of the ciscoRttMonMIB
            object.";
          smiv2:max-access "read-only";
          smiv2:oid "1.3.6.1.4.1.9.9.42.1.3.2.1.1";
        }

        leaf rttMonStatsCollectTimeouts {
          type int32 {
            range "0..2147483647";
          }
          description
           "The number of occasions when a RTT operation was not
            completed before a timeout occurred, i.e.
            rttMonCtrlAdminTimeout was exceeded.
            
            Since the RTT operation was never completed, the 
            completion time of these operations are not accumulated,
            nor do they increment rttMonStatsCaptureCompletions (in 
            any of the statistics distribution buckets).
            
            This object has the special behavior as defined by the
            ROLLOVER NOTE in the DESCRIPTION of the ciscoRttMonMIB
            object.";
          smiv2:max-access "read-only";
          smiv2:oid "1.3.6.1.4.1.9.9.42.1.3.2.1.2";
        }

        leaf rttMonStatsCollectBusies {
          type int32 {
            range "0..2147483647";
          }
          description
           "The number of occasions when a RTT operation could not
            be initiated because a previous RTT operation has not 
            been completed.
            
            When the RttMonRttType is 'pathEcho' this can occur for
            both connection oriented protocols and connectionless
            protocols.
            
            When the RttMonRttType is 'echo' this can only occur for
            connection oriented protocols such as SNA. 
            
            When the initiation of a new operation cannot be started,
            this object will be incremented and the operation will be
            omitted.  (The next operation will start at the next 
            Frequency).  Since, a RTT operation was never initiated, 
            the completion time of these operations is not 
            accumulated, nor do they increment 
            rttMonStatsCaptureCompletions.
            
            When the RttMonRttType is 'pathEcho', and this error 
            occurs and the rttMonStatsCapturePathIndex cannot be 
            determined, this error will be accumulated in the source 
            to target path, that will always exist.
            
            This object has the special behavior as defined by the
            ROLLOVER NOTE in the DESCRIPTION of the ciscoRttMonMIB
            object.";
          smiv2:max-access "read-only";
          smiv2:oid "1.3.6.1.4.1.9.9.42.1.3.2.1.3";
        }

        leaf rttMonStatsCollectNoConnections {
          type int32 {
            range "0..2147483647";
          }
          description
           "When the RttMonRttType is 'echo' or 'pathEcho' this is
            the number of occasions when a RTT operation could not be
            initiated because the connection to the target has not 
            been established.  For all other RttMonRttTypes this
            object will remain zero.
            
            This cannot occur for connectionless protocols, but may
            occur for connection oriented protocols, such as SNA.
            
            Since a RTT operation was never initiated, the completion
            time of these operations are not accumulated, nor do they
            increment rttMonStatsCaptureCompletions. 
            
            If this error occurs and the rttMonStatsCapturePathIndex
            cannot be determined, this error will be accumulated
            in the source to target path, that will always exist.
            
            This object has the special behavior as defined by the
            ROLLOVER NOTE in the DESCRIPTION of the ciscoRttMonMIB
            object.";
          smiv2:max-access "read-only";
          smiv2:oid "1.3.6.1.4.1.9.9.42.1.3.2.1.4";
        }

        leaf rttMonStatsCollectDrops {
          type int32 {
            range "0..2147483647";
          }
          description
           "The number of occasions when a RTT operation could not
            be initiated because some necessary internal resource 
            (for example memory, or SNA subsystem) was not available,
            or the operation completion could not be recognized.
            
            Since a RTT operation was never initiated or was not
            recognized, the completion time of these operations 
            are not accumulated, nor do they increment 
            rttMonStatsCaptureCompletions (in the expected 
            Distribution Bucket).
            
            When the RttMonRttType is 'pathEcho', and this error 
            occurs and the rttMonStatsCapturePathIndex cannot be 
            determined, this error will be accumulated in the 
            source to target path, that will always exist.
            
            This object has the special behavior as defined by the
            ROLLOVER NOTE in the DESCRIPTION of the ciscoRttMonMIB
            object.";
          smiv2:max-access "read-only";
          smiv2:oid "1.3.6.1.4.1.9.9.42.1.3.2.1.5";
        }

        leaf rttMonStatsCollectSequenceErrors {
          type int32 {
            range "0..2147483647";
          }
          description
           "When the RttMonRttType is 'echo' of 'pathEcho' this is
            the number of RTT operation completions received with 
            an unexpected sequence identifier.  For all other values
            of RttMonRttType this object will remain zero.
            
            When this has occurred some of the possible reasons may
            be:  
               - a duplicate packet was received
               - a response was received after it had timed-out
               - a corrupted packet was received and was not detected
            
            The completion time of these operations are not 
            accumulated, nor do they increment 
            rttMonStatsCaptureCompletions (in the expected
            Distribution Bucket).
            
            This object has the special behavior as defined by the
            ROLLOVER NOTE in the DESCRIPTION of the ciscoRttMonMIB
            object.";
          smiv2:max-access "read-only";
          smiv2:oid "1.3.6.1.4.1.9.9.42.1.3.2.1.6";
        }

        leaf rttMonStatsCollectVerifyErrors {
          type int32 {
            range "0..2147483647";
          }
          description
           "The number of RTT operation completions received with
            data that does not compare with the expected data.  The 
            completion time of these operations are not accumulated, 
            nor do they increment rttMonStatsCaptureCompletions (in
            the expected Distribution Bucket).
            
            This object has the special behavior as defined by the
            ROLLOVER NOTE in the DESCRIPTION of the ciscoRttMonMIB
            object.";
          smiv2:max-access "read-only";
          smiv2:oid "1.3.6.1.4.1.9.9.42.1.3.2.1.7";
        }

        leaf rttMonStatsCollectAddress {
          type cisco-rttmon:RttMonTargetAddress;
          description
           "This object only applies when the RttMonRttType is
            'echo', 'pathEcho', 'dlsw', 'udpEcho', 'tcpConnect'.  
            For all other values of the RttMonRttType, this will be 
            null. 
            
            The object is a string which specifies the address of 
            the target for the this RTT operation.
            
            This address will be the address of the hop along the 
            path to the rttMonEchoAdminTargetAddress address, 
            including rttMonEchoAdminTargetAddress address, or just 
            the rttMonEchoAdminTargetAddress address, when the 
            path information is not collected.  This behavior is
            defined by the rttMonCtrlAdminRttType object.
            
            The interpretation of this string depends on the type 
            of RTT operation selected, as specified by the 
            rttMonEchoAdminProtocol object.";
          smiv2:max-access "read-only";
          smiv2:oid "1.3.6.1.4.1.9.9.42.1.3.2.1.8";
        }

        leaf rttMonControlEnableErrors {
          type int32 {
            range "0..2147483647";
          }
          status deprecated;
          description
           "The number of occasions when control enable request failed.
            Currently it is used for multicast operation type.
            
            This object has the special behavior as defined by the
            ROLLOVER NOTE in the DESCRIPTION of the ciscoRttMonMIB
            object.
            rttMonControlEnableErrors object is superseded by
            rttMonStatsCollectCtrlEnErrors.";
          smiv2:max-access "read-only";
          smiv2:oid "1.3.6.1.4.1.9.9.42.1.3.2.1.9";
        }

        leaf rttMonStatsRetrieveErrors {
          type int32 {
            range "0..2147483647";
          }
          status deprecated;
          description
           "The number of occasions when stats retrieval request failed.
            Currently it is used for multicast operation type.
            
            This object has the special behavior as defined by the
            ROLLOVER NOTE in the DESCRIPTION of the ciscoRttMonMIB
            object.
            rttMonStatsRetrieveErrors object is superseded by
            rttMonStatsCollectRetrieveErrors.";
          smiv2:max-access "read-only";
          smiv2:oid "1.3.6.1.4.1.9.9.42.1.3.2.1.10";
        }

        leaf rttMonStatsCollectCtrlEnErrors {
          type int32 {
            range "0..2147483647";
          }
          description
           "The object is same as rttMonControlEnableErrors,
            with corrected name for consistency.
            
            The number of occasions when control enable request failed.
            Currently it is used for multicast operation type.
            
            This object has the special behavior as defined by the
            ROLLOVER NOTE in the DESCRIPTION of the ciscoRttMonMIB
            object.";
          smiv2:max-access "read-only";
          smiv2:oid "1.3.6.1.4.1.9.9.42.1.3.2.1.11";
        }

        leaf rttMonStatsCollectRetrieveErrors {
          type int32 {
            range "0..2147483647";
          }
          description
           "The object is same as rttMonStatsRetrieveErrors,
            with corrected name for consistency.
            
            The number of occasions when stats retrieval request failed.
            Currently it is used for multicast operation type.
            
            This object has the special behavior as defined by the
            ROLLOVER NOTE in the DESCRIPTION of the ciscoRttMonMIB
            object.";
          smiv2:max-access "read-only";
          smiv2:oid "1.3.6.1.4.1.9.9.42.1.3.2.1.12";
        }
      }
    }

    container rttMonStatsTotalsTable {
      description
       "The statistics totals database.
        
        This table has the exact same behavior as the
        rttMonStatsCaptureTable, except it only keeps
        60 minute group values.
        
        For a complete table description see
        the rttMonStatsCaptureTable object.";
      smiv2:oid "1.3.6.1.4.1.9.9.42.1.3.3";

      list rttMonStatsTotalsEntry {
        key "rttMonCtrlAdminIndex rttMonStatsCaptureStartTimeIndex";
        description
         "A list of objects which accumulate the results of a
          series of RTT operations over a 60 minute time period.
          
          This entry has the exact same behavior as the 
          rttMonStatsCaptureEntry, except it only keeps
          60 minute group values.
          
          For a complete entry description see
          the rttMonStatsCaptureEntry object.";
        smiv2:oid "1.3.6.1.4.1.9.9.42.1.3.3.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonStatsCaptureStartTimeIndex {
          type leafref {
            path "/CISCO-RTTMON-MIB:CISCO-RTTMON-MIB/CISCO-RTTMON-MIB:rttMonStatsCaptureTable/CISCO-RTTMON-MIB:rttMonStatsCaptureEntry/CISCO-RTTMON-MIB:rttMonStatsCaptureStartTimeIndex";
          }
        }

        leaf rttMonStatsTotalsElapsedTime {
          type snmpv2-tc:TimeInterval;
          description
           "The length of time since this conceptual statistics row
            was created.";
          smiv2:max-access "read-only";
          smiv2:oid "1.3.6.1.4.1.9.9.42.1.3.3.1.1";
        }

        leaf rttMonStatsTotalsInitiations {
          type int32 {
            range "0..2147483647";
          }
          description
           "The number of RTT operations that have been initiated.
            
            This number includes all RTT operations which succeed 
            or fail for whatever reason.
            
            This object has the special behavior as defined by the
            ROLLOVER NOTE in the DESCRIPTION of the ciscoRttMonMIB
            object.";
          smiv2:max-access "read-only";
          smiv2:oid "1.3.6.1.4.1.9.9.42.1.3.3.1.2";
        }
      }
    }

    container rttMonHTTPStatsTable {
      description
       "The HTTP statistics collection database.
        
        The HTTP statistics table contains summarized information of
        the results for a conceptual RTT control row. A rolling
        accumulated history of this information is maintained in a 
        series of hourly 'group(s)'.
        
        The operation of this table is same as that of 
        rttMonStatsCaptureTable, except that this table can only 
        store a maximum of 2 hours of data.";
      smiv2:oid "1.3.6.1.4.1.9.9.42.1.3.4";

      list rttMonHTTPStatsEntry {
        key "rttMonCtrlAdminIndex rttMonHTTPStatsStartTimeIndex";
        description
         "A list of objects which accumulate the results of a
          series of RTT operations over a 60 minute time period.
          
          This entry is created only if the rttMonCtrlAdminRttType 
          is http. The operation of this table is same as that of
          rttMonStatsCaptureTable.";
        smiv2:oid "1.3.6.1.4.1.9.9.42.1.3.4.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonHTTPStatsStartTimeIndex {
          type yang:timestamp;
          description
           "This is the time when this row was created. This index
            uniquely identifies a HTTP Stats row in the 
            rttMonHTTPStatsTable.";
          smiv2:max-access "not-accessible";
          smiv2:oid "1.3.6.1.4.1.9.9.42.1.3.4.1.1";
        }

        leaf rttMonHTTPStatsCompletions {
          type yang:counter32;
          description
           "The number of HTTP operations that have completed
            successfully.";
          smiv2:max-access "read-only";
          smiv2:oid "1.3.6.1.4.1.9.9.42.1.3.4.1.2";
        }

        leaf rttMonHTTPStatsOverThresholds {
          type yang:counter32;
          description
           "The number of HTTP operations that violate threshold.";
          smiv2:max-access "read-only";
          smiv2:oid "1.3.6.1.4.1.9.9.42.1.3.4.1.3";
        }

        leaf rttMonHTTPStatsRTTSum {
          type yang:counter32;
          description
           "The sum of HTTP operations that are successfully measured.";
          smiv2:max-access "read-only";
          smiv2:oid "1.3.6.1.4.1.9.9.42.1.3.4.1.4";
        }

        leaf rttMonHTTPStatsRTTSum2Low {
          type yang:counter32;
          description
           "The sum of squares of the RTT's that are successfully
            measured (low order 32 bits).";
          smiv2:max-access "read-only";
          smiv2:oid "1.3.6.1.4.1.9.9.42.1.3.4.1.5";
        }

        leaf rttMonHTTPStatsRTTSum2High {
          type yang:counter32;
          description
           "The sum of squares of the RTT's that are successfully
            measured (high order 32 bits).";
          smiv2:max-access "read-only";
          smiv2:oid "1.3.6.1.4.1.9.9.42.1.3.4.1.6";
        }

        leaf rttMonHTTPStatsRTTMin {
          type yang:gauge32;
          description
           "The minimum RTT taken to perform HTTP operation.";
          smiv2:max-access "read-only";
          smiv2:oid "1.3.6.1.4.1.9.9.42.1.3.4.1.7";
        }

        leaf rttMonHTTPStatsRTTMax {
          type yang:gauge32;
          units "milliseconds";
          description
           "The maximum RTT taken to perform HTTP operation.";
          smiv2:max-access "read-only";
          smiv2:oid "1.3.6.1.4.1.9.9.42.1.3.4.1.8";
        }

        leaf rttMonHTTPStatsDNSRTTSum {
          type yang:counter32;
          description
           "The sum of RTT taken to perform DNS query within the
            HTTP operation.";
          smiv2:max-access "read-only";
          smiv2:oid "1.3.6.1.4.1.9.9.42.1.3.4.1.9";
        }

        leaf rttMonHTTPStatsTCPConnectRTTSum {
          type yang:counter32;
          description
           "The sum of RTT taken to connect to the HTTP server.";
          smiv2:max-access "read-only";
          smiv2:oid "1.3.6.1.4.1.9.9.42.1.3.4.1.10";
        }

        leaf rttMonHTTPStatsTransactionRTTSum {
          type yang:counter32;
          description
           "The sum of RTT taken to download the object specified by URL.";
          smiv2:max-access "read-only";
          smiv2:oid "1.3.6.1.4.1.9.9.42.1.3.4.1.11";
        }

        leaf rttMonHTTPStatsMessageBodyOctetsSum {
          type yang:counter32;
          description
           "The sum of the size of the message body received as a
            response to the HTTP request.";
          smiv2:max-access "read-only";
          smiv2:oid "1.3.6.1.4.1.9.9.42.1.3.4.1.12";
        }

        leaf rttMonHTTPStatsDNSServerTimeout {
          type yang:counter32;
          description
           "The number of requests that could not connect to the
            DNS Server.";
          smiv2:max-access "read-only";
          smiv2:oid "1.3.6.1.4.1.9.9.42.1.3.4.1.13";
        }

        leaf rttMonHTTPStatsTCPConnectTimeout {
          type yang:counter32;
          description
           "The number of requests that could not connect to the
            the HTTP Server.";
          smiv2:max-access "read-only";
          smiv2:oid "1.3.6.1.4.1.9.9.42.1.3.4.1.14";
        }

        leaf rttMonHTTPStatsTransactionTimeout {
          type yang:counter32;
          description
           "The number of requests that timed out during HTTP
            transaction.";
          smiv2:max-access "read-only";
          smiv2:oid "1.3.6.1.4.1.9.9.42.1.3.4.1.15";
        }

        leaf rttMonHTTPStatsDNSQueryError {
          type yang:counter32;
          description
           "The number of requests that had DNS Query errors.";
          smiv2:max-access "read-only";
          smiv2:oid "1.3.6.1.4.1.9.9.42.1.3.4.1.16";
        }

        leaf rttMonHTTPStatsHTTPError {
          type yang:counter32;
          description
           "The number of requests that had HTTP errors while
            downloading the base page.";
          smiv2:max-access "read-only";
          smiv2:oid "1.3.6.1.4.1.9.9.42.1.3.4.1.17";
        }

        leaf rttMonHTTPStatsError {
          type yang:counter32;
          description
           "The number of occasions when a HTTP operation could not
            be initiated because an internal error";
          smiv2:max-access "read-only";
          smiv2:oid "1.3.6.1.4.1.9.9.42.1.3.4.1.18";
        }

        leaf rttMonHTTPStatsBusies {
          type yang:counter32;
          description
           "The number of occasions when an HTTP operation could not
            be initiated because a previous HTTP operation has not
            been completed.";
          smiv2:max-access "read-only";
          smiv2:oid "1.3.6.1.4.1.9.9.42.1.3.4.1.19";
        }
      }
    }

    container rttMonJitterStatsTable {
      description
       "The Jitter statistics collection database.
        
        The Jitter statistics table contains summarized information of
        the results for a conceptual RTT control row. A rolling
        accumulated history of this information is maintained in a 
        series of hourly 'group(s)'.
        
        The operation of this table is same as that of 
        rttMonStatsCaptureTable, except that this table will store 
        2 hours of data.";
      smiv2:oid "1.3.6.1.4.1.9.9.42.1.3.5";

      list rttMonJitterStatsEntry {
        key "rttMonCtrlAdminIndex rttMonJitterStatsStartTimeIndex";
        description
         "A list of objects which accumulate the results of a
          series of RTT operations over a 60 minute time period.
          
          This entry is created only if the rttMonCtrlAdminRttType 
          is jitter. The operation of this table is same as that of
          rttMonStatsCaptureTable.";
        smiv2:oid "1.3.6.1.4.1.9.9.42.1.3.5.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonJitterStatsStartTimeIndex {
          type yang:timestamp;
          description
           "The time when this row was created.";
          smiv2:max-access "not-accessible";
          smiv2:oid "1.3.6.1.4.1.9.9.42.1.3.5.1.1";
        }

        leaf rttMonJitterStatsCompletions {
          type yang:counter32;
          description
           "The number of jitter operation that have completed
            successfully.";
          smiv2:max-access "read-only";
          smiv2:oid "1.3.6.1.4.1.9.9.42.1.3.5.1.2";
        }

        leaf rttMonJitterStatsOverThresholds {
          type yang:counter32;
          description
           "The number of jitter operations that violate threshold.";
          smiv2:max-access "read-only";
          smiv2:oid "1.3.6.1.4.1.9.9.42.1.3.5.1.3";
        }

        leaf rttMonJitterStatsNumOfRTT {
          type yang:counter32;
          description
           "The number of RTT's that are successfully measured.";
          smiv2:max-access "read-only";
          smiv2:oid "1.3.6.1.4.1.9.9.42.1.3.5.1.4";
        }

        leaf rttMonJitterStatsRTTSum {
          type yang:counter32;
          description
           "The sum of RTT's that are successfully measured (low order 32
            bits). The high order 32 bits are stored in
            rttMonJitterStatsRTTSumHigh.";
          smiv2:max-access "read-only";
          smiv2:oid "1.3.6.1.4.1.9.9.42.1.3.5.1.5";
        }

        leaf rttMonJitterStatsRTTSum2Low {
          type yang:counter32;
          description
           "The sum of squares of RTT's that are successfully measured
            (low order 32 bits).";
          smiv2:max-access "read-only";
          smiv2:oid "1.3.6.1.4.1.9.9.42.1.3.5.1.6";
        }

        leaf rttMonJitterStatsRTTSum2High {
          type yang:counter32;
          description
           "The sum of squares of RTT's that are successfully measured
            (high order 32 bits).";
          smiv2:max-access "read-only";
          smiv2:oid "1.3.6.1.4.1.9.9.42.1.3.5.1.7";
        }

        leaf rttMonJitterStatsRTTMin {
          type yang:gauge32;
          description
           "The minimum of RTT's that were successfully measured";
          smiv2:max-access "read-only";
          smiv2:oid "1.3.6.1.4.1.9.9.42.1.3.5.1.8";
        }

        leaf rttMonJitterStatsRTTMax {
          type yang:gauge32;
          description
           "The maximum of RTT's that were successfully measured";
          smiv2:max-access "read-only";
          smiv2:oid "1.3.6.1.4.1.9.9.42.1.3.5.1.9";
        }

        leaf rttMonJitterStatsMinOfPositivesSD {
          type yang:gauge32;
          description
           "The minimum of absolute values of all positive jitter values
            from packets sent from source to destination.";
          smiv2:max-access "read-only";
          smiv2:oid "1.3.6.1.4.1.9.9.42.1.3.5.1.10";
        }

        leaf rttMonJitterStatsMaxOfPositivesSD {
          type yang:gauge32;
          description
           "The maximum of absolute values of all positive jitter values
            from packets sent from source to destination.";
          smiv2:max-access "read-only";
          smiv2:oid "1.3.6.1.4.1.9.9.42.1.3.5.1.11";
        }

        leaf rttMonJitterStatsNumOfPositivesSD {
          type yang:counter32;
          description
           "The sum of number of all positive jitter values from packets
            sent from source to destination.";
          smiv2:max-access "read-only";
          smiv2:oid "1.3.6.1.4.1.9.9.42.1.3.5.1.12";
        }

        leaf rttMonJitterStatsSumOfPositivesSD {
          type yang:counter32;
          description
           "The sum of all positive jitter values from packets
            sent from source to destination.";
          smiv2:max-access "read-only";
          smiv2:oid "1.3.6.1.4.1.9.9.42.1.3.5.1.13";
        }

        leaf rttMonJitterStatsSum2PositivesSDLow {
          type yang:counter32;
          description
           "The sum of square of RTT's of all positive jitter values from
            packets sent from source to destination (low order 32 bits).";
          smiv2:max-access "read-only";
          smiv2:oid "1.3.6.1.4.1.9.9.42.1.3.5.1.14";
        }

        leaf rttMonJitterStatsSum2PositivesSDHigh {
          type yang:counter32;
          description
           "The sum of square of RTT's of all positive jitter values from
            packets sent from source to destination (high order 32 bits).";
          smiv2:max-access "read-only";
          smiv2:oid "1.3.6.1.4.1.9.9.42.1.3.5.1.15";
        }

        leaf rttMonJitterStatsMinOfNegativesSD {
          type yang:gauge32;
          description
           "The minimum of all negative jitter values from packets sent
            from source to destination.";
          smiv2:max-access "read-only";
          smiv2:oid "1.3.6.1.4.1.9.9.42.1.3.5.1.16";
        }

        leaf rttMonJitterStatsMaxOfNegativesSD {
          type yang:gauge32;
          description
           "The maximum of all negative jitter values from packets sent
            from source to destination.";
          smiv2:max-access "read-only";
          smiv2:oid "1.3.6.1.4.1.9.9.42.1.3.5.1.17";
        }

        leaf rttMonJitterStatsNumOfNegativesSD {
          type yang:counter32;
          description
           "The sum of number of all negative jitter values from packets
            sent from source to destination.";
          smiv2:max-access "read-only";
          smiv2:oid "1.3.6.1.4.1.9.9.42.1.3.5.1.18";
        }

        leaf rttMonJitterStatsSumOfNegativesSD {
          type yang:counter32;
          description
           "The sum of RTT's of all negative jitter values from packets
            sent from source to destination.";
          smiv2:max-access "read-only";
          smiv2:oid "1.3.6.1.4.1.9.9.42.1.3.5.1.19";
        }

        leaf rttMonJitterStatsSum2NegativesSDLow {
          type yang:counter32;
          description
           "The sum of square of RTT's of all negative jitter values from
            packets sent from source to destination (low order 32 bits).";
          smiv2:max-access "read-only";
          smiv2:oid "1.3.6.1.4.1.9.9.42.1.3.5.1.20";
        }

        leaf rttMonJitterStatsSum2NegativesSDHigh {
          type yang:counter32;
          description
           "The sum of square of RTT's of all negative jitter values from
            packets sent from source to destination (high order 32 bits).";
          smiv2:max-access "read-only";
          smiv2:oid "1.3.6.1.4.1.9.9.42.1.3.5.1.21";
        }

        leaf rttMonJitterStatsMinOfPositivesDS {
          type yang:gauge32;
          description
           "The minimum of all positive jitter values from packets sent
            from destination to source.";
          smiv2:max-access "read-only";
          smiv2:oid "1.3.6.1.4.1.9.9.42.1.3.5.1.22";
        }

        leaf rttMonJitterStatsMaxOfPositivesDS {
          type yang:gauge32;
          description
           "The maximum of all positive jitter values from packets sent
            from destination to source.";
          smiv2:max-access "read-only";
          smiv2:oid "1.3.6.1.4.1.9.9.42.1.3.5.1.23";
        }

        leaf rttMonJitterStatsNumOfPositivesDS {
          type yang:counter32;
          description
           "The sum of number of all positive jitter values from packets
            sent from destination to source.";
          smiv2:max-access "read-only";
          smiv2:oid "1.3.6.1.4.1.9.9.42.1.3.5.1.24";
        }

        leaf rttMonJitterStatsSumOfPositivesDS {
          type yang:counter32;
          description
           "The sum of RTT's of all positive jitter values from packets
            sent from destination to source.";
          smiv2:max-access "read-only";
          smiv2:oid "1.3.6.1.4.1.9.9.42.1.3.5.1.25";
        }

        leaf rttMonJitterStatsSum2PositivesDSLow {
          type yang:counter32;
          description
           "The sum of squares of RTT's of all positive jitter values from
            packets sent from destination to source (low order 32 bits).";
          smiv2:max-access "read-only";
          smiv2:oid "1.3.6.1.4.1.9.9.42.1.3.5.1.26";
        }

        leaf rttMonJitterStatsSum2PositivesDSHigh {
          type yang:counter32;
          description
           "The sum of squares of RTT's of all positive jitter values from
            packets sent from destination to source (high order 32 bits).";
          smiv2:max-access "read-only";
          smiv2:oid "1.3.6.1.4.1.9.9.42.1.3.5.1.27";
        }

        leaf rttMonJitterStatsMinOfNegativesDS {
          type yang:gauge32;
          description
           "The minimum of all negative jitter values from packets sent
            from destination to source.";
          smiv2:max-access "read-only";
          smiv2:oid "1.3.6.1.4.1.9.9.42.1.3.5.1.28";
        }

        leaf rttMonJitterStatsMaxOfNegativesDS {
          type yang:gauge32;
          description
           "The maximum of all negative jitter values from packets sent
            from destination to source.";
          smiv2:max-access "read-only";
          smiv2:oid "1.3.6.1.4.1.9.9.42.1.3.5.1.29";
        }

        leaf rttMonJitterStatsNumOfNegativesDS {
          type yang:counter32;
          description
           "The sum of number of all negative jitter values from packets
            sent from destination to source.";
          smiv2:max-access "read-only";
          smiv2:oid "1.3.6.1.4.1.9.9.42.1.3.5.1.30";
        }

        leaf rttMonJitterStatsSumOfNegativesDS {
          type yang:counter32;
          description
           "The sum of RTT's of all negative jitter values from packets
            sent from destination to source.";
          smiv2:max-access "read-only";
          smiv2:oid "1.3.6.1.4.1.9.9.42.1.3.5.1.31";
        }

        leaf rttMonJitterStatsSum2NegativesDSLow {
          type yang:counter32;
          description
           "The sum of squares of RTT's of all negative jitter values from
            packets sent from destination to source (low order 32 bits).";
          smiv2:max-access "read-only";
          smiv2:oid "1.3.6.1.4.1.9.9.42.1.3.5.1.32";
        }

        leaf rttMonJitterStatsSum2NegativesDSHigh {
          type yang:counter32;
          description
           "The sum of squares of RTT's of all negative jitter values from
            packets sent from destination to source (high order 32 bits).";
          smiv2:max-access "read-only";
          smiv2:oid "1.3.6.1.4.1.9.9.42.1.3.5.1.33";
        }

        leaf rttMonJitterStatsPacketLossSD {
          type yang:counter32;
          description
           "The number of packets lost when sent from source to
            destination.";
          smiv2:max-access "read-only";
          smiv2:oid "1.3.6.1.4.1.9.9.42.1.3.5.1.34";
        }

        leaf rttMonJitterStatsPacketLossDS {
          type yang:counter32;
          description
           "The number of packets lost when sent from destination to
            source.";
          smiv2:max-access "read-only";
          smiv2:oid "1.3.6.1.4.1.9.9.42.1.3.5.1.35";
        }

        leaf rttMonJitterStatsPacketOutOfSequence {
          type yang:counter32;
          description
           "The number of packets arrived out of sequence.";
          smiv2:max-access "read-only";
          smiv2:oid "1.3.6.1.4.1.9.9.42.1.3.5.1.36";
        }

        leaf rttMonJitterStatsPacketMIA {
          type yang:counter32;
          description
           "The number of packets that are lost for which we cannot
            determine the direction.";
          smiv2:max-access "read-only";
          smiv2:oid "1.3.6.1.4.1.9.9.42.1.3.5.1.37";
        }

        leaf rttMonJitterStatsPacketLateArrival {
          type yang:counter32;
          description
           "The number of packets that arrived after the timeout.";
          smiv2:max-access "read-only";
          smiv2:oid "1.3.6.1.4.1.9.9.42.1.3.5.1.38";
        }

        leaf rttMonJitterStatsError {
          type yang:counter32;
          description
           "The number of occasions when a jitter operation could not
            be initiated because an internal error";
          smiv2:max-access "read-only";
          smiv2:oid "1.3.6.1.4.1.9.9.42.1.3.5.1.39";
        }

        leaf rttMonJitterStatsBusies {
          type yang:counter32;
          description
           "The number of occasions when a jitter operation could not
            be initiated because a previous jitter operation has not
            been completed.";
          smiv2:max-access "read-only";
          smiv2:oid "1.3.6.1.4.1.9.9.42.1.3.5.1.40";
        }

        leaf rttMonJitterStatsOWSumSD {
          type yang:counter32;
          description
           "The sum of one way times from source to destination (low order
            32 bits). The high order 32 bits are stored in
            rttMonJitterStatsOWSumSDHigh.";
          smiv2:max-access "read-only";
          smiv2:oid "1.3.6.1.4.1.9.9.42.1.3.5.1.41";
        }

        leaf rttMonJitterStatsOWSum2SDLow {
          type yang:counter32;
          description
           "The sum of squares of one way times from source to destination
            (low order 32 bits).";
          smiv2:max-access "read-only";
          smiv2:oid "1.3.6.1.4.1.9.9.42.1.3.5.1.42";
        }

        leaf rttMonJitterStatsOWSum2SDHigh {
          type yang:counter32;
          description
           "The sum of squares of one way times from source to destination
            (high order 32 bits).";
          smiv2:max-access "read-only";
          smiv2:oid "1.3.6.1.4.1.9.9.42.1.3.5.1.43";
        }

        leaf rttMonJitterStatsOWMinSD {
          type yang:counter32;
          status deprecated;
          description
           "The minimum of all one way times from source to destination.
            rttMonJitterStatsOWMinSD object is superseded by
            rttMonJitterStatsOWMinSDNew.";
          smiv2:max-access "read-only";
          smiv2:oid "1.3.6.1.4.1.9.9.42.1.3.5.1.44";
        }

        leaf rttMonJitterStatsOWMaxSD {
          type yang:counter32;
          status deprecated;
          description
           "The maximum of all one way times from source to destination.
            rttMonJitterStatsOWMaxSD object is superseded by
            rttMonJitterStatsOWMaxSDNew.";
          smiv2:max-access "read-only";
          smiv2:oid "1.3.6.1.4.1.9.9.42.1.3.5.1.45";
        }

        leaf rttMonJitterStatsOWSumDS {
          type yang:counter32;
          description
           "The sum of one way times from destination to source (low order
            32 bits). The high order 32 bits are stored in
            rttMonJitterStatsOWSumDSHigh.";
          smiv2:max-access "read-only";
          smiv2:oid "1.3.6.1.4.1.9.9.42.1.3.5.1.46";
        }

        leaf rttMonJitterStatsOWSum2DSLow {
          type yang:counter32;
          description
           "The sum of squares of one way times from destination to source
            (low order 32 bits).";
          smiv2:max-access "read-only";
          smiv2:oid "1.3.6.1.4.1.9.9.42.1.3.5.1.47";
        }

        leaf rttMonJitterStatsOWSum2DSHigh {
          type yang:counter32;
          description
           "The sum of squares of one way times from destination to source
            (high order 32 bits).";
          smiv2:max-access "read-only";
          smiv2:oid "1.3.6.1.4.1.9.9.42.1.3.5.1.48";
        }

        leaf rttMonJitterStatsOWMinDS {
          type yang:counter32;
          status deprecated;
          description
           "The minimum of all one way times from destination to source.
            rttMonJitterStatsOWMinDS object is superseded by
            rttMonJitterStatsOWMinDSNew.";
          smiv2:max-access "read-only";
          smiv2:oid "1.3.6.1.4.1.9.9.42.1.3.5.1.49";
        }

        leaf rttMonJitterStatsOWMaxDS {
          type yang:counter32;
          status deprecated;
          description
           "The maximum of all one way times from destination to source.
            rttMonJitterStatsOWMaxDS object is superseded by
            rttMonJitterStatsOWMaxDSNew.";
          smiv2:max-access "read-only";
          smiv2:oid "1.3.6.1.4.1.9.9.42.1.3.5.1.50";
        }

        leaf rttMonJitterStatsNumOfOW {
          type yang:counter32;
          description
           "The number of one way times that are successfully measured.";
          smiv2:max-access "read-only";
          smiv2:oid "1.3.6.1.4.1.9.9.42.1.3.5.1.51";
        }

        leaf rttMonJitterStatsOWMinSDNew {
          type yang:gauge32;
          description
           "The minimum of all one way times from source to destination.
            Replaces deprecated rttMonJitterStatsOWMinSD.";
          smiv2:max-access "read-only";
          smiv2:oid "1.3.6.1.4.1.9.9.42.1.3.5.1.52";
        }

        leaf rttMonJitterStatsOWMaxSDNew {
          type yang:gauge32;
          description
           "The maximum of all one way times from source to destination.
            Replaces deprecated rttMonJitterStatsOWMaxSD.";
          smiv2:max-access "read-only";
          smiv2:oid "1.3.6.1.4.1.9.9.42.1.3.5.1.53";
        }

        leaf rttMonJitterStatsOWMinDSNew {
          type yang:gauge32;
          description
           "The minimum of all one way times from destination to source.
            Replaces deprecated rttMonJitterStatsOWMinDS.";
          smiv2:max-access "read-only";
          smiv2:oid "1.3.6.1.4.1.9.9.42.1.3.5.1.54";
        }

        leaf rttMonJitterStatsOWMaxDSNew {
          type yang:gauge32;
          description
           "The maximum of all one way times from destination to source.
            Replaces deprecated rttMonJitterStatsOWMaxDS";
          smiv2:max-access "read-only";
          smiv2:oid "1.3.6.1.4.1.9.9.42.1.3.5.1.55";
        }

        leaf rttMonJitterStatsMinOfMOS {
          type yang:gauge32 {
            range "0|100..500";
          }
          description
           "The minimum of all MOS values for the jitter operations
            in hundreds. 
            This value will be 0 if 
             - rttMonEchoAdminCodecType of the operation is notApplicable 
             - the operation is not started 
             - the operation is started but failed
            This value will be 1 for packet loss of 10% or more.";
          smiv2:max-access "read-only";
          smiv2:oid "1.3.6.1.4.1.9.9.42.1.3.5.1.56";
        }

        leaf rttMonJitterStatsMaxOfMOS {
          type yang:gauge32 {
            range "0|100..500";
          }
          description
           "The maximum of all MOS values for the jitter operations
            in hunderds. 
            This value will be 0 if 
             - rttMonEchoAdminCodecType of the operation is notApplicable 
             - the operation is not started 
             - the operation is started but failed
            This value will be 1 for packet loss of 10% or more.";
          smiv2:max-access "read-only";
          smiv2:oid "1.3.6.1.4.1.9.9.42.1.3.5.1.57";
        }

        leaf rttMonJitterStatsMinOfICPIF {
          type yang:gauge32;
          description
           "The minimum of all ICPIF values for the jitter operations.
            
            This value will be 93 for packet loss of 10% or more.";
          smiv2:max-access "read-only";
          smiv2:oid "1.3.6.1.4.1.9.9.42.1.3.5.1.58";
        }

        leaf rttMonJitterStatsMaxOfICPIF {
          type yang:gauge32;
          description
           "The maximum of all ICPIF values for the jitter operations.
            
            This value will be 93 for packet loss of 10% or more.";
          smiv2:max-access "read-only";
          smiv2:oid "1.3.6.1.4.1.9.9.42.1.3.5.1.59";
        }

        leaf rttMonJitterStatsIAJOut {
          type yang:gauge32;
          description
           "Interarrival Jitter (RFC 1889) at responder";
          reference
           "Refer to the following documents for the definition: RFC 1889";
          smiv2:max-access "read-only";
          smiv2:oid "1.3.6.1.4.1.9.9.42.1.3.5.1.60";
        }

        leaf rttMonJitterStatsIAJIn {
          type yang:gauge32;
          description
           "Interarrival Jitter (RFC 1889) at sender";
          reference
           "Refer to the following documents for the definition: RFC 1889";
          smiv2:max-access "read-only";
          smiv2:oid "1.3.6.1.4.1.9.9.42.1.3.5.1.61";
        }

        leaf rttMonJitterStatsAvgJitter {
          type yang:gauge32;
          description
           "The average of positive and negative jitter
            values for SD and DS direction.";
          smiv2:max-access "read-only";
          smiv2:oid "1.3.6.1.4.1.9.9.42.1.3.5.1.62";
        }

        leaf rttMonJitterStatsAvgJitterSD {
          type yang:gauge32;
          description
           "The average of positive and negative jitter
            values in SD direction.";
          smiv2:max-access "read-only";
          smiv2:oid "1.3.6.1.4.1.9.9.42.1.3.5.1.63";
        }

        leaf rttMonJitterStatsAvgJitterDS {
          type yang:gauge32;
          description
           "The average of positive and negative jitter
            values in DS direction.";
          smiv2:max-access "read-only";
          smiv2:oid "1.3.6.1.4.1.9.9.42.1.3.5.1.64";
        }

        leaf rttMonJitterStatsUnSyncRTs {
          type yang:counter32;
          description
           "The number of RTT operations that have completed with
            sender and responder out of sync with NTP. The NTP sync means 
            the total of NTP offset on sender and responder is within 
            configured tolerance level.";
          smiv2:max-access "read-only";
          smiv2:oid "1.3.6.1.4.1.9.9.42.1.3.5.1.65";
        }

        leaf rttMonJitterStatsRTTSumHigh {
          type yang:counter32;
          description
           "The sum of RTT's that are successfully measured
            (high order 32 bits). The low order 32 bits are 
            stored in rttMonJitterStatsRTTSum.";
          smiv2:max-access "read-only";
          smiv2:oid "1.3.6.1.4.1.9.9.42.1.3.5.1.66";
        }

        leaf rttMonJitterStatsOWSumSDHigh {
          type yang:counter32;
          description
           "The sum of one way times from source to destination
            (high order 32 bits). The low order 32 bits are 
            stored in rttMonJitterStatsOWSumSD.";
          smiv2:max-access "read-only";
          smiv2:oid "1.3.6.1.4.1.9.9.42.1.3.5.1.67";
        }

        leaf rttMonJitterStatsOWSumDSHigh {
          type yang:counter32;
          description
           "The sum of one way times from destination to source
            (high order 32 bits). The low order 32 bits are stored
            in rttMonJitterStatsOWSumDS.";
          smiv2:max-access "read-only";
          smiv2:oid "1.3.6.1.4.1.9.9.42.1.3.5.1.68";
        }
      }
    }

    container rttMonLpdGrpStatsTable {
      description
       "The Auto SAA L3 MPLS VPN LPD Group Database.
        
        The LPD Group statistics table contains summarized performance
        statistics for the LPD group.
        
        LPD Group - The set of 'single probes' which are subset of the
        'lspGroup' probe traversing set of paths between two PE end
        points are grouped together and called as the LPD group. The
        LPD group will be uniquely referenced by the LPD Group ID.
        
        A rolling accumulated history of this information is maintained
        in a series of hourly 'group(s)'.
        
        Each conceptual statistics row has a current hourly group, into
        which RTT results are accumulated. At the end of each hour a new
        hourly group is created which then becomes current. The
        counters and accumulators in the new group are initialized to
        zero. The previous group(s) is kept in the table until the table
        contains rttMplsVpnMonTypeLpdStatHours groups for the
        conceptual statistics row;  at this point, the oldest group is
        discarded and is replaced by the newly created one. The hourly
        group is uniquely identified by the
        rttMonLpdGrpStatsStartTimeIndex object.";
      smiv2:oid "1.3.6.1.4.1.9.9.42.1.3.7";

      list rttMonLpdGrpStatsEntry {
        key "rttMonLpdGrpStatsGroupIndex rttMonLpdGrpStatsStartTimeIndex";
        description
         "A list of objects which accumulate the results of a set of RTT
          operations over a 60 minute time period.
          
          The LPD group statistics table is a rollover table. When
          rttMonLpdGrpStatsStartTimeIndex groups exceeds the
          rttMplsVpnMonTypeLpdStatHours value, the oldest corresponding
          hourly group will be deleted and will be replaced with the new
          rttMonLpdGrpStatsStartTimeIndex hourly group.
          
          The LPD group statistics table has two indices. Each described
          as follows:
          
          - The first index correlates its entries to a LPD group via the
             rttMonLpdGrpStatsGroupIndex object.
          - The second index is a rollover group and it uniquely 
             identifies a 60 minute group. (The 
             rttMonLpdGrpStatsStartTimeIndex is used to make this value 
             unique.)";
        smiv2:oid "1.3.6.1.4.1.9.9.42.1.3.7.1";

        leaf rttMonLpdGrpStatsGroupIndex {
          type int32 {
            range "1..2147483647";
          }
          description
           "Uniquely identifies a row in rttMonLpdGrpStatsTable.
            
            This is a pseudo-random number which identifies a particular
            LPD group.";
          smiv2:max-access "not-accessible";
          smiv2:oid "1.3.6.1.4.1.9.9.42.1.3.7.1.1";
        }

        leaf rttMonLpdGrpStatsStartTimeIndex {
          type yang:timestamp;
          description
           "The time when this row was created.
            
            This object is the second index of the rttMonLpdGrpStatsTable.
            When the number of rttMonLpdGrpStatsStartTimeIndex groups
            exceeds the rttMplsVpnMonTypeLpdStatHours value, the oldest
            rttMonLpdGrpStatsStartTimeIndex group will be removed and
            replaced with the new entry.";
          smiv2:max-access "not-accessible";
          smiv2:oid "1.3.6.1.4.1.9.9.42.1.3.7.1.2";
        }

        leaf rttMonLpdGrpStatsTargetPE {
          type cisco-rttmon:RttMonTargetAddress;
          description
           "The object is a string that specifies the address of the
            target PE for this LPD group.";
          smiv2:max-access "read-only";
          smiv2:oid "1.3.6.1.4.1.9.9.42.1.3.7.1.3";
        }

        leaf rttMonLpdGrpStatsNumOfPass {
          type int32 {
            range "0..2147483647";
          }
          units "passes";
          description
           "This object represents the number of successfull completions
            of 'single probes' for all the set of paths in the LPD group.
            
            Whenever the rttMonLatestRttOperSense value is 'ok' for a
            particular probe in the LPD Group this object will be
            incremented.
            
            This object will be set to '0' on reset.";
          smiv2:max-access "read-only";
          smiv2:oid "1.3.6.1.4.1.9.9.42.1.3.7.1.4";
        }

        leaf rttMonLpdGrpStatsNumOfFail {
          type int32 {
            range "0..2147483647";
          }
          units "failures";
          description
           "This object represents the number of failed operations of
            'single probes' for all the set of paths in the LPD group.
            
            Whenever the rttMonLatestRttOperSense has a value other than
            'ok' or 'timeout' for a particular probe in the LPD Group this
            object will be incremented.
            
            This object will be set to '0' on reset.";
          smiv2:max-access "read-only";
          smiv2:oid "1.3.6.1.4.1.9.9.42.1.3.7.1.5";
        }

        leaf rttMonLpdGrpStatsNumOfTimeout {
          type int32 {
            range "0..2147483647";
          }
          units "timeouts";
          description
           "This object represents the number of timed out operations of
            'single probes' for all the set of paths in the LPD group.
            
            Whenever the rttMonLatestRttOperSense has a value of 'timeout'
            for a particular probe in the LPD Group this object will be
            incremented.
            
            This object will be set to '0' on reset.";
          smiv2:max-access "read-only";
          smiv2:oid "1.3.6.1.4.1.9.9.42.1.3.7.1.6";
        }

        leaf rttMonLpdGrpStatsAvgRTT {
          type int32 {
            range "0..2147483647";
          }
          units "milliseconds";
          description
           "The average RTT across all set of probes in the LPD group.
            
            This object will be set to '0' on reset.";
          smiv2:max-access "read-only";
          smiv2:oid "1.3.6.1.4.1.9.9.42.1.3.7.1.7";
        }

        leaf rttMonLpdGrpStatsMinRTT {
          type int32 {
            range "0..2147483647";
          }
          units "milliseconds";
          description
           "The minimum of RTT's for all set of probes in the LPD group
            that were successfully measured.
            
            This object will be set to '0' on reset.";
          smiv2:max-access "read-only";
          smiv2:oid "1.3.6.1.4.1.9.9.42.1.3.7.1.8";
        }

        leaf rttMonLpdGrpStatsMaxRTT {
          type int32 {
            range "0..2147483647";
          }
          units "milliseconds";
          description
           "The maximum of RTT's for all set of probes in the LPD group
            that were successfully measured.
            
            This object will be set to '0' on reset.";
          smiv2:max-access "read-only";
          smiv2:oid "1.3.6.1.4.1.9.9.42.1.3.7.1.9";
        }

        leaf rttMonLpdGrpStatsMinNumPaths {
          type int32 {
            range "0..2147483647";
          }
          units "paths";
          description
           "The minimum number of active paths discovered to the
            rttMonLpdGrpStatsTargetPE target.
            
            This object will be set to '0' on reset.";
          smiv2:max-access "read-only";
          smiv2:oid "1.3.6.1.4.1.9.9.42.1.3.7.1.10";
        }

        leaf rttMonLpdGrpStatsMaxNumPaths {
          type int32 {
            range "0..2147483647";
          }
          units "paths";
          description
           "The maximum number of active paths discovered to the
            rttMonLpdGrpStatsTargetPE target.
            
            This object will be set to '0' on reset.";
          smiv2:max-access "read-only";
          smiv2:oid "1.3.6.1.4.1.9.9.42.1.3.7.1.11";
        }

        leaf rttMonLpdGrpStatsLPDStartTime {
          type yang:timestamp;
          units "tenths of milliseconds";
          description
           "The time when the last LSP Path Discovery to the group was
            attempted.
            
            This object will be set to '0' on reset.";
          smiv2:max-access "read-only";
          smiv2:oid "1.3.6.1.4.1.9.9.42.1.3.7.1.12";
        }

        leaf rttMonLpdGrpStatsLPDFailOccurred {
          type boolean;
          description
           "This object is set to true when the LSP Path Discovery
            to the target PE i.e. rttMonLpdGrpStatsTargetPE fails, and
            set to false when the LSP Path Discovery succeeds.
            
            When this value changes and rttMplsVpnMonReactLpdNotifyType is
            set to 'lpdPathDiscovery' or 'lpdAll' a
            rttMonLpdDiscoveryNotification will be generated.
            
            This object will be set to 'FALSE' on reset.";
          smiv2:max-access "read-only";
          smiv2:oid "1.3.6.1.4.1.9.9.42.1.3.7.1.13";
        }

        leaf rttMonLpdGrpStatsLPDFailCause {
          type cisco-rttmon:RttMplsVpnMonLpdFailureSense;
          description
           "This object identifies the cause of failure for the LSP Path
            Discovery last attempted. It will be only valid if
            rttMonLpdGrpStatsLPDFailOccurred is set to true.
            
            This object will be set to 'unknown' on reset.";
          smiv2:max-access "read-only";
          smiv2:oid "1.3.6.1.4.1.9.9.42.1.3.7.1.14";
        }

        leaf rttMonLpdGrpStatsLPDCompTime {
          type int32 {
            range "0..65535";
          }
          units "seconds";
          description
           "The completion time of the last successfull LSP Path Discovery
            to the target PE.
            
            This object will be set to '0' on reset.";
          smiv2:max-access "read-only";
          smiv2:oid "1.3.6.1.4.1.9.9.42.1.3.7.1.15";
        }

        leaf rttMonLpdGrpStatsGroupStatus {
          type cisco-rttmon:RttMplsVpnMonLpdGrpStatus;
          description
           "This object identifies the LPD Group status.
            
            When the LPD Group status changes and
            rttMplsVpnMonReactLpdNotifyType is set to 'lpdGroupStatus' or
            'lpdAll' a rttMonLpdGrpStatusNotification will be generated.
            
            When the LPD Group status value is 'unknown' or changes to
            'unknown' this notification will not be generated.
            
            When LSP Path Discovery is enabled for a particular row in
            rttMplsVpnMonCtrlTable, 'single probes' in the 'lspGroup' probe
            cannot generate notifications independently but will be
            generating depending on the state of the group. Notifications 
            are only generated if the failure/restoration of an individual
            probe causes the state of the LPD Group to change.
            
            This object will be set to 'unknown' on reset.";
          smiv2:max-access "read-only";
          smiv2:oid "1.3.6.1.4.1.9.9.42.1.3.7.1.16";
        }

        leaf rttMonLpdGrpStatsGroupProbeIndex {
          type int32 {
            range "1..2147483647";
          }
          units "identifier";
          description
           "This object identifies 'lspGroup' probe uniquely created for
            this particular LPD Group.";
          smiv2:max-access "read-only";
          smiv2:oid "1.3.6.1.4.1.9.9.42.1.3.7.1.17";
        }

        leaf rttMonLpdGrpStatsPathIds {
          type snmpv2-tc:DisplayString;
          description
           "A string which holds the list of information to uniquely
            identify the paths to the target PE. This information is used
            by the 'single probes' when testing the paths.
            
            Following three parameters are needed to uniquely identify a 
            path
              - lsp-selector (127.x.x.x)
              - outgoing-interface (i/f)
              - label-stack (s), if mutiple labels they will be colon (:)
                separated.
            
            These parameters will be hyphen (-) separated for a particular
            path. This set of information will be comma (,) separated for
            all the paths discovered as part of this LPD Group.
            
            For example: If there are 5 paths in the LPD group then this
            object will return all the identifier's to uniquely identify
            the path.
            
            The output will look like '127.0.0.1-Se3/0.1-20:18,
            127.0.0.2-Se3/0.1-20,127.0.0.3-Se3/0.1-20,127.0.0.4-Se3/0.1-20,
            127.0.0.5-Se3/0.1-20'.
            
            This object will be set to '0' on reset.";
          smiv2:max-access "read-only";
          smiv2:oid "1.3.6.1.4.1.9.9.42.1.3.7.1.18";
        }

        leaf rttMonLpdGrpStatsProbeStatus {
          type snmpv2-tc:DisplayString;
          description
           "A string which holds the latest operation return code for
            all the set of 'single probes' which are part of the LPD group.
            The return codes will be comma separated and will follow the
            same sequence of probes as followed in
            'rttMonLpdGrpStatsPathIds'. The latest operation return code
            will be mapped to 'up','down' or 'unkwown'.
            
            'up' - Probe state is up when the rttMonLatestRttOperSense
            value is 'ok'.
            'down' - Probe state is down when the rttMonLatestRttOperSense
            has value other then 'ok' and 'other'.
            'unknown' - Probe state is unkown when the
            rttMonLatestRttOperSense value is 'other'.
            
            For example: If there are 5 paths in the LPD group then this
            object output will look like 'ok,ok,ok,down,down'.
            
            This object will be set to '0' on reset.";
          smiv2:max-access "read-only";
          smiv2:oid "1.3.6.1.4.1.9.9.42.1.3.7.1.19";
        }

        leaf rttMonLpdGrpStatsResetTime {
          type yang:timestamp;
          description
           "This object specifies the time when this statistics row was
            last reset using the rttMonApplLpdGrpStatsReset object.";
          smiv2:max-access "read-only";
          smiv2:oid "1.3.6.1.4.1.9.9.42.1.3.7.1.20";
        }
      }
    }

    container rttMonHistoryCollectionTable {
      description
       "The history collection database.
        
        The history table contains a point by point rolling 
        history of the most recent RTT operations for each 
        conceptual RTT control row.  The rolling history of this 
        information is maintained in a series of 'live(s)', each
        containing a series of 'bucket(s)', each 'bucket' 
        contains a series of 'sample(s)'.
        
        Each conceptual history row can have lives.  A life is 
        defined by the rttMonCtrlOperRttLife object.  A new life 
        will be created when rttMonCtrlOperState transitions
        'active'.  When the number of lives become greater 
        than rttMonHistoryAdminNumLives the oldest life will be 
        discarded and a new life will be created by incrementing
        the index.
        
        The path exploration RTT operation will be kept as an
        entry in this table.";
      smiv2:oid "1.3.6.1.4.1.9.9.42.1.4.1";

      list rttMonHistoryCollectionEntry {
        key "rttMonCtrlAdminIndex rttMonHistoryCollectionLifeIndex rttMonHistoryCollectionBucketIndex rttMonHistoryCollectionSampleIndex";
        description
         "A list of history objects that are recorded for each
          RTT operation.
          
          The history collection table has four indices.  Each 
          described as follows:
            -  The first index correlates its entries to a 
                conceptual RTT control row via the 
                rttMonCtrlAdminIndex object.  
            -  The second index uniquely identifies the results 
                of each 'life' as defined by the 
                rttMonCtrlOperRttLife object.  
            -  The third index uniquely identifies the number of 
                buckets in a life.  A bucket will contain one 
                sample per bucket if the rttMonCtrlAdminRttType 
                object is set to any value
                other than 'pathEcho'.  If the 
                rttMonCtrlAdminRttType object is set to 
                'pathEcho', a bucket will contain one sample per 
                hop along a path to the target (including the 
                target).  
            -  The fourth index uniquely identifies the number of 
                samples in a bucket.   Again, if the 
                rttMonCtrlAdminRttType object is set to 
                'pathEcho', this value is associated with each 
                hop in an ascending order, thus for the 
                first hop on a path, this index will be 1, the 
                second will be 2 and so on.   For all other values
                of rttMonCtrlAdminRttType this will be 1.";
        smiv2:oid "1.3.6.1.4.1.9.9.42.1.4.1.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonHistoryCollectionLifeIndex {
          type int32 {
            range "1..2147483647";
          }
          description
           "This uniquely defines a life for a conceptual history
            row.
            
            For a particular value of rttMonHistoryCollectionLifeIndex,
            the agent assigns the first value of 1, the second value 
            of 2, and so on.  The sequence keeps incrementing, 
            despite older (lower) values being removed from the 
            table.";
          smiv2:max-access "not-accessible";
          smiv2:oid "1.3.6.1.4.1.9.9.42.1.4.1.1.1";
        }

        leaf rttMonHistoryCollectionBucketIndex {
          type int32 {
            range "1..2147483647";
          }
          description
           "When the RttMonRttType is 'pathEcho', this uniquely
            defines a bucket for a given value of 
            rttMonHistoryCollectionLifeIndex.  For all other 
            RttMonRttType this value will be the number of
            operations per a lifetime.  Thus, this object 
            increments on each operation attempt.
            
            For a particular value of 
            rttMonHistoryCollectionLifeIndex, the agent assigns 
            the first value of 1, the second value of 2, and so 
            on.  The sequence keeps incrementing until the number
            of buckets equals rttMonHistoryAdminNumBuckets, after
            which the most recent rttMonHistoryAdminNumBuckets 
            buckets are retained (the index is incremented though).";
          smiv2:max-access "not-accessible";
          smiv2:oid "1.3.6.1.4.1.9.9.42.1.4.1.1.2";
        }

        leaf rttMonHistoryCollectionSampleIndex {
          type int32 {
            range "1..512";
          }
          description
           "This uniquely defines a row for a given value of
            rttMonHistoryCollectionBucketIndex.  This object
            represents a hop along a path to the Target.
            
            For a particular value of 
            rttMonHistoryCollectionBucketIndex, the agent assigns 
            the first value of 1, the second value of 2, and so on.
            The sequence keeps incrementing until the number of 
            samples equals rttMonHistoryAdminNumSamples, then no 
            new samples are created for the current 
            rttMonHistoryCollectionBucketIndex.
            
            When the RttMonRttType is 'pathEcho', this value 
            directly represents the number of hops along a 
            path to a target, thus we can only support 512 hops.
            For all other values of RttMonRttType this object
            will be one.";
          smiv2:max-access "not-accessible";
          smiv2:oid "1.3.6.1.4.1.9.9.42.1.4.1.1.3";
        }

        leaf rttMonHistoryCollectionSampleTime {
          type yang:timestamp;
          description
           "The time that the RTT operation was initiated.";
          smiv2:max-access "read-only";
          smiv2:oid "1.3.6.1.4.1.9.9.42.1.4.1.1.4";
        }

        leaf rttMonHistoryCollectionAddress {
          type cisco-rttmon:RttMonTargetAddress;
          description
           "When the RttMonRttType is 'echo' or 'pathEcho' this
            is a string which specifies the address of the target for
            the this RTT operation.  For all other values of
            RttMonRttType this string will be null.
            
            This address will be the address of the hop along the
            path to the rttMonEchoAdminTargetAddress address,
            including rttMonEchoAdminTargetAddress address, or just
            the rttMonEchoAdminTargetAddress address, when the
            path information is not collected.  This behavior is
            defined by the rttMonCtrlAdminRttType object.
            
            The interpretation of this string depends on the type
            of RTT operation selected, as specified by the
            rttMonEchoAdminProtocol object.
            
            See rttMonEchoAdminTargetAddress for a complete
            description.";
          smiv2:max-access "read-only";
          smiv2:oid "1.3.6.1.4.1.9.9.42.1.4.1.1.5";
        }

        leaf rttMonHistoryCollectionCompletionTime {
          type yang:gauge32;
          units "milliseconds";
          description
           "This is the operation completion time of the RTT
            operation.  If the RTT operation fails 
            (rttMonHistoryCollectionSense is any 
            value other than ok), this has a value of 0.";
          smiv2:max-access "read-only";
          smiv2:oid "1.3.6.1.4.1.9.9.42.1.4.1.1.6";
        }

        leaf rttMonHistoryCollectionSense {
          type cisco-rttmon:RttResponseSense;
          description
           "A sense code for the completion status of the RTT
            operation.";
          smiv2:max-access "read-only";
          smiv2:oid "1.3.6.1.4.1.9.9.42.1.4.1.1.7";
        }

        leaf rttMonHistoryCollectionApplSpecificSense {
          type int32 {
            range "0..2147483647";
          }
          description
           "An application specific sense code for the
            completion status of the last RTT operation.  This 
            object will only be valid when the 
            rttMonHistoryCollectionSense object is set to 
            'applicationSpecific'.  Otherwise, this object's 
            value is not valid.";
          smiv2:max-access "read-only";
          smiv2:oid "1.3.6.1.4.1.9.9.42.1.4.1.1.8";
        }

        leaf rttMonHistoryCollectionSenseDescription {
          type snmpv2-tc:DisplayString;
          description
           "A sense description for the completion status of
            the last RTT operation when the 
            rttMonHistoryCollectionSense object is set to 
            'applicationSpecific'.";
          smiv2:max-access "read-only";
          smiv2:oid "1.3.6.1.4.1.9.9.42.1.4.1.1.9";
        }
      }
    }

    container rttMonLatestHTTPOperTable {
      description
       "A table which contains the status of latest HTTP RTT
        operation.";
      smiv2:oid "1.3.6.1.4.1.9.9.42.1.5.1";

      list rttMonLatestHTTPOperEntry {
        key "rttMonCtrlAdminIndex";
        description
         "A list of objects that record the latest HTTP RTT
          operation. This entry is created automatically after the 
          rttMonCtrlAdminEntry is created. Also the entry is 
          automatically deleted when rttMonCtrlAdminEntry is deleted.";
        smiv2:oid "1.3.6.1.4.1.9.9.42.1.5.1.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonLatestHTTPOperRTT {
          type yang:gauge32;
          description
           "Round Trip Time taken to perform HTTP operation. This value
            is the sum of DNSRTT, TCPConnectRTT and TransactionRTT.";
          smiv2:max-access "read-only";
          smiv2:oid "1.3.6.1.4.1.9.9.42.1.5.1.1.1";
        }

        leaf rttMonLatestHTTPOperDNSRTT {
          type yang:gauge32;
          description
           "Round Trip Time taken to perform DNS query within the
            HTTP operation. If an IP Address is specified in the URL, 
            then DNSRTT is 0.";
          smiv2:max-access "read-only";
          smiv2:oid "1.3.6.1.4.1.9.9.42.1.5.1.1.2";
        }

        leaf rttMonLatestHTTPOperTCPConnectRTT {
          type yang:gauge32;
          description
           "Round Trip Time taken to connect to the HTTP server.";
          smiv2:max-access "read-only";
          smiv2:oid "1.3.6.1.4.1.9.9.42.1.5.1.1.3";
        }

        leaf rttMonLatestHTTPOperTransactionRTT {
          type yang:gauge32;
          description
           "Round Trip Time taken to download the object specified by
            the URL.";
          smiv2:max-access "read-only";
          smiv2:oid "1.3.6.1.4.1.9.9.42.1.5.1.1.4";
        }

        leaf rttMonLatestHTTPOperMessageBodyOctets {
          type yang:gauge32;
          description
           "The size of the message body received as a response to
            the HTTP request.";
          smiv2:max-access "read-only";
          smiv2:oid "1.3.6.1.4.1.9.9.42.1.5.1.1.5";
        }

        leaf rttMonLatestHTTPOperSense {
          type cisco-rttmon:RttResponseSense;
          description
           "An application specific sense code for the completion status
            of the latest RTT operation.";
          smiv2:max-access "read-only";
          smiv2:oid "1.3.6.1.4.1.9.9.42.1.5.1.1.6";
        }

        leaf rttMonLatestHTTPErrorSenseDescription {
          type snmpv2-tc:DisplayString;
          description
           "An sense description for the completion status
            of the latest RTT operation.";
          smiv2:max-access "read-only";
          smiv2:oid "1.3.6.1.4.1.9.9.42.1.5.1.1.7";
        }
      }
    }

    container rttMonLatestJitterOperTable {
      description
       "A table which contains the status of latest Jitter
        operation.";
      smiv2:oid "1.3.6.1.4.1.9.9.42.1.5.2";

      list rttMonLatestJitterOperEntry {
        key "rttMonCtrlAdminIndex";
        description
         "A list of objects that record the latest Jitter
          operation.";
        smiv2:oid "1.3.6.1.4.1.9.9.42.1.5.2.1";

        leaf rttMonCtrlAdminIndex {
          type leafref {
            path "/CISCO-RTTMON-MIB:CISCO-RTTMON-MIB/CISCO-RTTMON-MIB:rttMonCtrlAdminTable/CISCO-RTTMON-MIB:rttMonCtrlAdminEntry/CISCO-RTTMON-MIB:rttMonCtrlAdminIndex";
          }
        }

        leaf rttMonLatestJitterOperNumOfRTT {
          type yang:gauge32;
          description
           "The number of RTT's that were successfully measured.";
          smiv2:max-access "read-only";
          smiv2:oid "1.3.6.1.4.1.9.9.42.1.5.2.1.1";
        }

        leaf rttMonLatestJitterOperRTTSum {
          type yang:gauge32;
          description
           "The sum of Jitter RTT's that are successfully measured (low
            order 32 bits). The high order 32 bits are stored in
            rttMonLatestJitterOperRTTSumHigh.";
          smiv2:max-access "read-only";
          smiv2:oid "1.3.6.1.4.1.9.9.42.1.5.2.1.2";
        }

        leaf rttMonLatestJitterOperRTTSum2 {
          type yang:gauge32;
          description
           "The sum of squares of RTT's that are successfully measured (low
            order 32 bits). The high order 32 bits are stored in
            rttMonLatestJitterOperRTTSum2High.";
          smiv2:max-access "read-only";
          smiv2:oid "1.3.6.1.4.1.9.9.42.1.5.2.1.3";
        }

        leaf rttMonLatestJitterOperRTTMin {
          type yang:gauge32;
          description
           "The minimum of RTT's that were successfully measured.";
          smiv2:max-access "read-only";
          smiv2:oid "1.3.6.1.4.1.9.9.42.1.5.2.1.4";
        }

        leaf rttMonLatestJitterOperRTTMax {
          type yang:gauge32;
          description
           "The maximum of RTT's that were successfully measured.";
          smiv2:max-access "read-only";
          smiv2:oid "1.3.6.1.4.1.9.9.42.1.5.2.1.5";
        }

        leaf rttMonLatestJitterOperMinOfPositivesSD {
          type yang:gauge32;
          description
           "The minimum of all positive jitter values from packets sent
            from source to destination.";
          smiv2:max-access "read-only";
          smiv2:oid "1.3.6.1.4.1.9.9.42.1.5.2.1.6";
        }

        leaf rttMonLatestJitterOperMaxOfPositivesSD {
          type yang:gauge32;
          description
           "The maximum of all positive jitter values from packets sent
            from source to destination.";
          smiv2:max-access "read-only";
          smiv2:oid "1.3.6.1.4.1.9.9.42.1.5.2.1.7";
        }

        leaf rttMonLatestJitterOperNumOfPositivesSD {
          type yang:gauge32;
          description
           "The sum of all positive jitter values from packets
            sent from source to destination.";
          smiv2:max-access "read-only";
          smiv2:oid "1.3.6.1.4.1.9.9.42.1.5.2.1.8";
        }

        leaf rttMonLatestJitterOperSumOfPositivesSD {
          type yang:gauge32;
          description
           "The sum of RTT's of all positive jitter values from packets
            sent from source to destination.";
          smiv2:max-access "read-only";
          smiv2:oid "1.3.6.1.4.1.9.9.42.1.5.2.1.9";
        }

        leaf rttMonLatestJitterOperSum2PositivesSD {
          type yang:gauge32;
          description
           "The sum of square of RTT's of all positive jitter values from
            packets sent from source to destination.";
          smiv2:max-access "read-only";
          smiv2:oid "1.3.6.1.4.1.9.9.42.1.5.2.1.10";
        }

        leaf rttMonLatestJitterOperMinOfNegativesSD {
          type yang:gauge32;
          description
           "The minimum of absolute values of all negative jitter values
            from packets sent from source to destination.";
          smiv2:max-access "read-only";
          smiv2:oid "1.3.6.1.4.1.9.9.42.1.5.2.1.11";
        }

        leaf rttMonLatestJitterOperMaxOfNegativesSD {
          type yang:gauge32;
          description
           "The maximum of absolute values of all negative jitter values
            from packets sent from source to destination.";
          smiv2:max-access "read-only";
          smiv2:oid "1.3.6.1.4.1.9.9.42.1.5.2.1.12";
        }

        leaf rttMonLatestJitterOperNumOfNegativesSD {
          type yang:gauge32;
          description
           "The sum of number of all negative jitter values from packets
            sent from source to destination.";
          smiv2:max-access "read-only";
          smiv2:oid "1.3.6.1.4.1.9.9.42.1.5.2.1.13";
        }

        leaf rttMonLatestJitterOperSumOfNegativesSD {
          type yang:gauge32;
          description
           "The sum of all negative jitter values from packets
            sent from source to destination.";
          smiv2:max-access "read-only";
          smiv2:oid "1.3.6.1.4.1.9.9.42.1.5.2.1.14";
        }

        leaf rttMonLatestJitterOperSum2NegativesSD {
          type yang:gauge32;
          description
           "The sum of square of RTT's of all negative jitter values from
            packets sent from source to destination.";
          smiv2:max-access "read-only";
          smiv2:oid "1.3.6.1.4.1.9.9.42.1.5.2.1.15";
        }

        leaf rttMonLatestJitterOperMinOfPositivesDS {
          type yang:gauge32;
          description
           "The minimum of all positive jitter values from packets sent
            from destination to source.";
          smiv2:max-access "read-only";
          smiv2:oid "1.3.6.1.4.1.9.9.42.1.5.2.1.16";
        }

        leaf rttMonLatestJitterOperMaxOfPositivesDS {
          type yang:gauge32;
          description
           "The maximum of all positive jitter values from packets sent
            from destination to source.";
          smiv2:max-access "read-only";
          smiv2:oid "1.3.6.1.4.1.9.9.42.1.5.2.1.17";
        }

        leaf rttMonLatestJitterOperNumOfPositivesDS {
          type yang:gauge32;
          description
           "The sum of number of all positive jitter values from packets
            sent from destination to source.";
          smiv2:max-access "read-only";
          smiv2:oid "1.3.6.1.4.1.9.9.42.1.5.2.1.18";
        }

        leaf rttMonLatestJitterOperSumOfPositivesDS {
          type yang:gauge32;
          description
           "The sum of RTT's of all positive jitter values from packets
            sent from destination to source.";
          smiv2:max-access "read-only";
          smiv2:oid "1.3.6.1.4.1.9.9.42.1.5.2.1.19";
        }

        leaf rttMonLatestJitterOperSum2PositivesDS {
          type yang:gauge32;
          description
           "The sum of squares of RTT's of all positive jitter values from
            packets sent from destination to source.";
          smiv2:max-access "read-only";
          smiv2:oid "1.3.6.1.4.1.9.9.42.1.5.2.1.20";
        }

        leaf rttMonLatestJitterOperMinOfNegativesDS {
          type yang:gauge32;
          description
           "The minimum of all negative jitter values from packets sent
            from destination to source.";
          smiv2:max-access "read-only";
          smiv2:oid "1.3.6.1.4.1.9.9.42.1.5.2.1.21";
        }

        leaf rttMonLatestJitterOperMaxOfNegativesDS {
          type yang:gauge32;
          description
           "The maximum of all negative jitter values from packets sent
            from destination to source.";
          smiv2:max-access "read-only";
          smiv2:oid "1.3.6.1.4.1.9.9.42.1.5.2.1.22";
        }

        leaf rttMonLatestJitterOperNumOfNegativesDS {
          type yang:gauge32;
          description
           "The sum of number of all negative jitter values from packets
            sent from destination to source.";
          smiv2:max-access "read-only";
          smiv2:oid "1.3.6.1.4.1.9.9.42.1.5.2.1.23";
        }

        leaf rttMonLatestJitterOperSumOfNegativesDS {
          type yang:gauge32;
          description
           "The sum of RTT's of all negative jitter values from packets
            sent from destination to source.";
          smiv2:max-access "read-only";
          smiv2:oid "1.3.6.1.4.1.9.9.42.1.5.2.1.24";
        }

        leaf rttMonLatestJitterOperSum2NegativesDS {
          type yang:gauge32;
          description
           "The sum of squares of RTT's of all negative jitter values from
            packets sent from destination to source.";
          smiv2:max-access "read-only";
          smiv2:oid "1.3.6.1.4.1.9.9.42.1.5.2.1.25";
        }

        leaf rttMonLatestJitterOperPacketLossSD {
          type yang:gauge32;
          description
           "The number of packets lost when sent from source to
            destination.";
          smiv2:max-access "read-only";
          smiv2:oid "1.3.6.1.4.1.9.9.42.1.5.2.1.26";
        }

        leaf rttMonLatestJitterOperPacketLossDS {
          type yang:gauge32;
          description
           "The number of packets lost when sent from destination to
            source.";
          smiv2:max-access "read-only";
          smiv2:oid "1.3.6.1.4.1.9.9.42.1.5.2.1.27";
        }

        leaf rttMonLatestJitterOperPacketOutOfSequence {
          type yang:gauge32;
          description
           "The number of packets arrived out of sequence.";
          smiv2:max-access "read-only";
          smiv2:oid "1.3.6.1.4.1.9.9.42.1.5.2.1.28";
        }

        leaf rttMonLatestJitterOperPacketMIA {
          type yang:gauge32;
          description
           "The number of packets that are lost for which we cannot
            determine the direction.";
          smiv2:max-access "read-only";
          smiv2:oid "1.3.6.1.4.1.9.9.42.1.5.2.1.29";
        }

        leaf rttMonLatestJitterOperPacketLateArrival {
          type yang:gauge32;
          description
           "The number of packets that arrived after the timeout.";
          smiv2:max-access "read-only";
          smiv2:oid "1.3.6.1.4.1.9.9.42.1.5.2.1.30";
        }

        leaf rttMonLatestJitterOperSense {
          type cisco-rttmon:RttResponseSense;
          description
           "An application specific sense code for the completion status
            of the latest Jitter RTT operation.";
          smiv2:max-access "read-only";
          smiv2:oid "1.3.6.1.4.1.9.9.42.1.5.2.1.31";
        }

        leaf rttMonLatestJitterErrorSenseDescription {
          type snmpv2-tc:DisplayString;
          description
           "An sense description for the completion status
            of the latest Jitter RTT operation.";
          smiv2:max-access "read-only";
          smiv2:oid "1.3.6.1.4.1.9.9.42.1.5.2.1.32";
        }

        leaf rttMonLatestJitterOperOWSumSD {
          type yang:gauge32;
          description
           "The sum of one way latency from source to destination (low
            order 32 bits). The high order 32 bits are stored in
            rttMonLatestJitterOperOWSumSDHigh.";
          smiv2:max-access "read-only";
          smiv2:oid "1.3.6.1.4.1.9.9.42.1.5.2.1.33";
        }

        leaf rttMonLatestJitterOperOWSum2SD {
          type yang:gauge32;
          description
           "The sum of squares of one way latency from source to
            destination (low order 32 bits). The high order 32 bits are
            stored in rttMonLatestJitterOperOWSum2SDHigh.";
          smiv2:max-access "read-only";
          smiv2:oid "1.3.6.1.4.1.9.9.42.1.5.2.1.34";
        }

        leaf rttMonLatestJitterOperOWMinSD {
          type yang:gauge32;
          description
           "The minimum of all one way latency from source to
            destination.";
          smiv2:max-access "read-only";
          smiv2:oid "1.3.6.1.4.1.9.9.42.1.5.2.1.35";
        }

        leaf rttMonLatestJitterOperOWMaxSD {
          type yang:gauge32;
          description
           "The maximum of all one way latency from source to
            destination.";
          smiv2:max-access "read-only";
          smiv2:oid "1.3.6.1.4.1.9.9.42.1.5.2.1.36";
        }

        leaf rttMonLatestJitterOperOWSumDS {
          type yang:gauge32;
          description
           "The sum of one way latency from destination to source (low
            order 32 bits). The high order 32 bits are stored in
            rttMonLatestJitterOperOWSumDSHigh.";
          smiv2:max-access "read-only";
          smiv2:oid "1.3.6.1.4.1.9.9.42.1.5.2.1.37";
        }

        leaf rttMonLatestJitterOperOWSum2DS {
          type yang:gauge32;
          description
           "The sum of squares of one way latency from destination to
            source (low order 32 bits). The high order 32 bits are stored in
            rttMonLatestJitterOperOWSum2DSHigh.";
          smiv2:max-access "read-only";
          smiv2:oid "1.3.6.1.4.1.9.9.42.1.5.2.1.38";
        }

        leaf rttMonLatestJitterOperOWMinDS {
          type yang:gauge32;
          description
           "The minimum of all one way latency from destination to
            source.";
          smiv2:max-access "read-only";
          smiv2:oid "1.3.6.1.4.1.9.9.42.1.5.2.1.39";
        }

        leaf rttMonLatestJitterOperOWMaxDS {
          type yang:gauge32;
          description
           "The maximum of all one way latency from destination to
            source.";
          smiv2:max-access "read-only";
          smiv2:oid "1.3.6.1.4.1.9.9.42.1.5.2.1.40";
        }

        leaf rttMonLatestJitterOperNumOfOW {
          type yang:gauge32;
          description
           "The number of successful one way latency measurements.";
          smiv2:max-access "read-only";
          smiv2:oid "1.3.6.1.4.1.9.9.42.1.5.2.1.41";
        }

        leaf rttMonLatestJitterOperMOS {
          type yang:gauge32 {
            range "0|100..500";
          }
          description
           "The MOS value for the latest jitter operation in hundreds.
            This value will be 0 if 
             - rttMonEchoAdminCodecType of the operation is notApplicable 
             - the operation is not started 
             - the operation is started but failed
            This value will be 1 for packet loss of 10% or more.";
          smiv2:max-access "read-only";
          smiv2:oid "1.3.6.1.4.1.9.9.42.1.5.2.1.42";
        }

        leaf rttMonLatestJitterOperICPIF {
          type yang:gauge32 {
            range "0..2147483647";
          }
          description
           "Represents ICPIF value for the latest jitter operation.
            
            This value will be 93 for packet loss of 10% or more.";
          smiv2:max-access "read-only";
          smiv2:oid "1.3.6.1.4.1.9.9.42.1.5.2.1.43";
        }

        leaf rttMonLatestJitterOperIAJOut {
          type yang:gauge32 {
            range "0..2147483647";
          }
          description
           "Interarrival Jitter (RC1889) at responder.";
          reference
           "Refer to the following documents for the definition: RFC 1889";
          smiv2:max-access "read-only";
          smiv2:oid "1.3.6.1.4.1.9.9.42.1.5.2.1.44";
        }

        leaf rttMonLatestJitterOperIAJIn {
          type yang:gauge32 {
            range "0..2147483647";
          }
          description
           "Interarrival Jitter (RFC1889) at source.";
          reference
           "Refer to the following documents for the definition: RFC 1889";
          smiv2:max-access "read-only";
          smiv2:oid "1.3.6.1.4.1.9.9.42.1.5.2.1.45";
        }

        leaf rttMonLatestJitterOperAvgJitter {
          type yang:gauge32 {
            range "0..2147483647";
          }
          description
           "The average of positive and negative jitter
            values in SD and DS direction for latest operation.";
          smiv2:max-access "read-only";
          smiv2:oid "1.3.6.1.4.1.9.9.42.1.5.2.1.46";
        }

        leaf rttMonLatestJitterOperAvgSDJ {
          type yang:gauge32 {
            range "0..2147483647";
          }
          description
           "The average of positive and negative jitter values
            from source to destination for latest operation.";
          smiv2:max-access "read-only";
          smiv2:oid "1.3.6.1.4.1.9.9.42.1.5.2.1.47";
        }

        leaf rttMonLatestJitterOperAvgDSJ {
          type yang:gauge32 {
            range "0..2147483647";
          }
          description
           "The average of positive and negative jitter values
            from destination to source for latest operation.";
          smiv2:max-access "read-only";
          smiv2:oid "1.3.6.1.4.1.9.9.42.1.5.2.1.48";
        }

        leaf rttMonLatestJitterOperOWAvgSD {
          type yang:gauge32 {
            range "0..2147483647";
          }
          description
           "The average latency value from source to destination.";
          smiv2:max-access "read-only";
          smiv2:oid "1.3.6.1.4.1.9.9.42.1.5.2.1.49";
        }

        leaf rttMonLatestJitterOperOWAvgDS {
          type yang:gauge32 {
            range "0..2147483647";
          }
          description
           "The average latency value from destination to source.";
          smiv2:max-access "read-only";
          smiv2:oid "1.3.6.1.4.1.9.9.42.1.5.2.1.50";
        }

        leaf rttMonLatestJitterOperNTPState {
          type enumeration {
            enum "sync" {
              value "1";
            }
            enum "outOfSync" {
              value "2";
            }
          }
          description
           "A value of sync(1) means sender and responder was in sync
            with NTP. The NTP sync means the total of NTP offset 
            on sender and responder is within configured tolerance level.";
          smiv2:max-access "read-only";
          smiv2:oid "1.3.6.1.4.1.9.9.42.1.5.2.1.51";
        }

        leaf rttMonLatestJitterOperUnSyncRTs {
          type yang:counter32;
          description
           "The number of RTT operations that have completed with
            sender and responder out of sync with NTP. The NTP sync means 
            the total of NTP offset on sender and responder is within 
            configured tolerance level.";
          smiv2:max-access "read-only";
          smiv2:oid "1.3.6.1.4.1.9.9.42.1.5.2.1.52";
        }

        leaf rttMonLatestJitterOperRTTSumHigh {
          type yang:gauge32;
          description
           "The sum of Jitter RTT's that are successfully measured.
            (high order 32 bits). The low order 32 bits are stored
            in rttMonLatestJitterOperRTTSum.";
          smiv2:max-access "read-only";
          smiv2:oid "1.3.6.1.4.1.9.9.42.1.5.2.1.53";
        }

        leaf rttMonLatestJitterOperRTTSum2High {
          type yang:gauge32;
          description
           "The sum of squares of RTT's that are successfully measured
            (high order 32 bits). The low order 32 bits are stored in
            rttMonLatestJitterOperRTTSum2.";
          smiv2:max-access "read-only";
          smiv2:oid "1.3.6.1.4.1.9.9.42.1.5.2.1.54";
        }

        leaf rttMonLatestJitterOperOWSumSDHigh {
          type yang:gauge32;
          description
           "The sum of one way latency from source to destination
            (high order 32 bits). The low order 32 bits are stored in
            rttMonLatestJitterOperOWSumSD.";
          smiv2:max-access "read-only";
          smiv2:oid "1.3.6.1.4.1.9.9.42.1.5.2.1.55";
        }

        leaf rttMonLatestJitterOperOWSum2SDHigh {
          type yang:gauge32;
          description
           "The sum of squares of one way latency from source to
            destination (high order 32 bits). The low order 32 bits
            are stored in rttMonLatestJitterOperOWSum2SD.";
          smiv2:max-access "read-only";
          smiv2:oid "1.3.6.1.4.1.9.9.42.1.5.2.1.56";
        }

        leaf rttMonLatestJitterOperOWSumDSHigh {
          type yang:gauge32;
          description
           "The sum of one way latency from destination to source
            (high order 32 bits). The low order 32 bits are stored 
            in rttMonLatestJitterOperOWSumDS.";
          smiv2:max-access "read-only";
          smiv2:oid "1.3.6.1.4.1.9.9.42.1.5.2.1.57";
        }

        leaf rttMonLatestJitterOperOWSum2DSHigh {
          type yang:gauge32;
          description
           "The sum of squares of one way latency from destination to
            source (high order 32 bits). The low order 32 bits are
            stored in rttMonLatestJitterOperOWSum2DS.";
          smiv2:max-access "read-only";
          smiv2:oid "1.3.6.1.4.1.9.9.42.1.5.2.1.58";
        }
      }
    }
  }

  smiv2:alias "rttMonScheduleAdminTable" {
    description
     "A table of Round Trip Time (RTT) monitoring scheduling
      specific definitions.
      
      This table is controlled via the
      rttMonCtrlAdminTable.  Entries in this table are
      created via the rttMonCtrlAdminStatus object.";
    smiv2:oid "1.3.6.1.4.1.9.9.42.1.2.5";
  }

  smiv2:alias "rttMonScheduleAdminEntry" {
    description
     "A list of objects that define specific configuration for
      the scheduling of RTT operations.";
    smiv2:oid "1.3.6.1.4.1.9.9.42.1.2.5.1";
  }

  augment "/CISCO-RTTMON-MIB:CISCO-RTTMON-MIB/CISCO-RTTMON-MIB:rttMonCtrlAdminTable/CISCO-RTTMON-MIB:rttMonCtrlAdminEntry" {
    description
     "A list of objects that define specific configuration for
      the scheduling of RTT operations.";
    smiv2:oid "1.3.6.1.4.1.9.9.42.1.2.5.1";

    leaf rttMonScheduleAdminRttLife {
      type int32 {
        range "0..2147483647";
      }
      units "seconds";
      description
       "This object value will be placed into the
        rttMonCtrlOperRttLife object when the rttMonCtrlOperState
        object transitions to 'active' or 'pending'.
        
        The value 2147483647 has a special meaning.  When
        this object is set to 2147483647, the 
        rttMonCtrlOperRttLife object will not decrement.  
        And thus the life time will never end.";
      smiv2:defval "3600";
      smiv2:max-access "read-write";
      smiv2:oid "1.3.6.1.4.1.9.9.42.1.2.5.1.1";
    }

    leaf rttMonScheduleAdminRttStartTime {
      type yang:timeticks;
      description
       "This is the time when this conceptional row will
        activate.  
        
        This is the value of MIB-II's sysUpTime in the future.
        When sysUpTime equals this value this object will 
        cause the activation of a conceptual Rtt row.
        
        When an agent has the capability to determine date and 
        time, the agent should store this object as DateAndTime.
        This allows the agent to completely reset (restart) and
        still be able to start conceptual Rtt rows at the 
        intended time.  If the agent cannot keep date and time
        and the agent resets, all entries should take on one of
        the special value defined below.
        
        The first special value allows this conceptual Rtt 
        control row to immediately transition the 
        rttMonCtrlOperState object into 'active' state when the
        rttMonCtrlAdminStatus  object transitions to active.
        This special value is defined to be a value of this
        object that, when initially set, is 1.
        
        The second special value allows this conceptual Rtt 
        control row to immediately transition the 
        rttMonCtrlOperState object into 'pending' state when 
        the rttMonCtrlAdminStatus object transitions to active.  
        Also, when the rttMonCtrlOperRttLife counts down to zero 
        (and not when set to zero), this special value causes 
        this conceptual Rtt control row to  retransition the 
        rttMonCtrlOperState object into 'pending' state.  This 
        special value is defined to be a value of this object 
        that, when initially set, is smaller than the current
        sysUpTime. (With the exception of one, as defined in
        the previous paragraph)";
      smiv2:defval "0";
      smiv2:max-access "read-write";
      smiv2:oid "1.3.6.1.4.1.9.9.42.1.2.5.1.2";
    }

    leaf rttMonScheduleAdminConceptRowAgeout {
      type int32 {
        range "0..2073600";
      }
      units "seconds";
      status deprecated;
      description
       "The amount of time this conceptual Rtt control row will
        exist when not in an 'active' rttMonCtrlOperState.
        
        When this conceptual Rtt control row enters an 'active' 
        state, this timer will be reset and suspended.  When 
        this conceptual RTT control row enters a state other 
        than 'active', the timer will be restarted.
        
        NOTE:  When a conceptual Rtt control row ages out, the 
               agent needs to remove the associated entries in 
               the rttMonReactTriggerAdminTable and 
               rttMonReactTriggerOperTable.
        
        When this value is set to zero, this entry will
        never be aged out.
        rttMonScheduleAdminConceptRowAgeout object is superseded by
        rttMonScheduleAdminConceptRowAgeoutV2.";
      smiv2:defval "3600";
      smiv2:max-access "read-write";
      smiv2:oid "1.3.6.1.4.1.9.9.42.1.2.5.1.3";
    }

    leaf rttMonScheduleAdminRttRecurring {
      type boolean;
      description
       "When set to true, this entry will be scheduled to
        run automatically for the specified duration equal
        to the life configured, at the same time daily.
        
        This value cannot be set to true 
        (a) if rttMonScheduleAdminRttLife object has value greater or
           equal to 86400 seconds.
        (b) if sum of values of rttMonScheduleAdminRttLife and
           rttMonScheduleAdminConceptRowAgeout is less or equal to
           86400 seconds.";
      smiv2:defval "false";
      smiv2:max-access "read-write";
      smiv2:oid "1.3.6.1.4.1.9.9.42.1.2.5.1.4";
    }

    leaf rttMonScheduleAdminConceptRowAgeoutV2 {
      type int32 {
        range "0..2073600";
      }
      units "seconds";
      description
       "The amount of time this conceptual Rtt control row will
        exist when not in an 'active' rttMonCtrlOperState.
        
        When this conceptual Rtt control row enters an 'active'
        state, this timer will be reset and suspended.  When
        this conceptual RTT control row enters a state other
        than 'active', the timer will be restarted.
        
        NOTE:  It is the same as rttMonScheduleAdminConceptRowAgeout
               except DEFVAL is 0 to be consistent with CLI ageout
               default.
        
        When this value is set to zero, this entry will
        never be aged out.";
      smiv2:defval "0";
      smiv2:max-access "read-write";
      smiv2:oid "1.3.6.1.4.1.9.9.42.1.2.5.1.5";
    }
  }

  smiv2:alias "rttMonReactAdminTable" {
    status deprecated;
    description
     "A table of Round Trip Time (RTT) monitoring Notification
      and Trigger definitions.
      
      All Notification/Reactions are applied to all RTT 
      End-to-End operations.  Thus, they do not apply to hops
      along a path to the target, when RttMonRttType is 
      'pathEcho'.
      
      The format and content of SNA NMVT's are not defined 
      within this module.  
      
      It can be noted, however, that there are Alert NMVT's,
      and traps which are sent when an abnormal
      condition occurs, i.e. when one of 
      rttMonCtrlOperConnectionLostOccurred,
      rttMonCtrlOperTimeoutOccurred or
      rttMonCtrlOperOverThresholdOccurred are changed to true,
      and Resolution NMVT's, and Resolution traps which are 
      sent when that condition clears, i.e. when one of
      rttMonCtrlOperConnectionLostOccurred,
      rttMonCtrlOperTimeoutOccurred or
      rttMonCtrlOperOverThresholdOccurred is changed back to 
      false.
      
      When rttMonReactAdminActionType is set to one of the 
      following:
        -  triggerOnly
        -  trapAndTrigger
        -  nmvtAndTrigger
        -  trapNmvtAndTrigger
      The corresponding rows in the 
      rttMonReactTriggerAdminTable defined via the 
      rttMonCtrlAdminIndex will become active.
      
      This table augments the rttMonCtrlAdminTable.
      rttMonReactAdminTable object is superseded by rttMonReactTable.";
    smiv2:oid "1.3.6.1.4.1.9.9.42.1.2.6";
  }

  smiv2:alias "rttMonReactAdminEntry" {
    status deprecated;
    description
     "A list of objects that define RTT reaction operations.
      rttMonReactAdminEntry object is superseded by rttMonReactEntry.";
    smiv2:oid "1.3.6.1.4.1.9.9.42.1.2.6.1";
  }

  augment "/CISCO-RTTMON-MIB:CISCO-RTTMON-MIB/CISCO-RTTMON-MIB:rttMonCtrlAdminTable/CISCO-RTTMON-MIB:rttMonCtrlAdminEntry" {
    status deprecated;
    description
     "A list of objects that define RTT reaction operations.
      rttMonReactAdminEntry object is superseded by rttMonReactEntry.";
    smiv2:oid "1.3.6.1.4.1.9.9.42.1.2.6.1";

    leaf rttMonReactAdminConnectionEnable {
      type boolean;
      status deprecated;
      description
       "If true, a reaction is generated when a RTT
        operation to a rttMonEchoAdminTargetAddress
        (echo type) causes 
        rttMonCtrlOperConnectionLostOccurred to change its 
        value.  Thus connections to intermediate hops will 
        not cause this value to change.
        rttMonReactAdminConnectionEnable object is superseded by
        rttMonReactVar.";
      smiv2:defval "false";
      smiv2:max-access "read-write";
      smiv2:oid "1.3.6.1.4.1.9.9.42.1.2.6.1.1";
    }

    leaf rttMonReactAdminTimeoutEnable {
      type boolean;
      status deprecated;
      description
       "If true, a reaction is generated when a RTT
        operation causes rttMonCtrlOperTimeoutOccurred 
        to change its value.  
        
        When the RttMonRttType is 'pathEcho' timeouts to 
        intermediate hops will not cause 
        rttMonCtrlOperTimeoutOccurred to change its value.
        rttMonReactAdminTimeoutEnable object is superseded by
        rttMonReactVar.";
      smiv2:defval "false";
      smiv2:max-access "read-write";
      smiv2:oid "1.3.6.1.4.1.9.9.42.1.2.6.1.2";
    }

    leaf rttMonReactAdminThresholdType {
      type enumeration {
        enum "never" {
          value "1";
        }
        enum "immediate" {
          value "2";
        }
        enum "consecutive" {
          value "3";
        }
        enum "xOfy" {
          value "4";
        }
        enum "average" {
          value "5";
        }
      }
      status deprecated;
      description
       "This object specifies the conditions under which
        rttMonCtrlOperOverThresholdOccurred is changed:
        
        NOTE:  When the RttMonRttType is 'pathEcho' this 
               objects' value and all associated 
               object values are only valid when RTT 
               'echo' operations are to the
               rttMonEchoAdminTargetAddress object address.  Thus
               'pathEcho' operations to intermediate
               hops will not cause this object to change.
        
        never       - rttMonCtrlOperOverThresholdOccurred is 
                       never set
        immediate   - rttMonCtrlOperOverThresholdOccurred is set 
                       to true when an operation completion time 
                       exceeds rttMonCtrlAdminThreshold; 
                       conversely 
                       rttMonCtrlOperOverThresholdOccurred is set 
                       to false when an operation completion time 
                       falls below 
                       rttMonReactAdminThresholdFalling 
        consecutive - rttMonCtrlOperOverThresholdOccurred is set 
                       to true when an operation completion time 
                       exceeds rttMonCtrlAdminThreshold on 
                       rttMonReactAdminThresholdCount consecutive 
                       RTT operations; conversely, 
                       rttMonCtrlOperOverThresholdOccurred is set 
                       to false when an operation completion time
                       falls under the 
                       rttMonReactAdminThresholdFalling 
                       for the same number of consecutive 
                       operations 
        xOfy        - rttMonCtrlOperOverThresholdOccurred is set 
                       to true when x (as specified by 
                       rttMonReactAdminThresholdCount) out of the 
                       last y (as specified by 
                       rttMonReactAdminThresholdCount2) 
                       operation completion time exceeds 
                       rttMonCtrlAdminThreshold; 
                       conversely, it is set to false when x, 
                       out of the last y operation completion
                       time fall below
                       rttMonReactAdminThresholdFalling
                       NOTE: When x > y, the probe will never
                             generate a reaction.
        average     - rttMonCtrlOperOverThresholdOccurred is set 
                       to true when the running average of the 
                       previous rttMonReactAdminThresholdCount 
                       operation completion times exceed 
                       rttMonCtrlAdminThreshold; conversely, it 
                       is set to false when the running average 
                       falls below the 
                       rttMonReactAdminThresholdFalling
        
        If this value is changed by a management station, 
        rttMonCtrlOperOverThresholdOccurred is set to false, but 
        no reaction is generated if the prior value of 
        rttMonCtrlOperOverThresholdOccurred was true.
        rttMonReactAdminThresholdType object is superseded by
        rttMonReactThresholdType.";
      smiv2:defval "never";
      smiv2:max-access "read-write";
      smiv2:oid "1.3.6.1.4.1.9.9.42.1.2.6.1.3";
    }

    leaf rttMonReactAdminThresholdFalling {
      type int32 {
        range "0..2147483647";
      }
      units "milliseconds";
      status deprecated;
      description
       "This object defines a threshold limit. If the RTT
        operation time falls below this limit and if the conditions
        specified in rttMonReactAdminThresholdType are satisfied, an 
        threshold is generated.
        rttMonReactAdminThresholdFalling object is superseded by
        rttMonReactThresholdFalling.";
      smiv2:defval "3000";
      smiv2:max-access "read-write";
      smiv2:oid "1.3.6.1.4.1.9.9.42.1.2.6.1.4";
    }

    leaf rttMonReactAdminThresholdCount {
      type int32 {
        range "1..16";
      }
      status deprecated;
      description
       "This object defines the 'x' value of the xOfy condition
        specified in rttMonReactAdminThresholdType.
        rttMonReactAdminThresholdCount object is superseded by
        rttMonReactThresholdCountX.";
      smiv2:defval "5";
      smiv2:max-access "read-write";
      smiv2:oid "1.3.6.1.4.1.9.9.42.1.2.6.1.5";
    }

    leaf rttMonReactAdminThresholdCount2 {
      type int32 {
        range "1..16";
      }
      status deprecated;
      description
       "This object defines the 'y' value of the xOfy condition
        specified in rttMonReactAdminThresholdType.
        rttMonReactAdminThresholdCount2 object is superseded by
        rttMonReactThresholdCountyY.";
      smiv2:defval "5";
      smiv2:max-access "read-write";
      smiv2:oid "1.3.6.1.4.1.9.9.42.1.2.6.1.6";
    }

    leaf rttMonReactAdminActionType {
      type enumeration {
        enum "none" {
          value "1";
        }
        enum "trapOnly" {
          value "2";
        }
        enum "nmvtOnly" {
          value "3";
        }
        enum "triggerOnly" {
          value "4";
        }
        enum "trapAndNmvt" {
          value "5";
        }
        enum "trapAndTrigger" {
          value "6";
        }
        enum "nmvtAndTrigger" {
          value "7";
        }
        enum "trapNmvtAndTrigger" {
          value "8";
        }
      }
      status deprecated;
      description
       "Specifies what type(s), if any, of reaction(s) to
        generate if an operation violates one of the watched 
        conditions:
        
        none               - no reaction is generated
        trapOnly           - a trap is generated
        nmvtOnly           - an SNA NMVT is generated
        triggerOnly        - all trigger actions defined for this 
                              entry are initiated
        trapAndNmvt        - both a trap and an SNA NMVT are 
                              generated
        trapAndTrigger     - both a trap and all trigger actions 
                              are initiated 
        nmvtAndTrigger     - both a NMVT and all trigger actions 
                              are initiated
        trapNmvtAndTrigger - a NMVT, trap, and all trigger actions
                              are initiated
        
        A trigger action is defined via the 
        rttMonReactTriggerAdminTable.
        rttMonReactAdminActionType object is superseded by
        rttMonReactActionType.";
      smiv2:defval "none";
      smiv2:max-access "read-write";
      smiv2:oid "1.3.6.1.4.1.9.9.42.1.2.6.1.7";
    }

    leaf rttMonReactAdminVerifyErrorEnable {
      type boolean;
      status deprecated;
      description
       "If true, a reaction is generated when a RTT
        operation causes rttMonCtrlOperVerifyErrorOccurred 
        to change its value.
        rttMonReactAdminVerifyErrorEnable object is superseded by
        rttMonReactVar.";
      smiv2:defval "false";
      smiv2:max-access "read-write";
      smiv2:oid "1.3.6.1.4.1.9.9.42.1.2.6.1.8";
    }
  }

  smiv2:alias "rttMonStatisticsAdminTable" {
    description
     "A table of Round Trip Time (RTT) monitoring statistics
      definitions. 
      
      The definitions in this table control what and how many
      entries will be placed into the rttMonStatsCaptureTable.
      
      The statistics capture table is a rollover table.  When 
      the rttMonStatisticsAdminNumHourGroups index value 
      exceeds its value defined in this table, the oldest 
      corresponding group will be deleted and will be replaced 
      with the new group.  All other indices will only fill to 
      there maximum size.
      
      NOTE:  The maximum size of this table is defined to be
             the product of the rttMonCtrlAdminIndex times
             rttMonStatisticsAdminNumHourGroups times
             rttMonStatisticsAdminNumPaths times
             rttMonStatisticsAdminNumHops times
             rttMonStatisticsAdminNumDistBuckets. 
      
      NOTE WELL:  Each of the 'Num' objects values in this 
                  have a special behavior.  When one of the
                  objects is set to a value larger than the
                  Rtt application can support the set will
                  succeed, but the resultant value will
                  be set to the applications maximum value. 
                  The setting management station must reread
                  this object to verify the actual value.
      
      This table augments the rttMonCtrlAdminTable.";
    smiv2:oid "1.3.6.1.4.1.9.9.42.1.2.7";
  }

  smiv2:alias "rttMonStatisticsAdminEntry" {
    description
     "A list of objects that define RTT statistics
      capture operations.";
    smiv2:oid "1.3.6.1.4.1.9.9.42.1.2.7.1";
  }

  augment "/CISCO-RTTMON-MIB:CISCO-RTTMON-MIB/CISCO-RTTMON-MIB:rttMonCtrlAdminTable/CISCO-RTTMON-MIB:rttMonCtrlAdminEntry" {
    description
     "A list of objects that define RTT statistics
      capture operations.";
    smiv2:oid "1.3.6.1.4.1.9.9.42.1.2.7.1";

    leaf rttMonStatisticsAdminNumHourGroups {
      type int32 {
        range "0..25";
      }
      description
       "The maximum number of groups of paths to record.
        Specifically this is the number of hourly groups 
        to keep before rolling over.  
        
        The value of one is not advisable because the 
        group will close and immediately be deleted before
        the network management station will have the 
        opportunity to retrieve the statistics. 
        
        The value used in the rttMonStatsCaptureTable to 
        uniquely identify this group is the 
        rttMonStatsCaptureStartTimeIndex.
        
        HTTP and Jitter probes store only two hours of data.
        
        When this object is set to the value of zero all 
        rttMonStatsCaptureTable data capturing will be shut off.";
      smiv2:defval "2";
      smiv2:max-access "read-write";
      smiv2:oid "1.3.6.1.4.1.9.9.42.1.2.7.1.1";
    }

    leaf rttMonStatisticsAdminNumPaths {
      type int32 {
        range "1..128";
      }
      description
       "When RttMonRttType is 'pathEcho' this is the maximum
        number of statistics paths to record per hourly group.  
        This value directly represents the path to a target.  
        For all other RttMonRttTypes this value will be 
        forced to one by the agent.
        
        NOTE: For 'pathEcho' a source to target path will be 
              created to to hold all errors that occur when a 
              specific path or connection has not be found/setup. 
              Thus, it is advised to set this value greater
              than one.
        
        Since this index does not rollover, only the first
        rttMonStatisticsAdminNumPaths will be kept.";
      smiv2:defval "5";
      smiv2:max-access "read-write";
      smiv2:oid "1.3.6.1.4.1.9.9.42.1.2.7.1.2";
    }

    leaf rttMonStatisticsAdminNumHops {
      type int32 {
        range "1..30";
      }
      description
       "When RttMonRttType is 'pathEcho' this is the maximum
        number of statistics hops to record per path group.  
        This value directly represents the number of hops along 
        a path to a target, thus we can only support 30 hops.  
        For all other RttMonRttTypes this value will be 
        forced to one by the agent.
        
        Since this index does not rollover, only the first
        rttMonStatisticsAdminNumHops will be kept. This object 
        is applicable to pathEcho probes only.";
      smiv2:defval "16";
      smiv2:max-access "read-write";
      smiv2:oid "1.3.6.1.4.1.9.9.42.1.2.7.1.3";
    }

    leaf rttMonStatisticsAdminNumDistBuckets {
      type int32 {
        range "1..20";
      }
      description
       "The maximum number of statistical distribution
        Buckets to accumulate.
        
        Since this index does not rollover, only the first
        rttMonStatisticsAdminNumDistBuckets will be kept.
        
        The last rttMonStatisticsAdminNumDistBucket will
        contain all entries from its distribution interval
        start point to infinity. This object is not applicable 
        to http and jitter probes.";
      smiv2:defval "1";
      smiv2:max-access "read-write";
      smiv2:oid "1.3.6.1.4.1.9.9.42.1.2.7.1.4";
    }

    leaf rttMonStatisticsAdminDistInterval {
      type int32 {
        range "1..100";
      }
      units "milliseconds";
      description
       "The statistical distribution buckets interval.
        
        Distribution Bucket Example:
        
        rttMonStatisticsAdminNumDistBuckets = 5 buckets
        rttMonStatisticsAdminDistInterval = 10 milliseconds
        
        | Bucket 1 | Bucket 2 | Bucket 3 | Bucket 4 | Bucket 5  |
        |  0-9 ms  | 10-19 ms | 20-29 ms | 30-39 ms | 40-Inf ms |
        
        Odd Example:
        
        rttMonStatisticsAdminNumDistBuckets = 1 buckets
        rttMonStatisticsAdminDistInterval = 10 milliseconds
        
        | Bucket 1  |
        |  0-Inf ms |
        
        Thus, this odd example shows that the value of 
        rttMonStatisticsAdminDistInterval does not apply when
        rttMonStatisticsAdminNumDistBuckets is one.
        This object is not applicable to http and jitter probes.";
      smiv2:defval "20";
      smiv2:max-access "read-write";
      smiv2:oid "1.3.6.1.4.1.9.9.42.1.2.7.1.5";
    }
  }

  smiv2:alias "rttMonHistoryAdminTable" {
    description
     "A table of Round Trip Time (RTT) monitoring history
      definitions.
      
      The definitions in this table control what and how many
      entries will be placed into the 
      rttMonHistoryCollectionTable.
      
      The history collection table is a rollover table.  When 
      the rttMonHistoryAdminNumLives index value exceeds its 
      value defined in this table, the oldest corresponding 
      'lives' group will be deleted and will be replaced with 
      the new 'lives' group.  All other indices will only fill
      to their maximum size.
      
      NOTE:  The maximum size of this table is defined to be
             the product of the rttMonCtrlAdminIndex times
             rttMonHistoryAdminNumLives times
             rttMonHistoryAdminNumBuckets times
             rttMonHistoryAdminNumSamples.
      
      NOTE WELL:  Each of the 'Num' objects values in this 
                  have a special behavior.  When one of the
                  objects is set to a value larger than the
                  Rtt application can support the set will
                  succeed, but the resultant value will
                  be set to the applications maximum value. 
                  The setting management station must reread
                  this object to verify the actual value.
      
      NOTE: this table is not applicable to http and jitter 
            probes";
    smiv2:oid "1.3.6.1.4.1.9.9.42.1.2.8";
  }

  smiv2:alias "rttMonHistoryAdminEntry" {
    description
     "A list of objects that define RTT history collection
      operations.";
    smiv2:oid "1.3.6.1.4.1.9.9.42.1.2.8.1";
  }

  augment "/CISCO-RTTMON-MIB:CISCO-RTTMON-MIB/CISCO-RTTMON-MIB:rttMonCtrlAdminTable/CISCO-RTTMON-MIB:rttMonCtrlAdminEntry" {
    description
     "A list of objects that define RTT history collection
      operations.";
    smiv2:oid "1.3.6.1.4.1.9.9.42.1.2.8.1";

    leaf rttMonHistoryAdminNumLives {
      type int32 {
        range "0..2";
      }
      description
       "The maximum number of history lives to record.  A life
        is defined by the countdown (or transition) to zero 
        by the rttMonCtrlOperRttLife object.  A new life is
        created when the same conceptual RTT control row is
        restarted via the transition of the 
        rttMonCtrlOperRttLife object and its subsequent 
        countdown.
        
        The value of zero will shut off all 
        rttMonHistoryAdminTable data collection.";
      smiv2:defval "0";
      smiv2:max-access "read-write";
      smiv2:oid "1.3.6.1.4.1.9.9.42.1.2.8.1.1";
    }

    leaf rttMonHistoryAdminNumBuckets {
      type int32 {
        range "1..60";
      }
      description
       "The maximum number of history buckets to record.  When
        the RttMonRttType is 'pathEcho'  this value directly 
        represents a path to a target.  For all other 
        RttMonRttTypes this value should be set to the number 
        of operations to keep per lifetime.
        
        After rttMonHistoryAdminNumBuckets are filled, the 
        and the oldest entries are deleted and the most recent
        rttMonHistoryAdminNumBuckets buckets are retained.";
      smiv2:defval "15";
      smiv2:max-access "read-write";
      smiv2:oid "1.3.6.1.4.1.9.9.42.1.2.8.1.2";
    }

    leaf rttMonHistoryAdminNumSamples {
      type int32 {
        range "1..30";
      }
      description
       "The maximum number of history samples to record per
        bucket.  When the RttMonRttType is 'pathEcho' this 
        value directly represents the number of hops along a 
        path to a target, thus we can only support 30 hops.
        For all other RttMonRttTypes this value will be 
        forced to one by the agent.";
      smiv2:defval "16";
      smiv2:max-access "read-write";
      smiv2:oid "1.3.6.1.4.1.9.9.42.1.2.8.1.3";
    }

    leaf rttMonHistoryAdminFilter {
      type enumeration {
        enum "none" {
          value "1";
        }
        enum "all" {
          value "2";
        }
        enum "overThreshold" {
          value "3";
        }
        enum "failures" {
          value "4";
        }
      }
      description
       "Defines a filter for adding RTT results to the history
        buffer:
        
        none          - no history is recorded
        all           - the results of all completion times 
                         and failed completions are recorded
        overThreshold - the results of completion times
                         over rttMonCtrlAdminThreshold are 
                         recorded.
        failures      - the results of failed operations (only) 
                         are recorded.";
      smiv2:defval "none";
      smiv2:max-access "read-write";
      smiv2:oid "1.3.6.1.4.1.9.9.42.1.2.8.1.4";
    }
  }

  smiv2:alias "rttMonCtrlOperTable" {
    description
     "A table of which contains the Operational values for the
      probe, and the conceptual RTT control row. 
      
      This table augments the rttMonCtrlAdminTable.";
    smiv2:oid "1.3.6.1.4.1.9.9.42.1.2.9";
  }

  smiv2:alias "rttMonCtrlOperEntry" {
    description
     "A list of objects that describe the current state
      of probe, and the conceptual RTT control row.";
    smiv2:oid "1.3.6.1.4.1.9.9.42.1.2.9.1";
  }

  augment "/CISCO-RTTMON-MIB:CISCO-RTTMON-MIB/CISCO-RTTMON-MIB:rttMonCtrlAdminTable/CISCO-RTTMON-MIB:rttMonCtrlAdminEntry" {
    description
     "A list of objects that describe the current state
      of probe, and the conceptual RTT control row.";
    smiv2:oid "1.3.6.1.4.1.9.9.42.1.2.9.1";

    leaf rttMonCtrlOperModificationTime {
      type yang:timestamp;
      description
       "This object is updated whenever an object in
        the conceptual RTT control row is changed or
        updated.";
      smiv2:max-access "read-only";
      smiv2:oid "1.3.6.1.4.1.9.9.42.1.2.9.1.1";
    }

    leaf rttMonCtrlOperDiagText {
      type snmpv2-tc:DisplayString {
        length "0..51";
      }
      description
       "A string which can be used as an aid in tracing problems.
        The content of this field will depend on the type of 
        target (rttMonEchoAdminProtocol). 
        
        When rttMonEchoAdminProtocol is one of snaLU0EchoAppl, or 
        snaLU2EchoAppl this object contains the name of the 
        Logical Unit (LU) being used for this RTT session (from
        the HOST's point of view), once the session has been 
        established; this can then be used to correlate this 
        name to the connection information stored in the 
        Mainframe Host.
        
        When rttMonEchoAdminProtocol is snaLU62EchoAppl, this 
        object contains the Logical Unit (LU) name being used for
        this RTT session, once the session has been established.  
        This name can be used by the management application to 
        correlate this objects value to the connection 
        information stored at this SNMP Agent via the APPC or 
        APPN mib.
        
        When rttMonEchoAdminProtocol is not one of the 
        previously mentioned values, this value will be null.
        
        It is primarily intended that this object contains 
        information which has significance to a human operator.";
      smiv2:defval "";
      smiv2:max-access "read-only";
      smiv2:oid "1.3.6.1.4.1.9.9.42.1.2.9.1.2";
    }

    leaf rttMonCtrlOperResetTime {
      type yang:timestamp;
      description
       "This object is set when the rttMonCtrlOperState is set
        to reset.";
      smiv2:max-access "read-only";
      smiv2:oid "1.3.6.1.4.1.9.9.42.1.2.9.1.3";
    }

    leaf rttMonCtrlOperOctetsInUse {
      type yang:gauge32;
      description
       "This object is the number of octets currently in use
        by this composite conceptual RTT row.  A composite
        conceptual row include the control, statistics, and 
        history conceptual rows combined.  (All octets that
        are addressed via the rttMonCtrlAdminIndex in this
        mib.)";
      smiv2:max-access "read-only";
      smiv2:oid "1.3.6.1.4.1.9.9.42.1.2.9.1.4";
    }

    leaf rttMonCtrlOperConnectionLostOccurred {
      type boolean;
      description
       "This object will only change its value when the
        RttMonRttType is 'echo' or 'pathEcho'.
        
        This object is set to true when the RTT connection fails 
        to be established or is lost, and set to false when a 
        connection is reestablished.  When the RttMonRttType
        is 'pathEcho', connection loss applies only to the
        rttMonEchoAdminTargetAddress and not to intermediate
        hops to the Target.
        
        When this value changes and 
        rttMonReactAdminConnectionEnable is true, a reaction 
        will occur. 
        
        If a trap is sent it is a 
        rttMonConnectionChangeNotification.
        
        When this value changes and any one of the rttMonReactTable row
        has rttMonReactVar object value as 'connectionLoss(8)',
        a reaction may occur.
        
        If a trap is sent it is rttMonNotification with rttMonReactVar
        value of 'connectionLoss'.";
      smiv2:defval "false";
      smiv2:max-access "read-only";
      smiv2:oid "1.3.6.1.4.1.9.9.42.1.2.9.1.5";
    }

    leaf rttMonCtrlOperTimeoutOccurred {
      type boolean;
      description
       "This object will change its value for all
        RttMonRttTypes.
        
        This object is set to true when an operation times out, 
        and set to false when an operation completes under 
        rttMonCtrlAdminTimeout.  When this value changes, a 
        reaction may occur, as defined by 
        rttMonReactAdminTimeoutEnable. 
        
        When the RttMonRttType is 'pathEcho', this timeout
        applies only to the rttMonEchoAdminTargetAddress and
        not to intermediate hops to the Target.
        
        If a trap is sent it is a rttMonTimeoutNotification.
        
        When this value changes and any one of the rttMonReactTable
        row has rttMonReactVar object value as 'timeout(7)', a reaction
        may occur.
        
        If a trap is sent it is rttMonNotification with rttMonReactVar
        value of 'timeout'.";
      smiv2:defval "false";
      smiv2:max-access "read-only";
      smiv2:oid "1.3.6.1.4.1.9.9.42.1.2.9.1.6";
    }

    leaf rttMonCtrlOperOverThresholdOccurred {
      type boolean;
      description
       "This object will change its value for all
        RttMonRttTypes.
        
        This object is changed by operation completion times over
        threshold, as defined by rttMonReactAdminThresholdType.  
        When this value changes, a reaction may occur, as defined 
        by rttMonReactAdminThresholdType. 
        
        If a trap is sent it is a rttMonThresholdNotification.
        
        This object is set to true if the operation completion time
        exceeds the rttMonCtrlAdminThreshold and set to false when an
        operation completes under rttMonCtrlAdminThreshold. When this
        value changes, a reaction may occur, as defined by
        rttMonReactThresholdType.
        
        If a trap is sent it is rttMonNotification with rttMonReactVar
        value of 'rtt'.";
      smiv2:defval "false";
      smiv2:max-access "read-only";
      smiv2:oid "1.3.6.1.4.1.9.9.42.1.2.9.1.7";
    }

    leaf rttMonCtrlOperNumRtts {
      type int32 {
        range "0..2147483647";
      }
      description
       "This is the total number of probe operations that have
        been attempted.   
        
        This value is incremented for each start of an RTT 
        operation.  Thus when rttMonCtrlAdminRttType is set to 
        'pathEcho' this value will be incremented by one and 
        not for very every hop along the path.
        
        This object has the special behavior as defined by the
        ROLLOVER NOTE in the DESCRIPTION of the ciscoRttMonMIB
        object.
        
        This value is not effected by the rollover of a statistics
        hourly group.";
      smiv2:max-access "read-only";
      smiv2:oid "1.3.6.1.4.1.9.9.42.1.2.9.1.8";
    }

    leaf rttMonCtrlOperRttLife {
      type int32 {
        range "0..2147483647";
      }
      units "seconds";
      description
       "This object is decremented every second, until it
        reaches zero.  When the value of this object is zero
        RTT operations for this row are suspended.  This 
        object will either reach zero by a countdown or 
        it will transition to zero via setting the
        rttMonCtrlOperState.
        
        When this object reaches zero the agent needs to 
        transition the rttMonCtrlOperState to 'inactive'.
        
        REMEMBER:  The value 2147483647 has a special 
                   meaning.  When this object has the
                   value 2147483647, this object will
                   not decrement.  And thus the life 
                   time will never.
        
        When the rttMonCtrlOperState object is 'active' and 
        the rttMonReactTriggerOperState object transitions to 
        'active' this object will not be updated with the 
        current value of rttMonCrtlAdminRttLife object.";
      smiv2:max-access "read-only";
      smiv2:oid "1.3.6.1.4.1.9.9.42.1.2.9.1.9";
    }

    leaf rttMonCtrlOperState {
      type enumeration {
        enum "reset" {
          value "1";
        }
        enum "orderlyStop" {
          value "2";
        }
        enum "immediateStop" {
          value "3";
        }
        enum "pending" {
          value "4";
        }
        enum "inactive" {
          value "5";
        }
        enum "active" {
          value "6";
        }
        enum "restart" {
          value "7";
        }
      }
      description
       "The RttMonOperStatus object is used to
        manage the 'state' of the probe that is implementing 
        conceptual RTT control row.
        
        This status object has six defined values:
        
        reset(1)          - reset this entry, transition
                            to 'pending'
        orderlyStop(2)    - shutdown this entry at the end
                             of the next RTT operation attempt, 
                             transition to 'inactive'
        immediateStop(3)  - shutdown this entry immediately
                             (if possible), transition to 
                             'inactive'
        pending(4)        - this value is not settable and
                             this conceptual RTT control row is 
                             waiting for further control either 
                             via the rttMonScheduleAdminTable 
                             or the rttMonReactAdminTable/
                             rttMonReactTriggerAdminTable;
                             This object can transition to this
                             value via two mechanisms, first by
                             reseting this object, and second
                             by creating a conceptual Rtt control
                             row with the 
                             rttMonScheduleAdminRttStartTime
                             object with the its special value
        inactive(5)       - this value is not settable and
                             this conceptual RTT control row is 
                             waiting for further control via
                             the rttMonScheduleAdminTable;
                             This object can transition to this
                             value via two mechanisms, first by
                             setting this object to 'orderlyStop'
                             or 'immediateStop', second by 
                             the rttMonCtrlOperRttLife object
                             reaching zero
        active(6)         - this value is not settable and
                             this conceptual RTT control row is
                             currently active
        restart(7)        - this value is only settable when the
                             state is active. It clears the data
                             of this entry and remain on active state.
        
        The probes action when this object is set to 'reset':
          -  all rows in rttMonStatsCaptureTable that relate to 
              this conceptual RTT control row are destroyed and 
              the indices are set to 1
          -  if rttMonStatisticsAdminNumHourGroups is not zero, a 
              single new rttMonStatsCaptureTable row is created
          -  all rows in rttMonHistoryCaptureTable that relate 
              to this RTT definition are destroyed and the indices
              are set to 1
          -  implied history used for timeout or threshold
              notification (see rttMonReactAdminThresholdType or
              rttMonReactThresholdType)
              is purged
          -  rttMonCtrlOperRttLife is set to 
              rttMonScheduleAdminRttLife
          -  rttMonCtrlOperNumRtts is set to zero
          -  rttMonCtrlOperTimeoutOccurred, 
              rttMonCtrlOperOverThresholdOccurred, and 
              rttMonCtrlOperConnectionLostOccurred are set to 
              false; if this causes a change in the value of 
              either of these objects, resolution notifications 
              will not occur
          -  the next RTT operation is controlled by the objects
              in the rttMonScheduleAdminTable or the 
              rttMonReactAdminTable/rttMonReactTriggerAdminTable
          -  if the rttMonReactTriggerOperState is 'active', it 
              will transition to 'pending'
          -  all rttMonReactTriggerAdminEntries pointing to
              this conceptual entry with their 
              rttMonReactTriggerOperState object 'active', 
              will transition their OperState to 'pending'
          -  all open connections must be maintained
        
        This can be used to synchronize various RTT 
        definitions, so that the RTT requests occur 
        simultaneously, or as simultaneously as possible.
        
        The probes action when this object transitions to 
          'inactive' (via setting this object to 'orderlyStop' 
          or 'immediateStop' or by rttMonCtrlOperRttLife 
          reaching zero):
          -  all statistics and history collection information
              table entries will be closed and kept
          -  implied history used for timeout or threshold
              notification (see rttMonReactAdminThresholdType or
              rttMonReactThresholdType)
              is purged
          -  rttMonCtrlOperTimeoutOccurred, 
              rttMonCtrlOperOverThresholdOccurred, and 
              rttMonCtrlOperConnectionLostOccurred are set to 
              false; if this causes a change in the value of 
              either of these objects, resolution notifications 
              will not occur.
          -  the next RTT request is controlled by the objects
              in the rttMonScheduleAdminTable
          -  if the rttMonReactTriggerOperState is 'active', it 
              will transition to 'pending' (this denotes that
              the Trigger will be ready the next time this
              object goes active)
          -  all rttMonReactTriggerAdminEntries pointing to
              this conceptual entry with their 
              rttMonReactTriggerOperState object 'active', 
              will transition their OperState to 'pending'
          -  all open connections are to be closed and cleanup.
        
                     rttMonCtrlOperState
                            STATE
                  +-------------------------------------------+
                  |      A       |       B      |      C      |
        ACTION       |  'pending'   |  'inactive'  |   'active'  |
        +----------------+--------------+--------------+-------------+
        | OperState set  |    noError   |inconsistent- |   noError   |
        |  to 'reset'    |              | Value        |             |
        |                |    -> A      |              |   -> A      |
        +----------------+--------------+--------------+-------------+
        | OperState set  |    noError   |    noError   |   noError   |
        |to 'orderlyStop'|    -> B      |    -> B      |   -> B      |
        |     or to      |              |              |             |
        |'immediateStop' |              |              |             |
        +----------------+--------------+--------------+-------------+
        |  Event causes  |    -> C      |    -> B      |   -> C      |
        | Trigger State  |              |              |   see (3)   |
        | to transition  |              |              |             |
        | to 'active'    |              |              |             |
        +----------------+--------------+--------------+-------------+
        | AdminStatus    |    -> C      |    -> C      |   see (1)   |
        | transitions to |              |              |             |
        | 'active' &     |              |              |             |
        | RttStartTime is|              |              |             |
        | special value  |              |              |             |
        | of one.        |              |              |             |
        +----------------+--------------+--------------+-------------+
        | AdminStatus    |    -> A      |    -> A      |   see (1)   |
        | transitions to |              |              |             |
        | 'active' &     |              |              |             |
        | RttStartTime is|              |              |             |
        | special value  |              |              |             |
        | of less than   |              |              |             |
        | current time,  |              |              |             |
        | excluding one. |              |              |             |
        +----------------+--------------+--------------+-------------+
        | AdminStatus    |    -> A      |    -> B      |   see (2)   |
        | transitions to |              |              |             |
        | 'notInService' |              |              |             |
        +----------------+--------------+--------------+-------------+
        | AdminStatus    |    -> B      |    -> B      |   -> B      |
        | transitions to |              |              |             |
        | 'delete'       |              |              |             |
        +----------------+--------------+--------------+-------------+
        | AdminStatus is |    -> C      |    -> C      |   -> C      |
        | 'active' & the |              |              |   see (3)   |
        | RttStartTime   |              |              |             |
        | arrives        |              |              |             |
        +----------------+--------------+--------------+-------------+
        |   RowAgeout    |    -> B      |    -> B      |   -> B      |
        |    expires     |              |              |             |
        +----------------+--------------+--------------+-------------+
        |  OperRttLife   |    N/A       |    N/A       |   -> B      |
        | counts down to |              |              |             |
        | zero           |              |              |             |
        +----------------+--------------+--------------+-------------+
        
        (1) - rttMonCtrlOperState must have transitioned to 'inactive'
        or 'pending' before the rttMonCtrlAdminStatus can
        transition to 'active'.  See (2).
        (2) - rttMonCtrlAdminStatus cannot transition to 'notInService'
        unless rttMonCtrlOperState has been previously forced
        to 'inactive' or 'pending'.
        (3) - when this happens the rttMonCtrlOperRttLife will not
        be updated with the rttMonCtrlAdminRttLife.
        
        NOTE:  In order for all objects in a PDU to be set
               at the same time, this object can not be
               part of a multi-bound PDU.";
      smiv2:max-access "read-write";
      smiv2:oid "1.3.6.1.4.1.9.9.42.1.2.9.1.10";
    }

    leaf rttMonCtrlOperVerifyErrorOccurred {
      type boolean;
      description
       "This object is true if rttMonCtrlAdminVerifyData is
        set to true and data corruption occurs.";
      smiv2:defval "false";
      smiv2:max-access "read-only";
      smiv2:oid "1.3.6.1.4.1.9.9.42.1.2.9.1.11";
    }
  }

  smiv2:alias "rttMonLatestRttOperTable" {
    description
     "A table of which contains the status of latest RTT
      operation. 
      
      When the RttMonRttType is 'pathEcho', operations 
      performed to the hops along the path will be recorded
      in this table.
      
      This table augments the RTT definition table, 
      rttMonCtrlAdminTable.";
    smiv2:oid "1.3.6.1.4.1.9.9.42.1.2.10";
  }

  smiv2:alias "rttMonLatestRttOperEntry" {
    description
     "A list of objects that record the latest RTT operation.";
    smiv2:oid "1.3.6.1.4.1.9.9.42.1.2.10.1";
  }

  augment "/CISCO-RTTMON-MIB:CISCO-RTTMON-MIB/CISCO-RTTMON-MIB:rttMonCtrlAdminTable/CISCO-RTTMON-MIB:rttMonCtrlAdminEntry" {
    description
     "A list of objects that record the latest RTT operation.";
    smiv2:oid "1.3.6.1.4.1.9.9.42.1.2.10.1";

    leaf rttMonLatestRttOperCompletionTime {
      type yang:gauge32;
      units "milliseconds/microseconds";
      description
       "The completion time of the latest RTT operation
        successfully completed.
        
        The unit of this object will be microsecond when
        rttMonCtrlAdminRttType is set to 'jitter' and 
        rttMonEchoAdminPrecision is set to 'microsecond'.
        Otherwise, the unit of this object will be millisecond.";
      smiv2:max-access "read-only";
      smiv2:oid "1.3.6.1.4.1.9.9.42.1.2.10.1.1";
    }

    leaf rttMonLatestRttOperSense {
      type cisco-rttmon:RttResponseSense;
      description
       "A sense code for the completion status of the latest
        RTT operation.";
      smiv2:max-access "read-only";
      smiv2:oid "1.3.6.1.4.1.9.9.42.1.2.10.1.2";
    }

    leaf rttMonLatestRttOperApplSpecificSense {
      type int32 {
        range "0..2147483647";
      }
      description
       "An application specific sense code for the
        completion status of the latest RTT operation.  This 
        object will only be valid when the 
        rttMonLatestRttOperSense object is set to 
        'applicationSpecific'.  Otherwise, this object's 
        value is not valid.";
      smiv2:max-access "read-only";
      smiv2:oid "1.3.6.1.4.1.9.9.42.1.2.10.1.3";
    }

    leaf rttMonLatestRttOperSenseDescription {
      type snmpv2-tc:DisplayString;
      description
       "A sense description for the completion status of
        the latest RTT operation when the 
        rttMonLatestRttOperSense object is set to 
        'applicationSpecific'.";
      smiv2:max-access "read-only";
      smiv2:oid "1.3.6.1.4.1.9.9.42.1.2.10.1.4";
    }

    leaf rttMonLatestRttOperTime {
      type yang:timestamp;
      description
       "The value of the agent system time at the time of the
        latest RTT operation.";
      smiv2:max-access "read-only";
      smiv2:oid "1.3.6.1.4.1.9.9.42.1.2.10.1.5";
    }

    leaf rttMonLatestRttOperAddress {
      type cisco-rttmon:RttMonTargetAddress;
      description
       "When the RttMonRttType is 'echo', 'pathEcho', 'udpEcho',
        'tcpConnect', 'dns' and 'dlsw' this is a string which specifies 
        the address of the target for this RTT operation.  When the 
        RttMonRttType is not one of these types this object will 
        be null.
        
        This address will be the address of the hop along the
        path to the rttMonEchoAdminTargetAddress address,
        including rttMonEchoAdminTargetAddress address, or just
        the rttMonEchoAdminTargetAddress address, when the
        path information is not collected.  This behavior is
        defined by the rttMonCtrlAdminRttType object.
        
        The interpretation of this string depends on the type
        of RTT operation selected, as specified by the
        rttMonEchoAdminProtocol object.
        
        See rttMonEchoAdminTargetAddress for a complete
        description.";
      smiv2:max-access "read-only";
      smiv2:oid "1.3.6.1.4.1.9.9.42.1.2.10.1.6";
    }
  }

  smiv2:alias "rttMonReactTriggerOperTable" {
    description
     "A table of which contains the operational state
      of each entry in the 
      rttMonReactTriggerAdminTable.
      
      This table augments the RTT trigger 
      definition table, rttMonReactTriggerAdminTable.";
    smiv2:oid "1.3.6.1.4.1.9.9.42.1.2.12";
  }

  smiv2:alias "rttMonReactTriggerOperEntry" {
    description
     "A list of state objects for the
      rttMonReactTriggerAdminTable.";
    smiv2:oid "1.3.6.1.4.1.9.9.42.1.2.12.1";
  }

  augment "/CISCO-RTTMON-MIB:CISCO-RTTMON-MIB/CISCO-RTTMON-MIB:rttMonReactTriggerAdminTable/CISCO-RTTMON-MIB:rttMonReactTriggerAdminEntry" {
    description
     "A list of state objects for the
      rttMonReactTriggerAdminTable.";
    smiv2:oid "1.3.6.1.4.1.9.9.42.1.2.12.1";

    leaf rttMonReactTriggerOperState {
      type enumeration {
        enum "active" {
          value "1";
        }
        enum "pending" {
          value "2";
        }
      }
      description
       "This object takes on the value active
        when its associated entry in the 
        rttMonReactTriggerAdminTable has been
        triggered.
        
        When the associated entry in the
        rttMonReactTriggerAdminTable is not under
        a trigger state, this object will be
        pending.
        
        When this object is in the active state
        this entry can not be retriggered.";
      smiv2:max-access "read-only";
      smiv2:oid "1.3.6.1.4.1.9.9.42.1.2.12.1.1";
    }
  }

  smiv2:alias "rttMplsVpnMonTypeTable" {
    description
     "A table that contains Auto SAA L3 MPLS VPN configured RTT
      operation specific definitions.
      
      This table is controlled via the rttMplsVpnMonCtrlTable.
      Entries in this table are created via the
      rttMplsVpnMonCtrlStatus object.";
    smiv2:oid "1.3.6.1.4.1.9.9.42.1.2.16";
  }

  smiv2:alias "rttMplsVpnMonTypeEntry" {
    description
     "A list of objects that define RTT operation specific
      configuration for an Auto SAA L3 MPLS VPN.";
    smiv2:oid "1.3.6.1.4.1.9.9.42.1.2.16.1";
  }

  augment "/CISCO-RTTMON-MIB:CISCO-RTTMON-MIB/CISCO-RTTMON-MIB:rttMplsVpnMonCtrlTable/CISCO-RTTMON-MIB:rttMplsVpnMonCtrlEntry" {
    description
     "A list of objects that define RTT operation specific
      configuration for an Auto SAA L3 MPLS VPN.";
    smiv2:oid "1.3.6.1.4.1.9.9.42.1.2.16.1";

    leaf rttMplsVpnMonTypeInterval {
      type int32 {
        range "1..60000";
      }
      units "milliseconds";
      description
       "This value represents the inter-packet delay between packets
        and is in milliseconds. This value is currently used for
        Jitter probe. This object is applicable to jitter probe only.
        
        The usage of this value in RTT operation is same as
        rttMonEchoAdminInterval.";
      smiv2:defval "20";
      smiv2:max-access "read-write";
      smiv2:oid "1.3.6.1.4.1.9.9.42.1.2.16.1.1";
    }

    leaf rttMplsVpnMonTypeNumPackets {
      type int32 {
        range "1..60000";
      }
      description
       "This value represents the number of packets that need to be
        transmitted. This value is currently used for Jitter probe.
        This object is applicable to jitter probe only.
        
        The usage of this value in RTT operation is same as
        rttMonEchoAdminNumPackets.";
      smiv2:defval "10";
      smiv2:max-access "read-write";
      smiv2:oid "1.3.6.1.4.1.9.9.42.1.2.16.1.2";
    }

    leaf rttMplsVpnMonTypeDestPort {
      type int32 {
        range "1..65536";
      }
      description
       "This object represents the target's port number to which the
        packets need to be sent.
        
        This value will be configured as target port for all the
        operations that is going to be configured 
        
        The usage of this value is same as rttMonEchoAdminTargetPort
        in RTT operation. This object is applicable to jitter type.
        
        If this object is not being set random port will be used as
        destination port.";
      smiv2:max-access "read-write";
      smiv2:oid "1.3.6.1.4.1.9.9.42.1.2.16.1.3";
    }

    leaf rttMplsVpnMonTypeSecFreqType {
      type enumeration {
        enum "none" {
          value "1";
        }
        enum "timeout" {
          value "2";
        }
        enum "connectionLoss" {
          value "3";
        }
        enum "both" {
          value "4";
        }
      }
      description
       "This object specifies the reaction type for which the
        rttMplsVpnMonTypeSecFreqValue should be applied.
        
        The Value 'timeout' will cause secondary frequency to be set
        for frequency on timeout condition.
        
        The Value 'connectionLoss' will cause secondary frequency to
        be set for frequency on connectionloss condition.
        
        The Value 'both' will cause secondary frequency to be set for
        frequency on either of timeout/connectionloss condition.
        
        Notifications must be configured on corresponding reaction type
        in order to rttMplsVpnMonTypeSecFreqValue get effect.
        
        When LSP Path Discovery is enabled for this row the following
        rttMplsVpnMonReactLpdNotifyType notifications must be
        configured in order to rttMplsVpnMonTypeSecFreqValue get effect.
          - 'lpdGroupStatus' or 'lpdAll'.
        
        Since the Frequency of the operation changes the stats will be
        collected in new bucket.
        
        If any of the reaction type (timeout/connectionLoss) occurred
        for an operation configured by this Auto SAA L3 MPLS VPN and
        the following conditions are satisfied, the frequency of the
        operation will be changed to rttMplsVpnMonTypeSecFreqValue.
        
          1) rttMplsVpnMonTypeSecFreqType is set for a reaction type
          (timeout/connectionLoss).
          2) A notification is configured for the same reaction type
          (timeout/connectionLoss).
        
        When LSP Path Discovery is enabled for this row, if any of the
        reaction type (timeout/connectionLoss) occurred for 'single
        probes' configured by this Auto SAA L3 MPLS VPN and the
        following conditions are satisfied, the secondary frequency
        rttMplsVpnMonTypeSecFreqValue will be applied to the
        'lspGroup' probe.
        
          1) rttMplsVpnMonTypeSecFreqType is set for a reaction type
          (timeout/connectionLoss/both).
          2) rttMplsVpnMonReactLpdNotifyType object must be set to
          value of 'lpdGroupStatus' or 'lpdAll'.
        
        The frequency of the individual operations will be restored to
        original frequency once the trap is sent.";
      smiv2:defval "none";
      smiv2:max-access "read-write";
      smiv2:oid "1.3.6.1.4.1.9.9.42.1.2.16.1.4";
    }

    leaf rttMplsVpnMonTypeSecFreqValue {
      type int32 {
        range "1..604800";
      }
      description
       "This object represents the value that needs to be applied to
        secondary frequency of individual RTT operations configured by
        Auto SAA L3 MPLS VPN.
        
        Setting rttMplsVpnMonTypeSecFreqValue without setting
        rttMplsVpnMonTypeSecFreqType will not have any effect.";
      smiv2:defval "60";
      smiv2:max-access "read-write";
      smiv2:oid "1.3.6.1.4.1.9.9.42.1.2.16.1.5";
    }

    leaf rttMplsVpnMonTypeLspSelector {
      type binary;
      description
       "A string which specifies the address of the local host
        (127.X.X.X).
        
        This object will be used as lsp-selector in MPLS RTT
        operations configured by the Auto SAA L3 MPLS VPN.
        
        When LSP Path Discovery is enabled for the row, this object will
        be used to indicate the base LSP selector value to be used in
        the LSP Path Discovery.
        
        This value of this object is significant in MPLS load
        balancing scenario. This value will be used as one of the
        parameter in that load balancing.";
      smiv2:defval "7F 00 00 01";
      smiv2:max-access "read-write";
      smiv2:oid "1.3.6.1.4.1.9.9.42.1.2.16.1.6";
    }

    leaf rttMplsVpnMonTypeLSPReplyMode {
      type cisco-rttmon:RttMonLSPPingReplyMode;
      description
       "This object specifies the reply mode for the LSP Echo
        requests originated by the operations configured by the
        Auto SAA L3 MPLS VPN.
        
        This object is currently used by echo and pathEcho.";
      smiv2:defval "replyIpv4Udp";
      smiv2:max-access "read-write";
      smiv2:oid "1.3.6.1.4.1.9.9.42.1.2.16.1.7";
    }

    leaf rttMplsVpnMonTypeLSPTTL {
      type int32 {
        range "0..255";
      }
      description
       "This object represents the TTL setting for MPLS echo request
        packets originated by the operations configured by the
        Auto SAA L3 MPLS VPN.
        
        This object is currently used by echo and pathEcho.
        
        For 'echo' the default TTL will be set to 255.
        For 'pathEcho' the default will be set to 30.
        
        Note: This object cannot be set to the value of 0. The
        default value of 0 signifies the default TTL values will be
        used for 'echo' and 'pathEcho'.";
      smiv2:defval "0";
      smiv2:max-access "read-write";
      smiv2:oid "1.3.6.1.4.1.9.9.42.1.2.16.1.8";
    }

    leaf rttMplsVpnMonTypeLSPReplyDscp {
      type int32 {
        range "0..63|255";
      }
      description
       "This object specifies the DSCP value to be set in the IP header
        of the LSP echo reply packet.
        The value of this object will be in range of DiffServ codepoint
        values between 0 to 63.
        
        Note: This object cannot be set to value of 255. This default
        value specifies that DSCP is not set for this row.";
      smiv2:defval "255";
      smiv2:max-access "read-write";
      smiv2:oid "1.3.6.1.4.1.9.9.42.1.2.16.1.9";
    }

    leaf rttMplsVpnMonTypeLpdMaxSessions {
      type int32 {
        range "1..15";
      }
      description
       "This object represents the number of concurrent path discovery
        requests that will be active at one time per MPLS VPN control
        row. This object is meant for reducing the time for discovery
        of all the paths to the target in a large customer network.
        However its value should be chosen such that it does not cause
        any performance impact.
        
        Note: If the customer network has low end routers in the Core
        it is recommended to keep this value low.";
      smiv2:defval "1";
      smiv2:max-access "read-write";
      smiv2:oid "1.3.6.1.4.1.9.9.42.1.2.16.1.10";
    }

    leaf rttMplsVpnMonTypeLpdSessTimeout {
      type int32 {
        range "1..900";
      }
      units "seconds";
      description
       "This object specifies the maximum allowed duration of a
        particular tree trace request.
        
        If no response is received in configured time the request will
        be considered a failure.";
      smiv2:defval "120";
      smiv2:max-access "read-write";
      smiv2:oid "1.3.6.1.4.1.9.9.42.1.2.16.1.11";
    }

    leaf rttMplsVpnMonTypeLpdEchoTimeout {
      type int32 {
        range "0..604800000";
      }
      units "milliseconds";
      description
       "This object specifies the timeout value for the LSP echo
        requests which are sent while performing the LSP Path 
        Discovery.";
      smiv2:defval "5000";
      smiv2:max-access "read-write";
      smiv2:oid "1.3.6.1.4.1.9.9.42.1.2.16.1.12";
    }

    leaf rttMplsVpnMonTypeLpdEchoInterval {
      type int32 {
        range "0..3600000";
      }
      units "milliseconds";
      description
       "This object specifies the send interval between LSP echo
        requests which are sent while performing the LSP Path 
        Discovery.";
      smiv2:defval "0";
      smiv2:max-access "read-write";
      smiv2:oid "1.3.6.1.4.1.9.9.42.1.2.16.1.13";
    }

    leaf rttMplsVpnMonTypeLpdEchoNullShim {
      type boolean;
      description
       "This object specifies if the explicit-null label is added to
        LSP echo requests which are sent while performing the LSP Path
        Discovery.
        
        If set to TRUE all the probes configured as part of this control
        row will send the LSP echo requests with the explicit-null
        label added.";
      smiv2:defval "false";
      smiv2:max-access "read-write";
      smiv2:oid "1.3.6.1.4.1.9.9.42.1.2.16.1.14";
    }

    leaf rttMplsVpnMonTypeLpdScanPeriod {
      type int32 {
        range "0..7200";
      }
      units "minutes";
      description
       "This object specifies the scan time for the completion of LSP
        Path Discovery for all the PEs discovered for this control row.
        If the scan period is exceeded on completion of the LSP Path
        Discovery for all the PEs, the next discovery will start
        immediately else it will wait till expiry of scan period.
        
        For example: If the value is set to 30 minutes then on start of
        the LSP Path Discovery a timestamp will be taken say T1. At the
        end of the tree trace discovery one more timestamp will be taken
        again say T2. If (T2-T1) is greater than 30, the next discovery
        will start immediately else next discovery  will wait for
        [30 - (T2-T1)].
        
        Note: If the object is set to a special value of '0', it will
        force immediate start of the next discovery on all neighbours
        without any delay.";
      smiv2:defval "240";
      smiv2:max-access "read-write";
      smiv2:oid "1.3.6.1.4.1.9.9.42.1.2.16.1.15";
    }

    leaf rttMplsVpnMonTypeLpdStatHours {
      type int32 {
        range "0..2";
      }
      description
       "The maximum number of hours of data to be kept per LPD
        group. The LPD group statistics will be kept in an hourly
        bucket. At the maximum there can be two buckets.
        The value of 'one' is not advisable because the group will close
        and immediately be deleted before the network management station
        will have the opportunity to retrieve the statistics.
        
        The value used in the rttMplsVpnLpdGroupStatsTable to
        uniquely identify this group is the
        rttMonStatsCaptureStartTimeIndex.
        
        Note: When this object is set to the value of '0' all
        rttMplsVpnLpdGroupStatsTable data capturing will be shut off.";
      smiv2:defval "2";
      smiv2:max-access "read-write";
      smiv2:oid "1.3.6.1.4.1.9.9.42.1.2.16.1.16";
    }
  }

  smiv2:alias "rttMplsVpnMonScheduleTable" {
    description
     "A table of Auto SAA L3 MPLS VPN monitoring scheduling
      specific definitions.
      
      This table is controlled via the rttMplsVpnMonCtrlTable.
      Entries in this table are created via the
      rttMplsVpnMonCtrlStatus object.";
    smiv2:oid "1.3.6.1.4.1.9.9.42.1.2.17";
  }

  smiv2:alias "rttMplsVpnMonScheduleEntry" {
    description
     "A list of objects that define specific configuration for
      the scheduling of RTT operations.";
    smiv2:oid "1.3.6.1.4.1.9.9.42.1.2.17.1";
  }

  augment "/CISCO-RTTMON-MIB:CISCO-RTTMON-MIB/CISCO-RTTMON-MIB:rttMplsVpnMonCtrlTable/CISCO-RTTMON-MIB:rttMplsVpnMonCtrlEntry" {
    description
     "A list of objects that define specific configuration for
      the scheduling of RTT operations.";
    smiv2:oid "1.3.6.1.4.1.9.9.42.1.2.17.1";

    leaf rttMplsVpnMonScheduleRttStartTime {
      type yang:timeticks;
      description
       "This is the time when this conceptual row will
        activate. rttMplsVpnMonSchedulePeriod object must be specified
        before setting this object.
        
        This is the value of MIB-II's sysUpTime in the future.
        When sysUpTime equals this value this object will
        cause the activation of a conceptual Auto SAA L3 MPLS VPN row.
        
        When an agent has the capability to determine date and
        time, the agent should store this object as DateAndTime.
        This allows the agent to be able to activate conceptual
        Auto SAA L3 MPLS VPN row at the intended time.
        
        If this object has value as 1, this means start the operation
        now itself. Value of 0 puts the operation in pending state.";
      smiv2:defval "0";
      smiv2:max-access "read-write";
      smiv2:oid "1.3.6.1.4.1.9.9.42.1.2.17.1.1";
    }

    leaf rttMplsVpnMonSchedulePeriod {
      type int32 {
        range "1..604800";
      }
      units "seconds";
      description
       "Specifies the time duration over which all the probes created
        by the current Auto SAA L3 MPLS VPN have to be scheduled.
        
        This object must be set first before setting
        rttMplsVpnMonScheduleRttStartTime.";
      smiv2:max-access "read-write";
      smiv2:oid "1.3.6.1.4.1.9.9.42.1.2.17.1.2";
    }

    leaf rttMplsVpnMonScheduleFrequency {
      type int32 {
        range "1..604800";
      }
      units "seconds";
      description
       "Specifies the duration between initiating each RTT
        operation configured by the Auto SAA L3 MPLS VPN.
        
        This object cannot be set to a value which would be a
        shorter duration than rttMplsVpnMonCtrlTimeout.
        
        The usage of this value in RTT operation is same as
        rttMonCtrlAdminFrequency.";
      smiv2:defval "60";
      smiv2:max-access "read-write";
      smiv2:oid "1.3.6.1.4.1.9.9.42.1.2.17.1.3";
    }
  }

  smiv2:alias "rttMplsVpnMonReactTable" {
    description
     "A Table of Auto SAA L3 MPLS VPN Notification definitions.
      
      This table augments the rttMplsVpnMonCtrlTable.";
    smiv2:oid "1.3.6.1.4.1.9.9.42.1.2.18";
  }

  smiv2:alias "rttMplsVpnMonReactEntry" {
    description
     "A list of objects that define Auto SAA L3 MPLS VPN reaction
      configuration.";
    smiv2:oid "1.3.6.1.4.1.9.9.42.1.2.18.1";
  }

  augment "/CISCO-RTTMON-MIB:CISCO-RTTMON-MIB/CISCO-RTTMON-MIB:rttMplsVpnMonCtrlTable/CISCO-RTTMON-MIB:rttMplsVpnMonCtrlEntry" {
    description
     "A list of objects that define Auto SAA L3 MPLS VPN reaction
      configuration.";
    smiv2:oid "1.3.6.1.4.1.9.9.42.1.2.18.1";

    leaf rttMplsVpnMonReactConnectionEnable {
      type boolean;
      description
       "The value set for this will be applied as
        rttMonReactAdminConnectionEnable for individual probes created
        by the Auto SAA L3 MPLS VPN.
        
        When this object is set to true, rttMonReactVar for individual
        probes created by the Auto SAA L3 MPLS VPN will be set to
        'connectionLoss(8)'.";
      smiv2:defval "false";
      smiv2:max-access "read-write";
      smiv2:oid "1.3.6.1.4.1.9.9.42.1.2.18.1.1";
    }

    leaf rttMplsVpnMonReactTimeoutEnable {
      type boolean;
      description
       "The value set for this will be applied as
        rttMonReactAdminTimeoutEnable for individual probes created
        by the Auto SAA L3 MPLS VPN.
        
        When this object is set to true, rttMonReactVar for individual
        probes created by the Auto SAA L3 MPLS VPN will be set to
        'timeout(7)'.";
      smiv2:defval "false";
      smiv2:max-access "read-write";
      smiv2:oid "1.3.6.1.4.1.9.9.42.1.2.18.1.2";
    }

    leaf rttMplsVpnMonReactThresholdType {
      type enumeration {
        enum "never" {
          value "1";
        }
        enum "immediate" {
          value "2";
        }
        enum "consecutive" {
          value "3";
        }
      }
      description
       "The value corresponding to this object will be applied as
        rttMonReactAdminThresholdType for individual probes created by
        the Auto SAA L3 MPLS VPN.
        
        The value corresponding to this object will be applied as
        rttMonReactThresholdType for individual probes created by
        the Auto SAA L3 MPLS VPN.";
      smiv2:defval "never";
      smiv2:max-access "read-write";
      smiv2:oid "1.3.6.1.4.1.9.9.42.1.2.18.1.3";
    }

    leaf rttMplsVpnMonReactThresholdCount {
      type int32 {
        range "1..16";
      }
      description
       "This object value will be applied as
        rttMonReactAdminThresholdCount for individual probes created by
        the Auto SAA L3 MPLS VPN.
        
        This object value will be applied as rttMonReactThresholdCountX
        for individual probes created by the Auto SAA L3 MPLS VPN.";
      smiv2:defval "5";
      smiv2:max-access "read-write";
      smiv2:oid "1.3.6.1.4.1.9.9.42.1.2.18.1.4";
    }

    leaf rttMplsVpnMonReactActionType {
      type enumeration {
        enum "none" {
          value "1";
        }
        enum "trapOnly" {
          value "2";
        }
      }
      description
       "The value corresponding to this object will be applied as
        rttMonReactAdminActionType of individual probes created by
        this Auto SAA L3 MPLS VPN.
        
        The value corresponding to this object will be applied as
        rttMonReactActionType of individual probes created by
        this Auto SAA L3 MPLS VPN.";
      smiv2:defval "none";
      smiv2:max-access "read-write";
      smiv2:oid "1.3.6.1.4.1.9.9.42.1.2.18.1.5";
    }

    leaf rttMplsVpnMonReactLpdNotifyType {
      type enumeration {
        enum "none" {
          value "1";
        }
        enum "lpdPathDiscovery" {
          value "2";
        }
        enum "lpdGroupStatus" {
          value "3";
        }
        enum "lpdAll" {
          value "4";
        }
      }
      description
       "This object specifies the type of LPD notifications to be
        generated for the current Auto SAA L3 MPLS VPN control row.
        
        This object will be applicable only when LSP Path Discovery is
        enabled for this row.
        
        There are two types of notifications supported for the LPD -
        (a) rttMonLpdDiscoveryNotification - This notification will
            be sent on the failure of LSP Path Discovery to the
            particular PE. Reversal of the failure will also result in
            sending the notification.
        (b) rttMonLpdGrpStatusNotification - Individual probes in an LPD
            group will not generate notifications independently but will
            be generating dependent on the state of the group. Any
            individual probe can initiate the generation of a
            notification, dependent on the state of the group.
            Notifications are only generated if the failure/restoration
            of an individual probe causes the state of the group to
            change.
        
        The Value 'none' will not cause any notifications to be sent.
        
        The Value 'lpdPathDiscovery' will cause (a) to be sent.
        
        The Value 'lpdGroupStatus' will cause (b) to be sent.
        
        The Value 'lpdAll' will cause both (a) and (b) to sent
        depending on the failure conditions.";
      smiv2:defval "none";
      smiv2:max-access "read-write";
      smiv2:oid "1.3.6.1.4.1.9.9.42.1.2.18.1.6";
    }

    leaf rttMplsVpnMonReactLpdRetryCount {
      type int32 {
        range "1..16";
      }
      units "attempts";
      description
       "This object value specifies the number of attempts to be
        performed before declaring the path as 'down'. Each 'single
        probe' which is part of 'lspGroup' probe will be retried these
        many times before marking it as 'down'.
        
        This object will be applicable only when LSP Path Discovery is
        enabled for this row.
        
          - When rttMplsVpnMonTypeSecFreqType is not configured, the
            failure count will be incremented at the next cycle of
            'lspGroup' probe at interval's of
            rttMplsVpnMonScheduleFrequency value.
        
            For example: Assume there are 10 paths discovered and on
            the first run of the 'lspGroup' probe first two paths failed
            and rest passed. On the second run all the probes will be 
            run again. The probes 1 and 2 will be retried till the
            rttMplsVpnMonReactLpdRetryCount value, and
            then marked as 'down' and rttMonLpdGrpStatusNotification 
            will be sent if configured.
        
          - When rttMplsVpnMonTypeSecFreqType value is anything other
            than 'none', the retry will happen for the failed probes at
            the rttMplsVpnMonTypeSecFreqValue and only the failed
            probes will be retried.
        
            For example: Assume there are 10 paths discovered and on the
            first run of the 'lspGroup' probe first two paths failed and
            rest passed. The secondary frequency will be applied to the
            failed probes. At secondary frequency interval the first two
            probes will be run again. The probes 1 and 2 will be retried
            till the rttMplsVpnMonReactLpdRetryCount value, and
            then marked as 'down' and rttMonLpdGrpStatusNotification 
            will be sent if configured.";
      smiv2:defval "1";
      smiv2:max-access "read-write";
      smiv2:oid "1.3.6.1.4.1.9.9.42.1.2.18.1.7";
    }
  }

  notification rttMonConnectionChangeNotification {
    status deprecated;
    description
     "This notification is only valid when the RttMonRttType
      is 'echo' or 'pathEcho'.
      
      A rttMonConnectionChangeNotification indicates that a
      connection to a target (not to a hop along the path
      to a target) has either failed on establishment or 
      been lost and when reestablished.  Precisely, this
      has resulted in rttMonCtrlOperConnectionLostOccurred
      changing value.
      
      If History is not being collected, the instance values 
      for the rttMonHistoryCollectionAddress object will not 
      be valid.  When RttMonRttType is not 'echo' or 'pathEcho'
      the rttMonHistoryCollectionAddress object will be null.
      rttMonConnectionChangeNotification object is superseded by
      rttMonNotification.";
    smiv2:oid "1.3.6.1.4.1.9.9.42.2.0.1";

    container object-1 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlAdminTag {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminTag";
        }
      }
    }

    container object-2 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonHistoryCollectionLifeIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionLifeIndex";
        }
      }

      leaf rttMonHistoryCollectionBucketIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionBucketIndex";
        }
      }

      leaf rttMonHistoryCollectionSampleIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionSampleIndex";
        }
      }

      leaf rttMonHistoryCollectionAddress {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionAddress";
        }
      }
    }

    container object-3 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlOperConnectionLostOccurred {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlOperConnectionLostOccurred";
        }
      }
    }
  }

  notification rttMonTimeoutNotification {
    status deprecated;
    description
     "A rttMonTimeoutNotification indicates the occurrence of
      a timeout for a RTT operation, and it indicates the 
      clearing of such a condition by a subsequent RTT 
      operation. Precisely, this has resulted in 
      rttMonCtrlOperTimeoutOccurred changing value. 
      
      When the RttMonRttType is 'pathEcho', this 
      notification will only be sent when the timeout 
      occurs during an operation to the target and not to
      a hop along the path to the target.  This also 
      applies to the clearing of the timeout. 
      
      If History is not being collected, the instance values 
      for the rttMonHistoryCollectionAddress object will not 
      be valid.  When RttMonRttType is not 'echo' or 'pathEcho'
      the rttMonHistoryCollectionAddress object will be null.
      rttMonTimeoutNotification object is superseded by
      rttMonNotification.";
    smiv2:oid "1.3.6.1.4.1.9.9.42.2.0.2";

    container object-1 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlAdminTag {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminTag";
        }
      }
    }

    container object-2 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonHistoryCollectionLifeIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionLifeIndex";
        }
      }

      leaf rttMonHistoryCollectionBucketIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionBucketIndex";
        }
      }

      leaf rttMonHistoryCollectionSampleIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionSampleIndex";
        }
      }

      leaf rttMonHistoryCollectionAddress {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionAddress";
        }
      }
    }

    container object-3 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlOperTimeoutOccurred {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlOperTimeoutOccurred";
        }
      }
    }
  }

  notification rttMonThresholdNotification {
    status deprecated;
    description
     "A rttMonThresholdNotification indicates the
      occurrence of a threshold violation for a RTT operation,
      and it indicates the previous violation has subsided for
      a subsequent RTT operation.  Precisely, this has resulted
      in rttMonCtrlOperOverThresholdOccurred changing value.  
      
      When the RttMonRttType is 'pathEcho', this 
      notification will only be sent when the threshold
      violation occurs during an operation to the target and
      not to a hop along the path to the target.  This also
      applies to the subsiding of a threshold condition.
      
      If History is not being collected, the instance values 
      for the rttMonHistoryCollectionAddress object will not 
      be valid.  When RttMonRttType is not 'echo' or 'pathEcho'
      the rttMonHistoryCollectionAddress object will be null.
      
      rttMonThresholdNotification object is superseded by
      rttMonNotification.";
    smiv2:oid "1.3.6.1.4.1.9.9.42.2.0.3";

    container object-1 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlAdminTag {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminTag";
        }
      }
    }

    container object-2 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonHistoryCollectionLifeIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionLifeIndex";
        }
      }

      leaf rttMonHistoryCollectionBucketIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionBucketIndex";
        }
      }

      leaf rttMonHistoryCollectionSampleIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionSampleIndex";
        }
      }

      leaf rttMonHistoryCollectionAddress {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionAddress";
        }
      }
    }

    container object-3 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlOperOverThresholdOccurred {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlOperOverThresholdOccurred";
        }
      }
    }
  }

  notification rttMonVerifyErrorNotification {
    status deprecated;
    description
     "A rttMonVerifyErrorNotification indicates the
      occurrence of a data corruption in an RTT operation.
      rttMonVerifyErrorNotification object is superseded by
      rttMonNotification.";
    smiv2:oid "1.3.6.1.4.1.9.9.42.2.0.4";

    container object-1 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlAdminTag {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminTag";
        }
      }
    }

    container object-2 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonHistoryCollectionLifeIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionLifeIndex";
        }
      }

      leaf rttMonHistoryCollectionBucketIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionBucketIndex";
        }
      }

      leaf rttMonHistoryCollectionSampleIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionSampleIndex";
        }
      }

      leaf rttMonHistoryCollectionAddress {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionAddress";
        }
      }
    }

    container object-3 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlOperVerifyErrorOccurred {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlOperVerifyErrorOccurred";
        }
      }
    }
  }

  notification rttMonNotification {
    description
     "A rttMonNotification indicates the occurrence of a
      threshold violation, and it indicates the previous
      violation has subsided for a subsequent operation. 
      
      When the RttMonRttType is 'pathEcho', this
      notification will only be sent when the threshold
      violation occurs during an operation to the target and
      not to a hop along the path to the target. This also
      applies to the subsiding of a threshold condition.
      
      If History is not being collected, the instance values
      for the rttMonHistoryCollectionAddress object will not
      be valid. When RttMonRttType is not 'echo' or 'pathEcho'
      the rttMonHistoryCollectionAddress object will be null.
      
      rttMonReactVar defines the type of reaction that is
      configured for the probe ( e.g jitterAvg, rtt etc ).
      In the rttMonReactTable there are trap definitions
      for the probes and each probe may have more than
      one trap definitions for various types ( e.g rtt,
      jitterAvg, packetLoossSD etc ). So the object rttMonReactVar
      indicates the type ( e.g. rtt, packetLossSD, timeout etc )
      for which threshold violation traps has been generated.
      
      The object rttMonEchoAdminLSPSelector will be valid only
      for the probes based on 'mplsLspPingAppl' RttMonProtocol. For
      all other probes it will be null.";
    smiv2:oid "1.3.6.1.4.1.9.9.42.2.0.5";

    container object-1 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonCtrlAdminTag {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminTag";
        }
      }
    }

    container object-2 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonHistoryCollectionLifeIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionLifeIndex";
        }
      }

      leaf rttMonHistoryCollectionBucketIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionBucketIndex";
        }
      }

      leaf rttMonHistoryCollectionSampleIndex {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionSampleIndex";
        }
      }

      leaf rttMonHistoryCollectionAddress {
        type leafref {
          path "/CISCO-RTTMON-MIB:CISCO-RTTMON-MIB/CISCO-RTTMON-MIB:rttMonHistoryCollectionTable/CISCO-RTTMON-MIB:rttMonHistoryCollectionEntry/CISCO-RTTMON-MIB:rttMonHistoryCollectionAddress";
        }
      }
    }

    container object-3 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonReactConfigIndex {
        type leafref {
          path "/CISCO-RTTMON-MIB:CISCO-RTTMON-MIB/CISCO-RTTMON-MIB:rttMonReactTable/CISCO-RTTMON-MIB:rttMonReactEntry/CISCO-RTTMON-MIB:rttMonReactConfigIndex";
        }
      }

      leaf rttMonReactVar {
        type leafref {
          path "/CISCO-RTTMON-MIB:CISCO-RTTMON-MIB/CISCO-RTTMON-MIB:rttMonReactTable/CISCO-RTTMON-MIB:rttMonReactEntry/CISCO-RTTMON-MIB:rttMonReactVar";
        }
      }
    }

    container object-4 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonReactConfigIndex {
        type leafref {
          path "/CISCO-RTTMON-MIB:CISCO-RTTMON-MIB/CISCO-RTTMON-MIB:rttMonReactTable/CISCO-RTTMON-MIB:rttMonReactEntry/CISCO-RTTMON-MIB:rttMonReactConfigIndex";
        }
      }

      leaf rttMonReactOccurred {
        type leafref {
          path "/CISCO-RTTMON-MIB:CISCO-RTTMON-MIB/CISCO-RTTMON-MIB:rttMonReactTable/CISCO-RTTMON-MIB:rttMonReactEntry/CISCO-RTTMON-MIB:rttMonReactOccurred";
        }
      }
    }

    container object-5 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonReactConfigIndex {
        type leafref {
          path "/CISCO-RTTMON-MIB:CISCO-RTTMON-MIB/CISCO-RTTMON-MIB:rttMonReactTable/CISCO-RTTMON-MIB:rttMonReactEntry/CISCO-RTTMON-MIB:rttMonReactConfigIndex";
        }
      }

      leaf rttMonReactValue {
        type leafref {
          path "/CISCO-RTTMON-MIB:CISCO-RTTMON-MIB/CISCO-RTTMON-MIB:rttMonReactTable/CISCO-RTTMON-MIB:rttMonReactEntry/CISCO-RTTMON-MIB:rttMonReactValue";
        }
      }
    }

    container object-6 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonReactConfigIndex {
        type leafref {
          path "/CISCO-RTTMON-MIB:CISCO-RTTMON-MIB/CISCO-RTTMON-MIB:rttMonReactTable/CISCO-RTTMON-MIB:rttMonReactEntry/CISCO-RTTMON-MIB:rttMonReactConfigIndex";
        }
      }

      leaf rttMonReactThresholdRising {
        type leafref {
          path "/CISCO-RTTMON-MIB:CISCO-RTTMON-MIB/CISCO-RTTMON-MIB:rttMonReactTable/CISCO-RTTMON-MIB:rttMonReactEntry/CISCO-RTTMON-MIB:rttMonReactThresholdRising";
        }
      }
    }

    container object-7 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonReactConfigIndex {
        type leafref {
          path "/CISCO-RTTMON-MIB:CISCO-RTTMON-MIB/CISCO-RTTMON-MIB:rttMonReactTable/CISCO-RTTMON-MIB:rttMonReactEntry/CISCO-RTTMON-MIB:rttMonReactConfigIndex";
        }
      }

      leaf rttMonReactThresholdFalling {
        type leafref {
          path "/CISCO-RTTMON-MIB:CISCO-RTTMON-MIB/CISCO-RTTMON-MIB:rttMonReactTable/CISCO-RTTMON-MIB:rttMonReactEntry/CISCO-RTTMON-MIB:rttMonReactThresholdFalling";
        }
      }
    }

    container object-8 {

      leaf rttMonCtrlAdminIndex {
        type leafref {
          path "/CISCO-RTTMON-MIB:CISCO-RTTMON-MIB/CISCO-RTTMON-MIB:rttMonCtrlAdminTable/CISCO-RTTMON-MIB:rttMonCtrlAdminEntry/CISCO-RTTMON-MIB:rttMonCtrlAdminIndex";
        }
      }

      leaf rttMonEchoAdminLSPSelector {
        type leafref {
          path "/CISCO-RTTMON-MIB:CISCO-RTTMON-MIB/CISCO-RTTMON-MIB:rttMonEchoAdminTable/CISCO-RTTMON-MIB:rttMonEchoAdminEntry/CISCO-RTTMON-MIB:rttMonEchoAdminLSPSelector";
        }
      }
    }
  }

  notification rttMonLpdDiscoveryNotification {
    description
     "A rttMonLpdDiscoveryNotification indicates that the LSP Path
      Discovery to the target PE has failed, and it also indicates
      the clearing of such condition. Precisely this has resulted in
      rttMonLpdGrpStatsLPDFailOccurred changing value.
      
      When the rttMonLpdGrpStatsLPDFailOccurred is 'false', the
      instance value for rttMonLpdGrpStatsLPDFailCause is not valid.";
    smiv2:oid "1.3.6.1.4.1.9.9.42.2.0.6";

    container object-1 {

      leaf rttMplsVpnMonCtrlIndex {
        type leafref {
          path "/CISCO-RTTMON-MIB:CISCO-RTTMON-MIB/CISCO-RTTMON-MIB:rttMplsVpnMonCtrlTable/CISCO-RTTMON-MIB:rttMplsVpnMonCtrlEntry/CISCO-RTTMON-MIB:rttMplsVpnMonCtrlIndex";
        }
      }

      leaf rttMplsVpnMonCtrlTag {
        type leafref {
          path "/CISCO-RTTMON-MIB:CISCO-RTTMON-MIB/CISCO-RTTMON-MIB:rttMplsVpnMonCtrlTable/CISCO-RTTMON-MIB:rttMplsVpnMonCtrlEntry/CISCO-RTTMON-MIB:rttMplsVpnMonCtrlTag";
        }
      }
    }

    container object-2 {

      leaf rttMonLpdGrpStatsGroupIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsGroupIndex";
        }
      }

      leaf rttMonLpdGrpStatsStartTimeIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsStartTimeIndex";
        }
      }

      leaf rttMonLpdGrpStatsTargetPE {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsTargetPE";
        }
      }
    }

    container object-3 {

      leaf rttMonLpdGrpStatsGroupIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsGroupIndex";
        }
      }

      leaf rttMonLpdGrpStatsStartTimeIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsStartTimeIndex";
        }
      }

      leaf rttMonLpdGrpStatsLPDFailCause {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsLPDFailCause";
        }
      }
    }

    container object-4 {

      leaf rttMonLpdGrpStatsGroupIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsGroupIndex";
        }
      }

      leaf rttMonLpdGrpStatsStartTimeIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsStartTimeIndex";
        }
      }

      leaf rttMonLpdGrpStatsLPDFailOccurred {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsLPDFailOccurred";
        }
      }
    }
  }

  notification rttMonLpdGrpStatusNotification {
    description
     "A rttMonLpdGrpStatusNotification indicates that the LPD
      Group status rttMonLpdGrpStatsGroupStatus has changed indicating
      some connectivity change to the target PE.
      This has resulted in rttMonLpdGrpStatsGroupStatus changing
      value.";
    smiv2:oid "1.3.6.1.4.1.9.9.42.2.0.7";

    container object-1 {

      leaf rttMplsVpnMonCtrlIndex {
        type leafref {
          path "/CISCO-RTTMON-MIB:CISCO-RTTMON-MIB/CISCO-RTTMON-MIB:rttMplsVpnMonCtrlTable/CISCO-RTTMON-MIB:rttMplsVpnMonCtrlEntry/CISCO-RTTMON-MIB:rttMplsVpnMonCtrlIndex";
        }
      }

      leaf rttMplsVpnMonCtrlTag {
        type leafref {
          path "/CISCO-RTTMON-MIB:CISCO-RTTMON-MIB/CISCO-RTTMON-MIB:rttMplsVpnMonCtrlTable/CISCO-RTTMON-MIB:rttMplsVpnMonCtrlEntry/CISCO-RTTMON-MIB:rttMplsVpnMonCtrlTag";
        }
      }
    }

    container object-2 {

      leaf rttMonLpdGrpStatsGroupIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsGroupIndex";
        }
      }

      leaf rttMonLpdGrpStatsStartTimeIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsStartTimeIndex";
        }
      }

      leaf rttMonLpdGrpStatsTargetPE {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsTargetPE";
        }
      }
    }

    container object-3 {

      leaf rttMonLpdGrpStatsGroupIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsGroupIndex";
        }
      }

      leaf rttMonLpdGrpStatsStartTimeIndex {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsStartTimeIndex";
        }
      }

      leaf rttMonLpdGrpStatsGroupStatus {
        type leafref {
          path "/CISCO-RTTMON-MIB:CISCO-RTTMON-MIB/CISCO-RTTMON-MIB:rttMonLpdGrpStatsTable/CISCO-RTTMON-MIB:rttMonLpdGrpStatsEntry/CISCO-RTTMON-MIB:rttMonLpdGrpStatsGroupStatus";
        }
      }
    }
  }

  smiv2:alias "ciscoRttMonMIB" {
    smiv2:oid "1.3.6.1.4.1.9.9.42";
  }

  smiv2:alias "ciscoRttMonObjects" {
    smiv2:oid "1.3.6.1.4.1.9.9.42.1";
  }

  smiv2:alias "rttMonAppl" {
    smiv2:oid "1.3.6.1.4.1.9.9.42.1.1";
  }

  smiv2:alias "rttMonCtrl" {
    smiv2:oid "1.3.6.1.4.1.9.9.42.1.2";
  }

  smiv2:alias "rttMonStats" {
    smiv2:oid "1.3.6.1.4.1.9.9.42.1.3";
  }

  smiv2:alias "rttMonHistory" {
    smiv2:oid "1.3.6.1.4.1.9.9.42.1.4";
  }

  smiv2:alias "rttMonLatestOper" {
    smiv2:oid "1.3.6.1.4.1.9.9.42.1.5";
  }

  smiv2:alias "rttMonNotificationsPrefix" {
    smiv2:oid "1.3.6.1.4.1.9.9.42.2";
  }

  smiv2:alias "rttMonNotifications" {
    smiv2:oid "1.3.6.1.4.1.9.9.42.2.0";
  }

  smiv2:alias "ciscoRttMonMibConformance" {
    smiv2:oid "1.3.6.1.4.1.9.9.42.3";
  }

  smiv2:alias "ciscoRttMonMibCompliances" {
    smiv2:oid "1.3.6.1.4.1.9.9.42.3.1";
  }

  smiv2:alias "ciscoRttMonMibGroups" {
    smiv2:oid "1.3.6.1.4.1.9.9.42.3.2";
  }

}
