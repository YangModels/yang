module Cisco-IOS-XE-perf-measure-events {
  yang-version 1;
  namespace "http://cisco.com/ns/yang/Cisco-IOS-XE-perf-measure-events";
  prefix perf-measure-ios-xe-events;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for performance measure events data.
     Copyright (c) 2020 by Cisco Systems, Inc.
     All rights reserved.";

  revision 2020-07-01 {
    description
      "Initial revision";
    reference "1.0.0";
    cisco-semver:module-version "1.0.0";
    cisco-semver-internal:os-version "17.3.1";
  }

  grouping pm-dm-probe-end-notification {
    description
      "Performance measurement delay measurement probe end notification";
    leaf name {
      type string;
      description
        "Name of interface or policy name";
    }
  }

  grouping pm-dm-aggregation-end-notification {
    description
      "Performance measurement delay measurement aggregation end notification";
    leaf name {
      type string;
      description
        "Name of interface or policy name";
    }
  }

  grouping pm-dm-advertisement-event-notification {
    description
      "Performance measurement delay measurement advertisement event notification";
    leaf name {
      type string;
      description
        "Name of interface or policy name";
    }
  }

  notification pm-dm-probe-end-notif {
    description
      "Performance measurement delay measurement probe end notification queue";
    uses perf-measure-ios-xe-events:pm-dm-probe-end-notification;
  }
  notification pm-dm-aggr-end-notif {
    description
      "Performance measurement delay measurement aggregation end notification queue";
    uses perf-measure-ios-xe-events:pm-dm-aggregation-end-notification;
  }
  notification pm-dm-adv-event-notif {
    description
      "Performance measurement delay measurement advertisement event notification queue";
    uses perf-measure-ios-xe-events:pm-dm-advertisement-event-notification;
  }
  container Cisco-IOS-XE-perf-measure-events {
    config false;
    tailf:callpoint "ios-eventq-db";
    tailf:meta-data "callpoint" {
      tailf:meta-value "ios-eventq-db";
    }
    tailf:meta-data "greenprefix" {
      tailf:meta-value "/services;serviceName=iosevent";
    }
    tailf:meta-data "name" {
      tailf:meta-value "Cisco-IOS-XE-perf-measure-events";
    }
    tailf:hidden "full";
  }

  grouping __yangpp_metadata {
    description
      "Internal metadata for this module and imported modules";
  }

  container schema-metadata-Cisco-IOS-XE-perf-measure-events {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-perf-measure-events";
    }
    tailf:meta-data "organization" {
      tailf:meta-value "Cisco Systems, Inc.";
    }
    tailf:meta-data "semver" {
      tailf:meta-value "2020-07-01";
    }
  }
}
