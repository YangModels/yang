module Cisco-IOS-XE-ospf-events {
  yang-version 1;
  namespace "http://cisco.com/ns/yang/Cisco-IOS-XE-ospf-events";
  prefix ospf-ios-xe-events;

  import Cisco-IOS-XE-ospf-common {
    prefix ospf-ios-xe-common;
  }
  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "OSPF Notification events YANG definitions
     Copyright (c) 2020 by Cisco Systems, Inc.
     All rights reserved.";

  revision 2020-07-01 {
    description
      "Initial revision";
    reference "1.0.0";
    cisco-semver:module-version "1.0.0";
  }

  typedef ospfv3-notification-severity {
    type enumeration {
      enum "ospfv3-notif-severity-critical" {
        value 0;
        description
          "OSPFv3 Notification Critical severity";
      }
      enum "ospfv3-notif-severity-major" {
        value 1;
        description
          "OSPFv3 Notification Major severity";
      }
      enum "ospfv3-notif-severity-minor" {
        value 2;
        description
          "OSPFv3 Notification Minor severity";
      }
    }
    description
      "OSPFv3 notification severity";
  }

  grouping ospfv3-notif-nbr-state {
    description
      "OSPFv3 neighbor state";
    leaf severity {
      type ospf-ios-xe-events:ospfv3-notification-severity;
      description
        "Event severity";
    }
    leaf vrf-name {
      type string;
      description
        "VRF Name";
    }
    leaf process-id {
      type uint16;
      description
        "Process ID";
    }
    leaf af {
      type ospf-ios-xe-common:ospfv3-address-family-types;
      description
        "Address family identifier";
    }
    leaf router-id {
      type inet:ip-address;
      description
        "Router ID";
    }
    leaf nbr-addr {
      type inet:ipv6-address;
      description
        "Neighbor Address";
    }
    leaf nbr-id {
      type inet:ip-address;
      description
        "Neighbor ID";
    }
    leaf if-name {
      type string;
      description
        "Interface name";
    }
    leaf if-addr {
      type inet:ipv6-address;
      description
        "Interface address";
    }
    leaf nbr-state {
      type ospf-ios-xe-common:ospfv3-nbr-state;
      description
        "OSPFv3 Neighbor state";
    }
  }

  grouping ospfv3-notif-if-state {
    description
      "OSPFv3 interface state Notification";
    leaf severity {
      type ospf-ios-xe-events:ospfv3-notification-severity;
      description
        "Event severity";
    }
    leaf vrf-name {
      type string;
      description
        "VRF name";
    }
    leaf process-id {
      type uint16;
      description
        "Process ID";
    }
    leaf af {
      type ospf-ios-xe-common:ospfv3-address-family-types;
      description
        "Address family identifier";
    }
    leaf router-id {
      type inet:ip-address;
      description
        "Router ID";
    }
    leaf network-type {
      type ospf-ios-xe-common:ospfv3-network-type;
      description
        "OSPFv3 network type";
    }
    leaf if-name {
      type string;
      description
        "Interface name";
    }
    leaf if-state {
      type ospf-ios-xe-common:ospfv3-if-state;
      description
        "OSPFv3 interface state";
    }
  }

  notification ospfv3-nbr-state-change {
    description
      "OSPFv3 neighbor state change notification";
    uses ospf-ios-xe-events:ospfv3-notif-nbr-state;
  }
  notification ospfv3-if-state-change {
    description
      "OSPFv3 interface state change notification";
    uses ospf-ios-xe-events:ospfv3-notif-if-state;
  }
}
