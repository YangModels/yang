module Cisco-IOS-XE-controller-shdsl-oper {
  yang-version 1;
  namespace "http://cisco.com/ns/yang/Cisco-IOS-XE-controller-shdsl-oper";
  prefix shdsl-ios-xe-oper;

  import Cisco-IOS-XE-controller-shdsl-common {
    prefix shdsl-ios-xe-common;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring controller SHDSL operational information.
     Copyright (c) 2019 by Cisco Systems, Inc.
     All rights reserved.";

  revision 2020-03-01 {
    description
      "Initial revision";
    reference "1.0.0";
    cisco-semver:module-version "1.0.0";
    cisco-semver-internal:os-version "17.2.1";
  }

  grouping shdsl-controller-info {
    description
      "SHDSL Controller Information";
    leaf state {
      type shdsl-ios-xe-common:controller-state;
      description
        "Controller State";
    }
    leaf hardware {
      type string;
      description
        "Hardware";
    }
    leaf efm-capabilities {
      type string;
      description
        "Ethernet Capabilities";
    }
    leaf atm-capabilities {
      type string;
      description
        "ATM Capabilities";
    }
    leaf termination {
      type shdsl-ios-xe-common:term-type;
      description
        "Termination";
    }
    leaf configured-mode {
      type shdsl-ios-xe-common:mode-type;
      description
        "Configured Mode";
    }
    leaf vendor {
      type string;
      description
        "Vendor";
    }
    leaf chipset {
      type string;
      description
        "Description";
    }
    leaf phy-source {
      type string;
      description
        "Phy source";
    }
    leaf phy-firmware-files {
      type string;
      description
        "Phy Firmware Files";
    }
    leaf idc-firmware-version {
      type string;
      description
        "Integrated Device Control Firmware version";
    }
    leaf dfe-firmware-version {
      type string;
      description
        "Digital Front End Firmware Version";
    }
    list groups-conf {
      description
        "Groups Configuration";
      uses shdsl-ios-xe-common:shdsl-configured-group;
    }
  }

  container shdsl-oper-data {
    config false;
    description
      "SHDSL controller information";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    tailf:meta-data "name" {
      tailf:meta-value "Cisco-IOS-XE-controller-shdsl-oper";
    }
    list shdsl-info {
      key "slot-num subslot-num";
      description
        "SHDSL controller information";
      uses shdsl-ios-xe-oper:shdsl-controller-info;
      uses shdsl-ios-xe-common:shdsl-slot-info-key;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWQcM0u4AA+/fgEQAEAY9UD/v3vq/7976UANvd0YGO3XLTEJommmoeoaaD1BoA0aHqD0h6gAkkBT0mjT0k009T1AAAAAACRISaMptTRpoaAaaADCANAcwAAAAAAAAAAJFCJ6MSehSBoAADQHpMgep+DfB4VB3gBARjcw+A8yjhCrql5yTFIRR+ULa2+0DqCN/IQGzBNM2Dl1mN+BtLeOnRI59Imn5GgRCAhhEITiERCgGwbTHEKAW9stZxiytAhjF1QMweAfpRoJhvwuZc4W1iRNyWxEpEffkc0ct4MBlw12UU4KBKx0G46PNvPnOQiam80OkpRmk5ZECVtrhJZNDdm+teuo0QlKiWo8lWSFaPrbI8AksCHNJwhrWAybVTKMepKGgbSclKwdYVVQxWY6oZWhgocc0sTQybjHOgsyQyrQaDI5IFWJRdkLIkdAR/JnYz4NET7BFaojZQLCFFLc5Q2M9zgiwal+TYbqY4xgqK10moJVSyIrBmojMC5Ra58kULNEcEFxEjBk4Jdg7nYrNI1Lqpc1KLdBEk5hAxySQywhPGzc5zwAFkmlQyM5I6JBcMThkYcwmBtomGI8RrCMkrS5W9odgS0GrWlgWYxGGYqQeaRh051f7plSYxCkkG26ZTmwJ2QtvYdZBz4y2MuD2zQGliMUfDVoIxnAylcjzPMnZ6cWHqHYlcojKDCJDLWufBJeoHVPtcRCSHUGMtwqro9kIniEVdQUiMNGdSHEVEQESslKoVeAaJk3g8WOCNiIaTbc1ewWm1AyFcDrrRpguqVQm7JXZpf3gQOImEBsswoR4mswDPtxKTDnpLevM3O9F19mcAnV1NISSjelaSrV4RHvcDnOZXlPuF1CpnsNIzF6VjKRoNTi9JiKWVLJR8Ep3B9SuoA3Gq2KpSIm9ooMdrKeExaiO1LRl60A2FApcPFiJNBiJGFUntpYxOIxu1u8lfrNMNhBuG8C6AcsmFi4QSsbZyUUd2QEzEGuEGi3STR6yQiiVU9S3Ff1oP8019znpBgyDGf4u5IpwoSAOGaXc";
      }
      tailf:meta-data "uncompressed_size" {
        tailf:meta-value "2050";
      }
    }
    container Cisco-IOS-XE-controller-shdsl-common {
      description
        "Hidden internal container used for metadata";
      uses shdsl-ios-xe-common:__yangpp_metadata;
    }
  }

  container schema-metadata-Cisco-IOS-XE-controller-shdsl-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-controller-shdsl-oper";
    }
    tailf:meta-data "organization" {
      tailf:meta-value "Cisco Systems, Inc.";
    }
    tailf:meta-data "semver" {
      tailf:meta-value "2020-03-01";
    }
  }
}
