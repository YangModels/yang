module cisco-xe-routing-asr-openconfig-if-ethernet-deviation {
  namespace "http://openconfig.net/yang/cisco-xe-routing-asr-openconfig-if-ethernet-deviation";
  prefix cisco-xe-routing-asr-oc-if-eth-devs;

  import openconfig-interfaces {
    prefix oc-if;
  }
  import openconfig-if-ethernet {
    prefix oc-if-eth;
  }

  organization
    "Cisco Systems, Inc.";
  contact
    " Cisco Systems, Inc.
     Customer Service
     
     Postal: 170 W Tasman Drive
     San Jose, CA 95134
     
     Tel: +1 1800 553-NETS
     
     E-mail: cs-yang@cisco.com";
  description
    "This module defines deviation statements for openconfig-if-ethernet module for IOS XE Routing ASR devices.";

  revision 2018-07-01 {
    description
      "Deviated defaults for oc-if-ethernet interfaces to the values supported on the device";
  }
  revision 2017-11-01 {
    description
      "Remove defaults for oc-if-ethernet incompatible with some interfaces";
  }
  revision 2017-10-31 {
    description
      "CSR1K PD Ethernet feature deviations removed";
  }
  revision 2017-09-01 {
    description
      "CSR1K PD Ethernet feature deviations";
  }
  revision 2017-02-21 {
    description
      "Initial Revision";
    reference
      "RFC 6020: YANG - A Data Modeling Language for the
       Network Configuration Protocol (NETCONF)";
  }

  deviation "/oc-if:interfaces/oc-if:interface/oc-if-eth:ethernet/oc-if-eth:config/oc-if-eth:enable-flow-control" {
    deviate replace {
      default "true";
    }
    description
      "Setting default flow control is not compatible with all interface types.";
  }
  deviation "/oc-if:interfaces/oc-if:interface/oc-if-eth:ethernet/oc-if-eth:config/oc-if-eth:auto-negotiate" {
    deviate replace {
      default "false";
    }
  }
}
