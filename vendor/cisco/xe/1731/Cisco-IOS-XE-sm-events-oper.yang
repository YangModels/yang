module Cisco-IOS-XE-sm-events-oper {
  yang-version 1;
  namespace "http://cisco.com/ns/yang/Cisco-IOS-XE-sm-events-oper";
  prefix sm-event-oper;

  import Cisco-IOS-XE-sm-enum-types {
    prefix sm-enum-types;
  }
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for session operations events generated from the Cisco Wired
     devices. These models may produce high volume of data.
     Copyright (c) 2019-2020 by Cisco Systems, Inc.
     All rights reserved";

  revision 2020-07-01 {
    description
      "- Remove unused empty container sm-events";
    reference "0.0.0";
    cisco-semver:module-version "0.0.0";
    cisco-semver-internal:os-version "17.3.1";
  }
  revision 2020-03-01 {
    description
      "- Added interface name to session event data";
    reference "1.1.0";
    cisco-semver:module-version "1.1.0";
    cisco-semver-internal:os-version "17.2.1";
  }
  revision 2019-11-01 {
    description
      "Initial revision";
    reference "1.0.0";
    cisco-semver:module-version "1.0.0";
    cisco-semver-internal:os-version "17.1.1";
  }

  grouping session-authc-success-params {
    description
      "Parameters sent in case of a authentication SUCCESS event";
    leaf eap-method {
      type sm-enum-types:session-eap-method;
      description
        "EAP method for a dot1x client";
    }
  }

  grouping session-authz-success-params {
    description
      "Parameters sent in case of a authorization SUCCESS event";
    leaf res-vlan-id {
      type uint32;
      description
        "Resultant Vlan ID applied on a session";
    }
    leaf res-vlan-name {
      type string;
      description
        "Resultant Vlan name applied on a session";
    }
    leaf sgt {
      type uint32;
      description
        "Security Group Tag applied on a session";
    }
    leaf eap-method {
      type sm-enum-types:session-eap-method;
      description
        "EAP method for a dot1x client";
    }
  }

  grouping session-failure-params {
    description
      "Parameters sent in case of a FAILURE event";
    leaf failure-reason {
      type sm-enum-types:session-event-failure-reason;
      description
        "Reason for authentication session failure";
    }
    leaf failed-attribute {
      type string;
      description
        "Failed Attribute in case of session failure";
    }
  }

  grouping session-coa-params {
    description
      "Parameters sent in case of a COA event";
    leaf coa-req-type {
      type sm-enum-types:session-coa-request-type;
      description
        "COA request type";
    }
  }

  grouping session-security-violation-params {
    description
      "Parameters sent in case of a security violation event";
    leaf security-violation-action {
      type sm-enum-types:session-security-violation-action;
      description
        "Security violation type";
    }
  }

  grouping session-event-data {
    description
      "Wired session lifecycle events data model";
    leaf client-mac {
      type yang:mac-address;
      description
        "Wired Client's MAC Address";
    }
    leaf audit-session-id {
      type string;
      description
        "Audit session id of the session";
    }
    leaf method-id {
      type sm-enum-types:session-auth-method-id;
      description
        "Authentication method used for the session";
    }
    leaf username {
      type string;
      description
        "Client's username for a session";
    }
    leaf client-join-time {
      type yang:date-and-time;
      description
        "Client's join time";
    }
    leaf server-address {
      type inet:ip-address;
      description
        "IP address for the authentication server";
    }
    leaf session-event {
      type sm-enum-types:session-events;
      config false;
      description
        "DO NOT USE!  -- hidden internal";
      tailf:hidden "full";
      tailf:meta-data "hidden" {
        tailf:meta-value "true";
      }
    }
    leaf interface-name {
      type string;
      description
        "Name of the interface connected to client";
    }
    choice session-event-choice {
      description
        "Union of Session Events";
      case session-event-session-authc-success {
        container authc-success-params {
          description
            "Session event result authentication success parameters";
          uses sm-event-oper:session-authc-success-params;
        }
      }
      case session-event-session-authc-failed {
        container authc-failure-params {
          description
            "Session event result authentication failure parameters";
          uses sm-event-oper:session-failure-params;
        }
      }
      case session-event-session-authz-success {
        container authz-success-params {
          description
            "Session event result authorization success parameters";
          uses sm-event-oper:session-authz-success-params;
        }
      }
      case session-event-session-authz-failed {
        container authz-failure-params {
          description
            "Session event result authorization failure parameters";
          uses sm-event-oper:session-failure-params;
        }
      }
      case session-event-policy-update {
        container policy-change-params {
          description
            "Session event policy update parameters";
          uses sm-event-oper:session-authz-success-params;
        }
      }
      case session-event-coa-start {
        container coa-params {
          description
            "Event coa start parameters";
          uses sm-event-oper:session-coa-params;
        }
      }
      case session-event-security-violation {
        container security-violation-params {
          description
            "Event security violation parameters";
          uses sm-event-oper:session-security-violation-params;
        }
      }
    }
  }

  notification sessionevent {
    description
      "Session event Notification";
    uses sm-event-oper:session-event-data;
  }
  container Cisco-IOS-XE-sm-events-oper {
    config false;
    tailf:callpoint "sm-eventq-db";
    tailf:meta-data "callpoint" {
      tailf:meta-value "sm-eventq-db";
    }
    tailf:meta-data "greenprefix" {
      tailf:meta-value "/services;serviceName=smevent";
    }
    tailf:meta-data "name" {
      tailf:meta-value "Cisco-IOS-XE-sm-events-oper";
    }
    tailf:hidden "full";
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWcPAQdcAC3wfgBAGMhA/7//wv+//+mAGJ7PrsAB0HV2AA6IYhVN+qn6poNAyGnqD1H6pmk09T1GmgA1PRMiaaJHlDRp6mmRoGgAGgMBoAABoAAAAABgNAAANAAAAAAESokDNIaNMCaGmIxDTTRggJETQgFMIJRoAADCenqQNhFSVXClG2YXS+mnnH0BhE/bkEtSKJPKcMWVSMxKzW5MjVtzy/VSyLgLYkanIJakUSeXCLKNe398AkBQmNAS74gCbarlaeUP0lIhyQRpUakOlYMzvWUcgQBIBEgBCH0y69Lpq9666PJ7mKX/Fr2tfSJE80jV1cGEKtA5iq2JQrF7YbBsO75uvdmxtsemuvjviz7dra1OLNRWSQAcayXrlyWy+MYlpyUQwCSydsbVusTBBYJMjqI7ip4ZoloCSMjFYGH5tjuzkgEYu0GoNns/hewdAZZgknx3/VMG/voYCWIwmkljgisOahGggKa+1o/Dl18zMOBsd4pcxn8PkJOg4tLMLsyTuEN7WxJWxiAmZXYi8SwzCXDo0OM/aMqfxk63ws4gEfcV0+vu+fHO4KUAdZz3MFFrE+6SFwM7GmBF0ZVOTdQkCH5AnACsucoEozYxrKhQ8XADqd5H78QTTme9XWgAXNoSA15NdpVrpQxk50SSoneKujKJRokkDBh9fgxnha8oS76jOUccUR8bXus+hn1mPS0u1FHhmwwFc5i47bHnLvRWa6GZ0qh2i58jCeaCsA2gwxJE0AJVrRIjcXH0BHTD27d9kUh+mVPrYGNjYm0hsBiEDaD0k0lkfHR408691NNV1DfY8HGPU3kKOoVxkqzAt72wgYAbt8QhTt5jVmuNSh2DCmDxsp78Mv7NbMPomEQAkCPXOdQSwq2BVJGkJXaB6b3s0u3MDJM4sHttYqjI2SFktQEwQRYtCMhNmZmDi6WBouRBqzBpCSUlrRIlAeQM3ZvHaSjaPXgEi6vprsgSawI8u62svj5PfhVwIWY2dmfkOUjVoAmTmH+MqqvffFtTBADIhAlaPPVR8em3fS+L704462vtXGtmZ5w6urgwhGpB4yq2JQrF7YYjI8Wi692JBJINlKY73p30u9YtirwTGSQAcQVblybZd34sVnEpdyJNHCi1mh3zMSZHURzlTwTRKAJIyD7dGfw2joTsK/ruyYJBIHsB17l7tewhAXUgknVclgw3Q18gHRk5UJJZ/tDxlxUItqvvYkHo+bMhbY2K5j/jB/6DJxMM6DVYsQR4CH3iagrUxATMiPDgwhxAI4ryMt99pOtPqcyb8RgnxKhQ/rG+oKUAdZ0zGCreYot7pIXQ1puXEbW1yJqxuECBHgCYXOQFoIS497yAHfSpOCO2ILXe6DCYAQbQkLrkvtKuk2MjTVJKMG7q69maIsjUSQMGHvj9cacrbpCXUP29CY668dDLo879tjN7rXYvtMdu2mxY48wYKIAXo9B+u7YAl1GCUFyjGbdhk6Yom0XF/01tgKaDDEkYRMR1oa9Q25E/oCOzD38ebGiGn5aQxsbE2kNgNIAbA00Vu2jg+JIrscc+ukFU+wYYG77G/fPuYtcaw1gZN/iYQZZAAbN7whT5qMtX10KHYMLxstOIjHc5ZXrnhr6JMYiBA6BBJUq1IqSNdpCiDWXs6qBmqVDRoRBTVGISSktaJQrGc0HtmwqouNqwBkBNIVWLQjQJVjM1Y3zQeoFpZ12mSjMSeuyEi/O3AhKFgR5eVJs/8nturVCO7+kLf+LuSKcKEhh4CDrg=";
      }
      tailf:meta-data "uncompressed_size" {
        tailf:meta-value "5885";
      }
    }
    container Cisco-IOS-XE-sm-enum-types {
      description
        "Hidden internal container used for metadata";
      uses sm-enum-types:__yangpp_metadata;
    }
  }

  container schema-metadata-Cisco-IOS-XE-sm-events-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-sm-events-oper";
    }
    tailf:meta-data "organization" {
      tailf:meta-value "Cisco Systems, Inc.";
    }
    tailf:meta-data "semver" {
      tailf:meta-value "2020-07-01";
    }
  }
}
