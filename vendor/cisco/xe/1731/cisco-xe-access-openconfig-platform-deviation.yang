module cisco-xe-access-openconfig-platform-deviation {
  namespace "http://openconfig.net/yang/cisco-xe-access-openconfig-platform-deviation";
  prefix cisco-xe-access-oc-platform-devs;

  import openconfig-platform {
    prefix oc-platform;
  }
  import openconfig-alarms {
    prefix oc-alarms;
  }
  import openconfig-interfaces {
    prefix oc-if;
  }

  organization
    "Cisco Systems, Inc.";
  contact
    " Cisco Systems, Inc.
     Customer Service
     
     Postal: 170 W Tasman Drive
     San Jose, CA 95134
     
     Tel: +1 1800 553-NETS
     
     E-mail: cs-yang@cisco.com";
  description
    "This module defines deviation statements for openconfig-platform model applicable to IOS XE SP Access platforms.";

  revision 2018-12-12 {
    description
      "Initial revision";
    reference
      "RFC 6020: YANG - A Data Modeling Language for the
       Network Configuration Protocol (NETCONF)";
  }

  deviation "/oc-platform:components" {
    deviate not-supported;
    description
      "oc-platform currently is not supported on IOS XE SP Access platforms.";
  }
}
