module Cisco-IOS-XE-platform-oper {
  yang-version 1;
  namespace "http://cisco.com/ns/yang/Cisco-IOS-XE-platform-oper";
  prefix platform-ios-xe-oper;
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of platform components.
     Copyright (c) 2016-2017, 2019 by Cisco Systems, Inc.
     All rights reserved.";

  revision 2019-11-01 {
    description
      "Added status description field";
    reference "2.3.0";
    cisco-semver:module-version "2.3.0";
    cisco-semver-internal:os-version "17.1.1";
  }
  revision 2019-05-01 {
    description
      "- Added component status, temperature
       alarm data and new leaves to component state.
       - Added semantic version";
    reference "2.2.0";
    cisco-semver:module-version "2.2.0";
  }
  revision 2018-10-29 {
    description
      "Cleaned up spelling errors in descriptions.";
    reference "2.1.0";
    cisco-semver:module-version "2.1.0";
  }
  revision 2017-10-11 {
    description
      "Enumeration name fix";
    reference "2.0.0";
    cisco-semver:module-version "2.0.0";
  }
  revision 2017-02-06 {
    description
      "Initial revision";
    reference "1.0.0";
    cisco-semver:module-version "1.0.0";
  }

  typedef platform-comp-type {
    type enumeration {
      enum "comp-chassis" {
        value 0;
        tailf:code-name "ENUM_platform_comp_type_CHASSIS";
      }
      enum "comp-backplane" {
        value 1;
        tailf:code-name "ENUM_platform_comp_type_BACKPLANE";
      }
      enum "comp-power-supply" {
        value 2;
        tailf:code-name "ENUM_platform_comp_type_POWER_SUPPLY";
      }
      enum "comp-fan" {
        value 3;
        tailf:code-name "ENUM_platform_comp_type_FAN";
      }
      enum "comp-sensor" {
        value 4;
        tailf:code-name "ENUM_platform_comp_type_SENSOR";
      }
      enum "comp-module" {
        value 5;
        tailf:code-name "ENUM_platform_comp_type_MODULE";
      }
      enum "comp-linecard" {
        value 6;
        tailf:code-name "ENUM_platform_comp_type_LINECARD";
      }
      enum "comp-port" {
        value 7;
        tailf:code-name "ENUM_platform_comp_type_PORT";
      }
      enum "comp-cpu" {
        value 8;
        tailf:code-name "ENUM_platform_comp_type_CPU";
      }
      enum "comp-operating-system" {
        value 9;
        tailf:code-name "ENUM_platform_comp_type_OPERATING_SYSTEM";
      }
      enum "comp-optical-channel" {
        value 10;
        tailf:code-name "ENUM_platform_comp_type_OPTICAL_CHANNEL";
      }
      enum "comp-container" {
        value 11;
        tailf:code-name "ENUM_platform_comp_type_CONTAINER";
      }
      enum "comp-fru" {
        value 12;
        tailf:code-name "ENUM_platform_comp_type_FRU";
      }
      enum "comp-controller-card" {
        value 13;
        tailf:code-name "ENUM_platform_comp_type_CONTROLLER_CARD";
      }
      enum "comp-transceiver" {
        value 14;
        tailf:code-name "ENUM_platform_comp_type_TRANSCEIVER";
      }
    }
    description
      "Component Type";
  }

  typedef platform-comp-status {
    type enumeration {
      enum "status-active" {
        value 0;
        tailf:code-name "ENUM_platform_comp_status_OC_ACTIVE";
      }
      enum "status-inactive" {
        value 1;
        tailf:code-name "ENUM_platform_comp_status_OC_INACTIVE";
      }
      enum "status-disabled" {
        value 2;
        tailf:code-name "ENUM_platform_comp_status_OC_DISABLED";
      }
    }
    description
      "Component status";
  }

  typedef temp-alarm-severity {
    type enumeration {
      enum "severity-unknown" {
        value 0;
        tailf:code-name "ENUM_temp_alarm_severity_OC_UNKNOWN";
      }
      enum "severity-minor" {
        value 1;
        tailf:code-name "ENUM_temp_alarm_severity_OC_MINOR";
      }
      enum "severity-major" {
        value 2;
        tailf:code-name "ENUM_temp_alarm_severity_OC_MAJOR";
      }
      enum "severity-critical" {
        value 3;
        tailf:code-name "ENUM_temp_alarm_severity_OC_CRITICAL";
      }
      enum "severity-warning" {
        value 4;
        tailf:code-name "ENUM_temp_alarm_severity_OC_WARNING";
      }
    }
    description
      "Temperature Alarm Severity";
  }

  typedef status-description {
    type enumeration {
      enum "status-desc-ok" {
        value 0;
        description
          "Component in working state";
        tailf:code-name "ENUM_status_description_STATUS_OK";
      }
      enum "status-desc-thermal-failure" {
        value 1;
        description
          "Thermal failure";
        tailf:code-name "ENUM_status_description_STATUS_THERMAL_FAILURE";
      }
      enum "status-desc-fan-failure" {
        value 2;
        description
          "Fan failure";
        tailf:code-name "ENUM_status_description_STATUS_FAN_FAILURE";
      }
      enum "status-desc-supply-failure" {
        value 3;
        description
          "Power Supply failure";
        tailf:code-name "ENUM_status_description_STATUS_SUPPLY_FAILURE";
      }
      enum "status-desc-no-response" {
        value 4;
        description
          "No response from component";
        tailf:code-name "ENUM_status_description_STATUS_NO_RESPONSE";
      }
      enum "status-desc-no-input" {
        value 5;
        description
          "Component has no input";
        tailf:code-name "ENUM_status_description_STATUS_NO_INPUT";
      }
      enum "status-desc-bad-power" {
        value 6;
        description
          "Component has bad power";
        tailf:code-name "ENUM_status_description_STATUS_BAD_POWER";
      }
      enum "status-desc-overload" {
        value 7;
        description
          "Component is overloaded";
        tailf:code-name "ENUM_status_description_STATUS_OVERLOAD";
      }
      enum "status-desc-disabled" {
        value 8;
        description
          "Component is disabled";
        tailf:code-name "ENUM_status_description_STATUS_DISABLED";
      }
      enum "status-desc-vacant" {
        value 9;
        description
          "Component slot is vacant";
        tailf:code-name "ENUM_status_description_STATUS_VACANT";
      }
      enum "status-desc-standby" {
        value 10;
        description
          "Component is in standby or redundant state";
        tailf:code-name "ENUM_status_description_STATUS_STANDBY";
      }
      enum "status-desc-bad-cookie" {
        value 11;
        description
          "Component failure - bad cookie";
        tailf:code-name "ENUM_status_description_STATUS_BAD_COOKIE";
      }
      enum "status-desc-invalid" {
        value 12;
        description
          "Component in invalid state";
        tailf:code-name "ENUM_status_description_STATUS_INVALID";
      }
    }
    description
      "Detailed status";
  }

  typedef platform-prop-value-type {
    type enumeration {
      enum "property-string" {
        value 0;
        tailf:code-name "ENUM_platform_prop_value_type_PROPERTY_STRING";
      }
      enum "property-boolean" {
        value 1;
        tailf:code-name "ENUM_platform_prop_value_type_PROPERTY_BOOLEAN";
      }
      enum "property-int64" {
        value 2;
        tailf:code-name "ENUM_platform_prop_value_type_PROPERTY_INT64";
      }
      enum "property-uint64" {
        value 3;
        tailf:code-name "ENUM_platform_prop_value_type_PROPERTY_UINT64";
      }
      enum "property-decimal64" {
        value 4;
        tailf:code-name "ENUM_platform_prop_value_type_PROPERTY_DECIMAL64";
      }
    }
    description
      "Property value type";
  }

  grouping platform-comp-temp {
    description
      "Temperature state data for device components";
    leaf temp-instant {
      type decimal64 {
        fraction-digits 2;
      }
      description
        "Instantaneous temperature value of a component";
    }
    leaf temp-avg {
      type decimal64 {
        fraction-digits 2;
      }
      description
        "Arithmetic mean value of the statistic over a
         sampling period";
    }
    leaf temp-max {
      type decimal64 {
        fraction-digits 2;
      }
      description
        "High water mark value of the statistic over a
         sampling period";
    }
    leaf temp-min {
      type decimal64 {
        fraction-digits 2;
      }
      description
        "Low water mark value of the statistic over a
         sampling period";
    }
  }

  grouping temp-alarm-data {
    description
      "Temperature alarm data of a component";
    leaf alarm-status {
      type boolean;
      description
        "Alarm status";
    }
    leaf alarm-threshold {
      type uint32;
      description
        "Threshold value above which system generates an alarm";
    }
    leaf severity {
      type platform-ios-xe-oper:temp-alarm-severity;
      description
        "Alarm Severity";
    }
  }

  grouping platform-memory-state {
    description
      "Memory statistics of a component";
    leaf mem-available {
      type uint64;
      units "bytes";
      description
        "Available memory for a component";
    }
    leaf mem-utilized {
      type uint64;
      units "bytes";
      description
        "Utilized memory of a component";
    }
  }

  grouping platform-property-value {
    description
      "Property values can take on a variety of types.
       Signed and unsigned integer types may be provided in smaller sizes,
       e.g., int8, uint16, etc.";
    leaf property-value {
      type platform-ios-xe-oper:platform-prop-value-type;
      config false;
      description
        "DO NOT USE!  -- hidden internal";
      tailf:hidden "full";
      tailf:meta-data "hidden" {
        tailf:meta-value "true";
      }
    }
    choice property-value-choice {
      description
        "Value choice";
      case property-string {
        leaf string {
          type string;
          description
            "String property value";
        }
      }
      case property-boolean {
        leaf boolean {
          type boolean;
          description
            "Boolean property value";
        }
      }
      case property-int64 {
        leaf intsixfour {
          type int64;
          description
            "Integer64 property value";
        }
      }
      case property-uint64 {
        leaf uintsixfour {
          type uint64;
          description
            "Unsigned integer64 property value";
        }
      }
      case property-decimal64 {
        leaf decimal {
          type decimal64 {
            fraction-digits 2;
          }
          description
            "Decimal64 property value";
        }
      }
    }
  }

  grouping platform-state {
    description
      "Operational state data for device components";
    leaf type {
      type platform-ios-xe-oper:platform-comp-type;
      description
        "Type of component as identified by the system";
    }
    leaf id {
      type string;
      description
        "Unique identifier assigned to the component
         by the system";
    }
    leaf description {
      type string;
      description
        "System-supplied description of the component";
    }
    leaf mfg-name {
      type string;
      description
        "System-supplied identifier for the manufacturer of the
         component.  This data is particularly useful when a
         component manufacturer is different than the overall
         device vendor";
    }
    leaf version {
      type string;
      description
        "System-defined version string for a hardware, firmware,
         or software component";
    }
    leaf serial-no {
      type string;
      description
        "System-assigned serial number of the component";
    }
    leaf part-no {
      type string;
      description
        "System-assigned part number for the component.  This should
         be present in particular if the component is also an FRU
         (field replaceable unit)";
    }
    container temp {
      description
        "Temperature in degrees Celsius of the component. Values include
         the instantaneous, average, minimum, and maximum statistics. If
         average/minimum/maximum statistics are not supported, the target is expected
         to just supply the instant value";
      uses platform-ios-xe-oper:platform-comp-temp;
    }
    leaf location {
      type string;
      description
        "Component's Locations";
    }
    leaf empty {
      type boolean;
      description
        "If true, the component is empty";
    }
    leaf mfg-date {
      type yang:date-and-time;
      description
        "Manufacturing date of the component";
    }
    leaf firmware-ver {
      type string;
      description
        "Firmware version";
    }
    leaf removable {
      type boolean;
      description
        "If true, the component is removable";
    }
    leaf status {
      type platform-ios-xe-oper:platform-comp-status;
      description
        "Operational status of a component";
    }
    container comp-alarm-data {
      description
        "Temperature alarm data of a component";
      uses platform-ios-xe-oper:temp-alarm-data;
    }
    leaf parent {
      type string;
      description
        "Parent of a component";
    }
    container comp-mem-data {
      description
        "Available and utilized memory of a component";
      uses platform-ios-xe-oper:platform-memory-state;
    }
    leaf alloc-pwr {
      type uint32;
      units "watts";
      description
        "Power allocated to a component";
    }
    leaf used-pwr {
      type uint32;
      units "watts";
      description
        "Power drawn by a component";
    }
    leaf status-desc {
      type platform-ios-xe-oper:status-description;
      description
        "Operational status description";
    }
  }

  grouping platform-component {
    description
      "Top-level grouping for components in the device inventory";
    leaf cname {
      type string;
      description
        "References component name";
    }
    container state {
      description
        "Operational state data for each component";
      uses platform-ios-xe-oper:platform-state;
    }
    container platform-properties {
      description
        "Platform component properties";
      list platform-property {
        key "name";
        description
          "List of platform component properties";
        uses platform-ios-xe-oper:platform-properties;
      }
    }
    container platform-subcomponents {
      description
        "Platform subcomponents";
      list platform-subcomponent {
        key "name";
        description
          "List of platform subcomponents";
        uses platform-ios-xe-oper:platform-subcomponents;
      }
    }
  }

  grouping platform-subcomponents {
    description
      "Platform subcomponents";
    leaf name {
      type string;
      description
        "Subcomponent name";
    }
  }

  grouping platform-properties {
    description
      "Top-level grouping";
    leaf name {
      type string;
      description
        "Property name";
    }
    container value {
      description
        "Property value";
      uses platform-ios-xe-oper:platform-property-value;
    }
    leaf configurable {
      type boolean;
      description
        "Indication of whether the property is user-configurable";
    }
  }

  container components {
    config false;
    description
      "Enclosing container for the components in the system";
    tailf:callpoint "ios-oper-db";
    tailf:meta-data "callpoint" {
      tailf:meta-value "ios-oper-db";
    }
    tailf:meta-data "greenprefix" {
      tailf:meta-value "/services;serviceName=ios_oper";
    }
    tailf:meta-data "emulated" {
      tailf:meta-value "false";
    }
    list component {
      key "cname";
      description
        "List of components, keyed by component name";
      uses platform-ios-xe-oper:platform-component;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWTI6p+cABAvfgBAAEAYFED//3+q//9+qUAOHnNSzLRQA0BCNE00nqYgAYNAQwjQYaGgAAA0AAAAAJQQKekzU0agBo0AAaAAYaGgAAA0AAAAAJFAmRomU09IQGgAAGjGp/RGnlyv6cTRx9ojh9/GHTq9ogcZHQhxTmslDYRCsLMdC7tGjw1ZzR8+fVtkKSouHweAASgHeFIaaHSmlZqGWFMTsEfj9nTLlvBkJHVLvcpzDn6wa7YAggDYQSTIIY2JNuCENoBgQUFZLtGeYBGwQUCycaVvuMKckMRTWsSYiT2POMFjWMIMKyURhskbMsCTRckpV9ixiMvSJduGvgMUEAqKiELRv09/ruUayozazkiNkevZmjAxwZoECswDaDzbgq1Ymk8GHVWMQHDMRnFtM0nAe2M6VUfakZZ2ND4USOH5S1CEmnOwrTOgqhUUr8JNFlojG6A2nwI7cQlEdtPaJ1swxVQyCx7WnjKQcUWM6RcXOgOswIVMvZIIt1WccVs9wGqcit9ktOCC6duid4VYdKiWcnSS6jRS9dYtj6HsYKssJk44owkjrZnFMxMrwnbKaF9YBmhW1hULJKeN8dDKmEkKyKOu7odK1QUGlMq1MsZJG6igKZXghqBCGGAxWSsdnTArs1bLnYIBF0eSbjWCGea6rRP3CZTG6LXjrzy7aVHQtU9kgaGEZ3dMu/52sznKgUSVIAG2i/K8FD9bgcULxJz0QYZ3CKIlFjqVWVkIlxMo6aogGTYZEqZ1LBOmkDojnNYRQdG5lWMVEXHCIFzJCvijRFEk8ls9CSz/0DZSwnGlqX3wN94Z6HYFhWOV+RnwjJieWgBnhyNcOEr8VUx4iJJKjnlEngkmwK8mSmw2EQGQhfGhDJXlmZUHHVWRrgLJUXRbK6xnRJGqBrbagTAfPLfrSVqUgTyANndC48dvZZQUGtGYlQM6KpSBRFtb9MUwkAw4vQsqyrMWCSZSVwO6cwNt4UG54gEiSFeAPK6NIzvObGgO6BwYccalBDSshFQcSMUlTHhUlqWpaoTAKFWMYysLFFh2PaJ1LYArjTQvdaoxm1bqxCDSy38GgPEBgx/DZpcyAiEBMZ/xdyRThQkDI6p+c";
      }
      tailf:meta-data "uncompressed_size" {
        tailf:meta-value "2137";
      }
    }
  }

  container schema-metadata-Cisco-IOS-XE-platform-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-platform-oper";
    }
    tailf:meta-data "organization" {
      tailf:meta-value "Cisco Systems, Inc.";
    }
    tailf:meta-data "semver" {
      tailf:meta-value "2019-11-01";
    }
  }
}
