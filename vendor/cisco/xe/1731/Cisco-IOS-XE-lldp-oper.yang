module Cisco-IOS-XE-lldp-oper {
  yang-version 1;
  namespace "http://cisco.com/ns/yang/Cisco-IOS-XE-lldp-oper";
  prefix lldp-ios-xe-oper;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of Link Layer Discovery Protocol state information.
     Copyright (c) 2016-2017, 2019-2020 by Cisco Systems, Inc.
     All rights reserved.";

  revision 2020-07-01 {
    description
      "-Added Time to live leaf for the neighbor entry
       -Added new mgmt-type enum value mgmt-not-advertised indicating that a
        management address is not advertised
       -Added system cookie leaf for the neighbor entry";
    reference "0.0.0";
    cisco-semver:module-version "0.0.0";
    cisco-semver-internal:os-version "17.3.1";
  }
  revision 2020-03-01 {
    description
      "Added transmission and reception state details, neighboring device 
       physical media capabilities and failure counters";
    reference "1.4.0";
    cisco-semver:module-version "1.4.0";
    cisco-semver-internal:os-version "17.2.1";
  }
  revision 2019-05-01 {
    description
      "Added semantic version";
    reference "1.3.0";
    cisco-semver:module-version "1.3.0";
  }
  revision 2018-11-05 {
    description
      "- Adding port VLAN ID, power details,
         media attachment unit, and auto negotiation details.
       - Cleaned up spelling errors in descriptions.";
    reference "1.2.0";
    cisco-semver:module-version "1.2.0";
  }
  revision 2018-06-27 {
    description
      "Entries to support open config LLDP are added";
    reference "1.1.0";
    cisco-semver:module-version "1.1.0";
  }
  revision 2017-02-07 {
    description
      "Initial revision";
    reference "1.0.0";
    cisco-semver:module-version "1.0.0";
  }

  typedef lldp-pwr-pair-type {
    type enumeration {
      enum "power-pair-signal" {
        value 1;
        description
          "LLDP power pair is Signal";
        tailf:code-name "ENUM_lldp_pwr_pair_type_PWR_PR_SIGNAL";
      }
      enum "power-pair-spare" {
        value 2;
        description
          "LLDP power pair is Spare";
        tailf:code-name "ENUM_lldp_pwr_pair_type_PWR_PR_SPARE";
      }
    }
    description
      "LLDP Power pair type";
  }

  typedef lldp-pwr-class-type {
    type enumeration {
      enum "power-class-0" {
        value 1;
        description
          "LLDP power class 0";
        tailf:code-name "ENUM_lldp_pwr_class_type_PWR_CLASS_0";
      }
      enum "power-class-1" {
        value 2;
        description
          "LLDP power class 1";
        tailf:code-name "ENUM_lldp_pwr_class_type_PWR_CLASS_1";
      }
      enum "power-class-2" {
        value 3;
        description
          "LLDP power class 2";
        tailf:code-name "ENUM_lldp_pwr_class_type_PWR_CLASS_2";
      }
      enum "power-class-3" {
        value 4;
        description
          "LLDP power class 3";
        tailf:code-name "ENUM_lldp_pwr_class_type_PWR_CLASS_3";
      }
      enum "power-class-4" {
        value 5;
        description
          "LLDP power class 4";
        tailf:code-name "ENUM_lldp_pwr_class_type_PWR_CLASS_4";
      }
    }
    description
      "LLDP Power class type";
  }

  typedef lldp-pwr-device-type {
    type enumeration {
      enum "power-device-type-2-pse" {
        value 1;
        description
          "LLDP power device type is TYPE 2 PSE";
        tailf:code-name "ENUM_lldp_pwr_device_type_PWR_DEV_TYPE_2_PSE";
      }
      enum "power-device-type-2-pd" {
        value 2;
        description
          "LLDP power device type is TYPE 2 PD";
        tailf:code-name "ENUM_lldp_pwr_device_type_PWR_DEV_TYPE_2_PD";
      }
      enum "power-device-type-1-pse" {
        value 3;
        description
          "LLDP power device type is TYPE 1 PSE";
        tailf:code-name "ENUM_lldp_pwr_device_type_PWR_DEV_TYPE_1_PSE";
      }
      enum "power-device-type-1-pd" {
        value 4;
        description
          "LLDP power device type is TYPE 1 PD";
        tailf:code-name "ENUM_lldp_pwr_device_type_PWR_DEV_TYPE_1_PD";
      }
    }
    description
      "LLDP Power device type";
  }

  typedef lldp-pwr-source-type {
    type enumeration {
      enum "power-source-pse-and-local" {
        value 1;
        description
          "LLDP power source as PSE and Local";
        tailf:code-name "ENUM_lldp_pwr_source_type_PWR_SRC_PSE_AND_LOCAL";
      }
      enum "power-source-reserved" {
        value 2;
        description
          "LLDP power source as Reserved";
        tailf:code-name "ENUM_lldp_pwr_source_type_PWR_SRC_RESERVED";
      }
      enum "power-source-pse" {
        value 3;
        description
          "LLDP power source as PSE";
        tailf:code-name "ENUM_lldp_pwr_source_type_PWR_SRC_PSE";
      }
      enum "power-source-unknown" {
        value 4;
        description
          "LLDP power source as Unknown";
        tailf:code-name "ENUM_lldp_pwr_source_type_PWR_SRC_UNKNOWN";
      }
    }
    description
      "LLDP Power source";
  }

  typedef lldp-pwr-priority-type {
    type enumeration {
      enum "power-priority-unknown" {
        value 1;
        description
          "LLDP power priority as Unknown";
        tailf:code-name "ENUM_lldp_pwr_priority_type_PWR_PRI_UNKNOWN";
      }
      enum "power-priority-critical" {
        value 2;
        description
          "LLDP power source as Critical";
        tailf:code-name "ENUM_lldp_pwr_priority_type_PWR_PRI_CRITICAL";
      }
      enum "power-prioirty-high" {
        value 3;
        description
          "LLDP power source as High";
        tailf:code-name "ENUM_lldp_pwr_priority_type_PWR_PRI_HIGH";
      }
      enum "power-priority-low" {
        value 4;
        description
          "LLDP power source as Low";
        tailf:code-name "ENUM_lldp_pwr_priority_type_PWR_PRI_LOW";
      }
    }
    description
      "LLDP Power priority";
  }

  typedef chid-subtype {
    type enumeration {
      enum "chassis-entphyalias" {
        value 1;
        description
          "chassis id sub type holds the value of entity  
           MIB physical alias";
        tailf:code-name "ENUM_chid_subtype_CH_ENTPHYALIAS";
      }
      enum "chassis-ifalias" {
        value 2;
        description
          "chassis id subtype with value Interface alias";
        tailf:code-name "ENUM_chid_subtype_CH_IFALIAS";
      }
      enum "chassis-portentphyalias" {
        value 3;
        description
          "chassis id subtype with port component";
        tailf:code-name "ENUM_chid_subtype_CH_PORTENTPHYALIAS";
      }
      enum "chassis-mac" {
        value 4;
        description
          "chassis id sub type with MAC address";
        tailf:code-name "ENUM_chid_subtype_CH_MAC";
      }
      enum "chassis-net" {
        value 5;
        description
          "chassis id sub type with Network address";
        tailf:code-name "ENUM_chid_subtype_CH_NET";
      }
      enum "chassis-ifname" {
        value 6;
        description
          "chassis id sub type with interface name";
        tailf:code-name "ENUM_chid_subtype_CH_IFNAME";
      }
      enum "chassis-local" {
        value 7;
        description
          "chassis id subtype with locally assigned 
           identifier";
        tailf:code-name "ENUM_chid_subtype_CH_LOCAL";
      }
    }
    description
      "Chassis id sub-type";
  }

  typedef poid-type {
    type enumeration {
      enum "port-ifalias" {
        value 1;
        description
          "port id subtype with interface alias";
        tailf:code-name "ENUM_poid_type_PO_IFALIAS";
      }
      enum "port-portphyalias" {
        value 2;
        description
          "port id subtype with port component";
        tailf:code-name "ENUM_poid_type_PO_PORTPHYALIAS";
      }
      enum "port-mac" {
        value 3;
        description
          "Port id subtype with MAC address";
        tailf:code-name "ENUM_poid_type_PO_MAC";
      }
      enum "port-net" {
        value 4;
        description
          "Port id subtype with network address";
        tailf:code-name "ENUM_poid_type_PO_NET";
      }
      enum "port-ifname" {
        value 5;
        description
          "Port id sub type with interface name";
        tailf:code-name "ENUM_poid_type_PO_IFNAME";
      }
      enum "port-ckt" {
        value 6;
        description
          "Port id sub type with circuit";
        tailf:code-name "ENUM_poid_type_PO_CKT";
      }
      enum "port-local" {
        value 7;
        description
          "Port id sub type with local";
        tailf:code-name "ENUM_poid_type_PO_LOCAL";
      }
    }
    description
      "port id subtype";
  }

  typedef mgmt-type {
    type enumeration {
      enum "mgmt-ip" {
        value 1;
        description
          "specifies if the type of management address is 
           IPv4";
        tailf:code-name "ENUM_mgmt_type_MGMT_IP";
      }
      enum "mgmt-ipv6" {
        value 2;
        description
          "Specifies ipv6 address";
        tailf:code-name "ENUM_mgmt_type_MGMT_IPV6";
      }
      enum "mgmt-decnet" {
        value 3;
        description
          "Specifies decnet phase four address";
        tailf:code-name "ENUM_mgmt_type_MGMT_DECNET";
      }
      enum "mgmt-ipx" {
        value 4;
        description
          "Specifies ipx address";
        tailf:code-name "ENUM_mgmt_type_MGMT_IPX";
      }
      enum "mgmt-bv" {
        value 5;
        description
          "Specifies banyan vine address type";
        tailf:code-name "ENUM_mgmt_type_MGMT_BV";
      }
      enum "mgmt-at" {
        value 6;
        description
          "Specifies apple talk address type";
        tailf:code-name "ENUM_mgmt_type_MGMT_AT";
      }
      enum "mgmt-not-advertised" {
        value 7;
        description
          "Indicates that the management address field is 
           not advertised";
        tailf:code-name "ENUM_mgmt_type_MGMT_NOT_ADVT";
      }
    }
    description
      "Types of management address";
  }

  typedef rx-state {
    type enumeration {
      enum "wait-port-oper" {
        value 0;
        description
          "Transmission waits for port operation to come up";
        tailf:code-name "ENUM_rx_state_LLDP_WAIT_PORT_OPER";
      }
      enum "tx-init" {
        value 1;
        description
          "Reception is initialized";
        tailf:code-name "ENUM_rx_state_LLDP_RX_INIT";
      }
      enum "wait-for-frame" {
        value 2;
        description
          "Transmission waits for frame";
        tailf:code-name "ENUM_rx_state_LLDP_WAIT_FOR_FRAME";
      }
      enum "rx-frame" {
        value 3;
        description
          "Transmission waits for receive frame";
        tailf:code-name "ENUM_rx_state_LLDP_RX_FRAME";
      }
      enum "update-info" {
        value 4;
        description
          "Updates peer LLDP information for port";
        tailf:code-name "ENUM_rx_state_LLDP_UPDATE_INFO";
      }
      enum "delete-info" {
        value 5;
        description
          "Deletes Peer lldp info on TTL timeout when Port 
           is active";
        tailf:code-name "ENUM_rx_state_LLDP_DELETE_INFO";
      }
      enum "delete-aged-info" {
        value 6;
        description
          "Deletes Peer lldp info on TTL timeout when Port is 
           NOT enabled";
        tailf:code-name "ENUM_rx_state_LLDP_DELETE_AGED_INFO";
      }
    }
    description
      "Reception states available in LLDP";
  }

  typedef tx-state {
    type enumeration {
      enum "rx-init" {
        value 0;
        description
          "LLDP Transmission is initialized";
        tailf:code-name "ENUM_tx_state_LLDP_TX_INIT";
      }
      enum "idle" {
        value 1;
        description
          "Reception is in IDLE state";
        tailf:code-name "ENUM_tx_state_LLDP_IDLE";
      }
      enum "info-frame" {
        value 2;
        description
          "Information frame is received";
        tailf:code-name "ENUM_tx_state_LLDP_INFO_FRAME";
      }
      enum "shutdown-frame" {
        value 3;
        description
          "Shutdown frame is received";
        tailf:code-name "ENUM_tx_state_LLDP_SHUTDOWN_FRAME";
      }
    }
    description
      "Transmission states available in LLDP";
  }

  typedef phy-media-cap {
    type enumeration {
      enum "unknown" {
        value 0;
        description
          "Advertised value is not known";
        tailf:code-name "ENUM_phy_media_cap_LLDP_UNKNOWN";
      }
      enum "10baset" {
        value 1;
        description
          "10 Base-T half duplex mode is advertised";
        tailf:code-name "ENUM_phy_media_cap_LLDP_10BASE_T";
      }
      enum "10baset-fd" {
        value 2;
        description
          "10 Base-T full duplex mode is advertised";
        tailf:code-name "ENUM_phy_media_cap_LLDP_10BASE_TFD";
      }
      enum "100baset4" {
        value 3;
        description
          "10 Base-T4 mode is advertised";
        tailf:code-name "ENUM_phy_media_cap_LLDP_100BASE_T4";
      }
      enum "100basetx" {
        value 4;
        description
          "100 Base-TX half duplex mode is advertised";
        tailf:code-name "ENUM_phy_media_cap_LLDP_100BASE_TX";
      }
      enum "100basetx-fd" {
        value 5;
        description
          "100 Base-TX full duplex mode is advertised";
        tailf:code-name "ENUM_phy_media_cap_LLDP_100BASE_TXFD";
      }
      enum "100baset2" {
        value 6;
        description
          "100 Base-T2 half duplex mode is advertised";
        tailf:code-name "ENUM_phy_media_cap_LLDP_100BASE_T2";
      }
      enum "100baset2-fd" {
        value 7;
        description
          "100 Base-T2 full duplex mode is advertised";
        tailf:code-name "ENUM_phy_media_cap_LLDP_100BASE_T2FD";
      }
      enum "pause-fd" {
        value 8;
        description
          "Pause for full duplex mode is advertised";
        tailf:code-name "ENUM_phy_media_cap_LLDP_FDX_PAUSE";
      }
      enum "asym-pause-fd" {
        value 9;
        description
          "Asymmetric pause for full duplex mode is advertised";
        tailf:code-name "ENUM_phy_media_cap_LLDP_FDX_APAUSE";
      }
      enum "sym-pause-fd" {
        value 10;
        description
          "Symmetric pause for full duplex mode is advertised";
        tailf:code-name "ENUM_phy_media_cap_LLDP_FDX_SPAUSE";
      }
      enum "symm-asym-pause-fd" {
        value 11;
        description
          "Symmetric pause for full duplex mode is advertised";
        tailf:code-name "ENUM_phy_media_cap_LLDP_FDX_BPAUSE";
      }
      enum "1000basex-hd" {
        value 12;
        description
          "1000 BASE-X, -LX, -SX, -CX half duplex mode is 
           advertised";
        tailf:code-name "ENUM_phy_media_cap_LLDP_1000BASE_X";
      }
      enum "1000basex-fd" {
        value 13;
        description
          "1000 BASE-X, -LX, -SX, -CX full duplex mode is 
           advertised";
        tailf:code-name "ENUM_phy_media_cap_LLDP_1000BASE_XFD";
      }
      enum "1000base-t-hd" {
        value 14;
        description
          "1000 Base-T half duplex mode is advertised";
        tailf:code-name "ENUM_phy_media_cap_LLDP_1000BASE_T";
      }
      enum "1000baset-fd" {
        value 15;
        description
          "1000 Base-T full duplex mode is advertised";
        tailf:code-name "ENUM_phy_media_cap_LLDP_1000BASE_TFD";
      }
    }
    description
      "Physical media capabilities is advertised";
  }

  grouping lldp-capabilities {
    description
      "LLDP device type";
    leaf repeater {
      type empty;
      description
        "Repeater";
    }
    leaf bridge {
      type empty;
      description
        "Bridge";
    }
    leaf access-point {
      type empty;
      description
        "Access point";
    }
    leaf router {
      type empty;
      description
        "Router";
    }
    leaf telephone {
      type empty;
      description
        "Phone";
    }
    leaf docsis {
      type empty;
      description
        "Docsis";
    }
    leaf station {
      type empty;
      description
        "Station";
    }
    leaf other {
      type empty;
      description
        "Other";
    }
  }

  grouping lldp-auto-negotiation {
    description
      "LLDP Auto Negotiation";
    leaf enabled {
      type empty;
      description
        "Auto Negotiation is enabled";
    }
    leaf supported {
      type empty;
      description
        "Auto Negotiation is supported";
    }
  }

  grouping lldp-pwr-via-mdi {
    description
      "Holds details for LLDP Power-via-MDI";
    leaf power-pair {
      type lldp-ios-xe-oper:lldp-pwr-pair-type;
      description
        "Power pair details";
    }
    leaf power-class {
      type lldp-ios-xe-oper:lldp-pwr-class-type;
      description
        "Power class details";
    }
    leaf power-device-type {
      type lldp-ios-xe-oper:lldp-pwr-device-type;
      description
        "Power device type details";
    }
    leaf power-source {
      type lldp-ios-xe-oper:lldp-pwr-source-type;
      description
        "Power source details";
    }
    leaf power-priority {
      type lldp-ios-xe-oper:lldp-pwr-priority-type;
      description
        "Power priority details";
    }
    leaf power-requested {
      type uint32;
      units "milliWatts";
      description
        "Power requested by peer device";
    }
    leaf power-allocated {
      type uint32;
      units "milliWatts";
      description
        "Power allocated to peer device";
    }
  }

  grouping lldp-pwrt {
    description
      "LLDP Power type";
    leaf is-drawing-power {
      type empty;
      description
        "Power is drawn from the device";
    }
    container power-details {
      when "boolean(../is-drawing-power)";
      description
        "LLDP Power-via-MDI details";
      uses lldp-ios-xe-oper:lldp-pwr-via-mdi;
    }
  }

  grouping lldp-entry-key {
    description
      "Unique LLDP entry identifier";
    leaf device-id {
      type string;
      description
        "Device ID of the link";
    }
    leaf local-interface {
      type string;
      description
        "Name of the local interface on the current device";
    }
    leaf connecting-interface {
      type string;
      description
        "Name of the connected interface to 'local-interface'";
    }
  }

  grouping lldp-entry {
    description
      "LLDP entry details";
    leaf ttl {
      type uint32;
      description
        "TTL denoting hold-time of this link entry";
    }
    container capabilities {
      description
        "LLD device capabilities";
      uses lldp-ios-xe-oper:lldp-capabilities;
    }
    leaf port-vlan-id {
      type uint32;
      description
        "LLDP port VLAN ID";
    }
    leaf mau-type {
      type uint32;
      description
        "Media attachment unit type for LLDP";
    }
    container auto-neg {
      description
        "LLDP auto negotiation details";
      uses lldp-ios-xe-oper:lldp-auto-negotiation;
    }
    container power {
      description
        "LLDP Power-via-MDI details";
      uses lldp-ios-xe-oper:lldp-pwrt;
    }
  }

  grouping lldp-state-entry {
    description
      "LLDP state entry details";
    leaf enabled {
      type boolean;
      description
        "Provides the state of LLDP";
    }
    leaf hello-timer {
      type uint64;
      description
        "Denotes the time between advertisement packets";
    }
    leaf system-name {
      type string;
      description
        "Provides the name of the system";
    }
    leaf system-desc {
      type string;
      description
        "Provides system related information";
    }
    leaf chassis-id {
      type string;
      description
        "Provides information about the chassis";
    }
    leaf chassis-id-type {
      type lldp-ios-xe-oper:chid-subtype;
      description
        "Provides information about the subtype of 
         chassis ID";
    }
    leaf frame-in {
      type uint64;
      description
        "Denotes the number of input frames";
    }
    leaf frame-out {
      type uint64;
      description
        "Denotes the number of output frames";
    }
    leaf frame-error-in {
      type uint64;
      description
        "Denotes the number of input frames containing errors";
    }
    leaf frame-discard {
      type uint64;
      description
        "Denotes the number of discarded frames";
    }
    leaf tlv-discard {
      type uint64;
      description
        "Denotes the number of discarded TLVs";
    }
    leaf tlv-unknown {
      type uint64;
      description
        "Denotes the number of unknown TLVs";
    }
    leaf entries-aged-out {
      type uint64;
      description
        "Number of aged out entries";
    }
    leaf mem-failures {
      type uint64;
      description
        "Number of memory allocation failures";
    }
    leaf encap-failures {
      type uint64;
      description
        "Number of encapsulation failures";
    }
    leaf inqueue-overflow {
      type uint64;
      description
        "Number of queue overflow failures";
    }
    leaf table-overflow {
      type uint64;
      description
        "Number of table failures";
    }
  }

  grouping lldp-intf-entry {
    description
      "LLDP entry details for interface";
    leaf if-name {
      type string;
      description
        "Denotes the interface name";
    }
    leaf isenabled {
      type boolean;
      description
        "provides state of LLDP on the interface";
    }
    list lldp-neighbor-details {
      key "identifier";
      description
        "Holds neighbor information";
      uses lldp-ios-xe-oper:lldp-neighbor-entry;
    }
    leaf tx {
      type lldp-ios-xe-oper:tx-state;
      description
        "LLDP transmission state on the interface";
    }
    leaf rx {
      type lldp-ios-xe-oper:rx-state;
      description
        "LLDP reception state on the interface";
    }
  }

  grouping lldp-mgmt {
    description
      "Holds lldp's management address";
    leaf mgmt-addr {
      type string;
      description
        "Denotes the management ip address";
    }
    leaf mgmt-addr-type {
      type lldp-ios-xe-oper:mgmt-type;
      description
        "Denotes the type of management ip address";
    }
  }

  grouping lldp-neighbor-entry {
    description
      "Holds LLDP device neighbor entry";
    leaf identifier {
      type string;
      description
        "Provides information about the system generated id";
    }
    leaf chassis-id {
      type string;
      description
        "Provides information about the chassis";
    }
    leaf chassis-id-type {
      type lldp-ios-xe-oper:chid-subtype;
      description
        "Provides information about the subtype of 
         chassis ID";
    }
    leaf port-id {
      type string;
      description
        "Provides information about the port id";
    }
    leaf port-id-type {
      type lldp-ios-xe-oper:poid-type;
      description
        "Provides information about the port id's type";
    }
    leaf port-desc {
      type string;
      description
        "Provides information about the port's description";
    }
    leaf system-name {
      type string;
      description
        "Provides the name of the system";
    }
    leaf system-desc {
      type string;
      description
        "Provides system related information";
    }
    leaf time-remaining {
      type uint32;
      units "seconds";
      description
        "Specifies the timing of next advertisement";
    }
    leaf age {
      type uint32;
      units "seconds";
      description
        "Denotes the age of the current state";
    }
    leaf time-since-last-update {
      type uint32;
      units "seconds";
      description
        "Denotes the time since last update";
    }
    list mgmt-addrs {
      description
        "Denotes the management ip address";
      uses lldp-ios-xe-oper:lldp-mgmt;
    }
    container system-capabilities {
      description
        "Provides LLDP device system capabilities";
      uses lldp-ios-xe-oper:lldp-capabilities;
    }
    container enabled-capabilities {
      description
        "Provides LLDP device enabled capabilities";
      uses lldp-ios-xe-oper:lldp-capabilities;
    }
    leaf media-caps {
      type lldp-ios-xe-oper:phy-media-cap;
      description
        "Physical media capabilities of peer device";
    }
    leaf ttl {
      type uint32;
      units "seconds";
      description
        "The time-to-live (TTL) is a mandatory TLV which 
         indicates how long information from the neighbor should be 
         considered valid";
    }
    list orgtlv-detail {
      key "platform-id";
      description
        "Holds LLDP org specific TLV information";
      uses lldp-ios-xe-oper:lldp-orgtlv-entry;
    }
  }

  grouping lldp-orgtlv-entry {
    description
      "Holds LLDP org specific TLV entry";
    leaf platform-id {
      type string;
      description
        "Provides information about the platform identifier";
    }
    leaf system-cookie {
      type string;
      description
        "Provides system cookie - the info string for
         an LLDP org specific TLV (Type=127, Subtype=1)";
    }
  }

  container lldp-entries {
    config false;
    description
      "Data nodes for LLDP entries";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list lldp-entry {
      key "device-id local-interface connecting-interface";
      description
        "The list of LLDP entries";
      uses lldp-ios-xe-oper:lldp-entry-key;
      uses lldp-ios-xe-oper:lldp-entry;
    }
    container lldp-state-details {
      presence "lldp-state-details";
      description
        "The list of LLDP state entries";
      uses lldp-ios-xe-oper:lldp-state-entry;
    }
    list lldp-intf-details {
      key "if-name";
      description
        "The list of LLDP interface entries";
      uses lldp-ios-xe-oper:lldp-intf-entry;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWXJUeqQABQ7fgDAAEAZ9ED/v3+q/79/qUARJknulOpsUDXDFJlT8Rqn6ajU8oDQDQGJoNPSGgNNBCZFTPTUM0pozTQT1PUzSAyNMCTUlIDQAAA0PUD0gAAyHMAAAAAAAAAACKImQmEJiBQeoAMjTTCBofwxGj20bW6gJqm5jliEBE1JYtq+m/i++GMWyhObW34U041qTXy/+TODGg60QfboHjgt7K507Mu8L9Ns33icg/A9/Pe0Gi1q7558eeONSancvj4O0NyB8ChUNyPw9EH72DhxGRbSm1WMt5GclBJKplJRCmkQqIVIiQBoSpOfNxZSsZADuL0ownUKJcnSnM40KlyDjX0aCBTergxv2FZgGzYydq1YndQQLI6ZpJZTZoRVRUoME24RIwA72Rgk1QUPhrmAXMUQYMUFgqyWsiGyDBgiJo25bWsWscVqwVgt3350kgaYkD3MwuO06U+fVWn3RDY/X4J71PUlfVgHVSh7z1mMcVqPpHAKBsREOTiX3yJBreA+ee7eTEhJMCC1mmGxgnv2wjY8C4YBa0EKZ7lJ9InMKmTMQHGmyxrXLN7LqmeCey0j5sBocdSAlyokJko8eZVOihgCwFhMyeMq8NdFZAcSzE1iMDIuuNUAJuRm7CBw5a4z5Sa+PmHZq9ywJlKhGijx1DgGl+ewaN6nJCkDUgLJR2KsFpqpYCExS1BDnXkuAhLuVxNxGQhkS7UkEB1cCQGrl+EtFgK0IDBQnpPg0KWLzEmTQPYnrS3cZKcCYILKPipN9kHE0wwFlAaJYynKcicLg9Bvqk5zozEuJbfnERYJEZpZHFCBegDagLSYB+I9vPox4QYO4aRnLRsHedKXlqSTPEBQjD9I3EiRG0nI8T1wAy6ST5Yt5MV6GkbshFFwH9vaE490QBXQjGOdLYmErG/EHXnMJoaxkFpiAg6MwnOfb/uz1wdsYTJ271CSuWeGmdIITJ2JJCC7YzQhsEpvUBaSqOtoSi8xmZEWTAictsA5C6410LTCxgwTkEOB1uvmHDkYFwl5UT0jXhVOQPWpgm7+MEbs4yHVonbyamFxwWvevgEce8tiG8cF+DP/NA3Au6F2Y6c22O8Pm3q+InbfwDKqhV7WhTlGZeDaHl0DxTi0wHCIIUIAyOYUIS0BDA0gIg3CwcL46hzycekoTGc8C4ZJxK3nZLqZhoF6XkTLS6wlAYgoVMCk9Iql/MMi4nRw6FCWLhLqrUl8gJFYUKUECsORcFGCM0xDyjrtj1zC+JCpztWbTMpAZOwSG9/MAyQxmFjBMqoz/F3JFOFCQclR6pA==";
      }
      tailf:meta-data "uncompressed_size" {
        tailf:meta-value "2634";
      }
    }
  }

  container schema-metadata-Cisco-IOS-XE-lldp-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-lldp-oper";
    }
    tailf:meta-data "organization" {
      tailf:meta-value "Cisco Systems, Inc.";
    }
    tailf:meta-data "semver" {
      tailf:meta-value "2020-07-01";
    }
  }
}
