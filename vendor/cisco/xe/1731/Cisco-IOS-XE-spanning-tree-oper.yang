module Cisco-IOS-XE-spanning-tree-oper {
  yang-version 1;
  namespace "http://cisco.com/ns/yang/Cisco-IOS-XE-spanning-tree-oper";
  prefix stp-ios-xe-oper;
  import ietf-yang-types {
    prefix yang;
  }
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring vlans in a Network Element.
     Copyright (c) 2016-2017, 2019 by Cisco Systems, Inc.
     All rights reserved.";

  revision 2019-05-01 {
    description
      "Added semantic version";
    reference "1.1.0";
    cisco-semver:module-version "1.1.0";
  }
  revision 2017-08-10 {
    description
      "Initial revision";
    reference "1.0.0";
    cisco-semver:module-version "1.0.0";
  }

  typedef stp-port-state {
    type enumeration {
      enum "stp-disabled" {
        value 0;
        tailf:code-name "ENUM_stp_mgmt_port_state_STP_PORT_STATE_DISABLED";
      }
      enum "stp-blocking" {
        value 1;
        tailf:code-name "ENUM_stp_mgmt_port_state_STP_PORT_STATE_BLOCKING";
      }
      enum "stp-listening" {
        value 2;
        tailf:code-name "ENUM_stp_mgmt_port_state_STP_PORT_STATE_LISTENING";
      }
      enum "stp-learning" {
        value 3;
        tailf:code-name "ENUM_stp_mgmt_port_state_STP_PORT_STATE_LEARNING";
      }
      enum "stp-forwarding" {
        value 4;
        tailf:code-name "ENUM_stp_mgmt_port_state_STP_PORT_STATE_FORWARDING";
      }
      enum "stp-broken" {
        value 5;
        tailf:code-name "ENUM_stp_mgmt_port_state_STP_PORT_STATE_BROKEN";
      }
      enum "stp-invalid" {
        value 6;
        tailf:code-name "ENUM_stp_mgmt_port_state_STP_PORT_STATE_INVALID";
      }
    }
    description
      "Spanning Tree Protocol port states";
  }

  typedef stp-port-role {
    type enumeration {
      enum "stp-master" {
        value 0;
        tailf:code-name "ENUM_stp_mgmt_port_role_STP_PORT_ROLE_MASTER";
      }
      enum "stp-alternate" {
        value 1;
        tailf:code-name "ENUM_stp_mgmt_port_role_STP_PORT_ROLE_ALTERNATE";
      }
      enum "stp-root" {
        value 2;
        tailf:code-name "ENUM_stp_mgmt_port_role_STP_PORT_ROLE_ROOT";
      }
      enum "stp-designated" {
        value 3;
        tailf:code-name "ENUM_stp_mgmt_port_role_STP_PORT_ROLE_DESIGNATED";
      }
      enum "stp-backup" {
        value 4;
        tailf:code-name "ENUM_stp_mgmt_port_role_STP_PORT_ROLE_BACKUP";
      }
    }
    description
      "Spanning Tree Protocol port roles";
  }

  typedef stp-link-role {
    type enumeration {
      enum "stp-auto" {
        value 0;
        tailf:code-name "ENUM_stp_mgmt_link_type_STP_PORT_LINK_AUTO";
      }
      enum "stp-point-to-point" {
        value 1;
        tailf:code-name "ENUM_stp_mgmt_link_type_STP_PORT_LINK_POINT_TO_POINT";
      }
      enum "stp-shared" {
        value 2;
        tailf:code-name "ENUM_stp_mgmt_link_type_STP_PORT_LINK_SHARED";
      }
    }
    description
      "Type definition for the different link types";
  }

  typedef stp-port-guard {
    type enumeration {
      enum "stp-port-guard-default" {
        value 0;
        tailf:code-name "ENUM_stp_mgmt_port_guard_STP_MGMT_PORT_GUARD_DEFAULT";
      }
      enum "stp-port-guard-root" {
        value 1;
        tailf:code-name "ENUM_stp_mgmt_port_guard_STP_MGMT_PORT_GUARD_ROOT";
      }
      enum "stp-port-guard-loop" {
        value 2;
        tailf:code-name "ENUM_stp_mgmt_port_guard_STP_MGMT_PORT_GUARD_LOOP";
      }
      enum "stp-port-guard-none" {
        value 3;
        tailf:code-name "ENUM_stp_mgmt_port_guard_STP_MGMT_PORT_GUARD_NONE";
      }
    }
    description
      "Interface's spanning tree guard mode";
  }

  typedef stp-port-bpduguard {
    type enumeration {
      enum "stp-port-bpduguard-disable" {
        value 0;
        tailf:code-name "ENUM_stp_mgmt_port_bpduguard_STP_PORT_BPDUGUARD_DISABLE";
      }
      enum "stp-port-bpduguard-enable" {
        value 1;
        tailf:code-name "ENUM_stp_mgmt_port_bpduguard_STP_PORT_BPDUGUARD_ENABLE";
      }
      enum "stp-port-bpduguard-default" {
        value 2;
        tailf:code-name "ENUM_stp_mgmt_port_bpduguard_STP_PORT_BPDUGUARD_DEFAULT";
      }
    }
    description
      "Accept BPDUs on this interface";
  }

  typedef stp-port-bpdufilter {
    type enumeration {
      enum "stp-port-bpdufilter-disable" {
        value 0;
        tailf:code-name "ENUM_stp_mgmt_port_bpdufilter_STP_PORT_BPDUFILTER_DISABLE";
      }
      enum "stp-port-bpdufilter-enable" {
        value 1;
        tailf:code-name "ENUM_stp_mgmt_port_bpdufilter_STP_PORT_BPDUFILTER_ENABLE";
      }
      enum "stp-port-bpdufilter-default" {
        value 2;
        tailf:code-name "ENUM_stp_mgmt_port_bpdufilter_STP_PORT_BPDUFILTER_DEFAULT";
      }
    }
    description
      "Send or receive BPDUs on this interface";
  }

  typedef stp-mode {
    type enumeration {
      enum "stp-mode-pvst" {
        value 0;
        tailf:code-name "ENUM_stp_mgmt_mode_STP_GLOBAL_MODE_PVST";
      }
      enum "stp-mode-rapid-pvst" {
        value 1;
        tailf:code-name "ENUM_stp_mgmt_mode_STP_GLOBAL_MODE_RAPID_PVST";
      }
      enum "stp-mode-mst" {
        value 2;
        tailf:code-name "ENUM_stp_mgmt_mode_STP_GLOBAL_MODE_MST";
      }
    }
    description
      "Spanning tree operating mode";
  }

  grouping interfaces {
    description
      "List of interfaces on which STP is enable";
    leaf name {
      type string;
      description
        "Reference to the STP ethernet interface";
    }
    leaf cost {
      type uint64;
      description
        "The port's contribution, when it is the Root Port, to the Root Path Cost for the Bridge";
    }
    leaf port-priority {
      type uint16;
      description
        "The manageable component of the Port Identifier, also known as the Port Priority";
    }
    leaf port-num {
      type uint16;
      description
        "The port number of the bridge port";
    }
    leaf role {
      type stp-ios-xe-oper:stp-port-role;
      description
        "The current role of the bridge port";
    }
    leaf state {
      type stp-ios-xe-oper:stp-port-state;
      description
        "The current state of the bridge port";
    }
    leaf designated-root-priority {
      type uint32;
      description
        "The bridge priority of the bridge recorded as the root in the configuration BPDUs transmitted by the designated bridge for the segment to which the port is attached";
    }
    leaf designated-root-address {
      type yang:mac-address;
      description
        "The bridge address of the bridge recorded as the root in the configuration BPDUs transmitted by the designated bridge for the segment to which the port is attached";
    }
    leaf designated-cost {
      type uint32;
      description
        "The path cost of the Designated Port of the segment connected to this port";
    }
    leaf designated-bridge-priority {
      type uint32;
      description
        "The bridge priority of the bridge that this port considers to be the designated bridge for this port's segment";
    }
    leaf designated-bridge-address {
      type yang:mac-address;
      description
        "The bridge address of the bridge that this port considers to be the designated bridge for this port's segment";
    }
    leaf designated-port-priority {
      type uint16;
      description
        "The Port priority of the port on the Designated Bridge for this port's segment, two octet string";
    }
    leaf designated-port-num {
      type uint16;
      description
        "The Port number of the port on the Designated Bridge for this port's segment, two octet string";
    }
    leaf forward-transitions {
      type uint64;
      description
        "The number of times this port has transitioned from the Learning state to the Forwarding state";
    }
    leaf link-type {
      type stp-ios-xe-oper:stp-link-role;
      description
        "Interface's link type";
    }
    leaf guard {
      type stp-ios-xe-oper:stp-port-guard;
      description
        "Interface's spanning tree guard mode";
    }
    leaf bpdu-guard {
      type stp-ios-xe-oper:stp-port-bpduguard;
      description
        "BPDU guard on this interface";
    }
    leaf bpdu-filter {
      type stp-ios-xe-oper:stp-port-bpdufilter;
      description
        "BPDU filter on this interface";
    }
    leaf bpdu-sent {
      type uint64;
      description
        "The number of BPDU packet sent";
    }
    leaf bpdu-received {
      type uint64;
      description
        "The number of BPDU packet received";
    }
  }

  grouping stp-oper-crimson {
    description
      "Attributes of spanning-tree";
    leaf instance {
      type string;
      description
        "Spanning-tree enabled mode and id";
    }
    leaf hello-time {
      type int32;
      description
        "The interval between periodic transmissions of configuration messages by designated ports";
    }
    leaf max-age {
      type int32;
      description
        "The maximum age of the information transmitted by the bridge when it is the root bridge";
    }
    leaf forwarding-delay {
      type int32;
      description
        "The delay used by STP bridges to transition root and designated ports to forwarding";
    }
    leaf hold-count {
      type uint32;
      description
        "The maximum number of BPDUs per second that the switch can send from an interface";
    }
    leaf bridge-priority {
      type uint16;
      description
        "The manageable component of the Bridge Identifier";
    }
    leaf bridge-address {
      type yang:mac-address;
      description
        "A unique 48-bit Universally Administered MAC Address assigned to the bridge";
    }
    leaf designated-root-priority {
      type uint32;
      description
        "The bridge priority of the root of the spanning tree, as determined by the Spanning Tree Protocol, as executed by this node";
    }
    leaf designated-root-address {
      type yang:mac-address;
      description
        "The bridge address of the root of the spanning tree, as determined by the Spanning Tree Protocol, as executed by this node";
    }
    leaf root-port {
      type uint16;
      description
        "The port number of the port which offers the lowest cost path from this bridge to the root bridge";
    }
    leaf root-cost {
      type uint64;
      description
        "The cost of the path to the root as seen from this bridge";
    }
    leaf hold-time {
      type uint64;
      description
        "This time value determines the interval length during which no more than two Configuration bridge PDUs shall be transmitted by this node";
    }
    leaf topology-changes {
      type uint64;
      description
        "The total number of topology changes detected by this bridge since the management entity was last reset or initialized";
    }
    leaf time-of-last-topology-change {
      type yang:date-and-time;
      description
        "The time of the last topology change that was detected by the bridge entity.The time is POSIX time UTC";
    }
    container interfaces {
      description
        "List of interfaces on which STP is enable";
      list interface {
        key "name";
        description
          "List of interfaces on which STP is enable";
        uses stp-ios-xe-oper:interfaces;
      }
    }
  }

  grouping mst-global {
    description
      "Global state for MST ONLY";
    leaf mst-config-revision {
      type uint16;
      description
        "Configuration revision number(used by MSTP only)";
    }
    leaf mst-config-name {
      type string;
      description
        "Configuration name(used by MSTP only)";
    }
    leaf max-hops {
      type uint16;
      description
        "The max hops value for the spanning tree(used by MSTP only)";
    }
  }

  grouping stp-global {
    description
      "Global spanning tree state";
    leaf mode {
      type stp-ios-xe-oper:stp-mode;
      description
        "Spanning tree mode enabled on the device";
    }
    leaf bridge-assurance {
      type empty;
      description
        "Enable STP Bridge Assurance feature";
    }
    leaf loop-guard {
      type empty;
      description
        "Enable loopguard by default";
    }
    leaf bpdu-guard {
      type empty;
      description
        "Enable portfast bpdu guard";
    }
    leaf bpdu-filter {
      type empty;
      description
        "Enable portfast bpdu filter";
    }
    leaf etherchannel-misconfig-guard {
      type empty;
      description
        "Enable guard to protect against etherchannel misconfiguration";
    }
    container mst-only {
      description
        "Global state for MST ONLY";
      uses stp-ios-xe-oper:mst-global;
    }
  }

  container stp-details {
    config false;
    description
      "Top-level container for spanning tree operational data";
    tailf:callpoint "ios-oper-db";
    tailf:meta-data "callpoint" {
      tailf:meta-value "ios-oper-db";
    }
    tailf:meta-data "greenprefix" {
      tailf:meta-value "/services;serviceName=ios_oper";
    }
    list stp-detail {
      key "instance";
      description
        "List of mst/rapid-pvst spanning-tree, keyed by instance name";
      uses stp-ios-xe-oper:stp-oper-crimson;
    }
    container stp-global {
      presence "stp-global";
      description
        "Global state data";
      uses stp-ios-xe-oper:stp-global;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWc3rgc4AA0lfgBAAEAYQED/v38q/79+KQAKudANKAaEUybTRMTQyGRoMjTRiaaGGhpoAaAA0AAMhoGmVExDINAaYjQZMjIBoIohATJiCSeo0Hqaeo8UDT01M3MQL60BgzF6WKWmC7cFoZovFrwdIS0UzUzBDMcqkvIgi6ZLYmP1H+fXn9dt4sdq1oV+DwjxUYSJiSCIgZEggmFmFYkInvi4e8+Cj4jAbHUSgRhi8JSUySSQcALIgZ0UC8mYJwlDWW5G+QKYwrl4xEfn6d5fv9fVfPX1yPxX93I8nzSQJnm4H8RYLOkv6jI2jH1DP2JpFf2fbEsNLEkQkSxdm7t2IQ7BnWkEPbDSd3TlkXPMw9CLNa+xc9wuiqdaB6NZ1a82GiFg3es4XBSstoevIOj0Lx0rJjVB4waGGk6jryRbAuk0QmK0WwjVgvaU0+RRa39wW/s7bNCi2IKBK6YVBdkcwgHDdeg4PaK9C7sZfQfIZ6Ywdhi/MmZmZnFqE+USxWKhuzTjCw3BCtrRRCItQAj5ytoU3sOqmVLs8GZ4FhWDX+nYV0NpFnlFoeDXHiOPcZA6jLSN21jF+2oxF7UZh5jn0Dp/X95EEVwtMtXt8ZFxkEMEJiXN7i9m/NY03pSqZRQtSMSE+WqBhB2MNkM2uFcUDkYihyORkoD5rSdSO9WG2o32CrGGbBwZUsBSu7i32XtkGpMRzO70M+7nahpz5BF4nepaN80A5wZvA2Gtshd3YIWaoYNHZgphY4xUsc6cDavDJvP3FstFD6Qrs58oOs1HgSmhgXl7UI41iqgSa4818BxflpJn3NffYH7BDB58oD4kZkIj/xdyRThQkM3rgc4A=";
      }
      tailf:meta-data "uncompressed_size" {
        tailf:meta-value "1725";
      }
    }
  }

  container schema-metadata-Cisco-IOS-XE-spanning-tree-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-spanning-tree-oper";
    }
    tailf:meta-data "organization" {
      tailf:meta-value "Cisco Systems, Inc.";
    }
    tailf:meta-data "semver" {
      tailf:meta-value "2019-05-01";
    }
  }
}
