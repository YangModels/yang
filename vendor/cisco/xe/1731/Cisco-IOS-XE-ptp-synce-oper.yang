module Cisco-IOS-XE-ptp-synce-oper {
  yang-version 1;
  namespace "http://cisco.com/ns/yang/Cisco-IOS-XE-ptp-synce-oper";
  prefix ptp-synce-ios-xe-oper;
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for PTP (Precision Time Protocol) and 
     Synchronous Ethernet operational data.
     Copyright (c) 2019, 2020 by Cisco Systems, Inc.
     All rights reserved.";

  revision 2020-03-01 {
    description
      "Initial revision";
    reference "1.0.0";
    cisco-semver:module-version "1.0.0";
    cisco-semver-internal:os-version "17.2.1";
  }

  typedef ptp-clock-type {
    type enumeration {
      enum "ptp-clock-type-not-set" {
        value 0;
        description
          "PTP Clock type not set";
        tailf:code-name "ENUM_ptp_clk_type_TDL_PTP_CFG_CLK_TYPE_NOT_SET";
      }
      enum "ptp-clock-type-ordinary" {
        value 1;
        description
          "PTP Clock type Ordinary";
        tailf:code-name "ENUM_ptp_clk_type_TDL_PTP_CFG_CLK_TYPE_ORDINARY";
      }
      enum "ptp-clock-type-boundary" {
        value 2;
        description
          "PTP Clock type Boundary";
        tailf:code-name "ENUM_ptp_clk_type_TDL_PTP_CFG_CLK_TYPE_BOUNDARY";
      }
      enum "ptp-clock-type-e2e-transparent" {
        value 3;
        description
          "PTP Clock type edge to edge transparent";
        tailf:code-name "ENUM_ptp_clk_type_TDL_PTP_CFG_CLK_TYPE_E2E_TRANSPARENT";
      }
      enum "ptp-clock-type-invalid" {
        value 4;
        description
          "PTP Clock type reserved";
        tailf:code-name "ENUM_ptp_clk_type_TDL_PTP_CFG_CLK_INVALID";
      }
    }
    description
      "PTP Clock type";
  }

  typedef ptp-clock-state {
    type enumeration {
      enum "ptp-clock-state-unknown" {
        value 0;
        description
          "PTP clock state unknown";
        tailf:code-name "ENUM_ptp_clck_state_TDL_PTP_CLOCK_STATE_UNKNOWN";
      }
      enum "ptp-clock-state-initializing" {
        value 1;
        description
          "PTP clock state initializing";
        tailf:code-name "ENUM_ptp_clck_state_TDL_PTP_CLOCK_STATE_INITIALIZING";
      }
      enum "ptp-clock-state-freerun" {
        value 2;
        description
          "PTP clock state free run";
        tailf:code-name "ENUM_ptp_clck_state_TDL_PTP_CLOCK_STATE_FREERUN";
      }
      enum "ptp-clock-state-holdover" {
        value 3;
        description
          "PTP clock state hold over";
        tailf:code-name "ENUM_ptp_clck_state_TDL_PTP_CLOCK_STATE_HOLDOVER";
      }
      enum "ptp-clock-state-acquiring" {
        value 4;
        description
          "PTP clock state acquiring";
        tailf:code-name "ENUM_ptp_clck_state_TDL_PTP_CLOCK_STATE_ACQUIRING";
      }
      enum "ptp-clock-state-freq-locked" {
        value 5;
        description
          "PTP clock state freq locked";
        tailf:code-name "ENUM_ptp_clck_state_TDL_PTP_CLOCK_STATE_FREQ_LOCKED";
      }
      enum "ptp-clock-state-phase-aligned" {
        value 6;
        description
          "PTP clock state phase aligned";
        tailf:code-name "ENUM_ptp_clck_state_TDL_PTP_CLOCK_STATE_PHASE_ALIGNED";
      }
      enum "ptp-clock-state-invalid" {
        value 7;
        description
          "PTP clock state invalid";
        tailf:code-name "ENUM_ptp_clck_state_TDL_PTP_CLOCK_STATE_INVALID";
      }
    }
    description
      "PTP clock state";
  }

  typedef ptp-clock-time-source {
    type enumeration {
      enum "ptp-time-source-atomic-clock" {
        value 0;
        description
          "PTP clock time source atomic clock";
        tailf:code-name "ENUM_ptp_clk_time_source_TDL_PTP_TIME_SOURCE_ATOMIC_CLOCK";
      }
      enum "ptp-time-source-gps" {
        value 1;
        description
          "PTP clock time source GPS";
        tailf:code-name "ENUM_ptp_clk_time_source_TDL_PTP_TIME_SOURCE_GPS";
      }
      enum "ptp-time-source-terrestrial-radio" {
        value 2;
        description
          "PTP clock time source terrestrial radio";
        tailf:code-name "ENUM_ptp_clk_time_source_TDL_PTP_TIME_SOURCE_TERRESTRIAL_RADIO";
      }
      enum "ptp-time-source-ptp" {
        value 3;
        description
          "PTP clock time source PTP";
        tailf:code-name "ENUM_ptp_clk_time_source_TDL_PTP_TIME_SOURCE_PTP";
      }
      enum "ptp-time-source-ntp" {
        value 4;
        description
          "PTP clock time source NTP";
        tailf:code-name "ENUM_ptp_clk_time_source_TDL_PTP_TIME_SOURCE_NTP";
      }
      enum "ptp-time-source-hand-set" {
        value 5;
        description
          "PTP clock time source hand set";
        tailf:code-name "ENUM_ptp_clk_time_source_TDL_PTP_TIME_SOURCE_HAND_SET";
      }
      enum "ptp-time-source-other" {
        value 6;
        description
          "PTP clock time source other";
        tailf:code-name "ENUM_ptp_clk_time_source_TDL_PTP_TIME_SOURCE_OTHER";
      }
      enum "ptp-time-source-internal-oscillator" {
        value 7;
        description
          "PTP clock time source internal oscillator";
        tailf:code-name "ENUM_ptp_clk_time_source_TDL_PTP_TIME_SOURCE_INTERNAL_OSCILLATOR";
      }
      enum "ptp-time-source-invalid" {
        value 8;
        description
          "PTP clock time source invalid";
        tailf:code-name "ENUM_ptp_clk_time_source_TDL_PTP_TIME_SOURCE_INVALID";
      }
    }
    description
      "PTP clock time source";
  }

  typedef peer-address-type {
    type enumeration {
      enum "peer-address-mac" {
        value 0;
        description
          "Peer address is an MAC address";
        tailf:code-name "ENUM_peer_address_type_PEER_ADDRESS_MAC";
      }
      enum "peer-address-ip" {
        value 1;
        description
          "Peer address is an IP address";
        tailf:code-name "ENUM_peer_address_type_PEER_ADDRESS_IP";
      }
    }
    description
      "Peer address types";
  }

  typedef netsync-ql {
    type enumeration {
      enum "netsync-ql-null" {
        value 0;
        description
          "Network-clock Synchronization Quality Level Null";
        tailf:code-name "ENUM_tdl_oper_netsync_ql_TDL_NETSYNCE_QL_NULL";
      }
      enum "netsync-ql-dnu" {
        value 1;
        description
          "Network-clock Synchronization Quality Level Do Not Use for Sync";
        tailf:code-name "ENUM_tdl_oper_netsync_ql_TDL_NETSYNCE_QL_DNU";
      }
      enum "netsync-ql-dus" {
        value 2;
        description
          "Network-clock Synchronization Quality Level Do Not Use for Sync";
        tailf:code-name "ENUM_tdl_oper_netsync_ql_TDL_NETSYNCE_QL_DUS";
      }
      enum "netsync-ql-failed" {
        value 3;
        description
          "Network-clock Synchronization Quality Level failed";
        tailf:code-name "ENUM_tdl_oper_netsync_ql_TDL_NETSYNCE_QL_FAILED";
      }
      enum "netsync-ql-inv0" {
        value 4;
        description
          "Network-clock Synchronization Quality Level Unallocated SSM(Synchronization Status Message)  Value 0";
        tailf:code-name "ENUM_tdl_oper_netsync_ql_TDL_NETSYNCE_QL_INV0";
      }
      enum "netsync-ql-inv1" {
        value 5;
        description
          "Network-clock Synchronization Quality Level Unallocated SSM Value 1";
        tailf:code-name "ENUM_tdl_oper_netsync_ql_TDL_NETSYNCE_QL_INV1";
      }
      enum "netsync-ql-inv2" {
        value 6;
        description
          "Network-clock Synchronization Quality Level Unallocated SSM Value 2";
        tailf:code-name "ENUM_tdl_oper_netsync_ql_TDL_NETSYNCE_QL_INV2";
      }
      enum "netsync-ql-inv3" {
        value 7;
        description
          "Network-clock Synchronization Quality Level Unallocated SSM Value 3";
        tailf:code-name "ENUM_tdl_oper_netsync_ql_TDL_NETSYNCE_QL_INV3";
      }
      enum "netsync-ql-inv4" {
        value 8;
        description
          "Network-clock Synchronization Quality Level Unallocated SSM Value 4";
        tailf:code-name "ENUM_tdl_oper_netsync_ql_TDL_NETSYNCE_QL_INV4";
      }
      enum "netsync-ql-inv5" {
        value 9;
        description
          "Network-clock Synchronization Quality Level Unallocated SSM Value 5";
        tailf:code-name "ENUM_tdl_oper_netsync_ql_TDL_NETSYNCE_QL_INV5";
      }
      enum "netsync-ql-inv6" {
        value 10;
        description
          "Network-clock Synchronization Quality Level Unallocated SSM Value 6";
        tailf:code-name "ENUM_tdl_oper_netsync_ql_TDL_NETSYNCE_QL_INV6";
      }
      enum "netsync-ql-inv7" {
        value 11;
        description
          "Network-clock Synchronization Quality Level Unallocated SSM Value 7";
        tailf:code-name "ENUM_tdl_oper_netsync_ql_TDL_NETSYNCE_QL_INV7";
      }
      enum "netsync-ql-inv8" {
        value 12;
        description
          "Network-clock Synchronization Quality Level Unallocated SSM Value 8";
        tailf:code-name "ENUM_tdl_oper_netsync_ql_TDL_NETSYNCE_QL_INV8";
      }
      enum "netsync-ql-inv9" {
        value 13;
        description
          "Network-clock Synchronization Quality Level Unallocated SSM Value 9";
        tailf:code-name "ENUM_tdl_oper_netsync_ql_TDL_NETSYNCE_QL_INV9";
      }
      enum "netsync-ql-inv10" {
        value 14;
        description
          "Network-clock Synchronization Quality Level Unallocated SSM Value 10";
        tailf:code-name "ENUM_tdl_oper_netsync_ql_TDL_NETSYNCE_QL_INV10";
      }
      enum "netsync-ql-inv11" {
        value 15;
        description
          "Network-clock Synchronization Quality Level Unallocated SSM Value 11";
        tailf:code-name "ENUM_tdl_oper_netsync_ql_TDL_NETSYNCE_QL_INV11";
      }
      enum "netsync-ql-inv12" {
        value 16;
        description
          "Network-clock Synchronization Quality Level Unallocated SSM Value 12";
        tailf:code-name "ENUM_tdl_oper_netsync_ql_TDL_NETSYNCE_QL_INV12";
      }
      enum "netsync-ql-inv13" {
        value 17;
        description
          "Network-clock Synchronization Quality Level Unallocated SSM Value 13";
        tailf:code-name "ENUM_tdl_oper_netsync_ql_TDL_NETSYNCE_QL_INV13";
      }
      enum "netsync-ql-inv14" {
        value 18;
        description
          "Network-clock Synchronization Quality Level Unallocated SSM Value 14";
        tailf:code-name "ENUM_tdl_oper_netsync_ql_TDL_NETSYNCE_QL_INV14";
      }
      enum "netsync-ql-inv15" {
        value 19;
        description
          "Network-clock Synchronization Quality Level Unallocated SSM Value 15";
        tailf:code-name "ENUM_tdl_oper_netsync_ql_TDL_NETSYNCE_QL_INV15";
      }
      enum "netsync-ql-nsupp" {
        value 20;
        description
          "Network-clock Synchronization Quality Level Not Supporting SSM Processing";
        tailf:code-name "ENUM_tdl_oper_netsync_ql_TDL_NETSYNCE_QL_NSUPP";
      }
      enum "netsync-ql-prc" {
        value 21;
        description
          "Network-clock Synchronization Quality Level Primary Clock Reference";
        tailf:code-name "ENUM_tdl_oper_netsync_ql_TDL_NETSYNCE_QL_PRC";
      }
      enum "netsync-ql-prov" {
        value 22;
        description
          "Network-clock Synchronization Quality Level Provisional by Network Operator";
        tailf:code-name "ENUM_tdl_oper_netsync_ql_TDL_NETSYNCE_QL_PROV";
      }
      enum "netsync-ql-prs" {
        value 23;
        description
          "Network-clock Synchronization Quality Level PRS(Primary Reference Source) Traceable";
        tailf:code-name "ENUM_tdl_oper_netsync_ql_TDL_NETSYNCE_QL_PRS";
      }
      enum "netsync-ql-sec" {
        value 24;
        description
          "Network-clock Synchronization Quality Level Synchronous Equipment Clock";
        tailf:code-name "ENUM_tdl_oper_netsync_ql_TDL_NETSYNCE_QL_SEC";
      }
      enum "netsync-ql-smc" {
        value 25;
        description
          "Network-clock Synchronization Quality Level SONET(Synchronous Optical Networking) Clock Self timed";
        tailf:code-name "ENUM_tdl_oper_netsync_ql_TDL_NETSYNCE_QL_SMC";
      }
      enum "netsync-ql-ssu-a" {
        value 26;
        description
          "Network-clock Synchronization Quality Level Type I or V Slave Clock";
        tailf:code-name "ENUM_tdl_oper_netsync_ql_TDL_NETSYNCE_QL_SSU_A";
      }
      enum "netsync-ql-ssu-b" {
        value 27;
        description
          "Network-clock Synchronization Quality Level Type VI Slave Clock";
        tailf:code-name "ENUM_tdl_oper_netsync_ql_TDL_NETSYNCE_QL_SSU_B";
      }
      enum "netsync-ql-st2" {
        value 28;
        description
          "Network-clock Synchronization Quality Level Stratum 2";
        tailf:code-name "ENUM_tdl_oper_netsync_ql_TDL_NETSYNCE_QL_ST2";
      }
      enum "netsync-ql-st3" {
        value 29;
        description
          "Network-clock Synchronization Quality Level Stratum 3";
        tailf:code-name "ENUM_tdl_oper_netsync_ql_TDL_NETSYNCE_QL_ST3";
      }
      enum "netsync-ql-st3e" {
        value 30;
        description
          "Network-clock Synchronization Quality Level Stratum 3E";
        tailf:code-name "ENUM_tdl_oper_netsync_ql_TDL_NETSYNCE_QL_ST3E";
      }
      enum "netsync-ql-st4" {
        value 31;
        description
          "Network-clock Synchronization Quality Level Stratum 4 Free Run";
        tailf:code-name "ENUM_tdl_oper_netsync_ql_TDL_NETSYNCE_QL_ST4";
      }
      enum "netsync-ql-stu" {
        value 32;
        description
          "Network-clock Synchronization Quality Level Synchronized Trace ability Unknown";
        tailf:code-name "ENUM_tdl_oper_netsync_ql_TDL_NETSYNCE_QL_STU";
      }
      enum "netsync-ql-tnc" {
        value 33;
        description
          "Network-clock Synchronization Quality Level Transit Node Clock";
        tailf:code-name "ENUM_tdl_oper_netsync_ql_TDL_NETSYNCE_QL_TNC";
      }
      enum "netsync-ql-unc" {
        value 34;
        description
          "Network-clock Synchronization Quality Level Unconnected to an Input";
        tailf:code-name "ENUM_tdl_oper_netsync_ql_TDL_NETSYNCE_QL_UNC";
      }
      enum "netsync-ql-unk" {
        value 35;
        description
          "Network-clock Synchronization Quality Level Unknown Clock Source";
        tailf:code-name "ENUM_tdl_oper_netsync_ql_TDL_NETSYNCE_QL_UNK";
      }
      enum "netsync-ql-max" {
        value 36;
        description
          "Network-clock Synchronization Quality Level maximum";
        tailf:code-name "ENUM_tdl_oper_netsync_ql_TDL_NETSYNCE_QL_MAX";
      }
    }
    description
      "Network-clock Synchronization define Quality level value";
  }

  typedef signal-type {
    type enumeration {
      enum "na" {
        value 0;
        description
          "Network-clock Synchronization signal type unknown ethernet interfaces";
        tailf:code-name "ENUM_tdl_oper_netsync_sig_type_TDL_NETSYNCE_INTF_SIG_UNKNOWN";
      }
      enum "t1-sf" {
        value 1;
        description
          "Network-clock Synchronization signal type";
        tailf:code-name "ENUM_tdl_oper_netsync_sig_type_TDL_NETSYNCE_INTF_SIG_T1_SF";
      }
      enum "t1-esf" {
        value 2;
        description
          "Network-clock Synchronization signal type";
        tailf:code-name "ENUM_tdl_oper_netsync_sig_type_TDL_NETSYNCE_INTF_SIG_T1_ESF";
      }
      enum "t1-d4" {
        value 3;
        description
          "Network-clock Synchronization signal type";
        tailf:code-name "ENUM_tdl_oper_netsync_sig_type_TDL_NETSYNCE_INTF_SIG_T1_D4";
      }
      enum "e1" {
        value 4;
        description
          "Network-clock Synchronization signal type";
        tailf:code-name "ENUM_tdl_oper_netsync_sig_type_TDL_NETSYNCE_INTF_SIG_E1";
      }
      enum "e1-crc4" {
        value 5;
        description
          "Network-clock Synchronization signal type";
        tailf:code-name "ENUM_tdl_oper_netsync_sig_type_TDL_NETSYNCE_INTF_SIG_E1_CRC4";
      }
      enum "e1-crc4-120ohm" {
        value 6;
        description
          "Network-clock Synchronization signal type";
        tailf:code-name "ENUM_tdl_oper_netsync_sig_type_TDL_NETSYNCE_INTF_SIG_E1_CRC4_120OHM";
      }
      enum "e1-crc4-75ohm" {
        value 7;
        description
          "Network-clock Synchronization signal type";
        tailf:code-name "ENUM_tdl_oper_netsync_sig_type_TDL_NETSYNCE_INTF_SIG_E1_CRC4_75OHM";
      }
      enum "e1-fas" {
        value 8;
        description
          "Network-clock Synchronization signal type";
        tailf:code-name "ENUM_tdl_oper_netsync_sig_type_TDL_NETSYNCE_INTF_SIG_E1_FAS";
      }
      enum "e1-fas-120ohm" {
        value 9;
        description
          "Network-clock Synchronization signal type";
        tailf:code-name "ENUM_tdl_oper_netsync_sig_type_TDL_NETSYNCE_INTF_SIG_E1_FAS_120OHM";
      }
      enum "e1-fas-75ohm" {
        value 10;
        description
          "Network-clock Synchronization signal type";
        tailf:code-name "ENUM_tdl_oper_netsync_sig_type_TDL_NETSYNCE_INTF_SIG_E1_FAS_75OHM";
      }
      enum "e1-cas" {
        value 11;
        description
          "Network-clock Synchronization signal type";
        tailf:code-name "ENUM_tdl_oper_netsync_sig_type_TDL_NETSYNCE_INTF_SIG_E1_CAS";
      }
      enum "e1-cas-120ohm" {
        value 12;
        description
          "Network-clock Synchronization signal type";
        tailf:code-name "ENUM_tdl_oper_netsync_sig_type_TDL_NETSYNCE_INTF_SIG_E1_CAS_120OHM";
      }
      enum "e1-cas-75ohm" {
        value 13;
        description
          "Network-clock Synchronization signal type";
        tailf:code-name "ENUM_tdl_oper_netsync_sig_type_TDL_NETSYNCE_INTF_SIG_E1_CAS_75OHM";
      }
      enum "e1-cas-crc4" {
        value 14;
        description
          "Network-clock Synchronization signal type";
        tailf:code-name "ENUM_tdl_oper_netsync_sig_type_TDL_NETSYNCE_INTF_SIG_E1_CAS_CRC4";
      }
      enum "e1-cas-crc4-120ohm" {
        value 15;
        description
          "Network-clock Synchronization signal type";
        tailf:code-name "ENUM_tdl_oper_netsync_sig_type_TDL_NETSYNCE_INTF_SIG_E1_CAS_CRC4_120OHM";
      }
      enum "e1-cas-crc4-75ohm" {
        value 16;
        description
          "Network-clock Synchronization signal type";
        tailf:code-name "ENUM_tdl_oper_netsync_sig_type_TDL_NETSYNCE_INTF_SIG_E1_CAS_CRC4_75OHM";
      }
      enum "j1" {
        value 17;
        description
          "Network-clock Synchronization signal type";
        tailf:code-name "ENUM_tdl_oper_netsync_sig_type_TDL_NETSYNCE_INTF_SIG_J1";
      }
      enum "2m" {
        value 18;
        description
          "Network-clock Synchronization signal type";
        tailf:code-name "ENUM_tdl_oper_netsync_sig_type_TDL_NETSYNCE_INTF_SIG_2M";
      }
      enum "10m" {
        value 19;
        description
          "Network-clock Synchronization signal type";
        tailf:code-name "ENUM_tdl_oper_netsync_sig_type_TDL_NETSYNCE_INTF_SIG_10M";
      }
      enum "2048k" {
        value 20;
        description
          "Network-clock Synchronization signal type";
        tailf:code-name "ENUM_tdl_oper_netsync_sig_type_TDL_NETSYNCE_INTF_SIG_2048K";
      }
      enum "invalid" {
        value 21;
        description
          "Network-clock Synchronization signal type invalid";
        tailf:code-name "ENUM_tdl_oper_netsync_sig_type_TDL_NETSYNCE_INTF_SIG_INVALID";
      }
    }
    description
      "Network-clock Synchronization signal types";
  }

  grouping ptp-clock-quality {
    description
      "PTP clock quality";
    leaf clock-class {
      type uint8;
      description
        "Clock class value sent to slaves";
    }
    leaf offset-scaled-log-var {
      type uint16;
      description
        "Offset scaled log var";
    }
  }

  grouping ptp-clock-quality-received {
    description
      "PTP clock quality received";
    container clock-quality {
      description
        "Clock quality";
      uses ptp-synce-ios-xe-oper:ptp-clock-quality;
    }
    leaf protocol-address {
      type inet:ip-address;
      description
        "IP address of master device";
    }
  }

  grouping peer-address-data {
    description
      "Peer address of the PTP session";
    leaf peer-address {
      type ptp-synce-ios-xe-oper:peer-address-type;
      config false;
      description
        "DO NOT USE!  -- hidden internal";
      tailf:hidden "full";
      tailf:meta-data "hidden" {
        tailf:meta-value "true";
      }
    }
    choice peer-address-choice {
      description
        "Indicates whether peer address is MAC or IP";
      case peer-address-mac {
        leaf mac {
          type yang:mac-address;
          description
            "MAC address of the session";
        }
      }
      case peer-address-ip {
        leaf ip {
          type inet:ip-address;
          description
            "IP address of the session";
        }
      }
    }
  }

  grouping ptp-operational-session {
    description
      "PTP operational session";
    container address-type {
      description
        "Peer (MAC/IP) address";
      uses ptp-synce-ios-xe-oper:peer-address-data;
    }
    leaf pkts-in {
      type uint64;
      description
        "Number of packets received from peer";
    }
    leaf pkts-out {
      type uint64;
      description
        "Number of packets sent to peer";
    }
    leaf err-in {
      type uint64;
      description
        "Number of error packets received";
    }
    leaf err-out {
      type uint64;
      description
        "Number of error packets sent";
    }
  }

  grouping ptp-clock-runtime-state {
    description
      "PTP clock runtime state";
    leaf clock-state {
      type ptp-synce-ios-xe-oper:ptp-clock-state;
      description
        "Clock State";
    }
    leaf clock-domain {
      type uint8;
      description
        "Clock domain";
    }
    leaf pkts-sent {
      type uint64;
      description
        "Number of packets sent to peer";
    }
    leaf pkts-rcvd {
      type uint64;
      description
        "Number of packets received from peer";
    }
    list ptp-master {
      description
        "List of PTP masters attached to slave port";
      uses ptp-synce-ios-xe-oper:ptp-operational-session;
    }
    list ptp-slave {
      description
        "List of PTP slaves connected to master port";
      uses ptp-synce-ios-xe-oper:ptp-operational-session;
    }
  }

  grouping ptp-clock-time-properties {
    description
      "PTP clock time properties data set";
    leaf current-utc-offset {
      when "boolean(../current-utc-offset-valid)";
      type uint16;
      description
        "Current UTC clock offset value";
    }
    leaf current-utc-offset-valid {
      type empty;
      description
        "Is Current UTC clock offset value valid";
    }
    leaf leap59 {
      type boolean;
      description
        "Is leap 59";
    }
    leaf leap61 {
      type boolean;
      description
        "Is leap 61";
    }
    leaf time-traceable {
      type boolean;
      description
        "Is Time Traceable";
    }
    leaf frequency-traceable {
      type boolean;
      description
        "Is frequency Traceable";
    }
    leaf ptp-time-scale {
      type boolean;
      description
        "PTP time scale";
    }
    leaf time-source {
      type ptp-synce-ios-xe-oper:ptp-clock-time-source;
      description
        "Time Source";
    }
  }

  grouping ptp-time-interval {
    description
      "An IEEE-1588 defined representation of a time interval";
    leaf scaled-nano-seconds {
      type int64;
      units "nanoseconds";
      description
        "Time interval in nanoseconds multiplied by 2<SUP>16</SUP>";
    }
  }

  grouping ptp-clock-current-data-set {
    description
      "An IEEE-1588 defined data set containing attributes related to clock synchronization";
    leaf steps-removed {
      type uint16;
      description
        "Number communication path traversed with grandmaster";
    }
    container offset-from-master {
      description
        "Time difference between slave and master";
      uses ptp-synce-ios-xe-oper:ptp-time-interval;
    }
    container mean-path-delay {
      description
        "Mean propagation time between master and slave";
      uses ptp-synce-ios-xe-oper:ptp-time-interval;
    }
  }

  grouping ptp-key {
    description
      "PTP key values";
    leaf clock-type {
      type ptp-synce-ios-xe-oper:ptp-clock-type;
      description
        "PTP clock type";
    }
    leaf clock-domain {
      type uint64;
      description
        "PTP clock domain";
    }
    leaf clock-inst {
      type uint64;
      description
        "PTP clock instance";
    }
  }

  grouping ptp-data {
    description
      "PTP data values";
    container clock-quality {
      description
        "PTP clock quality sent";
      uses ptp-synce-ios-xe-oper:ptp-clock-quality;
    }
    list clock-quality-received {
      description
        "PTP clock quality received";
      uses ptp-synce-ios-xe-oper:ptp-clock-quality-received;
    }
    container runtime-state {
      description
        "PTP clock runtime state";
      uses ptp-synce-ios-xe-oper:ptp-clock-runtime-state;
    }
    container time-properties {
      description
        "PTP clock time properties data set";
      uses ptp-synce-ios-xe-oper:ptp-clock-time-properties;
    }
    container current-dataset {
      description
        "PTP clock current dataset";
      uses ptp-synce-ios-xe-oper:ptp-clock-current-data-set;
    }
  }

  grouping netsync-ql-data {
    description
      "Holds Quality Level values";
    leaf ql-tx {
      type ptp-synce-ios-xe-oper:netsync-ql;
      description
        "Quality Level value transmitted";
    }
    leaf ql-rx {
      type ptp-synce-ios-xe-oper:netsync-ql;
      description
        "Actual quality Level value received";
    }
    leaf cfg-ql-rx {
      type ptp-synce-ios-xe-oper:netsync-ql;
      description
        "Configured quality Level value";
    }
  }

  grouping netsync-key {
    description
      "Holds key, interface name and signal type";
    leaf interface {
      type string;
      description
        "Interface name";
    }
    leaf sig-type {
      type ptp-synce-ios-xe-oper:signal-type;
      description
        "Interface signal type";
    }
  }

  container ptp-synce-oper-data {
    config false;
    description
      "PTP (Precision Time Protocol) operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list ptp-dataset {
      key "clock-type clock-domain clock-inst";
      description
        "PTP (Precision Time Protocol) dataset";
      uses ptp-synce-ios-xe-oper:ptp-key;
      uses ptp-synce-ios-xe-oper:ptp-data;
    }
    list netsync-ql {
      key "interface sig-type";
      description
        "Sync-E (Synchronous Ethernet) operational data";
      uses ptp-synce-ios-xe-oper:netsync-ql-data;
      uses ptp-synce-ios-xe-oper:netsync-key;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWdre200AB9bfgEAAEAZ/8D////q////6UASCxHmtaNa60B2GqfqaTKnlNNk00nkmmg/VABp5R6NJ5JoabKAkhAU00mhBhMTTRiZGGgEyYTQBJqSNVP0R6k2p6jQZBoGgMnpNNAAHqBzTEyZNGEwTE0wCYBDBGBGASJAgRiYiUHqND1AAD1D1D0hpoaf3xTbYYfpQwkEhRGla6xp3NZG0nFJBjRESXJxzXY9su+NQksiitjlaJsl9wO3cu5FBGRNY/Iolz1Hod+etBiIJCiPFft7vrc+TPPA5ERHOc7ZXqotjUKKYovWOVonwKqmmsRyPDvhntnis7u34+WPYaPPe5ft/t9u0QIZnSTsJAzJFIUzkv8CBD3vqzERx6+znyEp9BM/XCZWVS/uL2plSUAMw2trKsUY8eUIFjg9mVrwEmwB3CzAqrQorpx87yCgoYbccN37ViiDKMmpLZ90QzQHgEQzM10G8MmvKzzlW0gKxeUrWe1iNM050lwkVr87B0lApZq6AIdmxDSCI+A75hCRPqZcH0mEePG3jTi1J570d2ZlqgX0ZXMO6V5+ExUEwkJDBoQOEeH1CIEqMWeo7xtkrqFzxQCJ45kV+/8ZCXKv21w2Gb75GawotJlISY1r0FihGSC0rSSBrgPHbeuaAohkxIuOkmuENIIwpwBKMstUYiRvlVBvX0uCRGu50Z8I64yDEnAYWbPiKSLQ9mA8wRikJMq1AkRAL3+OwFjpegx9WT6T2n+SQk8+nTISXmEriMa4cZIVqahDWQ1fJVXVmXur48tkGuMz3LXFfQbBh0a2aSKiQ0IO7odXKeNBWQV7+HmaXZ44Nuwxl9Z3mKpWEAaMgYJuNDBISolBWdSqmC0QCJyqBAkVxmIkSukiK2SEmcKzvrvhObKjoMXHmCGWTZpYqkJXhl4+Ndq+A4HA+mmAyH8guiLI4gC01U4TGEvazKhJQBauJ6L4cFXCSYqqimxIaEDNet/cJE6IGLAB3qWKCUTCBaQU5ZMNA0NZsy6GWI9q+2XmgB9L2Nhq4KoSSS81eAAQ5aYS828tJ5HTOEIKCsJigaflskpiUF8CroVW9lwOo1uZldG9p3+sWKEaqqYtPVgPNbfQrp2w8ueBz9TOvEzYfJRlVYl6EDJCg2gtbcCVpa80b6TQb19lx1YBu1R+fgaZV8ZZJJz8xI5tNgnvlPXagsovEuXj7fYDOeL7XIMcPZbgp1p6wEZx67IQVUjHvrG1CO5wCLPYx3SW/6Ntt7z3vIZ2fvdUG/OnLvuELV24Rqdllw11c0JsRnxJCDiLNUanhlUV6C3o5PQ1u0xMG3YL6zkloYWJZK5pGsECTdSWCEEjOVDO9qwXMBgTKzu4jLMngIUq3QgZ0Swg2IxngxN0GbJVwglXMQIZQ3duyf159Qn+/4u5IpwoSG1vbaaA=";
      }
      tailf:meta-data "uncompressed_size" {
        tailf:meta-value "4024";
      }
    }
  }

  container schema-metadata-Cisco-IOS-XE-ptp-synce-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-ptp-synce-oper";
    }
    tailf:meta-data "organization" {
      tailf:meta-value "Cisco Systems, Inc.";
    }
    tailf:meta-data "semver" {
      tailf:meta-value "2020-03-01";
    }
  }
}
