module Cisco-IOS-XE-zone-rpc {
  namespace "http://cisco.com/ns/yang/Cisco-IOS-XE-zone-rpc";
  prefix ios-xe-zone-rpc;

  import cisco-semver {
    prefix cisco-semver;
  }
  import Cisco-IOS-XE-rpc {
    prefix ios-xe-rpc;
  }

  organization
    "Cisco Systems";
  contact
    "<mailto:cs-yang@cisco.com>";
  description
    "NED Zone RPC YANG module for IOS
     Copyright (c) 2016-2019 by Cisco Systems, Inc.
     All rights reserved.";

  revision 2019-11-01 {
    description
      "- Updated augment";
    cisco-semver:module-version "2.0.0";
  }
  revision 2019-07-01 {
    description
      "- Establish semantic version baseline
       - Created for NED RPC modularisation";
    cisco-semver:module-version "1.0.0";
  }

  augment "/ios-xe-rpc:clear/ios-xe-rpc:input/ios-xe-rpc:clear-choice" {
    case zone-pair-case {
      container zone-pair {
        description
          "Clear zone-pair";
        leaf counter {
          description
            "Zone-pair counters";
          type empty;
        }
      }
    }
  }
  augment "/ios-xe-rpc:clear/ios-xe-rpc:input/ios-xe-rpc:clear-choice/ios-xe-rpc:platform-case/ios-xe-rpc:platform/ios-xe-rpc:platform-choice/ios-xe-rpc:hardware-case/ios-xe-rpc:hardware/ios-xe-rpc:qfp/ios-xe-rpc:active/ios-xe-rpc:feature/ios-xe-rpc:feature-choice" {
    case firewall-case {
      container firewall {
        description
          "Clear QFP Firewall";
        leaf drop {
          description
            "Clear firewall drop counters";
          type empty;
        }
      }
    }
  }
}
