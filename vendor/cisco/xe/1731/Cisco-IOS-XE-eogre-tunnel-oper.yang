module Cisco-IOS-XE-eogre-tunnel-oper {
  yang-version 1;
  namespace "http://cisco.com/ns/yang/Cisco-IOS-XE-eogre-tunnel-oper";
  prefix ios-eogre-tunnel-oper;

  import Cisco-IOS-XE-event-history-types {
    prefix event-history-types;
  }
  import Cisco-IOS-XE-tunnel-types {
    prefix tunnel-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     Ethernet over GRE (EoGRE) Tunnel domains and interfaces
     Copyright (c) 2020 by Cisco Systems, Inc.
     All rights reserved.";

  revision 2020-07-01 {
    description
      "Initial revision";
    reference "1.0.0";
    cisco-semver:module-version "1.0.0";
  }

  grouping st-tunnel-domain {
    description
      "Tunnel domain";
    container cfg {
      description
        "Domain Configuration";
      uses tunnel-types:tunnel-domain-common;
    }
    leaf active-tunnel-name {
      type string;
      description
        "Active tunnel name";
    }
    container history {
      description
        "Event history";
      uses event-history-types:event-history;
    }
  }

  grouping tunnel-intf-key {
    description
      "Interface key pair";
    leaf name {
      type string;
      description
        "Interface key name";
    }
    leaf type {
      type tunnel-types:tunnel-domain-mode;
      description
        "Interface key type";
    }
  }

  grouping st-tunnel-interface {
    description
      "List of tunnel interfaces";
    leaf gateway-address {
      type inet:ip-address;
      description
        "Gateway IP address";
    }
    leaf admin-status {
      type tunnel-types:tunnel-intf-status;
      description
        "Administrative status";
    }
    leaf status {
      type tunnel-types:tunnel-intf-status;
      description
        "Tunnel operational status";
    }
    leaf up-timestamp {
      type yang:date-and-time;
      description
        "Last time this gateway went up";
    }
    leaf mtu {
      type uint32;
      description
        "Maximum transmission unit";
    }
    container stats {
      description
        "Tunnel Statistics";
      uses tunnel-types:tunnel-stats;
    }
    leaf source-interface {
      type string;
      description
        "Source Interface";
    }
    leaf source-address {
      type inet:ip-address;
      description
        "Source IP Address";
    }
    container history {
      description
        "Event history for this gateway";
      uses event-history-types:event-history;
    }
    leaf intf-type {
      type tunnel-types:tunnel-intf-mode;
      description
        "Tunnel interface type";
    }
  }

  container eogre-tunnel-oper-data {
    config false;
    description
      "Top-level container for tunnel operational data";
    list tunnel-domain {
      key "name type";
      description
        "List of tunnel domains, keyed by domain name and type";
      uses tunnel-types:tunnel-domain-index;
      uses ios-eogre-tunnel-oper:st-tunnel-domain;
    }
    list tunnel-intf {
      key "name type";
      description
        "List of tunnel interfaces";
      uses ios-eogre-tunnel-oper:tunnel-intf-key;
      uses ios-eogre-tunnel-oper:st-tunnel-interface;
    }
  }
}
