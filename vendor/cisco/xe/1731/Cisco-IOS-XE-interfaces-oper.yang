module Cisco-IOS-XE-interfaces-oper {
  yang-version 1;
  namespace "http://cisco.com/ns/yang/Cisco-IOS-XE-interfaces-oper";
  prefix interfaces-ios-xe-oper;

  import Cisco-IOS-XE-ios-common-oper {
    prefix ios-common-ios-xe-oper;
  }
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring the interfaces in a Network Element.
     Copyright (c) 2016-2020 by Cisco Systems, Inc.
     All rights reserved.";

  revision 2020-07-01 {
    description
      "- Added storm control for broadcast, multicast, unicast,
         and unknown unicast
       - Added storm control for level shared case";
    reference "0.0.0";
    cisco-semver:module-version "0.0.0";
    cisco-semver-internal:os-version "17.3.1";
  }
  revision 2020-03-01 {
    description
      "- Added in-discards-64, in-errors-64, in-unknown-protocol-64,
         out-octets-64 to increase the storage class to 64 bits
       - Added has-child in classifier stats";
    reference "3.4.0";
    cisco-semver:module-version "3.4.0";
    cisco-semver-internal:os-version "17.2.1";
  }
  revision 2019-11-01 {
    description
      "- Added media type to interface
       - Added more interface speed values";
    reference "3.3.0";
    cisco-semver:module-version "3.3.0";
    cisco-semver-internal:os-version "17.1.1";
  }
  revision 2019-05-01 {
    description
      "- Added ethernet error counters.
       - Added semantic version";
    reference "3.2.0";
    cisco-semver:module-version "3.2.0";
  }
  revision 2018-10-29 {
    description
      "Cleaned up spelling errors in descriptions.";
    reference "3.1.0";
    cisco-semver:module-version "3.1.0";
  }
  revision 2018-06-29 {
    description
      "- Add switching interface speed values
       - Add synchronous serial interface model";
    reference "3.0.0";
    cisco-semver:module-version "3.0.0";
  }
  revision 2018-02-01 {
    description
      "IPv6 addresses";
    reference "2.0.0";
    cisco-semver:module-version "2.0.0";
  }
  revision 2017-10-10 {
    description
      "Initial revision";
    reference "1.0.0";
    cisco-semver:module-version "1.0.0";
  }

  typedef qos-match-type {
    type enumeration {
      enum "qos-match-dscp" {
        value 0;
        tailf:code-name "ENUM_qos_match_type_QOS_MATCH_DSCP";
      }
      enum "qos-match-src-ip" {
        value 1;
        tailf:code-name "ENUM_qos_match_type_QOS_MATCH_SOURCE_IP_ADDRESS";
      }
      enum "qos-match-dst-ip" {
        value 2;
        tailf:code-name "ENUM_qos_match_type_QOS_MATCH_DESTINATION_IP_ADDRESS";
      }
      enum "qos-match-src-port" {
        value 3;
        tailf:code-name "ENUM_qos_match_type_QOS_MATCH_SOURCE_PORT";
      }
      enum "qos-match-dst-port" {
        value 4;
        tailf:code-name "ENUM_qos_match_type_QOS_MATCH_DESTINATION_PORT";
      }
      enum "qos-match-proto" {
        value 5;
        tailf:code-name "ENUM_qos_match_type_QOS_MATCH_PROTOCOL";
      }
    }
    description
      "QOS match type";
  }

  typedef thresh-unit {
    type enumeration {
      enum "thresh-units-default" {
        value 0;
        tailf:code-name "ENUM_thresh_unit_THRESH_UNIT_DEFAULT";
      }
      enum "thresh-units-bytes" {
        value 1;
        tailf:code-name "ENUM_thresh_unit_THRESH_UNIT_BYTES";
      }
      enum "thresh-units-sec" {
        value 2;
        tailf:code-name "ENUM_thresh_unit_THRESH_UNIT_SEC";
      }
      enum "thresh-units-packets" {
        value 3;
        tailf:code-name "ENUM_thresh_unit_THRESH_UNIT_PACKETS";
      }
      enum "thresh-units-cells" {
        value 4;
        tailf:code-name "ENUM_thresh_unit_THRESH_UNIT_CELLS";
      }
      enum "thresh-units-percent" {
        value 5;
        tailf:code-name "ENUM_thresh_unit_THRESH_UNIT_PERCENT";
      }
    }
    description
      "Units of threshold";
  }

  typedef qos-direction {
    type enumeration {
      enum "qos-inbound" {
        value 0;
        description
          "Direction of traffic coming into the network entry";
        tailf:code-name "ENUM_qos_direction_QOS_INBOUND";
      }
      enum "qos-outbound" {
        value 1;
        description
          "Direction of traffic going out of the network entry";
        tailf:code-name "ENUM_qos_direction_QOS_OUTBOUND";
      }
    }
    description
      "QoS direction indication";
  }

  typedef aggregation-type {
    type enumeration {
      enum "lag-off" {
        value 0;
        description
          "LAG mode is off";
        tailf:code-name "ENUM_aggregation_type_LACP_FEC_MODE_OFF";
      }
      enum "lag-auto" {
        value 1;
        description
          "LAG mode is auto";
        tailf:code-name "ENUM_aggregation_type_LACP_FEC_MODE_AUTO";
      }
      enum "lag-active" {
        value 2;
        description
          "LAG mode is active";
        tailf:code-name "ENUM_aggregation_type_LACP_FEC_MODE_ACTIVE";
      }
      enum "lag-passive" {
        value 3;
        description
          "LAG mode is passive";
        tailf:code-name "ENUM_aggregation_type_LACP_FEC_MODE_PASSIVE";
      }
    }
    description
      "Type to define the lag-type, i.e., how the LAG is
       defined and managed";
  }

  typedef intf-state {
    type enumeration {
      enum "if-state-unknown" {
        value 0;
        tailf:code-name "ENUM_intf_state_STATE_INTF_UNKNOWN";
      }
      enum "if-state-up" {
        value 1;
        tailf:code-name "ENUM_intf_state_STATE_INTF_UP";
      }
      enum "if-state-down" {
        value 2;
        tailf:code-name "ENUM_intf_state_STATE_INTF_DOWN";
      }
      enum "if-state-test" {
        value 3;
        tailf:code-name "ENUM_intf_state_STATE_INTF_TEST";
      }
    }
    description
      "The desired state of the interface.
       This leaf has the same read semantics as ifAdminStatus.
       Reference:
       RFC 2863: The Interfaces Group MIB - ifAdminStatus";
  }

  typedef ether-duplex {
    type enumeration {
      enum "full-duplex" {
        value 0;
        tailf:code-name "ENUM_ether_duplex_ETHERNET_DUPLEX_FULL";
      }
      enum "half-duplex" {
        value 1;
        tailf:code-name "ENUM_ether_duplex_ETHERNET_DUPLEX_HALF";
      }
      enum "auto-duplex" {
        value 2;
        tailf:code-name "ENUM_ether_duplex_ETHERNET_DUPLEX_AUTO";
      }
      enum "unknown-duplex" {
        value 3;
        tailf:code-name "ENUM_ether_duplex_ETHERNET_DUPLEX_UNKNOWN";
      }
    }
    description
      "The duplex setting of the interface";
  }

  typedef ether-speed {
    type enumeration {
      enum "speed-10mb" {
        value 0;
        tailf:code-name "ENUM_ether_speed_ETHERNET_SPEED_10MB";
      }
      enum "speed-100mb" {
        value 1;
        tailf:code-name "ENUM_ether_speed_ETHERNET_SPEED_100MB";
      }
      enum "speed-1gb" {
        value 2;
        tailf:code-name "ENUM_ether_speed_ETHERNET_SPEED_1GB";
      }
      enum "speed-10gb" {
        value 3;
        tailf:code-name "ENUM_ether_speed_ETHERNET_SPEED_10GB";
      }
      enum "speed-25gb" {
        value 4;
        tailf:code-name "ENUM_ether_speed_ETHERNET_SPEED_25GB";
      }
      enum "speed-40gb" {
        value 5;
        tailf:code-name "ENUM_ether_speed_ETHERNET_SPEED_40GB";
      }
      enum "speed-50gb" {
        value 6;
        tailf:code-name "ENUM_ether_speed_ETHERNET_SPEED_50GB";
      }
      enum "speed-100gb" {
        value 7;
        tailf:code-name "ENUM_ether_speed_ETHERNET_SPEED_100GB";
      }
      enum "speed-unknown" {
        value 8;
        tailf:code-name "ENUM_ether_speed_ETHERNET_SPEED_UNKNOWN";
      }
      enum "speed-auto" {
        value 9;
        tailf:code-name "ENUM_ether_speed_ETHERNET_SPEED_AUTO";
      }
      enum "speed-2500mb" {
        value 10;
        description
          "Ethernet Speed 2500 MBPS";
        tailf:code-name "ENUM_ether_speed_ETHERNET_SPEED_2500MB";
      }
      enum "speed-5gb" {
        value 11;
        description
          "Ethernet Speed 5 GBPS";
        tailf:code-name "ENUM_ether_speed_ETHERNET_SPEED_5GB";
      }
      enum "speed-400gb" {
        value 12;
        description
          "Ethernet Speed 400 GBPS";
        tailf:code-name "ENUM_ether_speed_ETHERNET_SPEED_400GB";
      }
    }
    description
      "The speed setting of the interface";
  }

  typedef oper-state {
    type enumeration {
      enum "if-oper-state-invalid" {
        value 0;
        tailf:code-name "ENUM_oper_state_STATE_OPER_INVALID";
      }
      enum "if-oper-state-ready" {
        value 1;
        tailf:code-name "ENUM_oper_state_STATE_OPER_READY";
      }
      enum "if-oper-state-no-pass" {
        value 2;
        tailf:code-name "ENUM_oper_state_STATE_OPER_NO_PASS";
      }
      enum "if-oper-state-test" {
        value 3;
        tailf:code-name "ENUM_oper_state_STATE_OPER_TEST_MODE";
      }
      enum "if-oper-state-unknown" {
        value 4;
        tailf:code-name "ENUM_oper_state_STATE_OPER_UNKNOWN";
      }
      enum "if-oper-state-dormant" {
        value 5;
        tailf:code-name "ENUM_oper_state_STATE_OPER_DORMANT";
      }
      enum "if-oper-state-not-present" {
        value 6;
        tailf:code-name "ENUM_oper_state_STATE_OPER_NOT_PRESENT";
      }
      enum "if-oper-state-lower-layer-down" {
        value 7;
        tailf:code-name "ENUM_oper_state_STATE_OPER_LOWER_LAYER_DOWN";
      }
    }
    description
      "The current operational state of the interface.
       This leaf has the same semantics as ifOperStatus.
       Reference:
       RFC 2863: The Interfaces Group MIB - ifOperStatus";
  }

  typedef ietf-intf-type {
    type enumeration {
      enum "iana-iftype-other" {
        value 1;
        tailf:code-name "ENUM_ietf_intf_type_IANA_IFTYPE_OTHER";
      }
      enum "iana-iftype-regular1822" {
        value 2;
        tailf:code-name "ENUM_ietf_intf_type_IANA_IFTYPE_REGULAR1822";
      }
      enum "iana-iftype-hdh1822" {
        value 3;
        tailf:code-name "ENUM_ietf_intf_type_IANA_IFTYPE_HDH1822";
      }
      enum "iana-iftype-ddnx25" {
        value 4;
        tailf:code-name "ENUM_ietf_intf_type_IANA_IFTYPE_DDNX25";
      }
      enum "iana-iftype-rfc877x25" {
        value 5;
        tailf:code-name "ENUM_ietf_intf_type_IANA_IFTYPE_RFC877X25";
      }
      enum "iana-iftype-ethernet-csmacd" {
        value 6;
        tailf:code-name "ENUM_ietf_intf_type_IANA_IFTYPE_ETHERNETCSMACD";
      }
      enum "iana-iftype-iso88023-csmacd" {
        value 7;
        tailf:code-name "ENUM_ietf_intf_type_IANA_IFTYPE_ISO88023CSMACD";
      }
      enum "iana-iftype-iso88024-tokenbus" {
        value 8;
        tailf:code-name "ENUM_ietf_intf_type_IANA_IFTYPE_ISO88024TOKENBUS";
      }
      enum "iana-iftype-iso88025-tokenring" {
        value 9;
        tailf:code-name "ENUM_ietf_intf_type_IANA_IFTYPE_ISO88025TOKENRING";
      }
      enum "iana-iftype-iso88026-man" {
        value 10;
        tailf:code-name "ENUM_ietf_intf_type_IANA_IFTYPE_ISO88026MAN";
      }
      enum "iana-iftype-starlan" {
        value 11;
        tailf:code-name "ENUM_ietf_intf_type_IANA_IFTYPE_STARLAN";
      }
      enum "iana-iftype-proteon10mbit" {
        value 12;
        tailf:code-name "ENUM_ietf_intf_type_IANA_IFTYPE_PROTEON10MBIT";
      }
      enum "iana-iftype-proteon80mbit" {
        value 13;
        tailf:code-name "ENUM_ietf_intf_type_IANA_IFTYPE_PROTEON80MBIT";
      }
      enum "iana-iftype-hyperchannel" {
        value 14;
        tailf:code-name "ENUM_ietf_intf_type_IANA_IFTYPE_HYPERCHANNEL";
      }
      enum "iana-iftype-fddi" {
        value 15;
        tailf:code-name "ENUM_ietf_intf_type_IANA_IFTYPE_FDDI";
      }
      enum "iana-iftype-lapb" {
        value 16;
        tailf:code-name "ENUM_ietf_intf_type_IANA_IFTYPE_LAPB";
      }
      enum "iana-iftype-sdlc" {
        value 17;
        tailf:code-name "ENUM_ietf_intf_type_IANA_IFTYPE_SDLC";
      }
      enum "iana-iftype-ds1" {
        value 18;
        tailf:code-name "ENUM_ietf_intf_type_IANA_IFTYPE_DS1";
      }
      enum "iana-iftype-e1" {
        value 19;
        tailf:code-name "ENUM_ietf_intf_type_IANA_IFTYPE_E1";
      }
      enum "iana-iftype-basicisdn" {
        value 20;
        tailf:code-name "ENUM_ietf_intf_type_IANA_IFTYPE_BASICISDN";
      }
      enum "iana-iftype-primaryisdn" {
        value 21;
        tailf:code-name "ENUM_ietf_intf_type_IANA_IFTYPE_PRIMARYISDN";
      }
      enum "iana-iftype-prop-p2p-serial" {
        value 22;
        tailf:code-name "ENUM_ietf_intf_type_IANA_IFTYPE_PROPPOINTTOPOINTSERIAL";
      }
      enum "iana-iftype-ppp" {
        value 23;
        tailf:code-name "ENUM_ietf_intf_type_IANA_IFTYPE_PPP";
      }
      enum "iana-iftype-sw-loopback" {
        value 24;
        tailf:code-name "ENUM_ietf_intf_type_IANA_IFTYPE_SOFTWARELOOPBACK";
      }
      enum "iana-iftype-eon" {
        value 25;
        tailf:code-name "ENUM_ietf_intf_type_IANA_IFTYPE_EON";
      }
      enum "iana-iftype-ethernet3mbit" {
        value 26;
        tailf:code-name "ENUM_ietf_intf_type_IANA_IFTYPE_ETHERNET3MBIT";
      }
      enum "iana-iftype-nsip" {
        value 27;
        tailf:code-name "ENUM_ietf_intf_type_IANA_IFTYPE_NSIP";
      }
      enum "iana-iftype-slip" {
        value 28;
        tailf:code-name "ENUM_ietf_intf_type_IANA_IFTYPE_SLIP";
      }
      enum "iana-iftype-ultra" {
        value 29;
        tailf:code-name "ENUM_ietf_intf_type_IANA_IFTYPE_ULTRA";
      }
      enum "iana-iftype-ds3" {
        value 30;
        tailf:code-name "ENUM_ietf_intf_type_IANA_IFTYPE_DS3";
      }
      enum "iana-iftype-sip" {
        value 31;
        tailf:code-name "ENUM_ietf_intf_type_IANA_IFTYPE_SIP";
      }
      enum "iana-iftype-framerelay" {
        value 32;
        tailf:code-name "ENUM_ietf_intf_type_IANA_IFTYPE_FRAMERELAY";
      }
      enum "iana-iftype-rs232" {
        value 33;
        tailf:code-name "ENUM_ietf_intf_type_IANA_IFTYPE_RS232";
      }
      enum "iana-iftype-para" {
        value 34;
        tailf:code-name "ENUM_ietf_intf_type_IANA_IFTYPE_PARA";
      }
      enum "iana-iftype-arcnet" {
        value 35;
        tailf:code-name "ENUM_ietf_intf_type_IANA_IFTYPE_ARCNET";
      }
      enum "iana-iftype-arcnetplus" {
        value 36;
        tailf:code-name "ENUM_ietf_intf_type_IANA_IFTYPE_ARCNETPLUS";
      }
      enum "iana-iftype-atm" {
        value 37;
        tailf:code-name "ENUM_ietf_intf_type_IANA_IFTYPE_ATM";
      }
      enum "iana-iftype-miox25" {
        value 38;
        tailf:code-name "ENUM_ietf_intf_type_IANA_IFTYPE_MIOX25";
      }
      enum "iana-iftype-sonet" {
        value 39;
        tailf:code-name "ENUM_ietf_intf_type_IANA_IFTYPE_SONET";
      }
      enum "iana-iftype-x25ple" {
        value 40;
        tailf:code-name "ENUM_ietf_intf_type_IANA_IFTYPE_X25PLE";
      }
      enum "iana-iftype-iso88022-llc" {
        value 41;
        tailf:code-name "ENUM_ietf_intf_type_IANA_IFTYPE_ISO88022LLC";
      }
      enum "iana-iftype-localtalk" {
        value 42;
        tailf:code-name "ENUM_ietf_intf_type_IANA_IFTYPE_LOCALTALK";
      }
      enum "iana-iftype-smdsdxi" {
        value 43;
        tailf:code-name "ENUM_ietf_intf_type_IANA_IFTYPE_SMDSDXI";
      }
      enum "iana-iftype-framerelay-service" {
        value 44;
        tailf:code-name "ENUM_ietf_intf_type_IANA_IFTYPE_FRAMERELAYSERVICE";
      }
      enum "iana-iftype-v35" {
        value 45;
        tailf:code-name "ENUM_ietf_intf_type_IANA_IFTYPE_V35";
      }
      enum "iana-iftype-hssi" {
        value 46;
        tailf:code-name "ENUM_ietf_intf_type_IANA_IFTYPE_HSSI";
      }
      enum "iana-iftype-hippi" {
        value 47;
        tailf:code-name "ENUM_ietf_intf_type_IANA_IFTYPE_HIPPI";
      }
      enum "iana-iftype-modem" {
        value 48;
        tailf:code-name "ENUM_ietf_intf_type_IANA_IFTYPE_MODEM";
      }
      enum "iana-iftype-aal5" {
        value 49;
        tailf:code-name "ENUM_ietf_intf_type_IANA_IFTYPE_AAL5";
      }
      enum "iana-iftype-sonetpath" {
        value 50;
        tailf:code-name "ENUM_ietf_intf_type_IANA_IFTYPE_SONETPATH";
      }
      enum "iana-iftype-sonetvt" {
        value 51;
        tailf:code-name "ENUM_ietf_intf_type_IANA_IFTYPE_SONETVT";
      }
      enum "iana-iftype-smdsicip" {
        value 52;
        tailf:code-name "ENUM_ietf_intf_type_IANA_IFTYPE_SMDSICIP";
      }
      enum "iana-iftype-propvirtual" {
        value 53;
        tailf:code-name "ENUM_ietf_intf_type_IANA_IFTYPE_PROPVIRTUAL";
      }
      enum "iana-iftype-propmultiplexor" {
        value 54;
        tailf:code-name "ENUM_ietf_intf_type_IANA_IFTYPE_PROPMULTIPLEXOR";
      }
      enum "iana-iftype-ieee80212" {
        value 55;
        tailf:code-name "ENUM_ietf_intf_type_IANA_IFTYPE_IEEE80212";
      }
      enum "iana-iftype-fiberchannel" {
        value 56;
        tailf:code-name "ENUM_ietf_intf_type_IANA_IFTYPE_FIBRECHANNEL";
      }
      enum "iana-iftype-hippi-interface" {
        value 57;
        tailf:code-name "ENUM_ietf_intf_type_IANA_IFTYPE_HIPPIINTERFACE";
      }
      enum "iana-iftype-framerelay-interconnect" {
        value 58;
        tailf:code-name "ENUM_ietf_intf_type_IANA_IFTYPE_FRAMERELAYINTERCONNECT";
      }
      enum "iana-iftype-aflane8023" {
        value 59;
        tailf:code-name "ENUM_ietf_intf_type_IANA_IFTYPE_AFLANE8023";
      }
      enum "iana-iftype-aflane8025" {
        value 60;
        tailf:code-name "ENUM_ietf_intf_type_IANA_IFTYPE_AFLANE8025";
      }
      enum "iana-iftype-cctemul" {
        value 61;
        tailf:code-name "ENUM_ietf_intf_type_IANA_IFTYPE_CCTEMUL";
      }
      enum "iana-iftype-fastether" {
        value 62;
        tailf:code-name "ENUM_ietf_intf_type_IANA_IFTYPE_FASTETHER";
      }
      enum "iana-iftype-isdn" {
        value 63;
        tailf:code-name "ENUM_ietf_intf_type_IANA_IFTYPE_ISDN";
      }
      enum "iana-iftype-v11" {
        value 64;
        tailf:code-name "ENUM_ietf_intf_type_IANA_IFTYPE_V11";
      }
      enum "iana-iftype-v36" {
        value 65;
        tailf:code-name "ENUM_ietf_intf_type_IANA_IFTYPE_V36";
      }
      enum "iana-iftype-g703at64k" {
        value 66;
        tailf:code-name "ENUM_ietf_intf_type_IANA_IFTYPE_G703AT64K";
      }
      enum "iana-iftype-g703at2mb" {
        value 67;
        tailf:code-name "ENUM_ietf_intf_type_IANA_IFTYPE_G703AT2MB";
      }
      enum "iana-iftype-qllc" {
        value 68;
        tailf:code-name "ENUM_ietf_intf_type_IANA_IFTYPE_QLLC";
      }
      enum "iana-iftype-fastetherfx" {
        value 69;
        tailf:code-name "ENUM_ietf_intf_type_IANA_IFTYPE_FASTETHERFX";
      }
      enum "iana-iftype-channel" {
        value 70;
        tailf:code-name "ENUM_ietf_intf_type_IANA_IFTYPE_CHANNEL";
      }
      enum "iana-iftype-ieee80211" {
        value 71;
        tailf:code-name "ENUM_ietf_intf_type_IANA_IFTYPE_IEEE80211";
      }
      enum "iana-iftype-ibm370parchan" {
        value 72;
        tailf:code-name "ENUM_ietf_intf_type_IANA_IFTYPE_IBM370PARCHAN";
      }
      enum "iana-iftype-escon" {
        value 73;
        tailf:code-name "ENUM_ietf_intf_type_IANA_IFTYPE_ESCON";
      }
      enum "iana-iftype-dlsw" {
        value 74;
        tailf:code-name "ENUM_ietf_intf_type_IANA_IFTYPE_DLSW";
      }
      enum "iana-iftype-isdns" {
        value 75;
        tailf:code-name "ENUM_ietf_intf_type_IANA_IFTYPE_ISDNS";
      }
      enum "iana-iftype-isdnu" {
        value 76;
        tailf:code-name "ENUM_ietf_intf_type_IANA_IFTYPE_ISDNU";
      }
      enum "iana-iftype-lapd" {
        value 77;
        tailf:code-name "ENUM_ietf_intf_type_IANA_IFTYPE_LAPD";
      }
      enum "iana-iftype-ipswitch" {
        value 78;
        tailf:code-name "ENUM_ietf_intf_type_IANA_IFTYPE_IPSWITCH";
      }
      enum "iana-iftype-rsrb" {
        value 79;
        tailf:code-name "ENUM_ietf_intf_type_IANA_IFTYPE_RSRB";
      }
      enum "iana-iftype-atmlogical" {
        value 80;
        tailf:code-name "ENUM_ietf_intf_type_IANA_IFTYPE_ATMLOGICAL";
      }
      enum "iana-iftype-ds0" {
        value 81;
        tailf:code-name "ENUM_ietf_intf_type_IANA_IFTYPE_DS0";
      }
      enum "iana-iftype-ds0bundle" {
        value 82;
        tailf:code-name "ENUM_ietf_intf_type_IANA_IFTYPE_DS0BUNDLE";
      }
      enum "iana-iftype-bsc" {
        value 83;
        tailf:code-name "ENUM_ietf_intf_type_IANA_IFTYPE_BSC";
      }
      enum "iana-iftype-async" {
        value 84;
        tailf:code-name "ENUM_ietf_intf_type_IANA_IFTYPE_ASYNC";
      }
      enum "iana-iftype-cnr" {
        value 85;
        tailf:code-name "ENUM_ietf_intf_type_IANA_IFTYPE_CNR";
      }
      enum "iana-iftype-iso88025-dtr" {
        value 86;
        tailf:code-name "ENUM_ietf_intf_type_IANA_IFTYPE_ISO88025DTR";
      }
      enum "iana-iftype-eplrs" {
        value 87;
        tailf:code-name "ENUM_ietf_intf_type_IANA_IFTYPE_EPLRS";
      }
      enum "iana-iftype-arap" {
        value 88;
        tailf:code-name "ENUM_ietf_intf_type_IANA_IFTYPE_ARAP";
      }
      enum "iana-iftype-propcnls" {
        value 89;
        tailf:code-name "ENUM_ietf_intf_type_IANA_IFTYPE_PROPCNLS";
      }
      enum "iana-iftype-hostpad" {
        value 90;
        tailf:code-name "ENUM_ietf_intf_type_IANA_IFTYPE_HOSTPAD";
      }
      enum "iana-iftype-termpad" {
        value 91;
        tailf:code-name "ENUM_ietf_intf_type_IANA_IFTYPE_TERMPAD";
      }
      enum "iana-iftype-framerelay-mpi" {
        value 92;
        tailf:code-name "ENUM_ietf_intf_type_IANA_IFTYPE_FRAMERELAYMPI";
      }
      enum "iana-iftype-x213" {
        value 93;
        tailf:code-name "ENUM_ietf_intf_type_IANA_IFTYPE_X213";
      }
      enum "iana-iftype-adsl" {
        value 94;
        tailf:code-name "ENUM_ietf_intf_type_IANA_IFTYPE_ADSL";
      }
      enum "iana-iftype-radsl" {
        value 95;
        tailf:code-name "ENUM_ietf_intf_type_IANA_IFTYPE_RADSL";
      }
      enum "iana-iftype-sdsl" {
        value 96;
        tailf:code-name "ENUM_ietf_intf_type_IANA_IFTYPE_SDSL";
      }
      enum "iana-iftype-vdsl" {
        value 97;
        tailf:code-name "ENUM_ietf_intf_type_IANA_IFTYPE_VDSL";
      }
      enum "iana-iftype-iso88025-crfpint" {
        value 98;
        tailf:code-name "ENUM_ietf_intf_type_IANA_IFTYPE_ISO88025CRFPINT";
      }
      enum "iana-iftype-myrinet" {
        value 99;
        tailf:code-name "ENUM_ietf_intf_type_IANA_IFTYPE_MYRINET";
      }
      enum "iana-iftype-voiceem" {
        value 100;
        tailf:code-name "ENUM_ietf_intf_type_IANA_IFTYPE_VOICEEM";
      }
      enum "iana-iftype-voicefxo" {
        value 101;
        tailf:code-name "ENUM_ietf_intf_type_IANA_IFTYPE_VOICEFXO";
      }
      enum "iana-iftype-voicefxs" {
        value 102;
        tailf:code-name "ENUM_ietf_intf_type_IANA_IFTYPE_VOICEFXS";
      }
      enum "iana-iftype-voiceencap" {
        value 103;
        tailf:code-name "ENUM_ietf_intf_type_IANA_IFTYPE_VOICEENCAP";
      }
      enum "iana-iftype-voip" {
        value 104;
        tailf:code-name "ENUM_ietf_intf_type_IANA_IFTYPE_VOICEOVERIP";
      }
      enum "iana-iftype-atmdxi" {
        value 105;
        tailf:code-name "ENUM_ietf_intf_type_IANA_IFTYPE_ATMDXI";
      }
      enum "iana-iftype-atmfuni" {
        value 106;
        tailf:code-name "ENUM_ietf_intf_type_IANA_IFTYPE_ATMFUNI";
      }
      enum "iana-iftype-atmima" {
        value 107;
        tailf:code-name "ENUM_ietf_intf_type_IANA_IFTYPE_ATMIMA";
      }
      enum "iana-iftype-ppp-multilinkbundle" {
        value 108;
        tailf:code-name "ENUM_ietf_intf_type_IANA_IFTYPE_PPPMULTILINKBUNDLE";
      }
      enum "iana-iftype-ipovercdlc" {
        value 109;
        tailf:code-name "ENUM_ietf_intf_type_IANA_IFTYPE_IPOVERCDLC";
      }
      enum "iana-iftype-ipoverclaw" {
        value 110;
        tailf:code-name "ENUM_ietf_intf_type_IANA_IFTYPE_IPOVERCLAW";
      }
      enum "iana-iftype-stack2stack" {
        value 111;
        tailf:code-name "ENUM_ietf_intf_type_IANA_IFTYPE_STACKTOSTACK";
      }
      enum "iana-iftype-virtualipaddress" {
        value 112;
        tailf:code-name "ENUM_ietf_intf_type_IANA_IFTYPE_VIRTUALIPADDRESS";
      }
      enum "iana-iftype-mpc" {
        value 113;
        tailf:code-name "ENUM_ietf_intf_type_IANA_IFTYPE_MPC";
      }
      enum "iana-iftype-ipoveratm" {
        value 114;
        tailf:code-name "ENUM_ietf_intf_type_IANA_IFTYPE_IPOVERATM";
      }
      enum "iana-iftype-iso88025-fiber" {
        value 115;
        tailf:code-name "ENUM_ietf_intf_type_IANA_IFTYPE_ISO88025FIBER";
      }
      enum "iana-iftype-tdlc" {
        value 116;
        tailf:code-name "ENUM_ietf_intf_type_IANA_IFTYPE_TDLC";
      }
      enum "iana-iftype-gige" {
        value 117;
        tailf:code-name "ENUM_ietf_intf_type_IANA_IFTYPE_GIGABITETHERNET";
      }
      enum "iana-iftype-hdlc" {
        value 118;
        tailf:code-name "ENUM_ietf_intf_type_IANA_IFTYPE_HDLC";
      }
      enum "iana-iftype-lapf" {
        value 119;
        tailf:code-name "ENUM_ietf_intf_type_IANA_IFTYPE_LAPF";
      }
      enum "iana-iftype-v37" {
        value 120;
        tailf:code-name "ENUM_ietf_intf_type_IANA_IFTYPE_V37";
      }
      enum "iana-iftype-x25mlp" {
        value 121;
        tailf:code-name "ENUM_ietf_intf_type_IANA_IFTYPE_X25MLP";
      }
      enum "iana-iftype-x25huntgroup" {
        value 122;
        tailf:code-name "ENUM_ietf_intf_type_IANA_IFTYPE_X25HUNTGROUP";
      }
      enum "iana-iftype-transphdlc" {
        value 123;
        tailf:code-name "ENUM_ietf_intf_type_IANA_IFTYPE_TRANSPHDLC";
      }
      enum "iana-iftype-interleave" {
        value 124;
        tailf:code-name "ENUM_ietf_intf_type_IANA_IFTYPE_INTERLEAVE";
      }
      enum "iana-iftype-fast" {
        value 125;
        tailf:code-name "ENUM_ietf_intf_type_IANA_IFTYPE_FAST";
      }
      enum "iana-iftype-ip" {
        value 126;
        tailf:code-name "ENUM_ietf_intf_type_IANA_IFTYPE_IP";
      }
      enum "iana-iftype-docs-cable-maclayer" {
        value 127;
        tailf:code-name "ENUM_ietf_intf_type_IANA_IFTYPE_DOCSCABLEMACLAYER";
      }
      enum "iana-iftype-docs-cable-downstream" {
        value 128;
        tailf:code-name "ENUM_ietf_intf_type_IANA_IFTYPE_DOCSCABLEDOWNSTREAM";
      }
      enum "iana-iftype-docs-cable-upstream" {
        value 129;
        tailf:code-name "ENUM_ietf_intf_type_IANA_IFTYPE_DOCSCABLEUPSTREAM";
      }
      enum "iana-iftype-a12mppswitch" {
        value 130;
        tailf:code-name "ENUM_ietf_intf_type_IANA_IFTYPE_A12MPPSWITCH";
      }
      enum "iana-iftype-tunnel" {
        value 131;
        tailf:code-name "ENUM_ietf_intf_type_IANA_IFTYPE_TUNNEL";
      }
      enum "iana-iftype-coffee" {
        value 132;
        tailf:code-name "ENUM_ietf_intf_type_IANA_IFTYPE_COFFEE";
      }
      enum "iana-iftype-ces" {
        value 133;
        tailf:code-name "ENUM_ietf_intf_type_IANA_IFTYPE_CES";
      }
      enum "iana-iftype-atmsubinterface" {
        value 134;
        tailf:code-name "ENUM_ietf_intf_type_IANA_IFTYPE_ATMSUBINTERFACE";
      }
      enum "iana-iftype-l2vlan" {
        value 135;
        tailf:code-name "ENUM_ietf_intf_type_IANA_IFTYPE_L2VLAN";
      }
      enum "iana-iftype-l3ipvlan" {
        value 136;
        tailf:code-name "ENUM_ietf_intf_type_IANA_IFTYPE_L3IPVLAN";
      }
      enum "iana-iftype-l3ipxvlan" {
        value 137;
        tailf:code-name "ENUM_ietf_intf_type_IANA_IFTYPE_L3IPXVLAN";
      }
      enum "iana-iftype-digital-powerline" {
        value 138;
        tailf:code-name "ENUM_ietf_intf_type_IANA_IFTYPE_DIGITALPOWERLINE";
      }
      enum "iana-iftype-media-mailoverip" {
        value 139;
        tailf:code-name "ENUM_ietf_intf_type_IANA_IFTYPE_MEDIAMAILOVERIP";
      }
      enum "iana-iftype-dtm" {
        value 140;
        tailf:code-name "ENUM_ietf_intf_type_IANA_IFTYPE_DTM";
      }
      enum "iana-iftype-dcn" {
        value 141;
        tailf:code-name "ENUM_ietf_intf_type_IANA_IFTYPE_DCN";
      }
      enum "iana-iftype-ipforward" {
        value 142;
        tailf:code-name "ENUM_ietf_intf_type_IANA_IFTYPE_IPFORWARD";
      }
      enum "iana-iftype-msdsl" {
        value 143;
        tailf:code-name "ENUM_ietf_intf_type_IANA_IFTYPE_MSDSL";
      }
      enum "iana-iftype-ieee1394" {
        value 144;
        tailf:code-name "ENUM_ietf_intf_type_IANA_IFTYPE_IEEE1394";
      }
      enum "iana-iftype-gsn" {
        value 145;
        tailf:code-name "ENUM_ietf_intf_type_IANA_IFTYPE_IF_GSN";
      }
      enum "iana-iftype-dvbrcc-maclayer" {
        value 146;
        tailf:code-name "ENUM_ietf_intf_type_IANA_IFTYPE_DVBRCCMACLAYER";
      }
      enum "iana-iftype-dvbrcc-downstream" {
        value 147;
        tailf:code-name "ENUM_ietf_intf_type_IANA_IFTYPE_DVBRCCDOWNSTREAM";
      }
      enum "iana-iftype-dvbrcc-upstream" {
        value 148;
        tailf:code-name "ENUM_ietf_intf_type_IANA_IFTYPE_DVBRCCUPSTREAM";
      }
      enum "iana-iftype-atmvirtual" {
        value 149;
        tailf:code-name "ENUM_ietf_intf_type_IANA_IFTYPE_ATMVIRTUAL";
      }
      enum "iana-iftype-mplstunnel" {
        value 150;
        tailf:code-name "ENUM_ietf_intf_type_IANA_IFTYPE_MPLSTUNNEL";
      }
      enum "iana-iftype-srp" {
        value 151;
        tailf:code-name "ENUM_ietf_intf_type_IANA_IFTYPE_SRP";
      }
      enum "iana-iftype-voiceoveratm" {
        value 152;
        tailf:code-name "ENUM_ietf_intf_type_IANA_IFTYPE_VOICEOVERATM";
      }
      enum "iana-iftype-voiceoverframerelay" {
        value 153;
        tailf:code-name "ENUM_ietf_intf_type_IANA_IFTYPE_VOICEOVERFRAMERELAY";
      }
      enum "iana-iftype-idsl" {
        value 154;
        tailf:code-name "ENUM_ietf_intf_type_IANA_IFTYPE_IDSL";
      }
      enum "iana-iftype-compositelink" {
        value 155;
        tailf:code-name "ENUM_ietf_intf_type_IANA_IFTYPE_COMPOSITELINK";
      }
      enum "iana-iftype-ss7siglink" {
        value 156;
        tailf:code-name "ENUM_ietf_intf_type_IANA_IFTYPE_SS7SIGLINK";
      }
      enum "iana-iftype-propwireless-p2p" {
        value 157;
        tailf:code-name "ENUM_ietf_intf_type_IANA_IFTYPE_PROPWIRELESSP2P";
      }
      enum "iana-iftype-frforward" {
        value 158;
        tailf:code-name "ENUM_ietf_intf_type_IANA_IFTYPE_FRFORWARD";
      }
      enum "iana-iftype-rfc1483" {
        value 159;
        tailf:code-name "ENUM_ietf_intf_type_IANA_IFTYPE_RFC1483";
      }
      enum "iana-iftype-usb" {
        value 160;
        tailf:code-name "ENUM_ietf_intf_type_IANA_IFTYPE_USB";
      }
      enum "iana-iftype-ieee8023-adlag" {
        value 161;
        tailf:code-name "ENUM_ietf_intf_type_IANA_IFTYPE_IEEE8023ADLAG";
      }
      enum "iana-iftype-bgppolicy-accounting" {
        value 162;
        tailf:code-name "ENUM_ietf_intf_type_IANA_IFTYPE_BGPPOLICYACCOUNTING";
      }
      enum "iana-iftype-frf16mfrbundle" {
        value 163;
        tailf:code-name "ENUM_ietf_intf_type_IANA_IFTYPE_FRF16MFRBUNDLE";
      }
      enum "iana-iftype-h323gatekeeper" {
        value 164;
        tailf:code-name "ENUM_ietf_intf_type_IANA_IFTYPE_H323GATEKEEPER";
      }
      enum "iana-iftype-h323proxy" {
        value 165;
        tailf:code-name "ENUM_ietf_intf_type_IANA_IFTYPE_H323PROXY";
      }
      enum "iana-iftype-mpls" {
        value 166;
        tailf:code-name "ENUM_ietf_intf_type_IANA_IFTYPE_MPLS";
      }
      enum "iana-iftype-mfsiglink" {
        value 167;
        tailf:code-name "ENUM_ietf_intf_type_IANA_IFTYPE_MFSIGLINK";
      }
      enum "iana-iftype-hdsl2" {
        value 168;
        tailf:code-name "ENUM_ietf_intf_type_IANA_IFTYPE_HDSL2";
      }
      enum "iana-iftype-shdsl" {
        value 169;
        tailf:code-name "ENUM_ietf_intf_type_IANA_IFTYPE_SHDSL";
      }
      enum "iana-iftype-ds1fdl" {
        value 170;
        tailf:code-name "ENUM_ietf_intf_type_IANA_IFTYPE_DS1FDL";
      }
      enum "iana-iftype-pos" {
        value 171;
        tailf:code-name "ENUM_ietf_intf_type_IANA_IFTYPE_POS";
      }
      enum "iana-iftype-dvbasiin" {
        value 172;
        tailf:code-name "ENUM_ietf_intf_type_IANA_IFTYPE_DVBASIIN";
      }
      enum "iana-iftype-dvbasiout" {
        value 173;
        tailf:code-name "ENUM_ietf_intf_type_IANA_IFTYPE_DVBASIOUT";
      }
      enum "iana-iftype-plc" {
        value 174;
        tailf:code-name "ENUM_ietf_intf_type_IANA_IFTYPE_PLC";
      }
      enum "iana-iftype-nfas" {
        value 175;
        tailf:code-name "ENUM_ietf_intf_type_IANA_IFTYPE_NFAS";
      }
      enum "iana-iftype-tr008" {
        value 176;
        tailf:code-name "ENUM_ietf_intf_type_IANA_IFTYPE_TR008";
      }
      enum "iana-iftype-gr303rdt" {
        value 177;
        tailf:code-name "ENUM_ietf_intf_type_IANA_IFTYPE_GR303RDT";
      }
      enum "iana-iftype-gr303idt" {
        value 178;
        tailf:code-name "ENUM_ietf_intf_type_IANA_IFTYPE_GR303IDT";
      }
      enum "iana-iftype-isup" {
        value 179;
        tailf:code-name "ENUM_ietf_intf_type_IANA_IFTYPE_ISUP";
      }
      enum "iana-iftype-prop-docs-wireless-maclayer" {
        value 180;
        tailf:code-name "ENUM_ietf_intf_type_IANA_IFTYPE_PROPDOCSWIRELESSMACLAYER";
      }
      enum "iana-iftype-prop-docs-wireless-downstream" {
        value 181;
        tailf:code-name "ENUM_ietf_intf_type_IANA_IFTYPE_PROPDOCSWIRELESSDOWNSTREAM";
      }
      enum "iana-iftype-prop-docs-wireless-upstream" {
        value 182;
        tailf:code-name "ENUM_ietf_intf_type_IANA_IFTYPE_PROPDOCSWIRELESSUPSTREAM";
      }
      enum "iana-iftype-hiperlan2" {
        value 183;
        tailf:code-name "ENUM_ietf_intf_type_IANA_IFTYPE_HIPERLAN2";
      }
      enum "iana-iftype-prop-bwap2mp" {
        value 184;
        tailf:code-name "ENUM_ietf_intf_type_IANA_IFTYPE_PROPBWAP2MP";
      }
      enum "iana-iftype-sonetoverheadchannel" {
        value 185;
        tailf:code-name "ENUM_ietf_intf_type_IANA_IFTYPE_SONETOVERHEADCHANNEL";
      }
      enum "iana-iftype-digital-wrapperoverheadchannel" {
        value 186;
        tailf:code-name "ENUM_ietf_intf_type_IANA_IFTYPE_DIGITALWRAPPEROVERHEADCHANNEL";
      }
      enum "iana-iftype-aal2" {
        value 187;
        tailf:code-name "ENUM_ietf_intf_type_IANA_IFTYPE_AAL2";
      }
      enum "iana-iftype-radiomac" {
        value 188;
        tailf:code-name "ENUM_ietf_intf_type_IANA_IFTYPE_RADIOMAC";
      }
      enum "iana-iftype-atmradio" {
        value 189;
        tailf:code-name "ENUM_ietf_intf_type_IANA_IFTYPE_ATMRADIO";
      }
      enum "iana-iftype-imt" {
        value 190;
        tailf:code-name "ENUM_ietf_intf_type_IANA_IFTYPE_IMT";
      }
      enum "iana-iftype-mvl" {
        value 191;
        tailf:code-name "ENUM_ietf_intf_type_IANA_IFTYPE_MVL";
      }
      enum "iana-iftype-reachhdsl" {
        value 192;
        tailf:code-name "ENUM_ietf_intf_type_IANA_IFTYPE_REACHDSL";
      }
      enum "iana-iftype-frdlciendpt" {
        value 193;
        tailf:code-name "ENUM_ietf_intf_type_IANA_IFTYPE_FRDLCIENDPT";
      }
      enum "iana-iftype-atmvciendpt" {
        value 194;
        tailf:code-name "ENUM_ietf_intf_type_IANA_IFTYPE_ATMVCIENDPT";
      }
      enum "iana-iftype-opticalchannel" {
        value 195;
        tailf:code-name "ENUM_ietf_intf_type_IANA_IFTYPE_OPTICALCHANNEL";
      }
      enum "iana-iftype-opticaltransport" {
        value 196;
        tailf:code-name "ENUM_ietf_intf_type_IANA_IFTYPE_OPTICALTRANSPORT";
      }
      enum "iana-iftype-propatm" {
        value 197;
        tailf:code-name "ENUM_ietf_intf_type_IANA_IFTYPE_PROPATM";
      }
      enum "iana-iftype-voiceovercable" {
        value 198;
        tailf:code-name "ENUM_ietf_intf_type_IANA_IFTYPE_VOICEOVERCABLE";
      }
      enum "iana-iftype-infiniband" {
        value 199;
        tailf:code-name "ENUM_ietf_intf_type_IANA_IFTYPE_INFINIBAND";
      }
      enum "iana-iftype-telink" {
        value 200;
        tailf:code-name "ENUM_ietf_intf_type_IANA_IFTYPE_TELINK";
      }
      enum "iana-iftype-q2931" {
        value 201;
        tailf:code-name "ENUM_ietf_intf_type_IANA_IFTYPE_Q2931";
      }
      enum "iana-iftype-virtualatg" {
        value 202;
        tailf:code-name "ENUM_ietf_intf_type_IANA_IFTYPE_VIRTUALTG";
      }
      enum "iana-iftype-siptg" {
        value 203;
        tailf:code-name "ENUM_ietf_intf_type_IANA_IFTYPE_SIPTG";
      }
      enum "iana-iftype-sipsig" {
        value 204;
        tailf:code-name "ENUM_ietf_intf_type_IANA_IFTYPE_SIPSIG";
      }
      enum "iana-iftype-docs-cable-upstreamchannel" {
        value 205;
        tailf:code-name "ENUM_ietf_intf_type_IANA_IFTYPE_DOCSCABLEUPSTREAMCHANNEL";
      }
      enum "iana-iftype-econet" {
        value 206;
        tailf:code-name "ENUM_ietf_intf_type_IANA_IFTYPE_ECONET";
      }
      enum "iana-iftype-pon155" {
        value 207;
        tailf:code-name "ENUM_ietf_intf_type_IANA_IFTYPE_PON155";
      }
      enum "iana-iftype-pon622" {
        value 208;
        tailf:code-name "ENUM_ietf_intf_type_IANA_IFTYPE_PON622";
      }
      enum "iana-iftype-bridge-if" {
        value 209;
        tailf:code-name "ENUM_ietf_intf_type_IANA_IFTYPE_BRIDGE_IF";
      }
      enum "iana-iftype-linegroup" {
        value 210;
        tailf:code-name "ENUM_ietf_intf_type_IANA_IFTYPE_LINEGROUP";
      }
      enum "iana-iftype-voiceemfgd" {
        value 211;
        tailf:code-name "ENUM_ietf_intf_type_IANA_IFTYPE_VOICEEMFGD";
      }
      enum "iana-iftype-voiceefgdeana" {
        value 212;
        tailf:code-name "ENUM_ietf_intf_type_IANA_IFTYPE_VOICEFGDEANA";
      }
      enum "iana-iftype-voicedid" {
        value 213;
        tailf:code-name "ENUM_ietf_intf_type_IANA_IFTYPE_VOICEDID";
      }
      enum "iana-iftype-mpegtransport" {
        value 214;
        tailf:code-name "ENUM_ietf_intf_type_IANA_IFTYPE_MPEGTRANSPORT";
      }
      enum "iana-iftype-sixtofour" {
        value 215;
        tailf:code-name "ENUM_ietf_intf_type_IANA_IFTYPE_SIXTOFOUR";
      }
      enum "iana-iftype-gtp" {
        value 216;
        tailf:code-name "ENUM_ietf_intf_type_IANA_IFTYPE_GTP";
      }
      enum "iana-iftype-pdnetherloop1" {
        value 217;
        tailf:code-name "ENUM_ietf_intf_type_IANA_IFTYPE_PDNETHERLOOP1";
      }
      enum "iana-iftype-pdnetherloop2" {
        value 218;
        tailf:code-name "ENUM_ietf_intf_type_IANA_IFTYPE_PDNETHERLOOP2";
      }
      enum "iana-iftype-opticalchannel-group" {
        value 219;
        tailf:code-name "ENUM_ietf_intf_type_IANA_IFTYPE_OPTICALCHANNELGROUP";
      }
      enum "iana-iftype-homepna" {
        value 220;
        tailf:code-name "ENUM_ietf_intf_type_IANA_IFTYPE_HOMEPNA";
      }
      enum "iana-iftype-gfp" {
        value 221;
        tailf:code-name "ENUM_ietf_intf_type_IANA_IFTYPE_GFP";
      }
      enum "iana-iftype-ciscoislvlan" {
        value 222;
        tailf:code-name "ENUM_ietf_intf_type_IANA_IFTYPE_CISCOISLVLAN";
      }
      enum "iana-iftype-actelismetaloop" {
        value 223;
        tailf:code-name "ENUM_ietf_intf_type_IANA_IFTYPE_ACTELISMETALOOP";
      }
      enum "iana-iftype-fciplink" {
        value 224;
        tailf:code-name "ENUM_ietf_intf_type_IANA_IFTYPE_FCIPLINK";
      }
      enum "iana-iftype-rpr" {
        value 225;
        tailf:code-name "ENUM_ietf_intf_type_IANA_IFTYPE_RPR";
      }
      enum "iana-iftype-qam" {
        value 226;
        tailf:code-name "ENUM_ietf_intf_type_IANA_IFTYPE_QAM";
      }
      enum "iana-iftype-lmp" {
        value 227;
        tailf:code-name "ENUM_ietf_intf_type_IANA_IFTYPE_LMP";
      }
      enum "iana-iftype-cblvectastar" {
        value 228;
        tailf:code-name "ENUM_ietf_intf_type_IANA_IFTYPE_CBLVECTASTAR";
      }
      enum "iana-iftype-docs-cable-mcmts-downtream" {
        value 229;
        tailf:code-name "ENUM_ietf_intf_type_IANA_IFTYPE_DOCSCABLEMCMTSDOWNSTREAM";
      }
      enum "iana-iftype-adsl2" {
        value 230;
        tailf:code-name "ENUM_ietf_intf_type_IANA_IFTYPE_ADSL2";
      }
      enum "iana-iftype-macseccontrolledif" {
        value 231;
        tailf:code-name "ENUM_ietf_intf_type_IANA_IFTYPE_MACSECCONTROLLEDIF";
      }
      enum "iana-iftype-macsecuncontrolledif" {
        value 232;
        tailf:code-name "ENUM_ietf_intf_type_IANA_IFTYPE_MACSECUNCONTROLLEDIF";
      }
      enum "iana-iftype-aviciopticalether" {
        value 233;
        tailf:code-name "ENUM_ietf_intf_type_IANA_IFTYPE_AVICIOPTICALETHER";
      }
      enum "iana-iftype-atmbond" {
        value 234;
        tailf:code-name "ENUM_ietf_intf_type_IANA_IFTYPE_ATMBOND";
      }
      enum "iana-iftype-voicefgdos" {
        value 235;
        tailf:code-name "ENUM_ietf_intf_type_IANA_IFTYPE_VOICEFGDOS";
      }
      enum "iana-iftype-mocaversion1" {
        value 236;
        tailf:code-name "ENUM_ietf_intf_type_IANA_IFTYPE_MOCAVERSION1";
      }
      enum "iana-iftype-ieee80216-wman" {
        value 237;
        tailf:code-name "ENUM_ietf_intf_type_IANA_IFTYPE_IEEE80216WMAN";
      }
      enum "iana-iftype-adsl2plus" {
        value 238;
        tailf:code-name "ENUM_ietf_intf_type_IANA_IFTYPE_ADSL2PLUS";
      }
      enum "iana-iftype-dvbrcsmaclayer" {
        value 239;
        tailf:code-name "ENUM_ietf_intf_type_IANA_IFTYPE_DVBRCSMACLAYER";
      }
      enum "iana-iftype-dvbtdm" {
        value 240;
        tailf:code-name "ENUM_ietf_intf_type_IANA_IFTYPE_DVBTDM";
      }
      enum "iana-iftype-dvbrcstdma" {
        value 241;
        tailf:code-name "ENUM_ietf_intf_type_IANA_IFTYPE_DVBRCSTDMA";
      }
      enum "iana-iftype-x86laps" {
        value 242;
        tailf:code-name "ENUM_ietf_intf_type_IANA_IFTYPE_X86LAPS";
      }
      enum "iana-iftype-wwanpp" {
        value 243;
        tailf:code-name "ENUM_ietf_intf_type_IANA_IFTYPE_WWANPP";
      }
      enum "iana-iftype-wwanpp2" {
        value 244;
        tailf:code-name "ENUM_ietf_intf_type_IANA_IFTYPE_WWANPP2";
      }
      enum "iana-iftype-voiceebs" {
        value 245;
        tailf:code-name "ENUM_ietf_intf_type_IANA_IFTYPE_VOICEEBS";
      }
      enum "iana-iftype-ifpwtype" {
        value 246;
        tailf:code-name "ENUM_ietf_intf_type_IANA_IFTYPE_IFPWTYPE";
      }
      enum "iana-iftype-ilan" {
        value 247;
        tailf:code-name "ENUM_ietf_intf_type_IANA_IFTYPE_ILAN";
      }
      enum "iana-iftype-pip" {
        value 248;
        tailf:code-name "ENUM_ietf_intf_type_IANA_IFTYPE_PIP";
      }
      enum "iana-iftype-aluelp" {
        value 249;
        tailf:code-name "ENUM_ietf_intf_type_IANA_IFTYPE_ALUELP";
      }
      enum "iana-iftype-gpon" {
        value 250;
        tailf:code-name "ENUM_ietf_intf_type_IANA_IFTYPE_GPON";
      }
      enum "iana-iftype-vdsl2" {
        value 251;
        tailf:code-name "ENUM_ietf_intf_type_IANA_IFTYPE_VDSL2";
      }
      enum "iana-iftype-capwapdot11-profile" {
        value 252;
        tailf:code-name "ENUM_ietf_intf_type_IANA_IFTYPE_CAPWAPDOT11PROFILE";
      }
      enum "iana-iftype-capwapdot11-bss" {
        value 253;
        tailf:code-name "ENUM_ietf_intf_type_IANA_IFTYPE_CAPWAPDOT11BSS";
      }
      enum "iana-iftype-capwapwtp-virtualradio" {
        value 254;
        tailf:code-name "ENUM_ietf_intf_type_IANA_IFTYPE_CAPWAPWTPVIRTUALRADIO";
      }
      enum "iana-iftype-bits" {
        value 255;
        tailf:code-name "ENUM_ietf_intf_type_IANA_IFTYPE_BITS";
      }
      enum "iana-iftype-docs-cable-upstreamrfport" {
        value 256;
        tailf:code-name "ENUM_ietf_intf_type_IANA_IFTYPE_DOCSCABLEUPSTREAMRFPORT";
      }
      enum "iana-iftype-cable-downstreamrfport" {
        value 257;
        tailf:code-name "ENUM_ietf_intf_type_IANA_IFTYPE_CABLEDOWNSTREAMRFPORT";
      }
      enum "iana-iftype-vmware-virtualnic" {
        value 258;
        tailf:code-name "ENUM_ietf_intf_type_IANA_IFTYPE_VMWAREVIRTUALNIC";
      }
      enum "iana-iftype-ieee802154" {
        value 259;
        tailf:code-name "ENUM_ietf_intf_type_IANA_IFTYPE_IEEE802154";
      }
      enum "iana-iftype-otnodu" {
        value 260;
        tailf:code-name "ENUM_ietf_intf_type_IANA_IFTYPE_OTNODU";
      }
      enum "iana-iftype-otnotu" {
        value 261;
        tailf:code-name "ENUM_ietf_intf_type_IANA_IFTYPE_OTNOTU";
      }
      enum "iana-iftype-ifvfitype" {
        value 262;
        tailf:code-name "ENUM_ietf_intf_type_IANA_IFTYPE_IFVFITYPE";
      }
      enum "iana-iftype-g9981" {
        value 263;
        tailf:code-name "ENUM_ietf_intf_type_IANA_IFTYPE_G9981";
      }
      enum "iana-iftype-g9982" {
        value 264;
        tailf:code-name "ENUM_ietf_intf_type_IANA_IFTYPE_G9982";
      }
      enum "iana-iftype-g9983" {
        value 265;
        tailf:code-name "ENUM_ietf_intf_type_IANA_IFTYPE_G9983";
      }
      enum "iana-iftype-aluepon" {
        value 266;
        tailf:code-name "ENUM_ietf_intf_type_IANA_IFTYPE_ALUEPON";
      }
      enum "iana-iftype-aluepon-onu" {
        value 267;
        tailf:code-name "ENUM_ietf_intf_type_IANA_IFTYPE_ALUEPONONU";
      }
      enum "iana-iftype-aluepon-physicaluni" {
        value 268;
        tailf:code-name "ENUM_ietf_intf_type_IANA_IFTYPE_ALUEPONPHYSICALUNI";
      }
      enum "iana-iftype-aluepon-logicalink" {
        value 269;
        tailf:code-name "ENUM_ietf_intf_type_IANA_IFTYPE_ALUEPONLOGICALLINK";
      }
      enum "iana-iftype-alugpon-onu" {
        value 270;
        tailf:code-name "ENUM_ietf_intf_type_IANA_IFTYPE_ALUGPONONU";
      }
      enum "iana-iftype-alugpon-physicaluni" {
        value 271;
        tailf:code-name "ENUM_ietf_intf_type_IANA_IFTYPE_ALUGPONPHYSICALUNI";
      }
      enum "iana-iftype-vmwarenicteam" {
        value 272;
        tailf:code-name "ENUM_ietf_intf_type_IANA_IFTYPE_VMWARENICTEAM";
      }
      enum "iana-iftype-docs-ofdm-downstream" {
        value 277;
        tailf:code-name "ENUM_ietf_intf_type_IANA_IFTYPE_DOCSOFDMDOWNSTREAM";
      }
      enum "iana-iftype-docs-ofdma-upstream" {
        value 278;
        tailf:code-name "ENUM_ietf_intf_type_IANA_IFTYPE_DOCSOFDMAUPSTREAM";
      }
      enum "iana-iftype-gfast" {
        value 279;
        tailf:code-name "ENUM_ietf_intf_type_IANA_IFTYPE_GFAST";
      }
      enum "iana-iftype-sdci" {
        value 280;
        tailf:code-name "ENUM_ietf_intf_type_IANA_IFTYPE_SDCI";
      }
      enum "iana-iftype-xbox-wireless" {
        value 281;
        tailf:code-name "ENUM_ietf_intf_type_IANA_IFTYPE_XBOXWIRELESS";
      }
      enum "iana-iftype-fastdsl" {
        value 282;
        tailf:code-name "ENUM_ietf_intf_type_IANA_IFTYPE_FASTDSL";
      }
    }
    description
      "IANAifType
       This data type is used as the syntax of the ifType
       object in the (updated) definition of MIB-II's ifTable";
  }

  typedef interface-class {
    type enumeration {
      enum "interface-class-ethernet" {
        value 0;
        tailf:code-name "ENUM_intf_class_INTF_CLASS_ETHERNET";
      }
      enum "interface-class-t1e1serial" {
        value 1;
        tailf:code-name "ENUM_intf_class_INTF_CLASS_T1E1SERIAL";
      }
      enum "interface-class-unspecified" {
        value 2;
        tailf:code-name "ENUM_intf_class_INTF_CLASS_UNSPECIFIED";
      }
      enum "interface-class-syncserial" {
        value 3;
        tailf:code-name "ENUM_intf_class_INTF_CLASS_SYNCSERIAL";
      }
    }
    description
      "The broad class that this interface belongs to";
    tailf:info "externally-removed";
  }

  typedef media-type-class {
    type enumeration {
      enum "ether-media-type-none" {
        value 0;
        tailf:code-name "ENUM_media_type_class_ETHER_MEDIA_NONE";
      }
      enum "ether-media-type-aui" {
        value 1;
        tailf:code-name "ENUM_media_type_class_ETHER_MEDIA_AUI";
      }
      enum "ether-media-type-10baset" {
        value 2;
        tailf:code-name "ENUM_media_type_class_ETHER_MEDIA_10BASET";
      }
      enum "ether-media-type-nothing-here" {
        value 3;
        tailf:code-name "ENUM_media_type_class_ETHER_MEDIA_NOTHING_HERE";
      }
      enum "ether-media-type-rj45" {
        value 4;
        tailf:code-name "ENUM_media_type_class_ETHER_MEDIA_RJ45";
      }
      enum "ether-media-type-mii" {
        value 5;
        tailf:code-name "ENUM_media_type_class_ETHER_MEDIA_MII";
      }
      enum "ether-media-type-auto-select" {
        value 6;
        tailf:code-name "ENUM_media_type_class_ETHER_MEDIA_AUTO_SELECT";
      }
      enum "ether-media-type-epif-utp" {
        value 7;
        tailf:code-name "ENUM_media_type_class_ETHER_MEDIA_EPIF_UTP";
      }
      enum "ether-media-type-epif-fx" {
        value 8;
        tailf:code-name "ENUM_media_type_class_ETHER_MEDIA_EPIF_FX";
      }
      enum "ether-media-type-gpif-lx" {
        value 9;
        tailf:code-name "ENUM_media_type_class_ETHER_MEDIA_GPIF_LX";
      }
      enum "ether-media-type-gpif-sx" {
        value 10;
        tailf:code-name "ENUM_media_type_class_ETHER_MEDIA_GPIF_SX";
      }
      enum "ether-media-type-parallel" {
        value 11;
        tailf:code-name "ENUM_media_type_class_ETHER_MEDIA_PARALLEL";
      }
      enum "ether-media-type-serial10km" {
        value 12;
        tailf:code-name "ENUM_media_type_class_ETHER_MEDIA_SERIAL10KM";
      }
      enum "ether-media-type-vsr300m" {
        value 13;
        tailf:code-name "ENUM_media_type_class_ETHER_MEDIA_VSR300M";
      }
      enum "ether-media-type-metrowdm50km" {
        value 14;
        tailf:code-name "ENUM_media_type_class_ETHER_MEDIA_METROWDM50KM";
      }
      enum "ether-media-type-not-connected" {
        value 15;
        tailf:code-name "ENUM_media_type_class_ETHER_MEDIA_NOT_CONNECTED";
      }
      enum "ether-media-type-port-missing" {
        value 16;
        tailf:code-name "ENUM_media_type_class_ETHER_MEDIA_PORT_MISSING";
      }
      enum "ether-media-type-gbic-missing" {
        value 17;
        tailf:code-name "ENUM_media_type_class_ETHER_MEDIA_GBIC_MISSING";
      }
      enum "ether-media-type-feip-mmf-st" {
        value 18;
        tailf:code-name "ENUM_media_type_class_ETHER_MEDIA_FEIP_MMF_ST";
      }
      enum "ether-media-type-feip-mmf-sc" {
        value 19;
        tailf:code-name "ENUM_media_type_class_ETHER_MEDIA_FEIP_MMF_SC";
      }
      enum "ether-media-type-1000basecx-gigstack" {
        value 20;
        tailf:code-name "ENUM_media_type_class_ETHER_MEDIA_1000BASECX_GIGSTACK";
      }
      enum "ether-media-type-serial40km" {
        value 21;
        tailf:code-name "ENUM_media_type_class_ETHER_MEDIA_SERIAL40KM";
      }
      enum "ether-media-type-serial50km" {
        value 22;
        tailf:code-name "ENUM_media_type_class_ETHER_MEDIA_SERIAL50KM";
      }
      enum "ether-media-type-unapproved" {
        value 23;
        tailf:code-name "ENUM_media_type_class_ETHER_MEDIA_UNAPPROVED";
      }
      enum "ether-media-type-unsupported" {
        value 24;
        tailf:code-name "ENUM_media_type_class_ETHER_MEDIA_UNSUPPORTED";
      }
      enum "ether-media-type-bad-eeprom" {
        value 25;
        tailf:code-name "ENUM_media_type_class_ETHER_MEDIA_BAD_EEPROM";
      }
      enum "ether-media-type-gbic" {
        value 26;
        tailf:code-name "ENUM_media_type_class_ETHER_MEDIA_GBIC";
      }
      enum "ether-media-type-sfp" {
        value 27;
        tailf:code-name "ENUM_media_type_class_ETHER_MEDIA_SFP";
      }
      enum "ether-media-type-xenpak" {
        value 28;
        tailf:code-name "ENUM_media_type_class_ETHER_MEDIA_XENPAK";
      }
      enum "ether-media-type-100base-fx" {
        value 29;
        tailf:code-name "ENUM_media_type_class_ETHER_MEDIA_100BASE_FX";
      }
      enum "ether-media-type-100base-tx" {
        value 30;
        tailf:code-name "ENUM_media_type_class_ETHER_MEDIA_100BASE_TX";
      }
      enum "ether-media-type-rj21" {
        value 31;
        tailf:code-name "ENUM_media_type_class_ETHER_MEDIA_RJ21";
      }
      enum "ether-media-type-100mtrj-fx" {
        value 32;
        tailf:code-name "ENUM_media_type_class_ETHER_MEDIA_100MTRJ_FX";
      }
      enum "ether-media-type-100mtrj-lx" {
        value 33;
        tailf:code-name "ENUM_media_type_class_ETHER_MEDIA_100MTRJ_LX";
      }
      enum "ether-media-type-internal" {
        value 34;
        tailf:code-name "ENUM_media_type_class_ETHER_MEDIA_INTERNAL";
      }
      enum "ether-media-type-1000baset" {
        value 35;
        tailf:code-name "ENUM_media_type_class_ETHER_MEDIA_1000BASET";
      }
      enum "ether-media-type-gpif-zx" {
        value 36;
        tailf:code-name "ENUM_media_type_class_ETHER_MEDIA_GPIF_ZX";
      }
      enum "ether-media-type-1000base-cwdm-1470" {
        value 37;
        tailf:code-name "ENUM_media_type_class_ETHER_MEDIA_1000BASE_CWDM_1470";
      }
      enum "ether-media-type-1000base-cwdm-1490" {
        value 38;
        tailf:code-name "ENUM_media_type_class_ETHER_MEDIA_1000BASE_CWDM_1490";
      }
      enum "ether-media-type-1000base-cwdm-1510" {
        value 39;
        tailf:code-name "ENUM_media_type_class_ETHER_MEDIA_1000BASE_CWDM_1510";
      }
      enum "ether-media-type-1000base-cwdm-1530" {
        value 40;
        tailf:code-name "ENUM_media_type_class_ETHER_MEDIA_1000BASE_CWDM_1530";
      }
      enum "ether-media-type-1000base-cwdm-1550" {
        value 41;
        tailf:code-name "ENUM_media_type_class_ETHER_MEDIA_1000BASE_CWDM_1550";
      }
      enum "ether-media-type-1000base-cwdm-1570" {
        value 42;
        tailf:code-name "ENUM_media_type_class_ETHER_MEDIA_1000BASE_CWDM_1570";
      }
      enum "ether-media-type-1000base-cwdm-1590" {
        value 43;
        tailf:code-name "ENUM_media_type_class_ETHER_MEDIA_1000BASE_CWDM_1590";
      }
      enum "ether-media-type-1000base-cwdm-1610" {
        value 44;
        tailf:code-name "ENUM_media_type_class_ETHER_MEDIA_1000BASE_CWDM_1610";
      }
      enum "ether-media-type-1000base-dwdm-6061" {
        value 45;
        tailf:code-name "ENUM_media_type_class_ETHER_MEDIA_1000BASE_DWDM_6061";
      }
      enum "ether-media-type-1000base-dwdm-5979" {
        value 46;
        tailf:code-name "ENUM_media_type_class_ETHER_MEDIA_1000BASE_DWDM_5979";
      }
      enum "ether-media-type-1000base-dwdm-5898" {
        value 47;
        tailf:code-name "ENUM_media_type_class_ETHER_MEDIA_1000BASE_DWDM_5898";
      }
      enum "ether-media-type-1000base-dwdm-5817" {
        value 48;
        tailf:code-name "ENUM_media_type_class_ETHER_MEDIA_1000BASE_DWDM_5817";
      }
      enum "ether-media-type-1000base-dwdm-5655" {
        value 49;
        tailf:code-name "ENUM_media_type_class_ETHER_MEDIA_1000BASE_DWDM_5655";
      }
      enum "ether-media-type-1000base-dwdm-5575" {
        value 50;
        tailf:code-name "ENUM_media_type_class_ETHER_MEDIA_1000BASE_DWDM_5575";
      }
      enum "ether-media-type-1000base-dwdm-5494" {
        value 51;
        tailf:code-name "ENUM_media_type_class_ETHER_MEDIA_1000BASE_DWDM_5494";
      }
      enum "ether-media-type-1000base-dwdm-5413" {
        value 52;
        tailf:code-name "ENUM_media_type_class_ETHER_MEDIA_1000BASE_DWDM_5413";
      }
      enum "ether-media-type-1000base-dwdm-5252" {
        value 53;
        tailf:code-name "ENUM_media_type_class_ETHER_MEDIA_1000BASE_DWDM_5252";
      }
      enum "ether-media-type-1000base-dwdm-5172" {
        value 54;
        tailf:code-name "ENUM_media_type_class_ETHER_MEDIA_1000BASE_DWDM_5172";
      }
      enum "ether-media-type-1000base-dwdm-5092" {
        value 55;
        tailf:code-name "ENUM_media_type_class_ETHER_MEDIA_1000BASE_DWDM_5092";
      }
      enum "ether-media-type-1000base-dwdm-5012" {
        value 56;
        tailf:code-name "ENUM_media_type_class_ETHER_MEDIA_1000BASE_DWDM_5012";
      }
      enum "ether-media-type-1000base-dwdm-4851" {
        value 57;
        tailf:code-name "ENUM_media_type_class_ETHER_MEDIA_1000BASE_DWDM_4851";
      }
      enum "ether-media-type-1000base-dwdm-4772" {
        value 58;
        tailf:code-name "ENUM_media_type_class_ETHER_MEDIA_1000BASE_DWDM_4772";
      }
      enum "ether-media-type-1000base-dwdm-4692" {
        value 59;
        tailf:code-name "ENUM_media_type_class_ETHER_MEDIA_1000BASE_DWDM_4692";
      }
      enum "ether-media-type-1000base-dwdm-4612" {
        value 60;
        tailf:code-name "ENUM_media_type_class_ETHER_MEDIA_1000BASE_DWDM_4612";
      }
      enum "ether-media-type-1000base-dwdm-4453" {
        value 61;
        tailf:code-name "ENUM_media_type_class_ETHER_MEDIA_1000BASE_DWDM_4453";
      }
      enum "ether-media-type-1000base-dwdm-4373" {
        value 62;
        tailf:code-name "ENUM_media_type_class_ETHER_MEDIA_1000BASE_DWDM_4373";
      }
      enum "ether-media-type-1000base-dwdm-4294" {
        value 63;
        tailf:code-name "ENUM_media_type_class_ETHER_MEDIA_1000BASE_DWDM_4294";
      }
      enum "ether-media-type-1000base-dwdm-4214" {
        value 64;
        tailf:code-name "ENUM_media_type_class_ETHER_MEDIA_1000BASE_DWDM_4214";
      }
      enum "ether-media-type-1000base-dwdm-4056" {
        value 65;
        tailf:code-name "ENUM_media_type_class_ETHER_MEDIA_1000BASE_DWDM_4056";
      }
      enum "ether-media-type-1000base-dwdm-3977" {
        value 66;
        tailf:code-name "ENUM_media_type_class_ETHER_MEDIA_1000BASE_DWDM_3977";
      }
      enum "ether-media-type-1000base-dwdm-3898" {
        value 67;
        tailf:code-name "ENUM_media_type_class_ETHER_MEDIA_1000BASE_DWDM_3898";
      }
      enum "ether-media-type-1000base-dwdm-3819" {
        value 68;
        tailf:code-name "ENUM_media_type_class_ETHER_MEDIA_1000BASE_DWDM_3819";
      }
      enum "ether-media-type-1000base-dwdm-3661" {
        value 69;
        tailf:code-name "ENUM_media_type_class_ETHER_MEDIA_1000BASE_DWDM_3661";
      }
      enum "ether-media-type-1000base-dwdm-3582" {
        value 70;
        tailf:code-name "ENUM_media_type_class_ETHER_MEDIA_1000BASE_DWDM_3582";
      }
      enum "ether-media-type-1000base-dwdm-3504" {
        value 71;
        tailf:code-name "ENUM_media_type_class_ETHER_MEDIA_1000BASE_DWDM_3504";
      }
      enum "ether-media-type-1000base-dwdm-3425" {
        value 72;
        tailf:code-name "ENUM_media_type_class_ETHER_MEDIA_1000BASE_DWDM_3425";
      }
      enum "ether-media-type-1000base-dwdm-3268" {
        value 73;
        tailf:code-name "ENUM_media_type_class_ETHER_MEDIA_1000BASE_DWDM_3268";
      }
      enum "ether-media-type-1000base-dwdm-3190" {
        value 74;
        tailf:code-name "ENUM_media_type_class_ETHER_MEDIA_1000BASE_DWDM_3190";
      }
      enum "ether-media-type-1000base-dwdm-3112" {
        value 75;
        tailf:code-name "ENUM_media_type_class_ETHER_MEDIA_1000BASE_DWDM_3112";
      }
      enum "ether-media-type-1000base-dwdm-3033" {
        value 76;
        tailf:code-name "ENUM_media_type_class_ETHER_MEDIA_1000BASE_DWDM_3033";
      }
      enum "ether-media-type-1000base-dwdm-6141" {
        value 77;
        tailf:code-name "ENUM_media_type_class_ETHER_MEDIA_1000BASE_DWDM_6141";
      }
      enum "ether-media-type-1000base-dwdm-5736" {
        value 78;
        tailf:code-name "ENUM_media_type_class_ETHER_MEDIA_1000BASE_DWDM_5736";
      }
      enum "ether-media-type-1000base-dwdm-5332" {
        value 79;
        tailf:code-name "ENUM_media_type_class_ETHER_MEDIA_1000BASE_DWDM_5332";
      }
      enum "ether-media-type-1000base-dwdm-4931" {
        value 80;
        tailf:code-name "ENUM_media_type_class_ETHER_MEDIA_1000BASE_DWDM_4931";
      }
      enum "ether-media-type-1000base-dwdm-4532" {
        value 81;
        tailf:code-name "ENUM_media_type_class_ETHER_MEDIA_1000BASE_DWDM_4532";
      }
      enum "ether-media-type-1000base-dwdm-4134" {
        value 82;
        tailf:code-name "ENUM_media_type_class_ETHER_MEDIA_1000BASE_DWDM_4134";
      }
      enum "ether-media-type-1000base-dwdm-3739" {
        value 83;
        tailf:code-name "ENUM_media_type_class_ETHER_MEDIA_1000BASE_DWDM_3739";
      }
      enum "ether-media-type-1000base-dwdm-3346" {
        value 84;
        tailf:code-name "ENUM_media_type_class_ETHER_MEDIA_1000BASE_DWDM_3346";
      }
      enum "ether-media-type-unknown" {
        value 85;
        tailf:code-name "ENUM_media_type_class_ETHER_MEDIA_UNKNOWN";
      }
      enum "ether-media-type-1000base-bx10u" {
        value 86;
        tailf:code-name "ENUM_media_type_class_ETHER_MEDIA_1000BASE_BX10U";
      }
      enum "ether-media-type-1000base-bx10d" {
        value 87;
        tailf:code-name "ENUM_media_type_class_ETHER_MEDIA_1000BASE_BX10D";
      }
      enum "ether-media-type-1000base-tdwdm" {
        value 88;
        tailf:code-name "ENUM_media_type_class_ETHER_MEDIA_1000BASE_TDWDM";
      }
      enum "ether-media-type-10gbase-sr" {
        value 89;
        tailf:code-name "ENUM_media_type_class_ETHER_MEDIA_10GBASE_SR";
      }
      enum "ether-media-type-10gbase-sr-sw" {
        value 90;
        tailf:code-name "ENUM_media_type_class_ETHER_MEDIA_10GBASE_SR_SW";
      }
      enum "ether-media-type-sfp-plus" {
        value 91;
        tailf:code-name "ENUM_media_type_class_ETHER_MEDIA_SFP_PLUS";
      }
      enum "ether-media-type-gpif-ex" {
        value 92;
        tailf:code-name "ENUM_media_type_class_ETHER_MEDIA_GPIF_EX";
      }
      enum "ether-media-type-100base-bx10u" {
        value 93;
        tailf:code-name "ENUM_media_type_class_ETHER_MEDIA_100BASE_BX10U";
      }
      enum "ether-media-type-100base-bx10d" {
        value 94;
        tailf:code-name "ENUM_media_type_class_ETHER_MEDIA_100BASE_BX10D";
      }
      enum "ether-media-type-10gbase-dwdm-3033" {
        value 95;
        tailf:code-name "ENUM_media_type_class_ETHER_MEDIA_10GBASE_DWDM_3033";
      }
      enum "ether-media-type-10gbase-dwdm-3112" {
        value 96;
        tailf:code-name "ENUM_media_type_class_ETHER_MEDIA_10GBASE_DWDM_3112";
      }
      enum "ether-media-type-10gbase-dwdm-3190" {
        value 97;
        tailf:code-name "ENUM_media_type_class_ETHER_MEDIA_10GBASE_DWDM_3190";
      }
      enum "ether-media-type-10gbase-dwdm-3268" {
        value 98;
        tailf:code-name "ENUM_media_type_class_ETHER_MEDIA_10GBASE_DWDM_3268";
      }
      enum "ether-media-type-10gbase-dwdm-3425" {
        value 99;
        tailf:code-name "ENUM_media_type_class_ETHER_MEDIA_10GBASE_DWDM_3425";
      }
      enum "ether-media-type-10gbase-dwdm-3504" {
        value 100;
        tailf:code-name "ENUM_media_type_class_ETHER_MEDIA_10GBASE_DWDM_3504";
      }
      enum "ether-media-type-10gbase-dwdm-3582" {
        value 101;
        tailf:code-name "ENUM_media_type_class_ETHER_MEDIA_10GBASE_DWDM_3582";
      }
      enum "ether-media-type-10gbase-dwdm-3661" {
        value 102;
        tailf:code-name "ENUM_media_type_class_ETHER_MEDIA_10GBASE_DWDM_3661";
      }
      enum "ether-media-type-10gbase-dwdm-3819" {
        value 103;
        tailf:code-name "ENUM_media_type_class_ETHER_MEDIA_10GBASE_DWDM_3819";
      }
      enum "ether-media-type-10gbase-dwdm-3898" {
        value 104;
        tailf:code-name "ENUM_media_type_class_ETHER_MEDIA_10GBASE_DWDM_3898";
      }
      enum "ether-media-type-10gbase-dwdm-3977" {
        value 105;
        tailf:code-name "ENUM_media_type_class_ETHER_MEDIA_10GBASE_DWDM_3977";
      }
      enum "ether-media-type-10gbase-dwdm-4056" {
        value 106;
        tailf:code-name "ENUM_media_type_class_ETHER_MEDIA_10GBASE_DWDM_4056";
      }
      enum "ether-media-type-10gbase-dwdm-4214" {
        value 107;
        tailf:code-name "ENUM_media_type_class_ETHER_MEDIA_10GBASE_DWDM_4214";
      }
      enum "ether-media-type-10gbase-dwdm-4294" {
        value 108;
        tailf:code-name "ENUM_media_type_class_ETHER_MEDIA_10GBASE_DWDM_4294";
      }
      enum "ether-media-type-10gbase-dwdm-4373" {
        value 109;
        tailf:code-name "ENUM_media_type_class_ETHER_MEDIA_10GBASE_DWDM_4373";
      }
      enum "ether-media-type-10gbase-dwdm-4453" {
        value 110;
        tailf:code-name "ENUM_media_type_class_ETHER_MEDIA_10GBASE_DWDM_4453";
      }
      enum "ether-media-type-10gbase-dwdm-4612" {
        value 111;
        tailf:code-name "ENUM_media_type_class_ETHER_MEDIA_10GBASE_DWDM_4612";
      }
      enum "ether-media-type-10gbase-dwdm-4692" {
        value 112;
        tailf:code-name "ENUM_media_type_class_ETHER_MEDIA_10GBASE_DWDM_4692";
      }
      enum "ether-media-type-10gbase-dwdm-4772" {
        value 113;
        tailf:code-name "ENUM_media_type_class_ETHER_MEDIA_10GBASE_DWDM_4772";
      }
      enum "ether-media-type-10gbase-dwdm-4851" {
        value 114;
        tailf:code-name "ENUM_media_type_class_ETHER_MEDIA_10GBASE_DWDM_4851";
      }
      enum "ether-media-type-10gbase-dwdm-5012" {
        value 115;
        tailf:code-name "ENUM_media_type_class_ETHER_MEDIA_10GBASE_DWDM_5012";
      }
      enum "ether-media-type-10gbase-dwdm-5092" {
        value 116;
        tailf:code-name "ENUM_media_type_class_ETHER_MEDIA_10GBASE_DWDM_5092";
      }
      enum "ether-media-type-10gbase-dwdm-5172" {
        value 117;
        tailf:code-name "ENUM_media_type_class_ETHER_MEDIA_10GBASE_DWDM_5172";
      }
      enum "ether-media-type-10gbase-dwdm-5252" {
        value 118;
        tailf:code-name "ENUM_media_type_class_ETHER_MEDIA_10GBASE_DWDM_5252";
      }
      enum "ether-media-type-10gbase-dwdm-5413" {
        value 119;
        tailf:code-name "ENUM_media_type_class_ETHER_MEDIA_10GBASE_DWDM_5413";
      }
      enum "ether-media-type-10gbase-dwdm-5494" {
        value 120;
        tailf:code-name "ENUM_media_type_class_ETHER_MEDIA_10GBASE_DWDM_5494";
      }
      enum "ether-media-type-10gbase-dwdm-5575" {
        value 121;
        tailf:code-name "ENUM_media_type_class_ETHER_MEDIA_10GBASE_DWDM_5575";
      }
      enum "ether-media-type-10gbase-dwdm-5655" {
        value 122;
        tailf:code-name "ENUM_media_type_class_ETHER_MEDIA_10GBASE_DWDM_5655";
      }
      enum "ether-media-type-10gbase-dwdm-5817" {
        value 123;
        tailf:code-name "ENUM_media_type_class_ETHER_MEDIA_10GBASE_DWDM_5817";
      }
      enum "ether-media-type-10gbase-dwdm-5898" {
        value 124;
        tailf:code-name "ENUM_media_type_class_ETHER_MEDIA_10GBASE_DWDM_5898";
      }
      enum "ether-media-type-10gbase-dwdm-5979" {
        value 125;
        tailf:code-name "ENUM_media_type_class_ETHER_MEDIA_10GBASE_DWDM_5979";
      }
      enum "ether-media-type-10gbase-dwdm-6061" {
        value 126;
        tailf:code-name "ENUM_media_type_class_ETHER_MEDIA_10GBASE_DWDM_6061";
      }
      enum "ether-media-type-10gbase-tdwdm" {
        value 127;
        tailf:code-name "ENUM_media_type_class_ETHER_MEDIA_10GBASE_TDWDM";
      }
      enum "ether-media-type-100base-zx" {
        value 128;
        tailf:code-name "ENUM_media_type_class_ETHER_MEDIA_100BASE_ZX";
      }
      enum "ether-media-type-100base-ex" {
        value 129;
        tailf:code-name "ENUM_media_type_class_ETHER_MEDIA_100BASE_EX";
      }
      enum "ether-media-type-sfp-plus-10ge-sr" {
        value 130;
        tailf:code-name "ENUM_media_type_class_ETHER_MEDIA_SFP_PLUS_10GE_SR";
      }
      enum "ether-media-type-sfp-plus-10ge-lr" {
        value 131;
        tailf:code-name "ENUM_media_type_class_ETHER_MEDIA_SFP_PLUS_10GE_LR";
      }
      enum "ether-media-type-sfp-plus-10ge-lrm" {
        value 132;
        tailf:code-name "ENUM_media_type_class_ETHER_MEDIA_SFP_PLUS_10GE_LRM";
      }
      enum "ether-media-type-sfp-plus-10ge-er" {
        value 133;
        tailf:code-name "ENUM_media_type_class_ETHER_MEDIA_SFP_PLUS_10GE_ER";
      }
      enum "ether-media-type-10gbase-cu1m" {
        value 134;
        tailf:code-name "ENUM_media_type_class_ETHER_MEDIA_10GBASE_CU1M";
      }
      enum "ether-media-type-10gbase-cu3m" {
        value 135;
        tailf:code-name "ENUM_media_type_class_ETHER_MEDIA_10GBASE_CU3M";
      }
      enum "ether-media-type-10gbase-cu5m" {
        value 136;
        tailf:code-name "ENUM_media_type_class_ETHER_MEDIA_10GBASE_CU5M";
      }
      enum "ether-media-type-10gbase-cu7m" {
        value 137;
        tailf:code-name "ENUM_media_type_class_ETHER_MEDIA_10GBASE_CU7M";
      }
      enum "ether-media-type-10gbase-cwdm-1470" {
        value 138;
        tailf:code-name "ENUM_media_type_class_ETHER_MEDIA_10GBASE_CWDM_1470";
      }
      enum "ether-media-type-10gbase-cwdm-1490" {
        value 139;
        tailf:code-name "ENUM_media_type_class_ETHER_MEDIA_10GBASE_CWDM_1490";
      }
      enum "ether-media-type-10gbase-cwdm-1510" {
        value 140;
        tailf:code-name "ENUM_media_type_class_ETHER_MEDIA_10GBASE_CWDM_1510";
      }
      enum "ether-media-type-10gbase-cwdm-1530" {
        value 141;
        tailf:code-name "ENUM_media_type_class_ETHER_MEDIA_10GBASE_CWDM_1530";
      }
      enum "ether-media-type-10gbase-cwdm-1550" {
        value 142;
        tailf:code-name "ENUM_media_type_class_ETHER_MEDIA_10GBASE_CWDM_1550";
      }
      enum "ether-media-type-10gbase-cwdm-1570" {
        value 143;
        tailf:code-name "ENUM_media_type_class_ETHER_MEDIA_10GBASE_CWDM_1570";
      }
      enum "ether-media-type-10gbase-cwdm-1590" {
        value 144;
        tailf:code-name "ENUM_media_type_class_ETHER_MEDIA_10GBASE_CWDM_1590";
      }
      enum "ether-media-type-10gbase-cwdm-1610" {
        value 145;
        tailf:code-name "ENUM_media_type_class_ETHER_MEDIA_10GBASE_CWDM_1610";
      }
      enum "ether-media-type-100base-lx" {
        value 146;
        tailf:code-name "ENUM_media_type_class_ETHER_MEDIA_100BASE_LX";
      }
      enum "ether-media-type-100lc-bx10-d" {
        value 147;
        tailf:code-name "ENUM_media_type_class_ETHER_MEDIA_100LC_BX10_D";
      }
      enum "ether-media-type-100lc-bx10-u" {
        value 148;
        tailf:code-name "ENUM_media_type_class_ETHER_MEDIA_100LC_BX10_U";
      }
      enum "ether-media-type-100base-bx10-d" {
        value 149;
        tailf:code-name "ENUM_media_type_class_ETHER_MEDIA_100BASE_BX10_D";
      }
      enum "ether-media-type-100base-bx10-u" {
        value 150;
        tailf:code-name "ENUM_media_type_class_ETHER_MEDIA_100BASE_BX10_U";
      }
      enum "ether-media-type-x2" {
        value 151;
        tailf:code-name "ENUM_media_type_class_ETHER_MEDIA_X2";
      }
      enum "ether-media-type-x2-missing" {
        value 152;
        tailf:code-name "ENUM_media_type_class_ETHER_MEDIA_X2_MISSING";
      }
      enum "ether-media-type-xg-draught" {
        value 153;
        tailf:code-name "ENUM_media_type_class_ETHER_MEDIA_XG_DRAUGHT";
      }
      enum "ether-media-type-1g-10gbaset" {
        value 154;
        tailf:code-name "ENUM_media_type_class_ETHER_MEDIA_1G_10GBASET";
      }
      enum "ether-media-type-xg-arcadia" {
        value 155;
        tailf:code-name "ENUM_media_type_class_ETHER_MEDIA_XG_ARCADIA";
      }
      enum "ether-media-type-sfp-plus-10ge-zr" {
        value 156;
        tailf:code-name "ENUM_media_type_class_ETHER_MEDIA_SFP_PLUS_10GE_ZR";
      }
      enum "ether-media-type-sfpp-10g-dwdm-61-41" {
        value 157;
        tailf:code-name "ENUM_media_type_class_ETHER_MEDIA_SFPP_10G_DWDM_61_41";
      }
      enum "ether-media-type-sfpp-10g-dwdm-60-61" {
        value 158;
        tailf:code-name "ENUM_media_type_class_ETHER_MEDIA_SFPP_10G_DWDM_60_61";
      }
      enum "ether-media-type-sfpp-10g-dwdm-59-79" {
        value 159;
        tailf:code-name "ENUM_media_type_class_ETHER_MEDIA_SFPP_10G_DWDM_59_79";
      }
      enum "ether-media-type-sfpp-10g-dwdm-58-98" {
        value 160;
        tailf:code-name "ENUM_media_type_class_ETHER_MEDIA_SFPP_10G_DWDM_58_98";
      }
      enum "ether-media-type-sfpp-10g-dwdm-58-17" {
        value 161;
        tailf:code-name "ENUM_media_type_class_ETHER_MEDIA_SFPP_10G_DWDM_58_17";
      }
      enum "ether-media-type-sfpp-10g-dwdm-57-36" {
        value 162;
        tailf:code-name "ENUM_media_type_class_ETHER_MEDIA_SFPP_10G_DWDM_57_36";
      }
      enum "ether-media-type-sfpp-10g-dwdm-56-55" {
        value 163;
        tailf:code-name "ENUM_media_type_class_ETHER_MEDIA_SFPP_10G_DWDM_56_55";
      }
      enum "ether-media-type-sfpp-10g-dwdm-55-75" {
        value 164;
        tailf:code-name "ENUM_media_type_class_ETHER_MEDIA_SFPP_10G_DWDM_55_75";
      }
      enum "ether-media-type-sfpp-10g-dwdm-54-94" {
        value 165;
        tailf:code-name "ENUM_media_type_class_ETHER_MEDIA_SFPP_10G_DWDM_54_94";
      }
      enum "ether-media-type-sfpp-10g-dwdm-54-13" {
        value 166;
        tailf:code-name "ENUM_media_type_class_ETHER_MEDIA_SFPP_10G_DWDM_54_13";
      }
      enum "ether-media-type-sfpp-10g-dwdm-53-33" {
        value 167;
        tailf:code-name "ENUM_media_type_class_ETHER_MEDIA_SFPP_10G_DWDM_53_33";
      }
      enum "ether-media-type-sfpp-10g-dwdm-52-52" {
        value 168;
        tailf:code-name "ENUM_media_type_class_ETHER_MEDIA_SFPP_10G_DWDM_52_52";
      }
      enum "ether-media-type-sfpp-10g-dwdm-51-72" {
        value 169;
        tailf:code-name "ENUM_media_type_class_ETHER_MEDIA_SFPP_10G_DWDM_51_72";
      }
      enum "ether-media-type-sfpp-10g-dwdm-50-92" {
        value 170;
        tailf:code-name "ENUM_media_type_class_ETHER_MEDIA_SFPP_10G_DWDM_50_92";
      }
      enum "ether-media-type-sfpp-10g-dwdm-50-12" {
        value 171;
        tailf:code-name "ENUM_media_type_class_ETHER_MEDIA_SFPP_10G_DWDM_50_12";
      }
      enum "ether-media-type-sfpp-10g-dwdm-49-32" {
        value 172;
        tailf:code-name "ENUM_media_type_class_ETHER_MEDIA_SFPP_10G_DWDM_49_32";
      }
      enum "ether-media-type-sfpp-10g-dwdm-48-51" {
        value 173;
        tailf:code-name "ENUM_media_type_class_ETHER_MEDIA_SFPP_10G_DWDM_48_51";
      }
      enum "ether-media-type-sfpp-10g-dwdm-47-72" {
        value 174;
        tailf:code-name "ENUM_media_type_class_ETHER_MEDIA_SFPP_10G_DWDM_47_72";
      }
      enum "ether-media-type-sfpp-10g-dwdm-46-92" {
        value 175;
        tailf:code-name "ENUM_media_type_class_ETHER_MEDIA_SFPP_10G_DWDM_46_92";
      }
      enum "ether-media-type-sfpp-10g-dwdm-46-12" {
        value 176;
        tailf:code-name "ENUM_media_type_class_ETHER_MEDIA_SFPP_10G_DWDM_46_12";
      }
      enum "ether-media-type-sfpp-10g-dwdm-45-32" {
        value 177;
        tailf:code-name "ENUM_media_type_class_ETHER_MEDIA_SFPP_10G_DWDM_45_32";
      }
      enum "ether-media-type-sfpp-10g-dwdm-44-53" {
        value 178;
        tailf:code-name "ENUM_media_type_class_ETHER_MEDIA_SFPP_10G_DWDM_44_53";
      }
      enum "ether-media-type-sfpp-10g-dwdm-43-73" {
        value 179;
        tailf:code-name "ENUM_media_type_class_ETHER_MEDIA_SFPP_10G_DWDM_43_73";
      }
      enum "ether-media-type-sfpp-10g-dwdm-42-94" {
        value 180;
        tailf:code-name "ENUM_media_type_class_ETHER_MEDIA_SFPP_10G_DWDM_42_94";
      }
      enum "ether-media-type-sfpp-10g-dwdm-42-14" {
        value 181;
        tailf:code-name "ENUM_media_type_class_ETHER_MEDIA_SFPP_10G_DWDM_42_14";
      }
      enum "ether-media-type-sfpp-10g-dwdm-41-35" {
        value 182;
        tailf:code-name "ENUM_media_type_class_ETHER_MEDIA_SFPP_10G_DWDM_41_35";
      }
      enum "ether-media-type-sfpp-10g-dwdm-40-56" {
        value 183;
        tailf:code-name "ENUM_media_type_class_ETHER_MEDIA_SFPP_10G_DWDM_40_56";
      }
      enum "ether-media-type-sfpp-10g-dwdm-39-77" {
        value 184;
        tailf:code-name "ENUM_media_type_class_ETHER_MEDIA_SFPP_10G_DWDM_39_77";
      }
      enum "ether-media-type-sfpp-10g-dwdm-38-98" {
        value 185;
        tailf:code-name "ENUM_media_type_class_ETHER_MEDIA_SFPP_10G_DWDM_38_98";
      }
      enum "ether-media-type-sfpp-10g-dwdm-38-19" {
        value 186;
        tailf:code-name "ENUM_media_type_class_ETHER_MEDIA_SFPP_10G_DWDM_38_19";
      }
      enum "ether-media-type-sfpp-10g-dwdm-37-40" {
        value 187;
        tailf:code-name "ENUM_media_type_class_ETHER_MEDIA_SFPP_10G_DWDM_37_40";
      }
      enum "ether-media-type-sfpp-10g-dwdm-36-61" {
        value 188;
        tailf:code-name "ENUM_media_type_class_ETHER_MEDIA_SFPP_10G_DWDM_36_61";
      }
      enum "ether-media-type-sfpp-10g-dwdm-35-82" {
        value 189;
        tailf:code-name "ENUM_media_type_class_ETHER_MEDIA_SFPP_10G_DWDM_35_82";
      }
      enum "ether-media-type-sfpp-10g-dwdm-35-04" {
        value 190;
        tailf:code-name "ENUM_media_type_class_ETHER_MEDIA_SFPP_10G_DWDM_35_04";
      }
      enum "ether-media-type-sfpp-10g-dwdm-34-25" {
        value 191;
        tailf:code-name "ENUM_media_type_class_ETHER_MEDIA_SFPP_10G_DWDM_34_25";
      }
      enum "ether-media-type-sfpp-10g-dwdm-33-47" {
        value 192;
        tailf:code-name "ENUM_media_type_class_ETHER_MEDIA_SFPP_10G_DWDM_33_47";
      }
      enum "ether-media-type-sfpp-10g-dwdm-32-68" {
        value 193;
        tailf:code-name "ENUM_media_type_class_ETHER_MEDIA_SFPP_10G_DWDM_32_68";
      }
      enum "ether-media-type-sfpp-10g-dwdm-31-90" {
        value 194;
        tailf:code-name "ENUM_media_type_class_ETHER_MEDIA_SFPP_10G_DWDM_31_90";
      }
      enum "ether-media-type-sfpp-10g-dwdm-31-12" {
        value 195;
        tailf:code-name "ENUM_media_type_class_ETHER_MEDIA_SFPP_10G_DWDM_31_12";
      }
      enum "ether-media-type-sfpp-10g-dwdm-30-33" {
        value 196;
        tailf:code-name "ENUM_media_type_class_ETHER_MEDIA_SFPP_10G_DWDM_30_33";
      }
      enum "ether-media-type-1000base-bx40da" {
        value 197;
        tailf:code-name "ENUM_media_type_class_ETHER_MEDIA_1000BASE_BX40DA";
      }
      enum "ether-media-type-1000base-bx80u" {
        value 198;
        tailf:code-name "ENUM_media_type_class_ETHER_MEDIA_1000BASE_BX80U";
      }
      enum "ether-media-type-1000base-bx80d" {
        value 199;
        tailf:code-name "ENUM_media_type_class_ETHER_MEDIA_1000BASE_BX80D";
      }
      enum "ether-media-type-1000base-bx40u" {
        value 200;
        tailf:code-name "ENUM_media_type_class_ETHER_MEDIA_1000BASE_BX40U";
      }
      enum "ether-media-type-1000base-bx40d" {
        value 201;
        tailf:code-name "ENUM_media_type_class_ETHER_MEDIA_1000BASE_BX40D";
      }
      enum "ether-media-type-sfp-plus-10ge-bxd" {
        value 202;
        tailf:code-name "ENUM_media_type_class_ETHER_MEDIA_SFP_PLUS_10GE_BXD";
      }
      enum "ether-media-type-sfp-plus-10ge-bxu" {
        value 203;
        tailf:code-name "ENUM_media_type_class_ETHER_MEDIA_SFP_PLUS_10GE_BXU";
      }
      enum "ether-media-type-sfp-plus-10ge-bx40d" {
        value 204;
        tailf:code-name "ENUM_media_type_class_ETHER_MEDIA_SFP_PLUS_10GE_BX40D";
      }
      enum "ether-media-type-sfp-plus-10ge-bx40u" {
        value 205;
        tailf:code-name "ENUM_media_type_class_ETHER_MEDIA_SFP_PLUS_10GE_BX40U";
      }
      enum "ether-media-type-sfpp-10g-cwdm-14-70" {
        value 206;
        tailf:code-name "ENUM_media_type_class_ETHER_MEDIA_SFPP_10G_CWDM_14_70";
      }
      enum "ether-media-type-sfpp-10g-cwdm-14-90" {
        value 207;
        tailf:code-name "ENUM_media_type_class_ETHER_MEDIA_SFPP_10G_CWDM_14_90";
      }
      enum "ether-media-type-sfpp-10g-cwdm-15-10" {
        value 208;
        tailf:code-name "ENUM_media_type_class_ETHER_MEDIA_SFPP_10G_CWDM_15_10";
      }
      enum "ether-media-type-sfpp-10g-cwdm-15-30" {
        value 209;
        tailf:code-name "ENUM_media_type_class_ETHER_MEDIA_SFPP_10G_CWDM_15_30";
      }
      enum "ether-media-type-sfpp-10g-cwdm-15-50" {
        value 210;
        tailf:code-name "ENUM_media_type_class_ETHER_MEDIA_SFPP_10G_CWDM_15_50";
      }
      enum "ether-media-type-sfpp-10g-cwdm-15-70" {
        value 211;
        tailf:code-name "ENUM_media_type_class_ETHER_MEDIA_SFPP_10G_CWDM_15_70";
      }
      enum "ether-media-type-sfpp-10g-cwdm-15-90" {
        value 212;
        tailf:code-name "ENUM_media_type_class_ETHER_MEDIA_SFPP_10G_CWDM_15_90";
      }
      enum "ether-media-type-sfpp-10g-cwdm-16-10" {
        value 213;
        tailf:code-name "ENUM_media_type_class_ETHER_MEDIA_SFPP_10G_CWDM_16_10";
      }
      enum "ether-media-type-sfpp-10g-acu7m" {
        value 214;
        tailf:code-name "ENUM_media_type_class_ETHER_MEDIA_SFPP_10G_ACU7M";
      }
      enum "ether-media-type-sfpp-10g-acu10m" {
        value 215;
        tailf:code-name "ENUM_media_type_class_ETHER_MEDIA_SFPP_10G_ACU10M";
      }
      enum "ether-media-type-cpak-100ge-sr10" {
        value 216;
        tailf:code-name "ENUM_media_type_class_ETHER_MEDIA_CPAK_100GE_SR10";
      }
      enum "ether-media-type-cpak-100ge-lr4" {
        value 217;
        tailf:code-name "ENUM_media_type_class_ETHER_MEDIA_CPAK_100GE_LR4";
      }
      enum "ether-media-type-cpak-100ge-sr4" {
        value 218;
        tailf:code-name "ENUM_media_type_class_ETHER_MEDIA_CPAK_100GE_SR4";
      }
      enum "ether-media-type-cfp-40g" {
        value 219;
        tailf:code-name "ENUM_media_type_class_ETHER_MEDIA_CFP_40G";
      }
      enum "ether-media-type-qsfp-40ge-lr" {
        value 220;
        tailf:code-name "ENUM_media_type_class_ETHER_MEDIA_QSFP_40GE_LR";
      }
      enum "ether-media-type-qsfp-40ge-sr" {
        value 221;
        tailf:code-name "ENUM_media_type_class_ETHER_MEDIA_QSFP_40GE_SR";
      }
      enum "ether-media-type-1000base-dr-lx" {
        value 222;
        tailf:code-name "ENUM_media_type_class_ETHER_MEDIA_1000BASE_DR_LX";
      }
      enum "ether-media-type-sfpp-10g-tdwdm" {
        value 223;
        tailf:code-name "ENUM_media_type_class_ETHER_MEDIA_SFPP_10G_TDWDM";
      }
      enum "ether-media-type-qsfp-40ge-er4" {
        value 224;
        tailf:code-name "ENUM_media_type_class_ETHER_MEDIA_QSFP_40GE_ER4";
      }
      enum "ether-media-type-sfpp-dwdm-10gep-61-83" {
        value 225;
        tailf:code-name "ENUM_media_type_class_ETHER_MEDIA_SFPP_DWDM_10GEP_61_83";
      }
      enum "ether-media-type-sfpp-dwdm-10gep-61-41" {
        value 226;
        tailf:code-name "ENUM_media_type_class_ETHER_MEDIA_SFPP_DWDM_10GEP_61_41";
      }
      enum "ether-media-type-sfpp-dwdm-10gep-61-01" {
        value 227;
        tailf:code-name "ENUM_media_type_class_ETHER_MEDIA_SFPP_DWDM_10GEP_61_01";
      }
      enum "ether-media-type-sfpp-dwdm-10gep-60-61" {
        value 228;
        tailf:code-name "ENUM_media_type_class_ETHER_MEDIA_SFPP_DWDM_10GEP_60_61";
      }
      enum "ether-media-type-sfpp-dwdm-10gep-60-20" {
        value 229;
        tailf:code-name "ENUM_media_type_class_ETHER_MEDIA_SFPP_DWDM_10GEP_60_20";
      }
      enum "ether-media-type-sfpp-dwdm-10gep-59-79" {
        value 230;
        tailf:code-name "ENUM_media_type_class_ETHER_MEDIA_SFPP_DWDM_10GEP_59_79";
      }
      enum "ether-media-type-sfpp-dwdm-10gep-59-39" {
        value 231;
        tailf:code-name "ENUM_media_type_class_ETHER_MEDIA_SFPP_DWDM_10GEP_59_39";
      }
      enum "ether-media-type-sfpp-dwdm-10gep-58-98" {
        value 232;
        tailf:code-name "ENUM_media_type_class_ETHER_MEDIA_SFPP_DWDM_10GEP_58_98";
      }
      enum "ether-media-type-sfpp-dwdm-10gep-58-58" {
        value 233;
        tailf:code-name "ENUM_media_type_class_ETHER_MEDIA_SFPP_DWDM_10GEP_58_58";
      }
      enum "ether-media-type-sfpp-dwdm-10gep-58-17" {
        value 234;
        tailf:code-name "ENUM_media_type_class_ETHER_MEDIA_SFPP_DWDM_10GEP_58_17";
      }
      enum "ether-media-type-sfpp-dwdm-10gep-57-77" {
        value 235;
        tailf:code-name "ENUM_media_type_class_ETHER_MEDIA_SFPP_DWDM_10GEP_57_77";
      }
      enum "ether-media-type-sfpp-dwdm-10gep-57-36" {
        value 236;
        tailf:code-name "ENUM_media_type_class_ETHER_MEDIA_SFPP_DWDM_10GEP_57_36";
      }
      enum "ether-media-type-sfpp-dwdm-10gep-56-96" {
        value 237;
        tailf:code-name "ENUM_media_type_class_ETHER_MEDIA_SFPP_DWDM_10GEP_56_96";
      }
      enum "ether-media-type-sfpp-dwdm-10gep-56-55" {
        value 238;
        tailf:code-name "ENUM_media_type_class_ETHER_MEDIA_SFPP_DWDM_10GEP_56_55";
      }
      enum "ether-media-type-sfpp-dwdm-10gep-56-15" {
        value 239;
        tailf:code-name "ENUM_media_type_class_ETHER_MEDIA_SFPP_DWDM_10GEP_56_15";
      }
      enum "ether-media-type-sfpp-dwdm-10gep-55-75" {
        value 240;
        tailf:code-name "ENUM_media_type_class_ETHER_MEDIA_SFPP_DWDM_10GEP_55_75";
      }
      enum "ether-media-type-sfpp-dwdm-10gep-55-34" {
        value 241;
        tailf:code-name "ENUM_media_type_class_ETHER_MEDIA_SFPP_DWDM_10GEP_55_34";
      }
      enum "ether-media-type-sfpp-dwdm-10gep-54-94" {
        value 242;
        tailf:code-name "ENUM_media_type_class_ETHER_MEDIA_SFPP_DWDM_10GEP_54_94";
      }
      enum "ether-media-type-sfpp-dwdm-10gep-54-54" {
        value 243;
        tailf:code-name "ENUM_media_type_class_ETHER_MEDIA_SFPP_DWDM_10GEP_54_54";
      }
      enum "ether-media-type-sfpp-dwdm-10gep-54-13" {
        value 244;
        tailf:code-name "ENUM_media_type_class_ETHER_MEDIA_SFPP_DWDM_10GEP_54_13";
      }
      enum "ether-media-type-sfpp-dwdm-10gep-53-73" {
        value 245;
        tailf:code-name "ENUM_media_type_class_ETHER_MEDIA_SFPP_DWDM_10GEP_53_73";
      }
      enum "ether-media-type-sfpp-dwdm-10gep-53-33" {
        value 246;
        tailf:code-name "ENUM_media_type_class_ETHER_MEDIA_SFPP_DWDM_10GEP_53_33";
      }
      enum "ether-media-type-sfpp-dwdm-10gep-52-93" {
        value 247;
        tailf:code-name "ENUM_media_type_class_ETHER_MEDIA_SFPP_DWDM_10GEP_52_93";
      }
      enum "ether-media-type-sfpp-dwdm-10gep-52-52" {
        value 248;
        tailf:code-name "ENUM_media_type_class_ETHER_MEDIA_SFPP_DWDM_10GEP_52_52";
      }
      enum "ether-media-type-sfpp-dwdm-10gep-52-12" {
        value 249;
        tailf:code-name "ENUM_media_type_class_ETHER_MEDIA_SFPP_DWDM_10GEP_52_12";
      }
      enum "ether-media-type-sfpp-dwdm-10gep-51-72" {
        value 250;
        tailf:code-name "ENUM_media_type_class_ETHER_MEDIA_SFPP_DWDM_10GEP_51_72";
      }
      enum "ether-media-type-sfpp-dwdm-10gep-51-32" {
        value 251;
        tailf:code-name "ENUM_media_type_class_ETHER_MEDIA_SFPP_DWDM_10GEP_51_32";
      }
      enum "ether-media-type-sfpp-dwdm-10gep-50-92" {
        value 252;
        tailf:code-name "ENUM_media_type_class_ETHER_MEDIA_SFPP_DWDM_10GEP_50_92";
      }
      enum "ether-media-type-sfpp-dwdm-10gep-50-52" {
        value 253;
        tailf:code-name "ENUM_media_type_class_ETHER_MEDIA_SFPP_DWDM_10GEP_50_52";
      }
      enum "ether-media-type-sfpp-dwdm-10gep-50-12" {
        value 254;
        tailf:code-name "ENUM_media_type_class_ETHER_MEDIA_SFPP_DWDM_10GEP_50_12";
      }
      enum "ether-media-type-sfpp-dwdm-10gep-49-72" {
        value 255;
        tailf:code-name "ENUM_media_type_class_ETHER_MEDIA_SFPP_DWDM_10GEP_49_72";
      }
      enum "ether-media-type-sfpp-dwdm-10gep-49-32" {
        value 256;
        tailf:code-name "ENUM_media_type_class_ETHER_MEDIA_SFPP_DWDM_10GEP_49_32";
      }
      enum "ether-media-type-sfpp-dwdm-10gep-48-91" {
        value 257;
        tailf:code-name "ENUM_media_type_class_ETHER_MEDIA_SFPP_DWDM_10GEP_48_91";
      }
      enum "ether-media-type-sfpp-dwdm-10gep-48-51" {
        value 258;
        tailf:code-name "ENUM_media_type_class_ETHER_MEDIA_SFPP_DWDM_10GEP_48_51";
      }
      enum "ether-media-type-sfpp-dwdm-10gep-48-11" {
        value 259;
        tailf:code-name "ENUM_media_type_class_ETHER_MEDIA_SFPP_DWDM_10GEP_48_11";
      }
      enum "ether-media-type-sfpp-dwdm-10gep-47-72" {
        value 260;
        tailf:code-name "ENUM_media_type_class_ETHER_MEDIA_SFPP_DWDM_10GEP_47_72";
      }
      enum "ether-media-type-sfpp-dwdm-10gep-47-32" {
        value 261;
        tailf:code-name "ENUM_media_type_class_ETHER_MEDIA_SFPP_DWDM_10GEP_47_32";
      }
      enum "ether-media-type-sfpp-dwdm-10gep-46-92" {
        value 262;
        tailf:code-name "ENUM_media_type_class_ETHER_MEDIA_SFPP_DWDM_10GEP_46_92";
      }
      enum "ether-media-type-sfpp-dwdm-10gep-46-52" {
        value 263;
        tailf:code-name "ENUM_media_type_class_ETHER_MEDIA_SFPP_DWDM_10GEP_46_52";
      }
      enum "ether-media-type-sfpp-dwdm-10gep-46-12" {
        value 264;
        tailf:code-name "ENUM_media_type_class_ETHER_MEDIA_SFPP_DWDM_10GEP_46_12";
      }
      enum "ether-media-type-sfpp-dwdm-10gep-45-72" {
        value 265;
        tailf:code-name "ENUM_media_type_class_ETHER_MEDIA_SFPP_DWDM_10GEP_45_72";
      }
      enum "ether-media-type-sfpp-dwdm-10gep-45-32" {
        value 266;
        tailf:code-name "ENUM_media_type_class_ETHER_MEDIA_SFPP_DWDM_10GEP_45_32";
      }
      enum "ether-media-type-sfpp-dwdm-10gep-44-92" {
        value 267;
        tailf:code-name "ENUM_media_type_class_ETHER_MEDIA_SFPP_DWDM_10GEP_44_92";
      }
      enum "ether-media-type-sfpp-dwdm-10gep-44-53" {
        value 268;
        tailf:code-name "ENUM_media_type_class_ETHER_MEDIA_SFPP_DWDM_10GEP_44_53";
      }
      enum "ether-media-type-sfpp-dwdm-10gep-44-13" {
        value 269;
        tailf:code-name "ENUM_media_type_class_ETHER_MEDIA_SFPP_DWDM_10GEP_44_13";
      }
      enum "ether-media-type-sfpp-dwdm-10gep-43-73" {
        value 270;
        tailf:code-name "ENUM_media_type_class_ETHER_MEDIA_SFPP_DWDM_10GEP_43_73";
      }
      enum "ether-media-type-sfpp-dwdm-10gep-43-33" {
        value 271;
        tailf:code-name "ENUM_media_type_class_ETHER_MEDIA_SFPP_DWDM_10GEP_43_33";
      }
      enum "ether-media-type-sfpp-dwdm-10gep-42-94" {
        value 272;
        tailf:code-name "ENUM_media_type_class_ETHER_MEDIA_SFPP_DWDM_10GEP_42_94";
      }
      enum "ether-media-type-sfpp-dwdm-10gep-42-54" {
        value 273;
        tailf:code-name "ENUM_media_type_class_ETHER_MEDIA_SFPP_DWDM_10GEP_42_54";
      }
      enum "ether-media-type-sfpp-dwdm-10gep-42-14" {
        value 274;
        tailf:code-name "ENUM_media_type_class_ETHER_MEDIA_SFPP_DWDM_10GEP_42_14";
      }
      enum "ether-media-type-sfpp-dwdm-10gep-41-75" {
        value 275;
        tailf:code-name "ENUM_media_type_class_ETHER_MEDIA_SFPP_DWDM_10GEP_41_75";
      }
      enum "ether-media-type-sfpp-dwdm-10gep-41-35" {
        value 276;
        tailf:code-name "ENUM_media_type_class_ETHER_MEDIA_SFPP_DWDM_10GEP_41_35";
      }
      enum "ether-media-type-sfpp-dwdm-10gep-40-95" {
        value 277;
        tailf:code-name "ENUM_media_type_class_ETHER_MEDIA_SFPP_DWDM_10GEP_40_95";
      }
      enum "ether-media-type-sfpp-dwdm-10gep-40-56" {
        value 278;
        tailf:code-name "ENUM_media_type_class_ETHER_MEDIA_SFPP_DWDM_10GEP_40_56";
      }
      enum "ether-media-type-sfpp-dwdm-10gep-40-16" {
        value 279;
        tailf:code-name "ENUM_media_type_class_ETHER_MEDIA_SFPP_DWDM_10GEP_40_16";
      }
      enum "ether-media-type-sfpp-dwdm-10gep-39-77" {
        value 280;
        tailf:code-name "ENUM_media_type_class_ETHER_MEDIA_SFPP_DWDM_10GEP_39_77";
      }
      enum "ether-media-type-sfpp-dwdm-10gep-39-37" {
        value 281;
        tailf:code-name "ENUM_media_type_class_ETHER_MEDIA_SFPP_DWDM_10GEP_39_37";
      }
      enum "ether-media-type-sfpp-dwdm-10gep-38-98" {
        value 282;
        tailf:code-name "ENUM_media_type_class_ETHER_MEDIA_SFPP_DWDM_10GEP_38_98";
      }
      enum "ether-media-type-sfpp-dwdm-10gep-38-58" {
        value 283;
        tailf:code-name "ENUM_media_type_class_ETHER_MEDIA_SFPP_DWDM_10GEP_38_58";
      }
      enum "ether-media-type-sfpp-dwdm-10gep-38-19" {
        value 284;
        tailf:code-name "ENUM_media_type_class_ETHER_MEDIA_SFPP_DWDM_10GEP_38_19";
      }
      enum "ether-media-type-sfpp-dwdm-10gep-37-79" {
        value 285;
        tailf:code-name "ENUM_media_type_class_ETHER_MEDIA_SFPP_DWDM_10GEP_37_79";
      }
      enum "ether-media-type-sfpp-dwdm-10gep-37-40" {
        value 286;
        tailf:code-name "ENUM_media_type_class_ETHER_MEDIA_SFPP_DWDM_10GEP_37_40";
      }
      enum "ether-media-type-sfpp-dwdm-10gep-37-00" {
        value 287;
        tailf:code-name "ENUM_media_type_class_ETHER_MEDIA_SFPP_DWDM_10GEP_37_00";
      }
      enum "ether-media-type-sfpp-dwdm-10gep-36-61" {
        value 288;
        tailf:code-name "ENUM_media_type_class_ETHER_MEDIA_SFPP_DWDM_10GEP_36_61";
      }
      enum "ether-media-type-sfpp-dwdm-10gep-36-22" {
        value 289;
        tailf:code-name "ENUM_media_type_class_ETHER_MEDIA_SFPP_DWDM_10GEP_36_22";
      }
      enum "ether-media-type-sfpp-dwdm-10gep-35-82" {
        value 290;
        tailf:code-name "ENUM_media_type_class_ETHER_MEDIA_SFPP_DWDM_10GEP_35_82";
      }
      enum "ether-media-type-sfpp-dwdm-10gep-35-43" {
        value 291;
        tailf:code-name "ENUM_media_type_class_ETHER_MEDIA_SFPP_DWDM_10GEP_35_43";
      }
      enum "ether-media-type-sfpp-dwdm-10gep-35-04" {
        value 292;
        tailf:code-name "ENUM_media_type_class_ETHER_MEDIA_SFPP_DWDM_10GEP_35_04";
      }
      enum "ether-media-type-sfpp-dwdm-10gep-34-64" {
        value 293;
        tailf:code-name "ENUM_media_type_class_ETHER_MEDIA_SFPP_DWDM_10GEP_34_64";
      }
      enum "ether-media-type-sfpp-dwdm-10gep-34-25" {
        value 294;
        tailf:code-name "ENUM_media_type_class_ETHER_MEDIA_SFPP_DWDM_10GEP_34_25";
      }
      enum "ether-media-type-sfpp-dwdm-10gep-33-86" {
        value 295;
        tailf:code-name "ENUM_media_type_class_ETHER_MEDIA_SFPP_DWDM_10GEP_33_86";
      }
      enum "ether-media-type-sfpp-dwdm-10gep-33-47" {
        value 296;
        tailf:code-name "ENUM_media_type_class_ETHER_MEDIA_SFPP_DWDM_10GEP_33_47";
      }
      enum "ether-media-type-sfpp-dwdm-10gep-33-07" {
        value 297;
        tailf:code-name "ENUM_media_type_class_ETHER_MEDIA_SFPP_DWDM_10GEP_33_07";
      }
      enum "ether-media-type-sfpp-dwdm-10gep-32-68" {
        value 298;
        tailf:code-name "ENUM_media_type_class_ETHER_MEDIA_SFPP_DWDM_10GEP_32_68";
      }
      enum "ether-media-type-sfpp-dwdm-10gep-32-29" {
        value 299;
        tailf:code-name "ENUM_media_type_class_ETHER_MEDIA_SFPP_DWDM_10GEP_32_29";
      }
      enum "ether-media-type-sfpp-dwdm-10gep-31-90" {
        value 300;
        tailf:code-name "ENUM_media_type_class_ETHER_MEDIA_SFPP_DWDM_10GEP_31_90";
      }
      enum "ether-media-type-sfpp-dwdm-10gep-31-51" {
        value 301;
        tailf:code-name "ENUM_media_type_class_ETHER_MEDIA_SFPP_DWDM_10GEP_31_51";
      }
      enum "ether-media-type-sfpp-dwdm-10gep-31-12" {
        value 302;
        tailf:code-name "ENUM_media_type_class_ETHER_MEDIA_SFPP_DWDM_10GEP_31_12";
      }
      enum "ether-media-type-sfpp-dwdm-10gep-30-72" {
        value 303;
        tailf:code-name "ENUM_media_type_class_ETHER_MEDIA_SFPP_DWDM_10GEP_30_72";
      }
      enum "ether-media-type-sfpp-dwdm-10gep-30-33" {
        value 304;
        tailf:code-name "ENUM_media_type_class_ETHER_MEDIA_SFPP_DWDM_10GEP_30_33";
      }
      enum "ether-media-type-ons-se-z1" {
        value 305;
        tailf:code-name "ENUM_media_type_class_ETHER_MEDIA_ONS_SE_Z1";
      }
      enum "ether-media-type-qsfp-100ge-lr" {
        value 306;
        tailf:code-name "ENUM_media_type_class_ETHER_MEDIA_QSFP_100GE_LR";
      }
      enum "ether-media-type-qsfp-100ge-sr" {
        value 307;
        tailf:code-name "ENUM_media_type_class_ETHER_MEDIA_QSFP_100GE_SR";
      }
      enum "ether-media-type-sfpp-10g-aoc1m" {
        value 308;
        tailf:code-name "ENUM_media_type_class_ETHER_MEDIA_SFPP_10G_AOC1M";
      }
      enum "ether-media-type-sfpp-10g-aoc2m" {
        value 309;
        tailf:code-name "ENUM_media_type_class_ETHER_MEDIA_SFPP_10G_AOC2M";
      }
      enum "ether-media-type-sfpp-10g-aoc3m" {
        value 310;
        tailf:code-name "ENUM_media_type_class_ETHER_MEDIA_SFPP_10G_AOC3M";
      }
      enum "ether-media-type-sfpp-10g-aoc5m" {
        value 311;
        tailf:code-name "ENUM_media_type_class_ETHER_MEDIA_SFPP_10G_AOC5M";
      }
      enum "ether-media-type-sfpp-10g-aoc7m" {
        value 312;
        tailf:code-name "ENUM_media_type_class_ETHER_MEDIA_SFPP_10G_AOC7M";
      }
      enum "ether-media-type-sfpp-10g-aoc10m" {
        value 313;
        tailf:code-name "ENUM_media_type_class_ETHER_MEDIA_SFPP_10G_AOC10M";
      }
      enum "ether-media-type-cpak-100ge-er4l" {
        value 314;
        tailf:code-name "ENUM_media_type_class_ETHER_MEDIA_CPAK_100GE_ER4L";
      }
      enum "ether-media-type-qsfp-40ge-sr-bd" {
        value 315;
        tailf:code-name "ENUM_media_type_class_ETHER_MEDIA_QSFP_40GE_SR_BD";
      }
      enum "ether-media-type-qsfp-40ge-bd-rx" {
        value 316;
        tailf:code-name "ENUM_media_type_class_ETHER_MEDIA_QSFP_40GE_BD_RX";
      }
      enum "ether-media-type-tunable-dwdm-sfpp" {
        value 317;
        tailf:code-name "ENUM_media_type_class_ETHER_MEDIA_TUNABLE_DWDM_SFPP";
      }
      enum "ether-media-type-qsfp-40ge-sr-s" {
        value 318;
        tailf:code-name "ENUM_media_type_class_ETHER_MEDIA_QSFP_40GE_SR_S";
      }
      enum "ether-media-type-qsfp-40ge-lr-s" {
        value 319;
        tailf:code-name "ENUM_media_type_class_ETHER_MEDIA_QSFP_40GE_LR_S";
      }
      enum "ether-media-type-qsfp-h40ge-aoc1m" {
        value 320;
        tailf:code-name "ENUM_media_type_class_ETHER_MEDIA_QSFP_H40GE_AOC1M";
      }
      enum "ether-media-type-qsfp-h40ge-aoc2m" {
        value 321;
        tailf:code-name "ENUM_media_type_class_ETHER_MEDIA_QSFP_H40GE_AOC2M";
      }
      enum "ether-media-type-qsfp-h40ge-aoc3m" {
        value 322;
        tailf:code-name "ENUM_media_type_class_ETHER_MEDIA_QSFP_H40GE_AOC3M";
      }
      enum "ether-media-type-qsfp-h40ge-aoc5m" {
        value 323;
        tailf:code-name "ENUM_media_type_class_ETHER_MEDIA_QSFP_H40GE_AOC5M";
      }
      enum "ether-media-type-qsfp-h40ge-aoc7m" {
        value 324;
        tailf:code-name "ENUM_media_type_class_ETHER_MEDIA_QSFP_H40GE_AOC7M";
      }
      enum "ether-media-type-qsfp-h40ge-aoc10m" {
        value 325;
        tailf:code-name "ENUM_media_type_class_ETHER_MEDIA_QSFP_H40GE_AOC10M";
      }
      enum "ether-media-type-qsfp-h40ge-aoc15m" {
        value 326;
        tailf:code-name "ENUM_media_type_class_ETHER_MEDIA_QSFP_H40GE_AOC15M";
      }
      enum "ether-media-type-qsfp-h40ge-aoc20m" {
        value 327;
        tailf:code-name "ENUM_media_type_class_ETHER_MEDIA_QSFP_H40GE_AOC20M";
      }
      enum "ether-media-type-qsfp-40ge-csr4" {
        value 328;
        tailf:code-name "ENUM_media_type_class_ETHER_MEDIA_QSFP_40GE_CSR4";
      }
      enum "ether-media-type-qsfp-40ge-sr4" {
        value 329;
        tailf:code-name "ENUM_media_type_class_ETHER_MEDIA_QSFP_40GE_SR4";
      }
      enum "ether-media-type-qsfp-40ge-lr4" {
        value 330;
        tailf:code-name "ENUM_media_type_class_ETHER_MEDIA_QSFP_40GE_LR4";
      }
      enum "ether-media-type-wsp-40ge-lr4l" {
        value 331;
        tailf:code-name "ENUM_media_type_class_ETHER_MEDIA_WSP_40GE_LR4L";
      }
      enum "ether-media-type-qsfp-h40ge-cu1m" {
        value 332;
        tailf:code-name "ENUM_media_type_class_ETHER_MEDIA_QSFP_H40GE_CU1M";
      }
      enum "ether-media-type-qsfp-h40ge-cu3m" {
        value 333;
        tailf:code-name "ENUM_media_type_class_ETHER_MEDIA_QSFP_H40GE_CU3M";
      }
      enum "ether-media-type-qsfp-h40ge-cu5m" {
        value 334;
        tailf:code-name "ENUM_media_type_class_ETHER_MEDIA_QSFP_H40GE_CU5M";
      }
      enum "ether-media-type-qsfp-h40ge-acu7m" {
        value 335;
        tailf:code-name "ENUM_media_type_class_ETHER_MEDIA_QSFP_H40GE_ACU7M";
      }
      enum "ether-media-type-qsfp-h40ge-acu10m" {
        value 336;
        tailf:code-name "ENUM_media_type_class_ETHER_MEDIA_QSFP_H40GE_ACU10M";
      }
      enum "ether-media-type-qsfp-100ge-psm4" {
        value 337;
        tailf:code-name "ENUM_media_type_class_ETHER_MEDIA_QSFP_100GE_PSM4";
      }
      enum "ether-media-type-qsfp-100ge-cwdm4" {
        value 338;
        tailf:code-name "ENUM_media_type_class_ETHER_MEDIA_QSFP_100GE_CWDM4";
      }
      enum "ether-media-type-qsfp-100ge-cu1m" {
        value 339;
        tailf:code-name "ENUM_media_type_class_ETHER_MEDIA_QSFP_100GE_CU1M";
      }
      enum "ether-media-type-qsfp-100ge-cu2m" {
        value 340;
        tailf:code-name "ENUM_media_type_class_ETHER_MEDIA_QSFP_100GE_CU2M";
      }
      enum "ether-media-type-qsfp-100ge-cu3m" {
        value 341;
        tailf:code-name "ENUM_media_type_class_ETHER_MEDIA_QSFP_100GE_CU3M";
      }
      enum "ether-media-type-qsfp-100ge-cu5m" {
        value 342;
        tailf:code-name "ENUM_media_type_class_ETHER_MEDIA_QSFP_100GE_CU5M";
      }
      enum "ether-media-type-qsfp-100ge-aoc1m" {
        value 343;
        tailf:code-name "ENUM_media_type_class_ETHER_MEDIA_QSFP_100GE_AOC1M";
      }
      enum "ether-media-type-qsfp-100ge-aoc2m" {
        value 344;
        tailf:code-name "ENUM_media_type_class_ETHER_MEDIA_QSFP_100GE_AOC2M";
      }
      enum "ether-media-type-qsfp-100ge-aoc3m" {
        value 345;
        tailf:code-name "ENUM_media_type_class_ETHER_MEDIA_QSFP_100GE_AOC3M";
      }
      enum "ether-media-type-qsfp-100ge-aoc5m" {
        value 346;
        tailf:code-name "ENUM_media_type_class_ETHER_MEDIA_QSFP_100GE_AOC5M";
      }
      enum "ether-media-type-qsfp-100ge-aoc7m" {
        value 347;
        tailf:code-name "ENUM_media_type_class_ETHER_MEDIA_QSFP_100GE_AOC7M";
      }
      enum "ether-media-type-qsfp-100ge-aoc10m" {
        value 348;
        tailf:code-name "ENUM_media_type_class_ETHER_MEDIA_QSFP_100GE_AOC10M";
      }
      enum "ether-media-type-qsfp-100ge-aoc15m" {
        value 349;
        tailf:code-name "ENUM_media_type_class_ETHER_MEDIA_QSFP_100GE_AOC15M";
      }
      enum "ether-media-type-qsfp-100ge-aoc20m" {
        value 350;
        tailf:code-name "ENUM_media_type_class_ETHER_MEDIA_QSFP_100GE_AOC20M";
      }
      enum "ether-media-type-qsfp-100ge-aoc25m" {
        value 351;
        tailf:code-name "ENUM_media_type_class_ETHER_MEDIA_QSFP_100GE_AOC25M";
      }
      enum "ether-media-type-qsfp-100ge-aoc30m" {
        value 352;
        tailf:code-name "ENUM_media_type_class_ETHER_MEDIA_QSFP_100GE_AOC30M";
      }
      enum "ether-media-type-qsfp-100ge-sm-sr" {
        value 353;
        tailf:code-name "ENUM_media_type_class_ETHER_MEDIA_QSFP_100GE_SM_SR";
      }
      enum "ether-media-type-qsfp-100ge-csr4" {
        value 354;
        tailf:code-name "ENUM_media_type_class_ETHER_MEDIA_QSFP_100GE_CSR4";
      }
      enum "ether-media-type-1000base-2bxd" {
        value 355;
        tailf:code-name "ENUM_media_type_class_ETHER_MEDIA_1000BASE_2BXD";
      }
      enum "ether-media-type-qsfp-h40ge-cudot5m" {
        value 356;
        tailf:code-name "ENUM_media_type_class_ETHER_MEDIA_QSFP_H40GE_CUDOT5M";
      }
      enum "ether-media-type-qsfp-h40ge-cu2m" {
        value 357;
        tailf:code-name "ENUM_media_type_class_ETHER_MEDIA_QSFP_H40GE_CU2M";
      }
      enum "ether-media-type-qsfp-h40ge-cu4m" {
        value 358;
        tailf:code-name "ENUM_media_type_class_ETHER_MEDIA_QSFP_H40GE_CU4M";
      }
      enum "ether-media-type-virtual" {
        value 359;
        tailf:code-name "ENUM_media_type_class_ETHER_MEDIA_VIRTUAL";
      }
      enum "ether-media-type-sfp-25ge-sr-s" {
        value 360;
        tailf:code-name "ENUM_media_type_class_ETHER_MEDIA_SFP_25GE_SR_S";
      }
      enum "ether-media-type-sfp-25ge-lr-s" {
        value 361;
        tailf:code-name "ENUM_media_type_class_ETHER_MEDIA_SFP_25GE_LR_S";
      }
      enum "ether-media-type-sfp-25ge-cu1m" {
        value 362;
        tailf:code-name "ENUM_media_type_class_ETHER_MEDIA_SFP_25GE_CU1M";
      }
      enum "ether-media-type-sfp-25ge-cu2m" {
        value 363;
        tailf:code-name "ENUM_media_type_class_ETHER_MEDIA_SFP_25GE_CU2M";
      }
      enum "ether-media-type-sfp-25ge-cu3m" {
        value 364;
        tailf:code-name "ENUM_media_type_class_ETHER_MEDIA_SFP_25GE_CU3M";
      }
      enum "ether-media-type-sfp-25ge-cu5m" {
        value 365;
        tailf:code-name "ENUM_media_type_class_ETHER_MEDIA_SFP_25GE_CU5M";
      }
      enum "ether-media-type-sfp-25ge-aoc1m" {
        value 366;
        tailf:code-name "ENUM_media_type_class_ETHER_MEDIA_SFP_25GE_AOC1M";
      }
      enum "ether-media-type-sfp-25ge-aoc2m" {
        value 367;
        tailf:code-name "ENUM_media_type_class_ETHER_MEDIA_SFP_25GE_AOC2M";
      }
      enum "ether-media-type-sfp-25ge-aoc3m" {
        value 368;
        tailf:code-name "ENUM_media_type_class_ETHER_MEDIA_SFP_25GE_AOC3M";
      }
      enum "ether-media-type-sfp-25ge-aoc5m" {
        value 369;
        tailf:code-name "ENUM_media_type_class_ETHER_MEDIA_SFP_25GE_AOC5M";
      }
      enum "ether-media-type-sfp-25ge-aoc7m" {
        value 370;
        tailf:code-name "ENUM_media_type_class_ETHER_MEDIA_SFP_25GE_AOC7M";
      }
      enum "ether-media-type-sfp-25ge-aoc10m" {
        value 371;
        tailf:code-name "ENUM_media_type_class_ETHER_MEDIA_SFP_25GE_AOC10M";
      }
      enum "ether-media-type-cvr-qsfp-sfp10g" {
        value 372;
        tailf:code-name "ENUM_media_type_class_ETHER_MEDIA_CVR_QSFP_SFP10G";
      }
      enum "ether-media-type-qsfp-h40ge-aoc25m" {
        value 373;
        tailf:code-name "ENUM_media_type_class_ETHER_MEDIA_QSFP_H40GE_AOC25M";
      }
      enum "ether-media-type-qsfp-h40ge-aoc30m" {
        value 374;
        tailf:code-name "ENUM_media_type_class_ETHER_MEDIA_QSFP_H40GE_AOC30M";
      }
      enum "ether-media-type-sfp-gpon" {
        value 375;
        tailf:code-name "ENUM_media_type_class_ETHER_MEDIA_SFP_GPON";
      }
      enum "ether-media-type-sfp-25ge-csr" {
        value 376;
        tailf:code-name "ENUM_media_type_class_ETHER_MEDIA_SFP_25GE_CSR";
      }
      enum "ether-media-type-10gbase-cu2m" {
        value 377;
        tailf:code-name "ENUM_media_type_class_ETHER_MEDIA_10GBASE_CU2M";
      }
      enum "ether-media-type-qsfp-100ge-er4l" {
        value 378;
        tailf:code-name "ENUM_media_type_class_ETHER_MEDIA_QSFP_100GE_ER4L";
      }
      enum "ether-media-type-sfp-10ge-csr-s" {
        value 379;
        tailf:code-name "ENUM_media_type_class_ETHER_MEDIA_SFP_10GE_CSR_S";
      }
      enum "ether-media-type-qsfp-40ge-csr-s" {
        value 380;
        tailf:code-name "ENUM_media_type_class_ETHER_MEDIA_QSFP_40GE_CSR_S";
      }
      enum "ether-media-type-qsfp28-4sfp25g-cu1m" {
        value 381;
        tailf:code-name "ENUM_media_type_class_ETHER_MEDIA_QSFP28_4SFP25G_CU1M";
      }
      enum "ether-media-type-qsfp28-4sfp25g-cu2m" {
        value 382;
        tailf:code-name "ENUM_media_type_class_ETHER_MEDIA_QSFP28_4SFP25G_CU2M";
      }
      enum "ether-media-type-qsfp28-4sfp25g-cu3m" {
        value 383;
        tailf:code-name "ENUM_media_type_class_ETHER_MEDIA_QSFP28_4SFP25G_CU3M";
      }
      enum "ether-media-type-qsfp28-4sfp25g-cu5m" {
        value 384;
        tailf:code-name "ENUM_media_type_class_ETHER_MEDIA_QSFP28_4SFP25G_CU5M";
      }
      enum "ether-media-type-10gbase-cu1-5m" {
        value 385;
        tailf:code-name "ENUM_media_type_class_ETHER_MEDIA_10GBASE_CU1_5M";
      }
      enum "ether-media-type-10gbase-cu2-5m" {
        value 386;
        tailf:code-name "ENUM_media_type_class_ETHER_MEDIA_10GBASE_CU2_5M";
      }
      enum "ether-media-type-qsfp-4x10g-lr-s" {
        value 387;
        tailf:code-name "ENUM_media_type_class_ETHER_MEDIA_QSFP_4X10G_LR_S";
      }
      enum "ether-media-type-qsfp-4x10g-aoc1m" {
        value 388;
        tailf:code-name "ENUM_media_type_class_ETHER_MEDIA_QSFP_4X10G_AOC1M";
      }
      enum "ether-media-type-qsfp-4x10g-aoc2m" {
        value 389;
        tailf:code-name "ENUM_media_type_class_ETHER_MEDIA_QSFP_4X10G_AOC2M";
      }
      enum "ether-media-type-qsfp-4x10g-aoc3m" {
        value 390;
        tailf:code-name "ENUM_media_type_class_ETHER_MEDIA_QSFP_4X10G_AOC3M";
      }
      enum "ether-media-type-qsfp-4x10g-aoc5m" {
        value 391;
        tailf:code-name "ENUM_media_type_class_ETHER_MEDIA_QSFP_4X10G_AOC5M";
      }
      enum "ether-media-type-qsfp-4x10g-aoc7m" {
        value 392;
        tailf:code-name "ENUM_media_type_class_ETHER_MEDIA_QSFP_4X10G_AOC7M";
      }
      enum "ether-media-type-qsfp-4x10g-aoc10m" {
        value 393;
        tailf:code-name "ENUM_media_type_class_ETHER_MEDIA_QSFP_4X10G_AOC10M";
      }
      enum "ether-media-type-qsfp-4x10g-aoc15m" {
        value 394;
        tailf:code-name "ENUM_media_type_class_ETHER_MEDIA_QSFP_4X10G_AOC15M";
      }
      enum "ether-media-type-qsfp-4sfp10g-cu0-5m" {
        value 395;
        tailf:code-name "ENUM_media_type_class_ETHER_MEDIA_QSFP_4SFP10G_CU0_5M";
      }
      enum "ether-media-type-qsfp-4sfp10g-cu1m" {
        value 396;
        tailf:code-name "ENUM_media_type_class_ETHER_MEDIA_QSFP_4SFP10G_CU1M";
      }
      enum "ether-media-type-qsfp-4sfp10g-cu2m" {
        value 397;
        tailf:code-name "ENUM_media_type_class_ETHER_MEDIA_QSFP_4SFP10G_CU2M";
      }
      enum "ether-media-type-qsfp-4sfp10g-cu3m" {
        value 398;
        tailf:code-name "ENUM_media_type_class_ETHER_MEDIA_QSFP_4SFP10G_CU3M";
      }
      enum "ether-media-type-qsfp-4sfp10g-cu4m" {
        value 399;
        tailf:code-name "ENUM_media_type_class_ETHER_MEDIA_QSFP_4SFP10G_CU4M";
      }
      enum "ether-media-type-qsfp-4sfp10g-cu5m" {
        value 400;
        tailf:code-name "ENUM_media_type_class_ETHER_MEDIA_QSFP_4SFP10G_CU5M";
      }
      enum "ether-media-type-qsfp-4x10g-ac1m" {
        value 401;
        tailf:code-name "ENUM_media_type_class_ETHER_MEDIA_QSFP_4X10G_AC1M";
      }
      enum "ether-media-type-qsfp-4x10g-ac3m" {
        value 402;
        tailf:code-name "ENUM_media_type_class_ETHER_MEDIA_QSFP_4X10G_AC3M";
      }
      enum "ether-media-type-qsfp-4x10g-ac5m" {
        value 403;
        tailf:code-name "ENUM_media_type_class_ETHER_MEDIA_QSFP_4X10G_AC5M";
      }
      enum "ether-media-type-qsfp-4x10g-ac7m" {
        value 404;
        tailf:code-name "ENUM_media_type_class_ETHER_MEDIA_QSFP_4X10G_AC7M";
      }
      enum "ether-media-type-qsfp-4x10g-ac10m" {
        value 405;
        tailf:code-name "ENUM_media_type_class_ETHER_MEDIA_QSFP_4X10G_AC10M";
      }
      enum "ether-media-type-qsfp-100ge-sr4" {
        value 406;
        tailf:code-name "ENUM_media_type_class_ETHER_MEDIA_QSFP_100GE_SR4";
      }
      enum "ether-media-type-qsfp-100ge-lr4" {
        value 407;
        tailf:code-name "ENUM_media_type_class_ETHER_MEDIA_QSFP_100GE_LR4";
      }
      enum "ether-media-type-10gbase-cu0-5m" {
        value 408;
        tailf:code-name "ENUM_media_type_class_ETHER_MEDIA_10GBASE_CU0_5M";
      }
      enum "ether-media-type-10gbase-cu4m" {
        value 409;
        tailf:code-name "ENUM_media_type_class_ETHER_MEDIA_10GBASE_CU4M";
      }
      enum "ether-media-type-qsfp-40g-100g-srbd" {
        value 410;
        tailf:code-name "ENUM_media_type_class_ETHER_MEDIA_QSFP_40G_100G_SRBD";
      }
      enum "ether-media-type-qsfp-h40ge-cu0-5m" {
        value 411;
        tailf:code-name "ENUM_media_type_class_ETHER_MEDIA_QSFP_H40GE_CU0_5M";
      }
    }
    description
      "Maximum possible values for media type";
  }

  typedef dot3-stats-versions {
    type enumeration {
      enum "not-supported" {
        value 0;
        description
          "Dot 3 error counters are not supported";
        tailf:code-name "ENUM_dot3_stats_versions_DOT3_NONE";
      }
      enum "dot3-version-2" {
        value 1;
        description
          "Version 2 dot 3 error counters";
        tailf:code-name "ENUM_dot3_stats_versions_DOT3_VERSION_2";
      }
    }
    description
      "The version of dot 3 error counters.";
  }

  typedef serial-crc {
    type enumeration {
      enum "serial-crc32" {
        value 0;
        description
          "32-bit Cyclic Redundancy Code";
        tailf:code-name "ENUM_serial_crc_SERIAL_CRC32";
      }
      enum "serial-crc16" {
        value 1;
        description
          "16 bit Cyclic Redundancy Code";
        tailf:code-name "ENUM_serial_crc_SERIAL_CRC16";
      }
    }
    description
      "The Cyclic Redundancy Code type";
  }

  typedef subrate-speed {
    type enumeration {
      enum "dsx1-subrate-56kbps" {
        value 0;
        description
          "56 kilobits per second subrate";
        tailf:code-name "ENUM_subrate_speed_DSX1_SUBRATE_56KBPS";
      }
      enum "dsx1-subrate-64kbps" {
        value 1;
        description
          "64 kilobits per second subrate";
        tailf:code-name "ENUM_subrate_speed_DSX1_SUBRATE_64KBPS";
      }
    }
    description
      "The subrate on a serial interface";
  }

  typedef t1e1-loopback-mode {
    type enumeration {
      enum "t1e1-no-loopback" {
        value 0;
        description
          "No loopback mode";
        tailf:code-name "ENUM_t1e1_loopback_mode_T1E1_NO_LOOPBACK";
      }
      enum "t1e1-cli-local-loopback" {
        value 1;
        description
          "Command line interface enforced local loopback";
        tailf:code-name "ENUM_t1e1_loopback_mode_T1E1_CLI_LOCAL_LOOPBACK";
      }
      enum "t1e1-line-cli-local-loopback" {
        value 2;
        description
          "Command line interface enforced line local loopback";
        tailf:code-name "ENUM_t1e1_loopback_mode_T1E1_LINE_CLI_LOCAL_LOOPBACK";
      }
      enum "t1e1-payload-cli-local-loopback" {
        value 3;
        description
          "Command line interface enforced payload local loopback";
        tailf:code-name "ENUM_t1e1_loopback_mode_T1E1_PAYLOAD_CLI_LOCAL_LOOPBACK";
      }
      enum "t1e1-local-line-loopback" {
        value 4;
        description
          "Local line loopback";
        tailf:code-name "ENUM_t1e1_loopback_mode_T1E1_LOCAL_LINE_LOOPBACK";
      }
      enum "t1e1-local-payload-loopback" {
        value 5;
        description
          "Local payload loopback";
        tailf:code-name "ENUM_t1e1_loopback_mode_T1E1_LOCAL_PAYLOAD_LOOPBACK";
      }
      enum "t1e1-local-ansi-fdl-remote-loopback" {
        value 6;
        description
          "Line ANSI FDL remote loopback";
        tailf:code-name "ENUM_t1e1_loopback_mode_T1E1_LINE_ANSI_FDL_REMOTE_LOOPBACK";
      }
      enum "t1e1-line-att-fdl-remote-loopback" {
        value 7;
        description
          "Line ATT FDL remote loopback";
        tailf:code-name "ENUM_t1e1_loopback_mode_T1E1_LINE_ATT_FDL_REMOTE_LOOPBACK";
      }
      enum "t1e1-payload-ansi-fdl-remote-loopback" {
        value 8;
        description
          "Payload ANSI FDL remote loopback";
        tailf:code-name "ENUM_t1e1_loopback_mode_T1E1_PAYLOAD_ANSI_FDL_REMOTE_LOOPBACK";
      }
      enum "t1e1-payload-att-fdl-remote-loopback" {
        value 9;
        description
          "Payload ATT FDL remote loopback";
        tailf:code-name "ENUM_t1e1_loopback_mode_T1E1_PAYLOAD_ATT_FDL_REMOTE_LOOPBACK";
      }
      enum "t1e1-line-iboc-remote-loopback" {
        value 10;
        description
          "Line IBOC remote loopback";
        tailf:code-name "ENUM_t1e1_loopback_mode_T1E1_LINE_IBOC_REMOTE_LOOPBACK";
      }
      enum "t1e1-line-ansi-fdl-local-loopback" {
        value 11;
        description
          "Line ANSI FDL local loopback";
        tailf:code-name "ENUM_t1e1_loopback_mode_T1E1_LINE_ANSI_FDL_LOCAL_LOOPBACK";
      }
      enum "t1e1-line-att-fdl-local-loopback" {
        value 12;
        description
          "Line ATT FDL local loopback";
        tailf:code-name "ENUM_t1e1_loopback_mode_T1E1_LINE_ATT_FDL_LOCAL_LOOPBACK";
      }
      enum "t1e1-payload-ansi-fdl-local-loopback" {
        value 13;
        description
          "Payload ANSI FDL local loopback";
        tailf:code-name "ENUM_t1e1_loopback_mode_T1E1_PAYLOAD_ANSI_FDL_LOCAL_LOOPBACK";
      }
      enum "t1e1-payload-att-fdl-local-loopback" {
        value 14;
        description
          "Payload ATT FDL local loopback";
        tailf:code-name "ENUM_t1e1_loopback_mode_T1E1_PAYLOAD_ATT_FDL_LOCAL_LOOPBACK";
      }
      enum "t1e1-line-iboc-local-loopback" {
        value 15;
        description
          "Line IBOC local loopback";
        tailf:code-name "ENUM_t1e1_loopback_mode_T1E1_LINE_IBOC_LOCAL_LOOPBACK";
      }
    }
    description
      "Loopback mode type";
  }

  typedef signal-status {
    type enumeration {
      enum "down" {
        value 0;
        description
          "Signal is down";
        tailf:code-name "ENUM_signal_status_SIGNAL_DOWN";
      }
      enum "up" {
        value 1;
        description
          "Signal is up";
        tailf:code-name "ENUM_signal_status_SIGNAL_UP";
      }
    }
    description
      "Synchronous serial interface signal status";
  }

  typedef idle-character-type {
    type enumeration {
      enum "flag" {
        value 0;
        description
          "Send HDLC flag characters between packets";
        tailf:code-name "ENUM_idle_character_type_CHARACTER_FLAG";
      }
      enum "marks" {
        value 1;
        description
          "Send mark characters between packets";
        tailf:code-name "ENUM_idle_character_type_CHARACTER_MARKS";
      }
    }
    description
      "Synchronous serial idle character";
  }

  typedef sc-filter-state {
    type enumeration {
      enum "inactive" {
        value 0;
        description
          "Storm control filter is inactive";
        tailf:code-name "ENUM_sc_filter_state_STATE_SC_FILTER_INACTIVE";
      }
      enum "link-down" {
        value 1;
        description
          "Storm control filter link is down";
        tailf:code-name "ENUM_sc_filter_state_STATE_SC_FILTER_LINKDOWN";
      }
      enum "blocking" {
        value 2;
        description
          "Storm control filter is blocking";
        tailf:code-name "ENUM_sc_filter_state_STATE_SC_FILTER_BLOCKING";
      }
      enum "forwarding" {
        value 3;
        description
          "Storm control filter is forwarding";
        tailf:code-name "ENUM_sc_filter_state_STATE_SC_FILTER_FORWARDING";
      }
    }
    description
      "Storm control filter state";
  }

  typedef sc-suppress-type {
    type enumeration {
      enum "bandwidth" {
        value 0;
        description
          "Storm control suppression is in bandwidth";
        tailf:code-name "ENUM_sc_suppress_type_SC_SUPPRESS_TYPE_BW";
      }
      enum "bits-per-second" {
        value 1;
        description
          "Storm control suppression is in bits-per-second";
        tailf:code-name "ENUM_sc_suppress_type_SC_SUPPRESS_TYPE_BPS";
      }
      enum "packets-per-second" {
        value 2;
        description
          "Storm control suppression is in packets-per-second";
        tailf:code-name "ENUM_sc_suppress_type_SC_SUPPRESS_TYPE_PPS";
      }
    }
    description
      "Storm control suppression type";
  }

  grouping wred-class-counts {
    description
      "WRED class count types";
    leaf wred-tx-pkts {
      type uint64;
      description
        "Transmitted packets";
    }
    leaf wred-tx-bytes {
      type uint64;
      description
        "Transmitted bytes";
    }
    leaf wred-tail-drop-pkts {
      type uint64;
      description
        "Tail drop packets";
    }
    leaf wred-tail-drop-bytes {
      type uint64;
      description
        "Tail drop bytes";
    }
    leaf wred-early-drop-pkts {
      type uint64;
      description
        "Early drop packets";
    }
    leaf wred-early-drop-bytes {
      type uint64;
      description
        "Early drop bytes";
    }
  }

  grouping marking-dscp-stats {
    description
      "Statistics for set dscp";
    leaf dscp {
      type uint32;
      description
        "dscp marking";
    }
    leaf marked-pkts {
      type uint64;
      description
        "Number of packets been marked";
    }
  }

  grouping marking-dscp-tunnel-stats {
    description
      "Statistics for set dscp tunnel";
    leaf dscp-val {
      type uint32;
      description
        "dscp value";
    }
    leaf marked-pkts {
      type uint64;
      description
        "Number of packets been marked";
    }
  }

  grouping marking-cos-stats {
    description
      "Statistics for set cos";
    leaf cos-val {
      type uint32;
      description
        "cos value";
    }
    leaf marked-pkts {
      type uint64;
      description
        "Number of packets been marked";
    }
  }

  grouping marking-cos-inner-stats {
    description
      "Statistics for set cos-inner";
    leaf cos-inner-val {
      type uint32;
      description
        "cos inner value";
    }
    leaf marked-pkts {
      type uint64;
      description
        "Number of packets been marked";
    }
  }

  grouping marking-discard-class-stats {
    description
      "Statistics for set discard-class";
    leaf disc-class-val {
      type uint32;
      description
        "discard-class value";
    }
    leaf marked-pkts {
      type uint64;
      description
        "Number of packets been marked";
    }
  }

  grouping marking-qos-grp-stats {
    description
      "Statistics for set qos-group";
    leaf qos-grp-val {
      type uint32;
      description
        "qos group value";
    }
    leaf marked-pkts {
      type uint64;
      description
        "Number of packets been marked";
    }
  }

  grouping marking-prec-stats {
    description
      "Statistics for set precedence";
    leaf prec-val {
      type uint32;
      description
        "precedence value";
    }
    leaf marked-pkts {
      type uint64;
      description
        "Number of packets been marked";
    }
  }

  grouping marking-prec-tunnel-stats {
    description
      "Statistics for set precedence tunnel";
    leaf prec-val {
      type uint32;
      description
        "precedence value";
    }
    leaf marked-pkts {
      type uint64;
      description
        "Number of packets been marked";
    }
  }

  grouping marking-mpls-exp-imp-stats {
    description
      "Statistics for set mpls exp imposition";
    leaf mpls-exp-imp-val {
      type uint32;
      description
        "mpls exp value";
    }
    leaf marked-pkts {
      type uint64;
      description
        "Number of packets been marked";
    }
  }

  grouping marking-mpls-exp-top-stats {
    description
      "Statistics for set mpls exp imposition";
    leaf mpls-exp-top-val {
      type uint32;
      description
        "mpls exp value";
    }
    leaf marked-pkts {
      type uint64;
      description
        "Number of packets been marked";
    }
  }

  grouping marking-fr-de-stats {
    description
      "Statistics for set fr-de";
    leaf fr-de {
      type boolean;
      description
        "fr de set or not";
    }
    leaf marked-pkts {
      type uint64;
      description
        "Number of packets been marked";
    }
  }

  grouping marking-fr-fecn-becn-stats {
    description
      "Statistics for set fr-fecn-becn";
    leaf fecn-becn-val {
      type uint32;
      description
        "fecn becn value. qos:percent-value-1to100";
    }
    leaf marked-pkts {
      type uint64;
      description
        "Number of packets been marked";
    }
  }

  grouping marking-atm-clp-stats {
    description
      "Statistics for set atm-clp";
    leaf atm-clp-val {
      type uint8;
      description
        "atm clp value";
    }
    leaf marked-pkts {
      type uint64;
      description
        "Number of packets been marked";
    }
  }

  grouping marking-vlan-inner-stats {
    description
      "Statistics for set vlan-inner";
    leaf vlan-inner-val {
      type uint32;
      description
        "vlan value";
    }
    leaf marked-pkts {
      type uint64;
      description
        "Number of packets been marked";
    }
  }

  grouping marking-dei-stats {
    description
      "Statistics for set dei";
    leaf dei-imp-value {
      type uint32;
      description
        "dei value";
    }
    leaf marked-pkts {
      type uint64;
      description
        "Number of packets been marked";
    }
  }

  grouping marking-dei-imp-stats {
    description
      "Statistics for set dei-imposition";
    leaf dei-imp-value {
      type uint32;
      description
        "dei value";
    }
    leaf marked-pkts {
      type uint64;
      description
        "Number of packets been marked";
    }
  }

  grouping marking-srp-priority-stats {
    description
      "Statistics for set srp-priority";
    leaf srp-priority-value {
      type uint8;
      description
        "srp priority value";
    }
    leaf marked-pkts {
      type uint64;
      description
        "Number of packets been marked";
    }
  }

  grouping marking-wlan-user-priority-stats {
    description
      "Statistics for set wlan-user-priority";
    leaf wlan-user-priority-value {
      type uint8;
      description
        "wlan user priority value";
    }
    leaf marked-pkts {
      type uint64;
      description
        "Number of packets been marked";
    }
  }

  grouping marking-stats {
    description
      "Marking statistics";
    container marking-dscp-stats-val {
      description
        "Statistics for set dscp";
      uses interfaces-ios-xe-oper:marking-dscp-stats;
    }
    container marking-dscp-tunnel-stats-val {
      description
        "Statistics for set dscp tunnel";
      uses interfaces-ios-xe-oper:marking-dscp-tunnel-stats;
    }
    container marking-cos-stats-val {
      description
        "Statistics for set cos";
      uses interfaces-ios-xe-oper:marking-cos-stats;
    }
    container marking-cos-inner-stats-val {
      description
        "Statistics for set cos-inner";
      uses interfaces-ios-xe-oper:marking-cos-inner-stats;
    }
    container marking-discard-class-stats-val {
      description
        "Statistics for set discard-class";
      uses interfaces-ios-xe-oper:marking-discard-class-stats;
    }
    container marking-qos-grp-stats-val {
      description
        "Statistics for set qos-group";
      uses interfaces-ios-xe-oper:marking-qos-grp-stats;
    }
    container marking-prec-stats-val {
      description
        "Statistics for set precedence";
      uses interfaces-ios-xe-oper:marking-prec-stats;
    }
    container marking-prec-tunnel-stats-val {
      description
        "Statistics for set precedence tunnel";
      uses interfaces-ios-xe-oper:marking-prec-tunnel-stats;
    }
    container marking-mpls-exp-imp-stats-val {
      description
        "Statistics for set mpls exp imposition";
      uses interfaces-ios-xe-oper:marking-mpls-exp-imp-stats;
    }
    container marking-mpls-exp-top-stats-val {
      description
        "Statistics for set mpls exp topmost";
      uses interfaces-ios-xe-oper:marking-mpls-exp-top-stats;
    }
    container marking-fr-de-stats-val {
      description
        "Statistics for set fr-de";
      uses interfaces-ios-xe-oper:marking-fr-de-stats;
    }
    container marking-fr-fecn-becn-stats-val {
      description
        "Statistics for set fr-fecn-becn";
      uses interfaces-ios-xe-oper:marking-fr-fecn-becn-stats;
    }
    container marking-atm-clp-stats-val {
      description
        "Statistics for set atm-clp";
      uses interfaces-ios-xe-oper:marking-atm-clp-stats;
    }
    container marking-vlan-inner-stats-val {
      description
        "Statistics for set vlan-inner";
      uses interfaces-ios-xe-oper:marking-vlan-inner-stats;
    }
    container marking-dei-stats-val {
      description
        "Statistics for set dei";
      uses interfaces-ios-xe-oper:marking-dei-stats;
    }
    container marking-dei-imp-stats-val {
      description
        "Statistics for set dei-imposition";
      uses interfaces-ios-xe-oper:marking-dei-imp-stats;
    }
    container marking-srp-priority-stats-val {
      description
        "Statistics for set srp-priority";
      uses interfaces-ios-xe-oper:marking-srp-priority-stats;
    }
    container marking-wlan-user-priority-stats-val {
      description
        "Statistics for set wlan-user-priority";
      uses interfaces-ios-xe-oper:marking-wlan-user-priority-stats;
    }
  }

  grouping cos-key {
    description
      "COS key type";
    leaf cos-min {
      type uint32;
      description
        "Min COS value";
    }
    leaf cos-max {
      type uint32;
      description
        "Max COS value";
    }
  }

  grouping disc-class-key {
    description
      "Discard class key type";
    leaf disc-class-min {
      type uint32;
      description
        "Minimum value for discard class in the range";
    }
    leaf disc-class-max {
      type uint32;
      description
        "Maximum value for discard class in the range";
    }
  }

  grouping dscp-key {
    description
      "DSCP key type";
    leaf dscp-min {
      type uint32;
      description
        "Minimum of dscp range";
    }
    leaf dscp-max {
      type uint32;
      description
        "Maximum of dscp range";
    }
  }

  grouping qos-grp-key {
    description
      "QoS group key type";
    leaf qos-group-min {
      type uint32;
      description
        "Specifies the minimum value range from 0 to used to identify a QoS group value";
    }
    leaf qos-group-max {
      type uint32;
      description
        "Specifies the maximum value range from 0 to used to identify a QoS group value";
    }
  }

  grouping mpls-exp-key {
    description
      "MPLS EXP key type";
    leaf exp-min {
      type uint32;
      description
        "The minimum EXP field value to be used as match criteria. Any number from 0 to 7";
    }
    leaf exp-max {
      type uint32;
      description
        "The maximum EXP field value to be used as match criteria. Any number from 0 to 7";
    }
  }

  grouping prec-key {
    description
      "Precedence key type";
    leaf prec-min {
      type uint32;
      description
        "Precedence min";
    }
    leaf prec-max {
      type uint32;
      description
        "Precedence max";
    }
  }

  grouping dei-key {
    description
      "DEI key type";
    leaf dei-min {
      type uint32;
      description
        "Dei min";
    }
    leaf dei-max {
      type uint32;
      description
        "Dei max";
    }
  }

  grouping clp-key {
    description
      "CLP key type";
    leaf clp-val {
      type uint32;
      description
        "Composed by multiple atm clp values";
    }
  }

  grouping subclass-list {
    description
      "Subclass data";
    leaf match-type {
      type interfaces-ios-xe-oper:qos-match-type;
      description
        "Subclass match type";
    }
    list cos-counters {
      key "cos-min cos-max";
      description
        "Counters for sub-class matching a range of
         Class-of-Service (COS) value (and, optionally, additional COS range";
      uses interfaces-ios-xe-oper:cos-key;
      uses interfaces-ios-xe-oper:wred-class-counts;
    }
    container cos-default {
      description
        "statistics for cos default";
      uses interfaces-ios-xe-oper:wred-class-counts;
    }
    list dscp-counters {
      key "dscp-min dscp-max";
      description
        "List for statistics based on dscp value range";
      uses interfaces-ios-xe-oper:dscp-key;
      uses interfaces-ios-xe-oper:wred-class-counts;
    }
    container dscp-default {
      description
        "Statistics for dscp default";
      uses interfaces-ios-xe-oper:wred-class-counts;
    }
    list discard-class-counters {
      key "disc-class-min disc-class-max";
      description
        "Composed multiple discard class ranges";
      uses interfaces-ios-xe-oper:disc-class-key;
      uses interfaces-ios-xe-oper:wred-class-counts;
    }
    container disc-class-default {
      description
        "Statistics for discard class default";
      uses interfaces-ios-xe-oper:wred-class-counts;
    }
    list precedence-counters {
      key "prec-min prec-max";
      description
        "List for statistics based on precedence value range";
      uses interfaces-ios-xe-oper:prec-key;
      uses interfaces-ios-xe-oper:wred-class-counts;
    }
    container prec-default {
      description
        "Precedence default";
      uses interfaces-ios-xe-oper:wred-class-counts;
    }
    list mpls-exp-counters {
      key "exp-min exp-max";
      description
        "List for statistics based on mpls exp value range";
      uses interfaces-ios-xe-oper:mpls-exp-key;
      uses interfaces-ios-xe-oper:wred-class-counts;
    }
    container mpls-exp-default {
      description
        "Statistics for mpls-exp default";
      uses interfaces-ios-xe-oper:wred-class-counts;
    }
    list dei-counters {
      key "dei-min dei-max";
      description
        "Composed by multiple dei ranges";
      uses interfaces-ios-xe-oper:dei-key;
      uses interfaces-ios-xe-oper:wred-class-counts;
    }
    container dei-counts-default {
      description
        "Statistics for dei default";
      uses interfaces-ios-xe-oper:wred-class-counts;
    }
    list clp-counters {
      key "clp-val";
      description
        "Statistics for each value range for a specific subclass type";
      uses interfaces-ios-xe-oper:clp-key;
      uses interfaces-ios-xe-oper:wred-class-counts;
    }
    container clp-default {
      description
        "Statistic for atm clp default";
      uses interfaces-ios-xe-oper:wred-class-counts;
    }
  }

  grouping classifier-entry-statistics {
    description
      "Classifier entry statistics";
    leaf classified-pkts {
      type uint64;
      description
        "Number of total packets which filtered to the classifier-entry";
    }
    leaf classified-bytes {
      type uint64;
      description
        "Number of total bytes which filtered to the classifier-entry";
    }
    leaf classified-rate {
      type uint64;
      description
        "Rate of average data flow through the classifier-entry";
    }
  }

  grouping diffserv-target-classifier-statistics-key {
    description
      "Diffserv classifier statistics key";
    leaf classifier-entry-name {
      type string;
      description
        "Classifier Entry Name";
    }
    leaf parent-path {
      type string;
      description
        "Path of the Classifier Entry in a hierarchical policy";
    }
  }

  grouping wred-stats {
    description
      "WRED counters";
    leaf early-drop-pkts {
      type uint64;
      description
        "Early drop packets";
    }
    leaf early-drop-bytes {
      type uint64;
      description
        "Early drop bytes";
    }
    leaf mean-queue-depth {
      type uint16;
      description
        "Current mean queue depth";
    }
    leaf transmitted-pkts {
      type uint64;
      description
        "Transmitted packets";
    }
    leaf transmitted-bytes {
      type uint64;
      description
        "Transmitted bytes";
    }
    leaf tail-drop-pkts {
      type uint64;
      description
        "Total number of packets dropped";
    }
    leaf tail-drop-bytes {
      type uint64;
      description
        "Total number of bytes dropped";
    }
    leaf drop-pkts-flow {
      type uint64;
      description
        "Total number of packets dropped";
    }
    leaf drop-pkts-no-buffer {
      type uint64;
      description
        "Number of packets dropped due to buffers being
         unavailable system-wide or at the associated interface.
         This is a sub-set of drop-pkts";
    }
    leaf queue-peak-size-pkts {
      type uint64;
      description
        "Queue max que depth Packets";
    }
    leaf queue-peak-size-bytes {
      type uint64;
      description
        "Queue max que depth Bytes";
    }
    leaf bandwidth-exceed-drops {
      type uint64;
      description
        "Priority stats. Bandwidth exceed drops";
    }
  }

  grouping cac-stats {
    description
      "CAC statistics";
    leaf num-admitted-flows {
      type uint32;
      description
        "Number of admitted flows";
    }
    leaf num-non-admitted-flows {
      type uint32;
      description
        "Number of non-admitted flows";
    }
  }

  grouping queuing-statistics {
    description
      "Queue related statistics";
    leaf output-pkts {
      type uint64;
      description
        "Number of packets transmitted from queue";
    }
    leaf output-bytes {
      type uint64;
      description
        "Number of bytes transmitted from queue";
    }
    leaf queue-size-pkts {
      type uint64;
      description
        "Number of packets currently buffered ";
    }
    leaf queue-size-bytes {
      type uint64;
      description
        "Number of bytes currently buffered";
    }
    leaf drop-pkts {
      type uint64;
      description
        "Total number of packets dropped";
    }
    leaf drop-bytes {
      type uint64;
      description
        "Total number of bytes dropped";
    }
    container wred-stats {
      description
        "WRED Counters";
      uses interfaces-ios-xe-oper:wred-stats;
    }
    container cac-stats {
      description
        "CAC statistics";
      uses interfaces-ios-xe-oper:cac-stats;
    }
  }

  grouping meter-statistics {
    description
      "Metering Counters";
    leaf meter-id {
      type uint16;
      description
        "Meter Identifier";
    }
    leaf meter-succeed-pkts {
      type uint64;
      description
        "Number of packets which succeed the meter";
    }
    leaf meter-succeed-bytes {
      type uint64;
      description
        "Bytes of packets which succeed the meter";
    }
    leaf meter-failed-pkts {
      type uint64;
      description
        "Number of packets which failed the meter";
    }
    leaf meter-failed-bytes {
      type uint64;
      description
        "Bytes of packets which failed the meter";
    }
  }

  grouping diffserv-target-classifier-statistics {
    description
      "Diffserv classifier statistics";
    container classifier-entry-stats {
      description
        "Classifier Counters";
      uses interfaces-ios-xe-oper:classifier-entry-statistics;
    }
    list meter-stats {
      key "meter-id";
      description
        "Meter statistics";
      uses interfaces-ios-xe-oper:meter-statistics;
    }
    container queuing-stats {
      description
        "Queuing Counters";
      uses interfaces-ios-xe-oper:queuing-statistics;
    }
    list subclass-list {
      key "match-type";
      description
        "List of statistics for random-detect
         based on subclass type and value pair
         Technically these are a field in the queuing
         statistics -> wred statistics, but GREEN EI
         does not allow that nesting structure";
      uses interfaces-ios-xe-oper:subclass-list;
    }
    container marking-stats {
      description
        "Statistics for marking actions";
      uses interfaces-ios-xe-oper:marking-stats;
    }
    leaf has-child {
      type boolean;
      description
        "Class has child policy flag";
    }
  }

  grouping diffserv-target-entry-key {
    description
      "Key to the diffserv";
    leaf direction {
      type interfaces-ios-xe-oper:qos-direction;
      description
        "Direction fo the traffic flow either inbound or outbound";
    }
    leaf policy-name {
      type string;
      description
        "Policy entry name";
    }
  }

  grouping agg-priority-stats {
    description
      "Type for counters in aggregate priority";
    leaf output-pkts {
      type uint64;
      description
        "Number of packets transmitted from queue";
    }
    leaf output-bytes {
      type uint64;
      description
        "Number of bytes transmitted from queue";
    }
    leaf queue-size-pkts {
      type uint64;
      description
        "Number of packets currently buffered";
    }
    leaf queue-size-bytes {
      type uint64;
      description
        "Number of bytes currently buffered";
    }
    leaf drop-pkts {
      type uint64;
      description
        "Total number of packets dropped";
    }
    leaf drop-bytes {
      type uint64;
      description
        "Total number of bytes dropped";
    }
    leaf drop-pkts-flow {
      type uint64;
      description
        "Number of packets that were dropped by
         flow-based fair-queuing (fair-queue).
         This is a sub-set of drop-pkts";
    }
    leaf drop-pkts-no-buffer {
      type uint64;
      description
        "Number of packets dropped due to buffers being
         unavailable system-wide or at the associated interface.
         This is a sub-set of drop-pkts";
    }
  }

  grouping threshold {
    description
      "Threshold Parameters";
    leaf bytes {
      type uint64;
      description
        "Threshold bytes";
    }
    leaf thresh-size-metric {
      type uint32;
      description
        "Threshold size unit";
    }
    leaf unit-val {
      type interfaces-ios-xe-oper:thresh-unit;
      description
        "Threshold size basic units";
    }
    leaf threshold-interval {
      type uint64;
      description
        "Threshold interval";
    }
    leaf thresh-interval-metric {
      type uint32;
      description
        "Threshold units metric";
    }
    leaf interval-unit-val {
      type interfaces-ios-xe-oper:thresh-unit;
      description
        "Threshold interval basic units";
    }
  }

  grouping priority-oper-list {
    description
      "Priority based statistics";
    leaf priority-level {
      type uint16;
      description
        "Priority Level, 0 means no priority level set";
    }
    container agg-priority-stats {
      description
        "Counters in aggregate priority";
      uses interfaces-ios-xe-oper:agg-priority-stats;
    }
    container qlimit-default-thresh {
      description
        "queue limit default threshold";
      uses interfaces-ios-xe-oper:threshold;
    }
    list qlimit-cos-thresh-list {
      key "cos-min cos-max";
      description
        "cos-based queue limit data";
      uses interfaces-ios-xe-oper:cos-key;
      uses interfaces-ios-xe-oper:threshold;
    }
    list qlimit-disc-class-thresh-list {
      key "disc-class-min disc-class-max";
      description
        "discard-class-based queue limit data";
      uses interfaces-ios-xe-oper:disc-class-key;
      uses interfaces-ios-xe-oper:threshold;
    }
    list qlimit-qos-grp-thresh-list {
      key "qos-group-min qos-group-max";
      description
        "qos-group-based queue limit data";
      uses interfaces-ios-xe-oper:qos-grp-key;
      uses interfaces-ios-xe-oper:threshold;
    }
    list qlimit-mpls-exp-thresh-list {
      key "exp-min exp-max";
      description
        "mpls-exp-based queue limit data";
      uses interfaces-ios-xe-oper:mpls-exp-key;
      uses interfaces-ios-xe-oper:threshold;
    }
    list qlimit-dscp-thresh-list {
      key "dscp-min dscp-max";
      description
        "queue limit per dscp range";
      uses interfaces-ios-xe-oper:dscp-key;
      uses interfaces-ios-xe-oper:threshold;
    }
  }

  grouping diffserv-target-entry {
    description
      "Diffserv target data";
    list diffserv-target-classifier-stats {
      key "classifier-entry-name parent-path";
      description
        "Statistics for each Classifier Entry in a Policy";
      uses interfaces-ios-xe-oper:diffserv-target-classifier-statistics-key;
      uses interfaces-ios-xe-oper:diffserv-target-classifier-statistics;
    }
    list priority-oper-list {
      key "priority-level";
      description
        "Statistics for aggregate priority per policy instance";
      uses interfaces-ios-xe-oper:priority-oper-list;
    }
  }

  grouping lag-aggregate-state {
    description
      "Operational state variables for logical
       aggregate / LAG interfaces";
    leaf aggregate-id {
      type string;
      description
        "Specify the logical aggregate interface to which
         this id belongs";
    }
    leaf lag-type {
      type interfaces-ios-xe-oper:aggregation-type;
      description
        "Type to define the lag-type, i.e., how the LAG is
         defined and managed";
    }
    leaf min-links {
      type uint16;
      description
        "Specifies the minimum number of member
         interfaces that must be active for the aggregate interface
         to be available";
    }
    leaf lag-speed {
      type uint32;
      description
        "Reports effective speed of the aggregate interface,
         based on speed of active member interfaces";
    }
    leaf-list members {
      type string;
      ordered-by user;
      description
        "List of current member interfaces for the aggregate,
         expressed as references to existing interfaces";
    }
  }

  grouping protocol-statistics {
    description
      "Protocol specific statistics";
    leaf in-pkts {
      type uint64;
      description
        "The total number of packets received for the specified
         address family, including those received in error";
    }
    leaf in-octets {
      type uint64;
      description
        "The total number of octets received in input packets
         for the specified address family, including those received
         in error.";
    }
    leaf in-error-pkts {
      type uint64;
      description
        "Number of packets discarded due to errors for the
         specified address family, including errors in the
         header, no route found to the destination, invalid
         address, unknown protocol, etc.";
    }
    leaf in-forwarded-pkts {
      type uint64;
      description
        "The number of input packets for which the device was not
         their final destination and for which the device
         attempted to find a route to forward them to that final
         destination.";
    }
    leaf in-forwarded-octets {
      type uint64;
      description
        "The number of octets received in input packets
         for the specified address family for which the device was
         not their final destination and for which the
         device attempted to find a route to forward them to that
         final destination.";
    }
    leaf in-discarded-pkts {
      type uint64;
      description
        "The number of input IP packets for the
         specified address family, for which no problems were
         encountered to prevent their continued processing, but
         were discarded (e.g., for lack of buffer space).";
    }
    leaf out-pkts {
      type uint64;
      description
        "The total number of IP packets for the
         specified address family that the device supplied
         to the lower layers for transmission.  This includes
         packets generated locally and those forwarded by the
         device.";
    }
    leaf out-octets {
      type uint64;
      description
        "The total number of octets in IP packets for the
         specified address family that the device
         supplied to the lower layers for transmission.  This
         includes packets generated locally and those forwarded by
         the device.";
    }
    leaf out-error-pkts {
      type uint64;
      description
        "Number of IP packets for the specified address family
         locally generated and discarded due to errors, including
         no route found to the IP destination.";
    }
    leaf out-forwarded-pkts {
      type uint64;
      description
        "The number of packets for which this entity was not their
         final IP destination and for which it was successful in
         finding a path to their final destination.text";
    }
    leaf out-forwarded-octets {
      type uint64;
      description
        "The number of octets in packets for which this entity was
         not their final IP destination and for which it was
         successful in finding a path to their final destination.";
    }
    leaf out-discarded-pkts {
      type uint64;
      description
        "The number of output IP packets for the
         specified address family for which no problem was
         encountered to prevent their transmission to their
         destination, but were discarded (e.g., for lack of
         buffer space).";
    }
  }

  grouping intf-statistics {
    description
      "Interface statistics";
    leaf discontinuity-time {
      type yang:date-and-time;
      description
        "The time on the most recent occasion at which any one or
         more of this interface's counters suffered a
         discontinuity.  If no such discontinuities have occurred
         since the last re-initialization of the local management
         subsystem, then this node contains the time the local
         management subsystem re-initialized itself";
    }
    leaf in-octets {
      type uint64;
      description
        "The total number of octets received on the interface,
         including framing characters.
         Discontinuities in the value of this counter can occur
         at re-initialization of the management system, and at
         other times as indicated by the value of discontinuity-time";
    }
    leaf in-unicast-pkts {
      type uint64;
      description
        "The number of packets, delivered by this sub-layer to a
         higher (sub-)layer, that were not addressed to a
         multicast or broadcast address at this sub-layer.
         Discontinuities in the value of this counter can occur
         at re-initialization of the management system, and at
         other times as indicated by the value of
         'discontinuity-time'.";
    }
    leaf in-broadcast-pkts {
      type uint64;
      description
        "The number of packets, delivered by this sub-layer to a
         higher (sub-)layer, that were addressed to a broadcast
         address at this sub-layer.
         Discontinuities in the value of this counter can occur
         at re-initialization of the management system, and at
         other times as indicated by the value of
         'discontinuity-time'";
    }
    leaf in-multicast-pkts {
      type uint64;
      description
        "The number of packets, delivered by this sub-layer to a
         higher (sub-)layer, that were addressed to a multicast
         address at this sub-layer.  For a MAC-layer protocol,
         this includes both Group and Functional addresses.
         Discontinuities in the value of this counter can occur
         at re-initialization of the management system, and at
         other times as indicated by the value of
         'discontinuity-time'";
    }
    leaf in-discards {
      type uint32;
      description
        "The number of inbound packets that were chosen to be
         discarded even though no errors had been detected to
         prevent their being deliverable to a higher-layer
         protocol.  One possible reason for discarding such a
         packet could be to free up buffer space.
         Discontinuities in the value of this counter can occur
         at re-initialization of the management system, and at
         other times as indicated by the value of
         'discontinuity-time'";
    }
    leaf in-errors {
      type uint32;
      description
        "For packet-oriented interfaces, the number of inbound
         packets that contained errors preventing them from being
         deliverable to a higher-layer protocol.  For character-
         oriented or fixed-length interfaces, the number of
         inbound transmission units that contained errors
         preventing them from being deliverable to a higher-layer protocol.
         Discontinuities in the value of this counter can occur
         at re-initialization of the management system, and at
         other times as indicated by the value of
         'discontinuity-time'";
    }
    leaf in-unknown-protos {
      type uint32;
      description
        "For packet-oriented interfaces, the number of packets
         received via the interface that were discarded because
         of an unknown or unsupported protocol.  For
         character-oriented or fixed-length interfaces that
         support protocol multiplexing, the number of transmission
         units received via the interface that were discarded because
         of an unknown or unsupported protocol.
         For any interface that does not support protocol
         multiplexing, this counter is not present.
         Discontinuities in the value of this counter can occur
         at re-initialization of the management system, and at
         other times as indicated by the value of 'discontinuity-time'";
    }
    leaf out-octets {
      type uint32;
      description
        "The total number of octets transmitted out of the
         interface, including framing characters.
         Discontinuities in the value of this counter can occur
         at re-initialization of the management system, and at
         other times as indicated by the value of
         'discontinuity-time'";
    }
    leaf out-unicast-pkts {
      type uint64;
      description
        "The total number of packets that higher-level protocols
         requested be transmitted, and that were not addressed
         to a multicast or broadcast address at this sub-layer,
         including those that were discarded or not sent.
         Discontinuities in the value of this counter can occur
         at re-initialization of the management system, and at
         other times as indicated by the value of 'discontinuity-time'";
    }
    leaf out-broadcast-pkts {
      type uint64;
      description
        "The total number of packets that higher-level protocols
         requested be transmitted, and that were addressed to a
         broadcast address at this sub-layer, including those
         that were discarded or not sent.
         Discontinuities in the value of this counter can occur
         at re-initialization of the management system, and at
         other times as indicated by the value of
         'discontinuity-time'";
    }
    leaf out-multicast-pkts {
      type uint64;
      description
        "The total number of packets that higher-level protocols
         requested be transmitted, and that were addressed to a
         multicast address at this sub-layer, including those
         that were discarded or not sent.  For a MAC-layer
         protocol, this includes both Group and Functional addresses.
         Discontinuities in the value of this counter can occur
         at re-initialization of the management system, and at
         other times as indicated by the value of
         'discontinuity-time'";
    }
    leaf out-discards {
      type uint64;
      description
        "The number of outbound packets that were chosen to be
         discarded even though no errors had been detected to
         prevent their being transmitted.  One possible reason
         for discarding such a packet could be to free up buffer space.
         Discontinuities in the value of this counter can occur
         at re-initialization of the management system, and at
         other times as indicated by the value of
         'discontinuity-time'";
    }
    leaf out-errors {
      type uint64;
      description
        "For packet-oriented interfaces, the number of outbound
         packets that could not be transmitted because of errors.
         For character-oriented or fixed-length interfaces, the
         number of outbound transmission units that could not be
         transmitted because of errors.
         Discontinuities in the value of this counter can occur
         at re-initialization of the management system, and at
         other times as indicated by the value of
         'discontinuity-time'";
    }
    leaf rx-pps {
      type uint64;
      description
        "The receive packet per second rate on this interface";
    }
    leaf rx-kbps {
      type uint64;
      description
        "The receive kilobits per second rate on this interface";
    }
    leaf tx-pps {
      type uint64;
      description
        "The transmit packet per second rate on this interface";
    }
    leaf tx-kbps {
      type uint64;
      description
        "The transmit kilobits per second rate on this interface";
    }
    leaf num-flaps {
      type uint64;
      description
        "The number of times the interface state
         transitioned between up and down";
    }
    leaf in-crc-errors {
      type uint64;
      description
        "Number of receive error events due to FCS/CRC check
         failure";
    }
    leaf in-discards-64 {
      type uint64;
      description
        "The number of inbound packets that were chosen to be
         discarded even though no errors had been detected to
         prevent their being deliverable to a higher-layer
         protocol.  One possible reason for discarding such a
         packet could be to free up buffer space.
         Discontinuities in the value of this counter can occur
         at re-initialization of the management system, and at
         other times as indicated by the value of
         'discontinuity-time'";
    }
    leaf in-errors-64 {
      type uint64;
      description
        "For packet-oriented interfaces, the number of inbound
         packets that contained errors preventing them from being
         deliverable to a higher-layer protocol.  For character-
         oriented or fixed-length interfaces, the number of
         inbound transmission units that contained errors
         preventing them from being deliverable to a higher-layer protocol.
         Discontinuities in the value of this counter can occur
         at re-initialization of the management system, and at
         other times as indicated by the value of
         'discontinuity-time'";
    }
    leaf in-unknown-protos-64 {
      type uint64;
      description
        "For packet-oriented interfaces, the number of packets
         received via the interface that were discarded because
         of an unknown or unsupported protocol.  For
         character-oriented or fixed-length interfaces that
         support protocol multiplexing, the number of transmission
         units received via the interface that were discarded because
         of an unknown or unsupported protocol.
         For any interface that does not support protocol
         multiplexing, this counter is not present.
         Discontinuities in the value of this counter can occur
         at re-initialization of the management system, and at
         other times as indicated by the value of 'discontinuity-time'";
    }
    leaf out-octets-64 {
      type uint64;
      description
        "The total number of octets transmitted out of the
         interface, including framing characters.
         Discontinuities in the value of this counter can occur
         at re-initialization of the management system, and at
         other times as indicated by the value of
         'discontinuity-time'";
    }
  }

  grouping ethernet-state {
    description
      "Ethernet State";
    leaf negotiated-duplex-mode {
      type interfaces-ios-xe-oper:ether-duplex;
      description
        "When auto-negotiate is set to TRUE, and the 
         interface has completed auto-negotiation with the 
         remote peer, this value shows the duplex mode that 
         has been negotiated.";
    }
    leaf negotiated-port-speed {
      type interfaces-ios-xe-oper:ether-speed;
      description
        "When auto-negotiate is set to TRUE, and 
         the interface has completed auto-negotiation with 
         the remote peer, this value shows the interface 
         speed that has been negotiated.";
    }
    leaf auto-negotiate {
      type boolean;
      description
        "Set to TRUE to request the interface to 
         auto-negotiate transmission parameters with its 
         peer interface. When set to FALSE, the transmission
         parameters are specified manually.";
    }
    leaf enable-flow-control {
      type boolean;
      description
        "Enable or disable flow control for this 
         interface. Ethernet flow control is a mechanism by 
         which a receiver may send PAUSE frames to a sender
         to stop transmission for a specified time.
         
         This setting should override auto-negotiated flow 
         control settings. If left unspecified, and 
         auto-negotiate is TRUE, flow control mode is 
         negotiated with the peer interface.";
    }
    leaf media-type {
      type interfaces-ios-xe-oper:media-type-class;
      description
        "Type of media attached to the interface";
    }
  }

  grouping dot3-v2-error-counters {
    description
      "dot 3 version 2 error counters";
    leaf dot3-alignment-errors {
      type uint64;
      description
        "A count of frames received that are not an integral number of
         octets in length and do not pass the FCS check.";
    }
    leaf dot3-fcs-errors {
      type uint64;
      description
        "A count of frames received that are an integral number of
         octets in length and do not pass the FCS check.";
    }
    leaf dot3-single-collision-frames {
      type uint64;
      description
        "A count of frames that are involved in a single
         collision, and are subsequently transmitted
         successfully.";
    }
    leaf dot3-multiple-collision-frames {
      type uint64;
      description
        "A count of frames that are involved in more
         than one collision and are subsequently
         transmitted successfully.";
    }
    leaf dot3-sqe-test-errors {
      type uint64;
      description
        "A count of times that the signal quality error
         test errors is received on a particular interface.";
    }
    leaf dot3-deferred-transmissions {
      type uint64;
      description
        "A count of frames for which the first
         transmission attempt on a particular interface
         is delayed because the medium is busy.";
    }
    leaf dot3-late-collisions {
      type uint64;
      description
        "The number of times that a collision is
         detected on a particular interface later than
         one slot time into the transmission of a packet.";
    }
    leaf dot3-excessive-collisions {
      type uint64;
      description
        "A count of frames for which transmission on a
         particular interface fails due to excessive
         collisions.";
    }
    leaf dot3-internal-mac-transmit-errors {
      type uint64;
      description
        "A count of frames for which transmission on a
         particular interface fails due to an internal
         MAC sublayer transmit error.";
    }
    leaf dot3-carrier-sense-errors {
      type uint64;
      description
        "The number of times that the carrier sense
         condition was lost or never asserted when
         attempting to transmit a frame on a particular
         interface.";
    }
    leaf dot3-frame-too-longs {
      type uint64;
      description
        "A count of frames received on a particular
         interface that exceed the maximum permitted
         frame size.";
    }
    leaf dot3-internal-mac-receive-errors {
      type uint64;
      description
        "A count of frames for which reception on a
         particular interface fails due to an internal
         MAC sublayer receive error.";
    }
    leaf dot3-symbol-errors {
      type uint64;
      description
        "For an interface operating at 100 Mb/s, the
         number of times there was an invalid data symbol
         when a valid carrier was present.";
    }
    leaf dot3-duplex-status {
      type uint64;
      description
        "The current mode of operation of the MAC
         entity.  'unknown' indicates that the current
         duplex mode could not be determined.
         The possible value as defined by RFC 3635 are:
            unknown     1
            half duplex 2
            full duplex 3";
    }
    leaf dot3-hc-alignment-errors {
      type uint64;
      description
        "A count of frames received that are not an integral number of
         octets in length and do not pass the FCS check on interfaces 
         operating at 10 Gb/s or faster.";
    }
    leaf dot3-hc-inpause-frames {
      type uint64;
      description
        "MAC layer PAUSE frames received on the interface";
    }
    leaf dot3-hc-outpause-frames {
      type uint64;
      description
        "MAC layer PAUSE frames sent on the interface";
    }
    leaf dot3-hc-fcs-errors {
      type uint64;
      description
        "A count of frames received that are an integral number of
         octets in length and do not pass the FCS check on interfaces 
         operating at 10 Gb/s or faster.";
    }
    leaf dot3-hc-frame-too-longs {
      type uint64;
      description
        "A count of frames received on a particular
         interface that exceed the maximum permitted
         frame size on interfaces operating at 10 Gb/s or faster.";
    }
    leaf dot3-hc-internal-mac-transmit-errors {
      type uint64;
      description
        "A count of frames for which transmission on a
         particular interface fails due to an internal
         MAC sublayer transmit error on interfaces 
         operating at 10 Gb/s or faster.";
    }
    leaf dot3-hc-internal-mac-receive-errors {
      type uint64;
      description
        "A count of frames for which reception on a
         particular interface fails due to an internal
         MAC sublayer receive error on interfaces 
         operating at 10 Gb/s or faster.";
    }
    leaf dot3-hc-symbol-errors {
      type uint64;
      description
        "For an interface operating at 10 Gb/s or higher, the
         number of times the receiving media is non-idle
         (a carrier event) for a period of time equal to
         or greater than minimum frame size, and during which
         there was at least one occurrence of an event
         that causes the PHY to indicate 'Receive Error'";
    }
  }

  grouping dot3-counters {
    description
      "Dot 3 error counters";
    leaf dot3-stats-version {
      type interfaces-ios-xe-oper:dot3-stats-versions;
      description
        "Version of dot 3 error counters";
    }
    container dot3-error-counters-v2 {
      description
        "The Ethernet dot 3 version 2 error counters";
      uses interfaces-ios-xe-oper:dot3-v2-error-counters;
    }
  }

  grouping ethernet-statistics {
    description
      "Ethernet statistics";
    leaf in-mac-control-frames {
      type uint64;
      description
        "MAC layer control frames received on the interface";
    }
    leaf in-mac-pause-frames {
      type uint64;
      description
        "MAC layer PAUSE frames received on the interface";
    }
    leaf in-oversize-frames {
      type uint64;
      description
        "Number of oversize frames received on the interface";
    }
    leaf in-jabber-frames {
      type uint64;
      description
        "Number of jabber frames received on the
         interface.  Jabber frames are typically defined as oversize
         frames which also have a bad CRC.  Implementations may use
         slightly different definitions of what constitutes a jabber
         frame.  Often indicative of a NIC hardware problem.";
    }
    leaf in-fragment-frames {
      type uint64;
      description
        "Number of fragment frames received on the interface.";
    }
    leaf in-8021q-frames {
      type uint64;
      description
        "Number of 802.1q tagged frames received on the interface";
    }
    leaf out-mac-control-frames {
      type uint64;
      description
        "MAC layer control frames sent on the interface";
    }
    leaf out-mac-pause-frames {
      type uint64;
      description
        "MAC layer PAUSE frames sent on the interface";
    }
    leaf out-8021q-frames {
      type uint64;
      description
        "Number of 802.1q tagged frames sent on the interface";
    }
    leaf dot3-counters-supported {
      type empty;
      description
        "When present, the dot 3 version 2 error counters
         are valid";
    }
    container dot3-counters {
      when "boolean(../dot3-counters-supported)";
      description
        "dot 3 error counters";
      uses interfaces-ios-xe-oper:dot3-counters;
    }
  }

  grouping t1e1-serial-state {
    description
      "The T1/E1 serial state";
    leaf crc-type {
      type interfaces-ios-xe-oper:serial-crc;
      description
        "Cyclic Redundancy Code type configured on the interface";
    }
    leaf loopback {
      type interfaces-ios-xe-oper:t1e1-loopback-mode;
      description
        "Loopback mode the interface is operating in";
    }
    leaf keeplive {
      type uint32;
      description
        "Keep alive interval in seconds";
    }
    leaf timeslot {
      type uint32;
      description
        "Time slots bitmap occupied by this serial interface";
    }
    leaf subrate {
      type interfaces-ios-xe-oper:subrate-speed;
      description
        "Subrate operating per slot";
    }
  }

  grouping t1e1-serial-stats {
    description
      "The serial specific statistics";
    leaf in-abort-clock-error {
      type uint32;
      description
        "Number of receive abort packets due to clock slides";
    }
  }

  grouping interface-ext-state {
    description
      "Interface extended characteristics";
    leaf error-type {
      type ios-common-ios-xe-oper:port-error-code;
      description
        "Type of the error when port goes to error state";
    }
    leaf port-error-reason {
      type ios-common-ios-xe-oper:port-err-reason;
      description
        "Reason for the interface to be put into error state";
    }
    leaf auto-mdix-enabled {
      type boolean;
      description
        "Either straight through or crossover cable can be used to connect the 
         devices with auto MDI crossover enabled on the interfaces and the 
         interfaces automatically adjusts the medium to communicate successfully.";
    }
    leaf mdix-oper-status-enabled {
      type boolean;
      description
        "The status of interface is tracked where MDI crossover operates.
         by default status is show as on, if the media  type is crossover status show as off";
    }
    leaf fec-enabled {
      type boolean;
      description
        "Forward error correction is used for controlling errors in data 
         transmission over unreliable or noisy communication channels. 
         It will track whether fec is enabled on a interface. if enabled 
         show as true and take care noisy issues.if not enabled show as false ";
    }
    leaf mgig-downshift-enabled {
      type boolean;
      description
        "The port is not able to operate at its max speed and the speed 
         is down shifted.";
    }
  }

  grouping dce-state {
    description
      "Synchronous serial DCE mode state";
    leaf dce-terminal-timing-enable {
      type boolean;
      description
        "Enable DCE terminal timing";
    }
    leaf ignore-dtr {
      type boolean;
      description
        "Ignore DTR signal";
    }
    leaf serial-clock-rate {
      type uint32;
      units "bps";
      description
        "Serial clock rate in bps";
    }
  }

  grouping dte-state {
    description
      "Synchronous serial DTE mode state";
    leaf tx-invert-clk {
      type boolean;
      description
        "Invert transmit clock";
    }
    leaf ignore-dcd {
      type boolean;
      description
        "Ignore DCD signal";
    }
    leaf rx-clockrate {
      type uint32;
      units "bps";
      description
        "Received clock rate";
    }
    leaf rx-clock-threshold {
      type uint32;
      units "bps";
      description
        "Received clock rate threshold limit";
    }
  }

  grouping sync-serial-state {
    description
      "The synchronous serial state";
    leaf carrier-delay {
      type uint32;
      units "milli-seconds";
      description
        "Delay for interface transitions";
    }
    leaf dtr-pulse-time {
      type uint32;
      units "milli-seconds";
      description
        "DTR pulse time on reset";
    }
    leaf restart-delay {
      type uint32;
      units "milli-seconds";
      description
        "Serial interface restart-delay";
    }
    leaf cable-type {
      type string;
      description
        "Cable type attached on the interface";
    }
    leaf loopback {
      type boolean;
      description
        "Whether the interface is in loopback mode";
    }
    leaf nrzi-encoding {
      type boolean;
      description
        "Enable use of NRZI encoding";
    }
    leaf idle-character {
      type interfaces-ios-xe-oper:idle-character-type;
      description
        "Idle character type";
    }
    leaf rts-signal {
      type interfaces-ios-xe-oper:signal-status;
      description
        "RTS signal state";
    }
    leaf cts-signal {
      type interfaces-ios-xe-oper:signal-status;
      description
        "CTS signal state";
    }
    leaf dtr-signal {
      type interfaces-ios-xe-oper:signal-status;
      description
        "DTR signal state";
    }
    leaf dcd-signal {
      type interfaces-ios-xe-oper:signal-status;
      description
        "DCD signal state";
    }
    leaf dsr-signal {
      type interfaces-ios-xe-oper:signal-status;
      description
        "DSR signal state";
    }
    container dce-mode-state {
      description
        "Special state in DCE mode";
      uses interfaces-ios-xe-oper:dce-state;
    }
    container dte-mode-state {
      description
        "Special state in DTE mode";
      uses interfaces-ios-xe-oper:dte-state;
    }
  }

  grouping sc-suppress-level {
    description
      "Storm control suppression level";
    leaf suppress-type {
      type interfaces-ios-xe-oper:sc-suppress-type;
      config false;
      description
        "DO NOT USE!  -- hidden internal";
      tailf:hidden "full";
      tailf:meta-data "hidden" {
        tailf:meta-value "true";
      }
    }
    choice suppress-type-choice {
      description
        "Storm control suppression type";
      case bandwidth {
        leaf bandwidth {
          type decimal64 {
            fraction-digits 2;
          }
          units "percentage";
          description
            "Bandwidth percent suppression level";
        }
      }
      case bits-per-second {
        leaf bps {
          type uint64;
          units "bits per second";
          description
            "Bits-per-second suppression level";
        }
      }
      case packets-per-second {
        leaf pps {
          type uint64;
          units "packets per second";
          description
            "Packets-per-second suppression level";
        }
      }
    }
  }

  grouping sc-state {
    description
      "Storm control state";
    leaf filter-state {
      type interfaces-ios-xe-oper:sc-filter-state;
      description
        "Storm control filter state";
    }
    container current-rate {
      when "(../filter-state != 'inactive')";
      description
        "Storm control current rate";
      uses interfaces-ios-xe-oper:sc-suppress-level;
    }
  }

  grouping interface-sc-state {
    description
      "Storm control state for an interface";
    container broadcast {
      description
        "Broadcast storm control state";
      uses interfaces-ios-xe-oper:sc-state;
    }
    container multicast {
      description
        "Multicast storm control state";
      uses interfaces-ios-xe-oper:sc-state;
    }
    container unicast {
      description
        "Unicast storm control state";
      uses interfaces-ios-xe-oper:sc-state;
    }
    container unknown-unicast {
      description
        "Unknown unicast storm control state";
      uses interfaces-ios-xe-oper:sc-state;
    }
    leaf level-shared-support {
      type empty;
      description
        "Flag for level shared storm control support";
    }
    container level-shared {
      when "boolean(../level-shared-support)";
      description
        "Level shared storm control state";
      uses interfaces-ios-xe-oper:sc-state;
    }
  }

  grouping interface-state {
    description
      "Interface state details";
    leaf name {
      type string;
      description
        "The name of the interface.
         A server implementation MAY map this leaf to the ifName
         MIB object.  Such an implementation needs to use some
         mechanism to handle the differences in size and characters
         allowed between this leaf and ifName.  The definition of
         such a mechanism is outside the scope of this document";
    }
    leaf interface-type {
      type interfaces-ios-xe-oper:ietf-intf-type;
      description
        "When an interface entry is created, a server MAY
         initialize the type leaf with a valid value, e.g., if it
         is possible to derive the type from the name of the interface.
         If a client tries to set the type of an interface to a
         value that can never be used by the system, e.g., if the
         type is not supported or if the type does not match the
         name of the interface, the server MUST reject the request.
         A NETCONF server MUST reply with an rpc-error with the
         error-tag 'invalid-value' in this case";
    }
    leaf admin-status {
      type interfaces-ios-xe-oper:intf-state;
      description
        "The desired state of the interface.
         This leaf has the same read semantics as ifAdminStatus";
    }
    leaf oper-status {
      type interfaces-ios-xe-oper:oper-state;
      description
        "The current operational state of the interface.
         This leaf has the same semantics as ifOperStatus";
    }
    leaf last-change {
      type yang:date-and-time;
      description
        "The time the interface entered its current operational
         state. If the current state was entered prior to the
         last re-initialization of the local network management
         subsystem, then this node is not present";
    }
    leaf if-index {
      type int32;
      description
        "The ifIndex value for the ifEntry represented by this interface";
    }
    leaf phys-address {
      type yang:mac-address;
      description
        "The interface's address at its protocol sub-layer.  For
         example, for an 802.x interface, this object normally
         contains a Media Access Control (MAC) address.  The
         interface's media-specific modules must define the bit
         and byte ordering and the format of the value of this
         object.  For interfaces that do not have such an address
         (e.g., a serial line), this node is not present";
    }
    leaf-list higher-layer-if {
      type string;
      ordered-by user;
      description
        "A list of references to interfaces layered on top of this interface";
    }
    leaf-list lower-layer-if {
      type string;
      ordered-by user;
      description
        "A list of references to interfaces layered underneath this interface";
    }
    leaf speed {
      type uint64;
      description
        "An estimate of the interface's current bandwidth in bits
         per second.  For interfaces that do not vary in
         bandwidth or for those where no accurate estimation can
         be made, this node should contain the nominal bandwidth.
         For interfaces that have no concept of bandwidth, this
         node is not present";
    }
    container statistics {
      description
        "A collection of interface-related statistics objects";
      uses interfaces-ios-xe-oper:intf-statistics;
    }
    list diffserv-info {
      key "direction policy-name";
      description
        "diffserv related details";
      uses interfaces-ios-xe-oper:diffserv-target-entry-key;
      uses interfaces-ios-xe-oper:diffserv-target-entry;
    }
    leaf interface-class {
      type interfaces-ios-xe-oper:interface-class;
      config false;
      description
        "DO NOT USE!  -- hidden internal";
      tailf:hidden "full";
      tailf:meta-data "hidden" {
        tailf:meta-value "true";
      }
    }
    leaf vrf {
      type string;
      description
        "VRF to which this interface belongs to. If the 
         interface is not in a VRF then it is 'Global'";
    }
    leaf ipv4 {
      type inet:ip-address;
      description
        "IPv4 address configured on interface";
    }
    leaf ipv4-subnet-mask {
      type inet:ip-address;
      description
        "IPv4 Subnet Mask";
    }
    leaf description {
      type string;
      description
        "Interface description";
    }
    leaf mtu {
      type uint32;
      description
        "Maximum transmission unit";
    }
    leaf input-security-acl {
      type string;
      description
        "Input Security ACL";
    }
    leaf output-security-acl {
      type string;
      description
        "Output Security ACL";
    }
    container v4-protocol-stats {
      description
        "IPv4 traffic statistics for this interface";
      uses interfaces-ios-xe-oper:protocol-statistics;
    }
    container v6-protocol-stats {
      description
        "IPv6 traffic statistics for this interface";
      uses interfaces-ios-xe-oper:protocol-statistics;
    }
    leaf bia-address {
      type yang:mac-address;
      description
        "The burnt-in mac address that was associated with this
         interface from manufacturing. This is only relevant for
         interfaces that have the concept of burnt in ethernet 
         addresses, otherwise it is zero.";
    }
    leaf-list ipv6-addrs {
      type inet:ip-address;
      ordered-by user;
      description
        "A list of the IPv6 addresses associated with the interface.
         This contains all the IPv6 addresses, including the link local
         addresses, assigned to the interface";
    }
    list lag-aggregate-state {
      key "aggregate-id";
      description
        "Operational state variables for logical
         aggregate / LAG interfaces";
      uses interfaces-ios-xe-oper:lag-aggregate-state;
    }
    leaf ipv4-tcp-adjust-mss {
      type uint16;
      description
        "When ip tcp adjust-mss is configured, this value shows
         the tcp mss, or the value is zero.";
    }
    leaf ipv6-tcp-adjust-mss {
      type uint16;
      description
        "When ipv6 tcp adjust-mss is configured, this value shows
         the tcp mss, or the value is zero.";
    }
    leaf intf-ext-state-support {
      type empty;
      description
        "When present the interface extended state is valid";
    }
    container intf-ext-state {
      when "boolean(../intf-ext-state-support)";
      description
        "Interface extended state object";
      uses interfaces-ios-xe-oper:interface-ext-state;
    }
    container storm-control {
      description
        "Broadcast, multicast, unicast, and unknown unicast storm control state";
      uses interfaces-ios-xe-oper:interface-sc-state;
    }
    choice interface-class-choice {
      description
        "The broad class that the interface belongs";
      case interface-class-ethernet {
        container ether-state {
          description
            "The Ethernet state information";
          uses interfaces-ios-xe-oper:ethernet-state;
        }
        container ether-stats {
          description
            "The Ethernet statistics";
          uses interfaces-ios-xe-oper:ethernet-statistics;
        }
      }
      case interface-class-t1e1serial {
        container serial-state {
          description
            "The T1E1 serial state information";
          uses interfaces-ios-xe-oper:t1e1-serial-state;
        }
        container serial-stats {
          description
            "The T1E1 statistics";
          uses interfaces-ios-xe-oper:t1e1-serial-stats;
        }
      }
      case interface-class-unspecified {
        leaf intf-class-unspecified {
          type boolean;
          description
            "No specific interface class information";
        }
      }
      case interface-class-syncserial {
        container syncserial-state {
          description
            "The synchronous serial state information";
          uses interfaces-ios-xe-oper:sync-serial-state;
        }
      }
    }
  }

  container interfaces {
    config false;
    description
      "Operational state of interfaces";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list interface {
      key "name";
      description
        "List of interfaces";
      uses interfaces-ios-xe-oper:interface-state;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWYwfiUsAZlbfgFAAEAZ/8D////q////6YCyj6oGbuYgc3z5CHdmtG7gk33vTbZ3d70vPuOvi1lrGZbfdW5fbTxtD6AY6TNaNAB5AxNGqEUnrSmjLw9NC7sytNtji11kECpEq7GhQpyA0p7YD01VJaDKZm6y6GphGSaZACCmapoGgAaDamDU9JoBpo0QjSminsmmVP1TJ6ahoA9QAeoNAAaYUmhJ6iPSMTDUZNNNAAANAABKfqkoIKepqeRNiJoAAAA0AAARJCAQJoRlE9GjU9FG1NHqb0UbRNPChkEiIRoAQTQQJpKYgAaA9IAD/h+vj6aGPiB6YQHu93s8nHwL1GZZgCet6c+XLlHl0EujShMMAwKANHEZM7jxrUirAGZjBYAWAFbHdWy0vjW0hMNBiANHEmdvh8b6+JHy8r8STL4e9yVQGefiN7Rawlmwc7QMd39OXERjLsIIaQY9oWzA3ANdj12akZy2Zt3cTEwJlAGEURkzuLnmEujJg98i9y9y5cuXLq6uFwLpoICVRVLGBiXnB76CFiAMdCw5EUREhisiziWWnTpz8o7UdLYRjW7DmRLR+mGMhhbzdZppbS/yqyPN5qU0jimSR7sWIJcY4lxHaNzG5FkbLGpHoU37sNV/ySWMn7Nfzxbk9kCWvbchV87JhQu1nNecwYtNLHrXfq+/WLJdoL2oUN26qODBn00xrfXWBm6ElsBvPaU6JcuuVUU6EVQtRSNBEXcr5pnwzCmoY4lnWWxqoxme3cj61zx7dpZ7abUqqHjVe8p49KGne4VDhsNVpzdd0ndZzk0BWilAXL2vS5a3mbHQ8cPg4eaR71mMajFqCe52LwMHf16UaLvMRltE5mcbAFirbbHaNRjZoyG2G1SCWbY9nz+Pnldf3QMeYdR8qR6AB9OHJ83D3Oi3N0jDu3wrIXAuCgDRxGTO48PV7cMCLCAMzCRgBgALYHS2C31jbCQmGgxAGjiTO3t3vr4EfHrvxJMvZ6nJVAZ5+G5Wi0hAzYOdoGPC/xJSIikzYQQ0kY9oW1IFgwg+Xj6bqVYwOQPPtHn202rtb2ww9Y4ly4XaIJoVthjiZY3JyrbAxvkXuXuXLly5dXVwuBdNAGAkFhESDBxOcHxtiWditpz6c0Ef59baXxTi0Y2v46ES1frjlIZW7/NNOttb9asjzealNI4pkke7FiCXGOJcR2jcxuRZGyxqWiCb92Gq++SWMn9jX88W5FYgR2vluQrXOyYXF2s5rzmDtNLHrXfq+/WLJdoL2oUN26qODBn00xrfXWBm6ElsBvPaU6JcuuR1oVSkiLUUlQRF3K+aZ8MwpqGOJXx2NNBiUy27kfWuePbtLPPa7aqXomK95XHpI073CocMcIi8oQaiOoW90LPtvdaQYrrwJGNNRyVa1GOWmFzzrmcc3jSDlI4zpEZqrTDqcTkZCImcaxFNv2AHt2+EjtryAYCDIyb9pMgRbWf4gj+33gn2T44+7W0iwCEr/OxgJGKXSNohRFvf/H9Yif2oABGikijUKklJMakmZVlhWVlardaWNwyJYYyMzJsxtVMszNylSVWBAoEoACqg1bVB/4FkJGBJ/0gAj/RX+sRaACL8ft+0+M/dzRA+X4fiAfhCQIS5aNILVAjfuF4ntAEx/pvr/vVV9f3sMxvFbxyDfT8cZaFzdHXPntcjCSBXynauWMF5+sucTu2XWbCu9ul33UkK3dLlury221WdbmyQrtukJiSFd7dITEWfDTLOnNhXbp2dOhefp5706Jek2c5vIV1t0utupejZ3BcEkAkkYnGHEySLwTEEHGKD6ZxeI2WzKHJRt7SUrhMm2t6xGRLcTQPshH7QjVdI+8b+zdPZfDyzPi6t6iILAoIIIverOBza4wvV9bw59QZZ7eX8t4yZfRrtc6AAWdibth0RtT6Vy/B408y4p2ZocDcO+uxWetgUGBhBklMlkZ8kvC7TOPo2v1gSTCCycrTCZwjel5bz4xblHGbI8vU+n2+H5e1XqqsvPZKIJKISiISiISiISiISiISiIz4o8Lzlcq3MszW+jO1B8JrJOxYORNEkkuMnHYVlAD+9XDYIHcQzjlxRiF1CPEBP6CiBLwxzbW/vWffrb70IseHL4mBBLWTUb4zV+4t4dlg35REW+9sDTEdYImnn/pUltjOfUy284R3YoH54knTaDx94kTKgkgTNX4bz00Mu/V8DGj9Ug8OjlwRVy2dmQMHqZMnUbjFcAQCNKigvjDyoa5Zo2oYLQi56iBHaCmWk6FIh3ZFYzzgF5rDaxEEKg7d6bdK9djiFNl5ZLlZ6Fnrtd7RW8UtpSAhaLUU6cyjWBiokkkvUhM9HE5vc3jHHUse6Px5ssmixuq/NMmi52BJAvokocirKu1bmZVNoF9n0w15z/DoAesl17UQGvh4cereki5dJJEu7pJI8Dwfpmpq90kXLpKQlJSSQ3OKx5bh6ZBsd6oJBMgPt4UAKqtft+CuGLMsYZ2WZng8F0QLMsYSF4i3l4aaWDxFcB0IQhYwQwZhuF7a3Wl4syq9N7+W7job15llVtwAABbW7a0ETd3G7ba3G7m5pVCgEWWmHt5oBJUwScENTvErg6rhsdVQvcvgNEQJ2ltKpkiiF5JKxZEaLSAAAto3YCJu7jWy3aSIVFUAKDKTDzugElTBJwQzd4lljdMs/7JMxLBa3nbV2NWPN2tHlqayLP70TMSwWj0t1+nS/l5bRhxrgQI5IJIT2AAHoKknnyEQTz5igCArgFYokUSfmcqAEKSEkJJJJG2KrNfR+rPnRz19bO/he9lsIAbYwBQ0Ag/H7Xdtk/VSPn+zOP/f7PQf3nrz94iMksZIksqqfbp5BjUQtSQ5O2xYEWCGQIQ18DDALaTGMqdvVCgxjGVTRZS4mbMk/wmP7P0VGSfkP8f8f1/djAZgeg9L00B/NF/HDGmNuvjxibm+GHeCSCwAHMOMCh39wco4CDRIPE9Nea6PAktyUmZd3mFLzMRESYnnNTNJIlJJJePvC939Ne+hiYfjNofXV3fVKTMu7zCl5mIiJMTiamaSqRKqqqrn9Idz88vQonFDfkDMHogRBLLPDoNh+X9+gMOsgkL9fTzcOgvj7wcAzExIyUlyckwivASpEugrwMp6DASvyMpmDqGIWv/+/+ahPf87MYxt/q/u/ddXN4IxkmTrb3OzGNj/PWjPuf7Dq2bWDbbbTO0Y525JxdjiQdrXbbbbTOJjmNKUtj8wTXDFwQRFjWThntC/f9IJJJPcldzcLLYhFz2sO2V74G+eT+8+JRhPcUkKSg0JSdKlUkNSNH3UfdZaIRfGi9WL3Skl6tYP2/l4hbCRYQi51Kp1IUnTghPce7tCMG3+a1340cEERUoVfyfc8MabH71qYb+xMQelukmhJBzt6Qm5UcgaQ4a3iTQkgu3eE3MHDkgiKEyetPJ5GDaZ+Uz5BNNJiPUkB8HD84MYsQ9ljixMFO4Sgiw5BRSyRIkGD8fjZ6BLhgpaIRYQjmEKRhAyBNQDjAGujsvpSI5aFW7uQRFyWNeQ3q7VbVVQz5LpLF5yPekGq2vCkbGzSV3JHhShhXxZQ6qhgUmSZJJoEl2bQiRkFQgp9ulJb04+gswu07BCk1KCFBQwdyiFFNwsVYIWolLRCL1KLUWKswIUnqUQooYsCwSuQRohFhyCiljcIKhiASKANbsexwqExSbCyZVxgNQybDYYcoZEVRrdDexwqExSbGFBjjiQdzJ9mB2jY60mtCSpSYgggi3tXNG6OeW5CIbkJCgYhEo/t/tmez5nQNQ1JGVLhXemaoUwiCCBbZwtwEmyW27wRJEtKOQRB4BBBJInMKpNj9D5GRppJotVJkty7CnMohZhZ8CzCFcMySiZRefKbG/5zyvkQQRHn2TbZ/S3rQaJ309nNiJzTnjy8b465bzd09X4vxgTrCRSNJIUO9wnn4zoMgMwCMw0N4LfAi0iWXOePh8nx/s/qClHwfAB5Lb2Vy3m7o9Ppkk2KaKRJLKasFZIIIxJaANtJaAQ+PDcoiG5RLtdsbchjMt0CaQ3AYh2CgQLh2H1+aSTQ00qij8hEFfgCRQH9P2+J6/YTk7+3/X30sAMRbRFkG2eSftT8j6fsP2ELxUMz/IKC+prCJwLjk0su0wyv3Rp9lFDM503ZLsNvX1GiW+8kw3l9LT257KzMgwTLMRFxpAYTsh8peajDqnXlxUiXyFEDwsYA/8OQaulZSQTpKrCggc6RRU1nm48RsqbsMsP/VZ7aiq6GwWM475+Roh59DMIQHXWodDTGJSMm2lB23rRDMYdhBDUUQIqJ6QEcvDr5e/06Ay6WV49vtZ0VjKAABAEAQBAEAQBAEAUhc9t4bdXXPj8M93RVgPayprz/dY8FzRGNOn8U33xztw0l/LUdZ1juqM6bjl63geceJaK1KiSJIFrabQazTEYJkFVMxQxxmYG+7s6Qg6ishEF4OyJjz4yptR/YzwxFXvbHM4wjFCN3IZwEJm+udTmxvjHLnSCzL1iKZWoEI+YPxcVDHn4zqYIiFkt3joyGWKNQMSTHNHAhOhyahFusZsEVUdhI7+0LiJeoRUGNbVQ00WvUmkdsZilZjA+CSDCiGQIB38R5tGoAITNZUQISvNt8/E2+d1e4H0sGOCECQsV0M1sBKZxBC8GUL524v8TE7Fs00rHO/WM9Q/UxEbFe1z48QHTAzTQALTTLcN2lANiz95ppz6pSJb0OJXUKs0rtjXDXCfdCN8/pAMKN49xiMmsr25Ka5RW+zrZe4PKr53QkgXFw0QsWKboVhQvOtDagazsXKaYZ4CLI2aIqrWp7Za3HRGGk6lOqaZ5ixIDGVvoE+gBFOvun14ifiq8BYels0QTLNQGVphUgaETgiuDKYvpTa2dqmYKg7lk8OeNuwF4QI27k4fFecyuUTN9UURs471eIGTWsaS+mhuG3gUmUXUsI02ili9F4XgZLaEgtzODqtcy26aYmJgYSq3kopAqhqAUAhVEWFgjTahqAVEqLID6TBFxG8kcwooeUU3loNyVBudl2sueHW1iWER49ats45u2eG7hZjs2s60zZYXGXbczWbucbMt1ppYsgaSbAc0fifNWe04BsaO7XNCD0wNxhiyDbnAp8PTPCQjzHwNS76bzhzu0lVMQgNoiGcVXIvHlGZ5CiBa1U35E8AkuoZUcpmfyNasbmhx3pXrNGGp9ZFe0JtCFbPLNrLLiiwoiMjMIjCzyaCGkN0PrggyExSfWknPnjemMRVt5bMEezNW22NgQwEV5jFncya4yEiEiIPM6T4LKGhCQmqMgT86xgebLw1cXfXY4e1y2Fb1OYE9BRAgCLxARTXizPK3TqycFvb7ETknysDKDTP1Oki4HYiAEgORvprPexARhzhS3qa8zMhFtdEVzeA0SUYEe+S0ta3xnAjK+n1zrQ8Aw8DDU8D2RuM7fyhFqaxzOz3wpHNr1hSWh+CD5PsjZLZIS1LluzOKLWUEJ9lAew8iutTx6S5KbtFl0G3rBfqsFBtsAr/StDHgtD+4URhNwnCLRDvlJ9qrvSBt+IqSEDgi3zqUKh4CF3+QfbPO7XBQhrFdbchqnuMKwsjf4cLcfYezXizN8cSRspKMZUoaElF6baFFRGLQWxwx9iPGmB3yrO6nh/n9bkmDeBHwKEjfzr1boxwQG7jCa0Sb5aePUz24tgDhMRFAWnVMA6hXiLgwMnaQh/k/T7/b5n/Fbz+vit4i8XnGZSERGFUqKTqpiZJeXeXmJMyqQSUWa0zM2SS7qo1VVOlejLAkQ/GA5Dv2rceB64G+3bAhXj8fbquVVAsudlyzfPW2JSmKEkC2hFJtpFvcj2csRqhkdoMmBii21N6nyyafe+xUjPg7afBvYwLj6ASFtvp9XBJQFe3jluabcUVqKrBuyKDaY1DMI+sM/uTJQSEA+e7gKTjWUVHNWqH2JaRrS9IhaEFHKAoBxMNoMU+IyaUoGhlMPzBmirGPtcKDhn2Qy9CpjOlaBptT2G2l75lI3LtMM6ZR2yrfB9VHcDoOyZqhSnnMbKfObYXvxsdOvfa+57EczLBlWXUwXa8cNzrVXG1E58BjQIYhA4puZvApc2WbEDRAD03iSzg5d+1sM0ID2TnIyQia8fkClgMjsjXdkwuSNmGvJfCmvQxxt1N6VFtkkkgghsZpDAzfrxvU44DrcObxzhtbvNYKlxtM83pXTRJ3gDDBrnW+k7ZhB8MtnAsYSCMYmSFBx7rNJVLdopptcCUCQF6Y6l8PjJjcb5nzN+QeGJbvxCDDf9AksPmlHV61ckEN6m5QxFV34fMyx1O2De5NuuzHKttUEDztoz6edIp/HlXm9dWZipPueI3R4i6l7ywFggSaFqgYveDSDFCCtyrgCegaeFwTwvMiREvZeQGJIMvDGzOI/5Tr5hGrW+/UzTHB8GUDZaIgilWdp0J2FVR9vBUxPGRj0UxwUGxMDHJAdxCVvNbZGgLGFRHhF5Q+vsLZQp7ZW0uQRt0UKJiNL/PihU3M9CiO8w2JGNU0jwjl5BWMV4+ptnzzRXe9E3XxWCraNqy0riCd4qoNQ2l9ZJIU7ui93ljGnTGm/FZ9re7i59FXJY3z4widA5TLqovLpy8Ru754D1YXTe/alnibcyZY1+qLM84IElLZ/Aj8hAhANJEFirCKEEkO8Nh55nLTl6fVwXzfEr27vnirBsjXj6cd3PGGEnrQFy1QcY0LIx/dQZMxcNvRqG2eujZkv60VJTTToyNd6UfABeVYpXU3bbbG+9re+BnhC5eGSuT0ZR8IMNAL9AgglYXJilMxNLSaRrUYXzUnB6KGRQ5Zkwya0DjoA6yoozWFLkm7AI4ZZBW/axCrgaYTShscBab3jPZc1M9ANEgOgHTWrcGICKM2FYLYmGeIqQR0wWJun9fH59s/tvieKSe+h23dosC9HKx7uZ6H0HXlLO7MfmNs6UEBRjYkkEgIlnOXDMFewaVJtgym+aPvdpJ5ZvbfNCBpc6LGnKOGPm3EyWxeG57p3Ma4NIwTPm2bUt6BIcaaTJZZ0a0xhBQwCcWGygDS9COUHeEAimts4xg/I5maT866RgAJaNio0yzF+wSkLK1zpZdQAIgBNAJQtszFr+KAGvLqMjjqNP4mXSL02rufKExVLnnT8SFUmmftCIDkvq/VuLlTszz3d+KVKClpbnZe7QJAeaSaU3D9QR/QEa7/D6T98+bdEDt4gHvhIEJ7rl4yqBHqAJ2DESILj/LfX31Ve/3MNRvFbxWDAy+9bYlTJCv775qg0Mbj+59RtUq3n02TJd9zbrblsd7bTvukyRu2nLy5c1ZmrrbbMkdttEJJkjvbaISVeqmWdOV2cjp2cuHn6ee9LoXpbbc5zLkdbbTrbenNSXe3LYQ8evj4uJEk3gmIJGMUH0zi8RstmTmAiS4hVEDbPh13fG4bzpXlnryYPgtsz4RxBEZEYQQQZmafS+bnOafKwsvmGR7sX3iCrUhvGDDL9YePtcKFgNWm2wbbAIwM4y2WTJPpW537XnyvRZGeG879LOq7Uq8qrJdFJBFJBSRBSRBSRBSRBSRBSRBnmq8pl1ssz51vvCvrjIvxZsY8guUOA1p8u072S6f9+sIybapAaWbz4RsoYp5QEyFECDr07NWzmIlub/IQ3oLBgs+uKO48WZ6hHeZ30DLh4UMSC23jEtvGEHDIfbTOVTkUQCSBcRvHMvKplv3+sDAcjoDEY/eMZHy5JtnIlpMFOIwRrC94tJoJ4UbTqCu1DlEdINkUOKNLVaq7bdI63I4Kd81zsu05ZPOb60qIYilzKyvBSNVaXLFdrc2WlLlVZk0gyaqvggl5iittvbGtOulQfCcYoEmsokCRmcKcv5/b9dH/f8T8PxJ8sH6O8y0+xyQ4+qmz6phkQPMAw1YEXcayPsLCrikTfLL+Z/D+G25CDl0/I/55EVECwqg2/k78a6lGdqJAyZkklH9kA/Lt/7IgTNwGxDM1iUO6MP5UXKZ7LAGyjMg2GejDUNdkpFt/XR3JG8M8QE5LAXEewkqZbvszxbbXckZEsxG5gfnOwTMYdt9qkSoW5CiB3xLmEP1Kz3CItCSCM6KtZUkjpTeaqu08mI2UNy0KyWKeoWnrUSSV8hAaxQyvAY/wXSobDTGg+crtUoBhFHCCQTCHiAzw/ttpN0i4ss222TfL3bZXb4vP71Z4ZQAAIAgCAIAgCAIAgCkMnT23x1vi93hb2zr55zx9dV3zFG2Kt5t/1x/7mRqiemQ997XoAf6Wu6a7bVjuu7Ozcd0XnYyK598uel/XGL4vV6qB5xvLRWpUSRDYTiY0rqlTMm+KQwbWoWVppNVjjLJdXBYWLSmAtNQzyzMDvYBP7ndA3QVay3TpI6rPYBayIPhMOofEpxpYKKhTXWx1bgSG2cuObGsQ8MVsTYi3gBS5m+ngQr1osTJeo9VIZG9ziJNXExvQU4CERYSmCMuT17BQnomkl8b3mJ4pl74Wl6YhNEiwOrSUMaJzkVWs6muvdzlnIHR1S9DTqO16oSQKRrE/qx3ihxZXko6kUNEDy627zlysvpVYCQrtRGC7jOLAuqELX5ghoMhlmG4MVBwexxpzpPEP3mIjEuW5crw92CyTQALbTTKb9vfzSJfetzpdhnra9jEc5ti2eODNVXSig1ImcXOwjQtESoGFqEhChMgvTUCyXkIwjIySMlUAVSORkXsLAEKobhGrX8LgFoq85oRc4uUQN4tEY3jcTLTBeqVqEjrADKK5RQS+1ICmUG8HOhkCgzIWIZGlBlem5JZpbxkFVLPb7gGzYZt4dDEZNbYHRpjlYb0gtJXLZ5bGMwoxPDUHApLFdOyKgzY8shtsjoMB9a7gWostsYqrldMc8QXxijdosuccfbPUwFhtNNyvzXPL1mmwyJXkARnRdtQmdv0n35ifjxUnrzxdyBUGCXeerYEtJasgmsq2XCUgFrQ6gTF9cFMbaorZcGSEOlgkYKX7iHmlzJ808e7UJDl5kM8/YCoMyNmONCp8A1gDG15K9uGeLbjkhiMhpQIDFLJ7MPIFCD0wPcygcG1wMsSxKWQWffn4LBTjpjPx6REPKCoZMEQN9S0eUegFXFEC8RRV2Nfo2CHbwMhsp00VaS+Yj/i22xtC0ASxjSWmdzre4TdLWPoubbUyIjk9Hx5XRRYURGRmERhZ71ahNoQjZKxmee5JiFIFQ+oN3z37z8dRk8LXxmnkluvmVCGmLmqEQGdLMRWp7fOE8mAAIUMWDhDAH7d4xNdtz09ammdeDigV+FTAzYlQegHYUQN/YYfG0O3gycF/X2A3q5QF9TRrScvj61kXYgUYnK4A7sIUgW1FYBIB4BxUkjtWfcItxIFd+BK2usIkRSC6xmn1pt719KrdNsAWWro/L1Q393CEfLG1qew9xcDO/Ap0wmdHrb1Y9ynaci0KTCHsHo19I9uErUFxPtFN7M2+iHW/SyFNK9AIhbybi+pzMcfNkwbLD8JesrM8RQODfrFfvSKNsYBQHAP91m/JVQ7n5CqI9xYXwiHpB9qLWkDb9oqSEDg2nWUj7lCkmAMCGQDVg8hC7owHFoEfVfHi/yGuTXLHUhrBeOPAgNuVG6GFtDns4XkaFc4+GUQkDptoxM8JrWzuU2D6xNKXzmVb39yLW7M28428hVIaBydONdibKkcfApBb+0ebdEiDZ3t2UiLPsdaQiX34As0MRklQDbe1YDYC/h6j4n09H867vG9726FO6dReZSERGFUqKTqpiZJeXeXmJMyqQs1rG1rVOKqqqkktLfjlDZePZyER9AhUASFZ1B8cxD7M56KDGwf5j3v9pzV8JFsueYN962JmUJIFrCKXyrocfibv3cMRsJXIntpI2jEWG9OKhqPUdK/nLcqWGTrwfWtV8dYEmQ++rfjXLSik7OrBubQ4QxOIjNktJsiEkID5w6qOZ2+7hNzNbSQRCqRNWMCD7EMFpSXisyCj1YVBF0/EZOjSoCaGWkyRRjGYHDR4cfSL1MYzm7TOGu1PVLWtmUiFkL5N0sqUZ4ZtR8KNAA/GiETxu47AUigt9V9HCSCgLy9kjeTPxdZ99LnlCpJTboxJUfuwUOIiiTRkRSRwcYOGahA5Q0jDkKQ58IQiQQnpYAI4Zk4O7N3jewqc7oEHZOMzA/SBjdDrhWSyFma0ZEcmKSUoz1tOXQxxtziTWXkaA22RCFLpPRsJ6rFtxgYMnTqkLnOMprEksibTeJSFIKaoLBeoLEM4FCkUIK5HJtvbxqIosABG38YAjbB6FsFURXeIvhe1UnhAG/YdDHS8Eji9VY9Zc60O9wg+mWzgV4EGLiRnf6QhIR3SVu+CMBiSddOrxjUxqd7sbjx3t7ph9sqgzG6VfbiEG/zbSj1lsbcmpsQvAJJhYeb0TLU8QgQERzUc33MFTHzl06jP5iR7NCy/PkyyrqzQWE/I/HcIBvFQ+pxN0bIggCIEkEbs7fLGzmI/8Tl4hHs1rxzIZAB4yZdpnRRZqtUTF7FtZmVjM4yvarq226kpgnDRlGj9i0DZaIghgKlfFOSncVRR+PYqYrbIxZ9FMcFBDTHBAq+9OkuR1yOAe7R7eapRolkocse4A6XeM0Aorn2LmKTEb3+vbSRV4DhnBqZBVDDtUkWFkzcYQYnkx8kmMV5eZt2zONEV4i1CcIIc1SghTGabMfzoVS3VdcNuK6ZZxh1P40pJEZWzCX4xl6klqThbl7dY1MEqEheMinCEoXeoBEOBvFScSECqbWxQilZCjglqq7Bm5o7kWJaMZnCg2XMuN5Fo0kXazFUhHVWz7Ci2k2hOtWmkv9XqWfYBMme9UgsVYRQgknwEoKEQO81AJ4dQ9Dprcee/80ovJGN1Ty4uhPu8ulEseB7QgkK/VTshNUrugz5mj0V7vZer3UyrVJTpufUWeiZLKEpLmePcfP6xq0l+hgxgMNpC4FL8dhjbG6IPXY/WXNyzxeDxHsZxwtfPU4dztOlsLRka63xeJHhxLTMKj2iA5BCZKTQWDrCJggwBJfYKEFIIdZctGABxzOLiLJswVSxJetao6I4YgMADnEulgYD84EKgs2miZQDXY4qci+M8GZmc1AvEPVaNjvriq74xmaQQEZzunUaDQO2YE243kJJYoCmZsFkcja++hvltX1f3rUnDR8Dwm2zEeSFi0ZxdfoIToYjUkkoXDMtLGcLrgCjp5LvtDOOAOctZVX5xWEkBkSJBWEEgyxMUzMwszAzJgzCwzKZZlLEsWZWSzImMwypJLGfaBj6zXPt0CO6EEKWHBqlTsj7h79pMY3DvfigEhxo8+5mszGoGDDbFQYJfLAW7CtI2C5YbaruR3iFz9TByS3mMD0Cj1HxeAO4yYPwBfQygAqmNKIsGvMA3714jCAFMt3XfUULmeW7zdDwUE3AYgLOwVu5TUl0CefuFYEVGbh0+0cfuZdIyptW2r0sbi/SEzNe1f1KokxjXJlsJ+q8Y+PZ8Y8ZSofRXltNy5HDlEQexZEUT5vOHJeoef/0QB/uCM/M9P8VJJiSViEMiSzayzczSsZRX/8XckU4UJCMH4lL";
      }
      tailf:meta-data "uncompressed_size" {
        tailf:meta-value "52698";
      }
    }
    container Cisco-IOS-XE-ios-common-oper {
      description
        "Hidden internal container used for metadata";
      uses ios-common-ios-xe-oper:__yangpp_metadata;
    }
  }

  container schema-metadata-Cisco-IOS-XE-interfaces-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-interfaces-oper";
    }
    tailf:meta-data "organization" {
      tailf:meta-value "Cisco Systems, Inc.";
    }
    tailf:meta-data "semver" {
      tailf:meta-value "2020-07-01";
    }
  }
}
