module Cisco-IOS-XE-device-hardware-oper {
  yang-version 1;
  namespace "http://cisco.com/ns/yang/Cisco-IOS-XE-device-hardware-oper";
  prefix device-hardware-xe-oper;
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Device Hardware operational data.
     Copyright (c) 2017-2020 by Cisco Systems, Inc.
     All rights reserved.";

  revision 2020-07-01 {
    description
      "- Added device-system-data type 'reboot-reason-type'.
       - Added FC FRU type";
    reference "0.0.0";
    cisco-semver:module-version "0.0.0";
    cisco-semver-internal:os-version "17.3.1";
  }
  revision 2019-11-01 {
    description
      "Update copyright";
    reference "1.3.1";
    cisco-semver:module-version "1.3.1";
    cisco-semver-internal:os-version "17.1.1";
  }
  revision 2019-03-28 {
    description
      "- Added device alarm type 'Info'.
       - Added semantic version";
    reference "1.3.0";
    cisco-semver:module-version "1.3.0";
  }
  revision 2018-10-29 {
    description
      "- Added extensions to device inventory
       - Cleaned up spelling errors in descriptions.";
    reference "1.2.0";
    cisco-semver:module-version "1.2.0";
  }
  revision 2018-06-18 {
    description
      "Add entity information";
    reference "1.1.0";
    cisco-semver:module-version "1.1.0";
  }
  revision 2017-11-01 {
    description
      "Initial revision";
    reference "1.0.0";
    cisco-semver:module-version "1.0.0";
  }

  typedef b-fru {
    type enumeration {
      enum "device-hardware-fru-rp" {
        value 0;
        description
          "A Route Processor";
        tailf:code-name "ENUM_b_fru_BINOS_FRU_RP";
      }
      enum "device-hardware-fru-esp" {
        value 1;
        description
          "An Embedded Services Processor";
        tailf:code-name "ENUM_b_fru_BINOS_FRU_FP";
      }
      enum "device-hardware-fru-cp" {
        value 2;
        description
          "A Carrier Card";
        tailf:code-name "ENUM_b_fru_BINOS_FRU_CC";
      }
      enum "device-hardware-fru-max" {
        value 3;
        description
          "An illegal value for FRU type";
        tailf:code-name "ENUM_b_fru_BINOS_FRU_MAX";
      }
      enum "device-hardware-fru-fc" {
        value 4;
        description
          "A Fabric Card";
        tailf:code-name "ENUM_b_fru_BINOS_FRU_FC";
      }
    }
    description
      "The Field Replaceable Unit type";
  }

  typedef high-availability-role {
    type enumeration {
      enum "ha-role-active" {
        value 0;
        description
          "The role is Active ";
        tailf:code-name "ENUM_b_role_BINOS_ROLE_ACTIVE";
      }
      enum "ha-role-standby" {
        value 1;
        description
          "The role is Standby";
        tailf:code-name "ENUM_b_role_BINOS_ROLE_STANDBY";
      }
      enum "ha-role-unknown" {
        value 2;
        description
          "The role is unknown";
        tailf:code-name "ENUM_b_role_BINOS_ROLE_MAX";
      }
    }
    description
      "The High Availability role";
  }

  typedef reboot-reason-type {
    type enumeration {
      enum "normal" {
        value 0;
        description
          "System reboot reason is determined to be
           normal and intentional";
        tailf:code-name "ENUM_reboot_reason_type_REBOOT_REASON_TYPE_NORMAL";
      }
      enum "abnormal" {
        value 1;
        description
          "System reboot reason is determined to be
           abnormal or unintentional";
        tailf:code-name "ENUM_reboot_reason_type_REBOOT_REASON_TYPE_ABNORMAL";
      }
    }
    description
      "Reboot-reason normality classification type";
  }

  typedef hw-type {
    type enumeration {
      enum "hw-type-unknown" {
        value 0;
        description
          "Unknown Hardware Type";
        tailf:code-name "ENUM_hw_type_HW_TYPE_UNKNOWN";
      }
      enum "hw-type-chassis" {
        value 1;
        description
          "Chassis";
        tailf:code-name "ENUM_hw_type_HW_TYPE_CHASSIS";
      }
      enum "hw-type-cpu" {
        value 2;
        description
          "Central Processing Unit";
        tailf:code-name "ENUM_hw_type_HW_TYPE_CPU";
      }
      enum "hw-type-dram" {
        value 3;
        description
          "Dynamic Random Access Memory";
        tailf:code-name "ENUM_hw_type_HW_TYPE_DRAM";
      }
      enum "hw-type-flash" {
        value 4;
        description
          "Flash";
        tailf:code-name "ENUM_hw_type_HW_TYPE_FLASH";
      }
      enum "hw-type-emmc" {
        value 5;
        description
          "embedded Memory Controller";
        tailf:code-name "ENUM_hw_type_HW_TYPE_EMMC";
      }
      enum "hw-type-sdcard" {
        value 6;
        description
          "SD-Card";
        tailf:code-name "ENUM_hw_type_HW_TYPE_SDCARD";
      }
      enum "hw-type-usb" {
        value 7;
        description
          "Universal Serial Bus";
        tailf:code-name "ENUM_hw_type_HW_TYPE_USB";
      }
      enum "hw-type-pim" {
        value 8;
        description
          "Pluggable interface model";
        tailf:code-name "ENUM_hw_type_HW_TYPE_PIM";
      }
      enum "hw-type-transceiver" {
        value 9;
        description
          "Transceiver";
        tailf:code-name "ENUM_hw_type_HW_TYPE_TRANSCEIVER";
      }
      enum "hw-type-fantray" {
        value 10;
        description
          "Fan tray";
        tailf:code-name "ENUM_hw_type_HW_TYPE_FANTRAY";
      }
      enum "hw-type-pem" {
        value 11;
        description
          "Power Entry Module";
        tailf:code-name "ENUM_hw_type_HW_TYPE_PEM";
      }
    }
    description
      "The broad type of hardware device";
  }

  typedef alarm-severity {
    type enumeration {
      enum "alarm-severity-critical" {
        value 0;
        description
          "Critical Alarms";
        tailf:code-name "ENUM_alarm_severity_ALARM_SEVERITY_CRITICAL";
      }
      enum "alarm-severity-major" {
        value 1;
        description
          "Major Alarms";
        tailf:code-name "ENUM_alarm_severity_ALARM_SEVERITY_MAJOR";
      }
      enum "alarm-severity-minor" {
        value 2;
        description
          "Minor Alarms";
        tailf:code-name "ENUM_alarm_severity_ALARM_SEVERITY_MINOR";
      }
      enum "alarm-severity-info" {
        value 3;
        description
          "INFO Alarms";
        tailf:code-name "ENUM_alarm_severity_ALARM_SEVERITY_INFO";
      }
    }
    description
      "Alarm severity";
  }

  typedef hw-category {
    type enumeration {
      enum "hw-class-virtual" {
        value 0;
        description
          "Internal Virtual Device";
        tailf:code-name "ENUM_hw_category_HW_CLASS_VIRTUAL";
      }
      enum "hw-class-physical" {
        value 1;
        description
          "Physical HW Device";
        tailf:code-name "ENUM_hw_category_HW_CLASS_PHYSICAL";
      }
    }
    description
      "Device Category";
  }

  typedef module-status {
    type enumeration {
      enum "module-status-invalid" {
        value 0;
        description
          "An invalid value for module status";
        tailf:code-name "ENUM_module_status_MODULE_STATUS_INVALID";
      }
      enum "module-status-unknown" {
        value 1;
        description
          "An unknown value for module status";
        tailf:code-name "ENUM_module_status_MODULE_STATUS_UNKNOWN";
      }
      enum "module-status-booting" {
        value 2;
        description
          "The module is currently booting";
        tailf:code-name "ENUM_module_status_MODULE_STATUS_BOOTING";
      }
      enum "module-status-online" {
        value 3;
        description
          "The module is online and operational";
        tailf:code-name "ENUM_module_status_MODULE_STATUS_ONLINE";
      }
      enum "module-status-disabled" {
        value 4;
        description
          "The module is disabled";
        tailf:code-name "ENUM_module_status_MODULE_STATUS_DISABLED";
      }
      enum "module-status-failed" {
        value 5;
        description
          "The module has failed";
        tailf:code-name "ENUM_module_status_MODULE_STATUS_FAILED";
      }
      enum "module-status-removed" {
        value 6;
        description
          "The module has been removed";
        tailf:code-name "ENUM_module_status_MODULE_STATUS_REMOVED";
      }
      enum "module-status-stopped" {
        value 7;
        description
          "The module is stopped.";
        tailf:code-name "ENUM_module_status_MODULE_STATUS_STOPPED";
      }
      enum "module-status-incompatible" {
        value 8;
        description
          "The module hardware version is incompatible 
           with the current software version";
        tailf:code-name "ENUM_module_status_MODULE_STATUS_INCOMPATIBLE";
      }
      enum "module-status-cpld-failed" {
        value 9;
        description
          "A Complex Programmable Logic Device (CPLD)
           has failed. The module will not be usable";
        tailf:code-name "ENUM_module_status_MODULE_STATUS_CPLD_FAILED";
      }
      enum "module-status-actrpcpldfailed" {
        value 10;
        description
          "A Complex Programmable Logic Device (CPLD)
           has failed on the active RP. The module will 
           not be usable";
        tailf:code-name "ENUM_module_status_MODULE_STATUS_ACT_RP_CPLD_FAILED";
      }
      enum "module-status-mdr" {
        value 11;
        description
          "The module is currently undergoing a Minimal
           Disruptive Restart";
        tailf:code-name "ENUM_module_status_MODULE_STATUS_MDR";
      }
    }
    description
      "The status that the module is in";
  }

  grouping svc-loc {
    description
      "Service Location details";
    leaf fru {
      type device-hardware-xe-oper:b-fru;
      description
        "Field Replaceable Unit type";
    }
    leaf slotnum {
      type int16;
      description
        "Slot number";
    }
    leaf baynum {
      type int16;
      description
        "Bay number";
    }
    leaf chassisnum {
      type int16;
      description
        "Chassis number";
    }
  }

  grouping hw-alarm-key {
    description
      "The key to the hardware table";
    leaf alarm-id {
      type uint32;
      description
        "The Alarm Identifier";
    }
    leaf alarm-instance {
      type uint32;
      description
        "The instance of this alarm. This corresponds to the 
         entity index";
    }
  }

  grouping hw-alarm {
    description
      "The alarm information";
    leaf alarm-name {
      type string;
      description
        "The name of the alarm";
    }
    leaf alarm-category {
      type device-hardware-xe-oper:alarm-severity;
      description
        "The category (or severity) of the alarm that is being asserted";
    }
    leaf alarm-time {
      type yang:date-and-time;
      description
        "Time the alarm was raised";
    }
    leaf alarm-description {
      type string;
      description
        "Description of the alarm";
    }
  }

  grouping device-system-data {
    description
      "Device system data";
    leaf current-time {
      type yang:date-and-time;
      description
        "Current time on device in UTC";
    }
    leaf boot-time {
      type yang:date-and-time;
      description
        "This timestamp indicates the time that the system was last
         restarted.  The value is the timestamp in seconds relative
         to the Unix Epoch (Jan 1, 1970 00:00:00 UTC).";
    }
    leaf software-version {
      type string;
      description
        "Software version";
    }
    leaf rommon-version {
      type string;
      description
        "Rommon version";
    }
    leaf last-reboot-reason {
      type string;
      description
        "Last reboot reason";
    }
    leaf reason-severity {
      type device-hardware-xe-oper:reboot-reason-type;
      description
        "Reboot reason severity,
         either normal, i.e. intentional; 
         or abnormal, i.e., unintentional";
    }
  }

  grouping device-inventory-key {
    description
      "Key to the device inventory";
    leaf hw-type {
      type device-hardware-xe-oper:hw-type;
      description
        "Type of the hardware being represented";
    }
    leaf hw-dev-index {
      type uint32;
      description
        "The physical index of the inventory item";
    }
  }

  grouping device-inventory {
    description
      "inventory";
    leaf version {
      type string;
      description
        "Version of this device";
    }
    leaf part-number {
      type string;
      description
        "The part number of this device. This 
         is only valid if the device is a field replaceable
         unit";
    }
    leaf serial-number {
      type string;
      description
        "The serial number of the device. This is only
         valid if the device is individually trackable";
    }
    leaf hw-description {
      type string;
      description
        "Description of the device";
    }
    leaf dev-name {
      type string;
      description
        "Name of the Device";
    }
    leaf field-replaceable {
      type boolean;
      description
        "The device is field replaceable or not";
    }
    leaf hw-class {
      type device-hardware-xe-oper:hw-category;
      description
        "The Device Category";
    }
  }

  grouping device-hardware {
    description
      "Device hardware";
    list device-inventory {
      key "hw-type hw-dev-index";
      description
        "All the inventory in the hardware";
      uses device-hardware-xe-oper:device-inventory-key;
      uses device-hardware-xe-oper:device-inventory;
    }
    list device-alarm {
      key "alarm-id alarm-instance";
      description
        "The current alarms";
      uses device-hardware-xe-oper:hw-alarm-key;
      uses device-hardware-xe-oper:hw-alarm;
    }
    container device-system-data {
      presence "device-system-data";
      description
        "The current device system data";
      uses device-hardware-xe-oper:device-system-data;
    }
  }

  grouping entity-information {
    description
      "Information that describes the entity at the service location";
    leaf physical-index {
      type uint32;
      description
        "The SNMP physical index of this entity";
    }
    leaf status {
      type device-hardware-xe-oper:module-status;
      description
        "The current status of the entity";
    }
    leaf description {
      type string;
      description
        "The detailed description of this entity";
    }
    leaf status-last-change {
      type yang:date-and-time;
      description
        "The timestamp when the entity transitioned into
         its reported status";
    }
    leaf high-availability-state {
      type device-hardware-xe-oper:high-availability-role;
      description
        "The location's high availability state";
    }
    leaf chassis-state {
      type device-hardware-xe-oper:high-availability-role;
      description
        "The chassis role status";
    }
  }

  container device-hardware-data {
    config false;
    description
      "Device Hardware";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list entity-information {
      key "fru slotnum baynum chassisnum";
      description
        "The entity information";
      uses device-hardware-xe-oper:svc-loc;
      uses device-hardware-xe-oper:entity-information;
    }
    container device-hardware {
      presence "device-hardware";
      description
        "The device hardware model";
      uses device-hardware-xe-oper:device-hardware;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWc8e7RkAA91fgBAAEAYQED//3+q//9/qUANGPLd3U7t3bXOEoinpPKT9KfqNqnqMhoAzKeiaZqMNQSSR6E1NNooAxAAAB6gASIUNU9Mpp6aSbUPUBo8kA0AMMNDQAAAaAAAAAEkhTwmqe0TU9QAAGgDTQAw2/nA4WLzW6/o8/uXGDr2m+MN7b1SKuYwdHFL2PnWcjTYv2z13NeXbbn0WNNUdmttqpSrmMHRkaA4aa9F6t9FGtw5pDPjAJRCGQ4GmhxCAZBCE2yHHGz7X3JIOYP1HExzH4Fpnk9PIVJd2zMtARe3MQ5Tb0VTgDQqZYEyG9xkgFtYLLVfRcTmOd0Q2cmxpS40bh0OOuQK4nfUDXrMKnTfa6RCNGXSwULlWoTYjKVG1AsDS0dRcDwhpxaeiCLgq9ibBoTWF4rMTutmJX6FW2qrS7s+QE/YWmFUkH5oyFQJ5SRTMVZpWCY3rB0oimZTFME1zhmSmyoPDRdADMiQcreCoqz2iiyzyWgYBqq55Wr8q+IkxeTaLjLMvMZGY04hI0BBFs0Oh67bkX57oRIlcjBDCnCZENCrCcavtaQJ4lIJEsLYAopwKaKTm1gi84BKpvEM5xErmHMOQX9B1GkcDSp1iDcRF7cCp8omqmIbewgKiewGhU9cRNiiWzv4Z17Mu4j5Hep91s5xTXqLGG6gMLYq+h8QT6BKURm0nAEm/Jl2c1KoYSxFEtZClFMsoF7FxTbCTFXJTocrCtGwjZpfWC2At92MqOkhg0b0hkKUKYhkTIXVX5dt0lGCYIQsGQk5FzIazQcnpFqvEqTI0Qo1I6DVobLJixvjYnWhCqMkVDiK3qYFeYkVTM4IvaS8NjxnrCOkNWZxvZVwJ48FhboYZK6MreCvpvGGKysCqn2uwcR/tKtOj1TdhbQ7YCzrRMZUHsxn2M0cbTJArYXBIYEUv479+9DrYg6mnMaQsEUrGlitQrWMAsHEpQlfppGcrcZgpg4LGjoriCdX2AoTpc7YIB9glME6lutcAPhs/GSOgW5VRQXBFX/F3JFOFCQzx7tGQ";
      }
      tailf:meta-data "uncompressed_size" {
        tailf:meta-value "2010";
      }
    }
  }

  container schema-metadata-Cisco-IOS-XE-device-hardware-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-device-hardware-oper";
    }
    tailf:meta-data "organization" {
      tailf:meta-value "Cisco Systems, Inc.";
    }
    tailf:meta-data "semver" {
      tailf:meta-value "2020-07-01";
    }
  }
}
