module Cisco-IOS-XE-platform-common-oper {
  yang-version 1;
  namespace "http://cisco.com/ns/yang/Cisco-IOS-XE-platform-common-oper";
  prefix platform-common-ios-xe-oper;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     common to platform oper as well as platform events.
     Copyright (c) 2019 by Cisco Systems, Inc.
     All rights reserved.";

  revision 2019-11-01 {
    description
      "Initial revision";
    reference "1.0.0";
    cisco-semver:module-version "1.0.0";
    cisco-semver-internal:os-version "17.1.1";
  }

  typedef plat-comp-type {
    type enumeration {
      enum "comp-chassis" {
        value 0;
        description
          "Component type - chassis";
        tailf:code-name "ENUM_plat_comp_type_PLAT_CHASSIS";
      }
      enum "comp-backplane" {
        value 1;
        description
          "Component type - backplane";
        tailf:code-name "ENUM_plat_comp_type_PLAT_BACKPLANE";
      }
      enum "comp-power-supply" {
        value 2;
        description
          "Component type - power supply";
        tailf:code-name "ENUM_plat_comp_type_PLAT_POWER_SUPPLY";
      }
      enum "comp-fan" {
        value 3;
        description
          "Component type - fan or fan tray";
        tailf:code-name "ENUM_plat_comp_type_PLAT_FAN";
      }
      enum "comp-sensor" {
        value 4;
        description
          "Component type - sensor";
        tailf:code-name "ENUM_plat_comp_type_PLAT_SENSOR";
      }
      enum "comp-module" {
        value 5;
        description
          "Component type - module";
        tailf:code-name "ENUM_plat_comp_type_PLAT_MODULE";
      }
      enum "comp-linecard" {
        value 6;
        description
          "Component type - linecard";
        tailf:code-name "ENUM_plat_comp_type_PLAT_LINECARD";
      }
      enum "comp-port" {
        value 7;
        description
          "Component type - port";
        tailf:code-name "ENUM_plat_comp_type_PLAT_PORT";
      }
      enum "comp-cpu" {
        value 8;
        description
          "Component type - cpu";
        tailf:code-name "ENUM_plat_comp_type_PLAT_CPU";
      }
      enum "comp-operating-system" {
        value 9;
        description
          "Component type - operating system";
        tailf:code-name "ENUM_plat_comp_type_PLAT_OPERATING_SYSTEM";
      }
      enum "comp-optical-channel" {
        value 10;
        description
          "Component type - optical channel";
        tailf:code-name "ENUM_plat_comp_type_PLAT_OPTICAL_CHANNEL";
      }
      enum "comp-container" {
        value 11;
        description
          "Component type - container";
        tailf:code-name "ENUM_plat_comp_type_PLAT_CONTAINER";
      }
      enum "comp-fru" {
        value 12;
        description
          "Component type - fru";
        tailf:code-name "ENUM_plat_comp_type_PLAT_FRU";
      }
      enum "comp-controller-card" {
        value 13;
        description
          "Component type - controller card";
        tailf:code-name "ENUM_plat_comp_type_PLAT_CONTROLLER_CARD";
      }
      enum "comp-transceiver" {
        value 14;
        description
          "Component type - transceiver";
        tailf:code-name "ENUM_plat_comp_type_PLAT_TRANSCEIVER";
      }
    }
    description
      "Component Type";
  }

  typedef plat-comp-status {
    type enumeration {
      enum "status-active" {
        value 0;
        description
          "Component status - active";
        tailf:code-name "ENUM_plat_comp_status_PLAT_STATUS_ACTIVE";
      }
      enum "status-inactive" {
        value 1;
        description
          "Component status - inactive";
        tailf:code-name "ENUM_plat_comp_status_PLAT_STATUS_INACTIVE";
      }
      enum "status-disabled" {
        value 2;
        description
          "Component status - disabled";
        tailf:code-name "ENUM_plat_comp_status_PLAT_STATUS_DISABLED";
      }
    }
    description
      "Component status";
  }

  typedef plat-comp-status-desc {
    type enumeration {
      enum "ok" {
        value 0;
        description
          "Component status description - ok";
        tailf:code-name "ENUM_plat_comp_status_desc_STATUS_DESC_OK";
      }
      enum "thermal-failure" {
        value 1;
        description
          "Component status description - thermal failure";
        tailf:code-name "ENUM_plat_comp_status_desc_STATUS_DESC_THERMAL_FAILURE";
      }
      enum "fan-failure" {
        value 2;
        description
          "Component status description - fan failure";
        tailf:code-name "ENUM_plat_comp_status_desc_STATUS_DESC_FAN_FAILURE";
      }
      enum "supply-failure" {
        value 3;
        description
          "Component status description - supply failure";
        tailf:code-name "ENUM_plat_comp_status_desc_STATUS_DESC_SUPPLY_FAILURE";
      }
      enum "no-response" {
        value 4;
        description
          "Component status description - no response";
        tailf:code-name "ENUM_plat_comp_status_desc_STATUS_DESC_NO_RESPONSE";
      }
      enum "bad-power" {
        value 5;
        description
          "Component status description - bad power or 
           input is out of range";
        tailf:code-name "ENUM_plat_comp_status_desc_STATUS_DESC_BAD_POWER";
      }
      enum "overload" {
        value 6;
        description
          "Component status description - overload";
        tailf:code-name "ENUM_plat_comp_status_desc_STATUS_DESC_OVERLOAD";
      }
      enum "no-input-power" {
        value 7;
        description
          "Component status description - no input power";
        tailf:code-name "ENUM_plat_comp_status_desc_STATUS_DESC_NO_INPUT";
      }
      enum "disabled" {
        value 8;
        description
          "Component status description - disabled";
        tailf:code-name "ENUM_plat_comp_status_desc_STATUS_DESC_DISABLED";
      }
      enum "not-present" {
        value 9;
        description
          "Component status description - vacant";
        tailf:code-name "ENUM_plat_comp_status_desc_STATUS_DESC_VACANT";
      }
      enum "standby" {
        value 10;
        description
          "Component status description - standby";
        tailf:code-name "ENUM_plat_comp_status_desc_STATUS_DESC_STANDBY";
      }
      enum "bad-cookie" {
        value 11;
        description
          "Component status description - bad cookie";
        tailf:code-name "ENUM_plat_comp_status_desc_STATUS_DESC_BAD_COOKIE";
      }
      enum "invalid" {
        value 12;
        description
          "Component status description - invalid";
        tailf:code-name "ENUM_plat_comp_status_desc_STATUS_DESC_INVALID";
      }
    }
    description
      "Component status description";
  }

  typedef plat-sensor-alarm-severity {
    type enumeration {
      enum "alarm-severity-unknown" {
        value 0;
        description
          "Sensor alarm severity - unknown or normal";
        tailf:code-name "ENUM_plat_sensor_alarm_severity_PLAT_ALARM_SEV_UNKNOWN";
      }
      enum "alarm-severity-minor" {
        value 1;
        description
          "Sensor alarm severity - minor";
        tailf:code-name "ENUM_plat_sensor_alarm_severity_PLAT_ALARM_SEV_MINOR";
      }
      enum "alarm-severity-major" {
        value 2;
        description
          "Sensor alarm severity - major";
        tailf:code-name "ENUM_plat_sensor_alarm_severity_PLAT_ALARM_SEV_MAJOR";
      }
      enum "alarm-severity-critical" {
        value 3;
        description
          "Sensor alarm severity - critical";
        tailf:code-name "ENUM_plat_sensor_alarm_severity_PLAT_ALARM_SEV_CRITICAL";
      }
      enum "alarm-severity-warning" {
        value 4;
        description
          "Sensor alarm severity - warning";
        tailf:code-name "ENUM_plat_sensor_alarm_severity_PLAT_ALARM_SEV_WARNING";
      }
      enum "alarm-severity-shutdown" {
        value 5;
        description
          "Sensor alarm severity - shutdown";
        tailf:code-name "ENUM_plat_sensor_alarm_severity_PLAT_ALARM_SEV_SHUTDOWN";
      }
    }
    description
      "Temperature Alarm Severity";
  }

  typedef plat-sensor-type {
    type enumeration {
      enum "sensor-unknown" {
        value 0;
        description
          "Sensor type - unknown";
        tailf:code-name "ENUM_plat_sensor_type_PLAT_SENSOR_UNKNOWN";
      }
      enum "sensor-temp-cpu" {
        value 1;
        description
          "Sensor type - temperature cpu";
        tailf:code-name "ENUM_plat_sensor_type_PLAT_SENSOR_TEMP_CPU";
      }
      enum "sensor-temp-uadp" {
        value 2;
        description
          "Sensor type - temperature asic";
        tailf:code-name "ENUM_plat_sensor_type_PLAT_SENSOR_TEMP_UADP";
      }
      enum "sensor-temp-inlet" {
        value 3;
        description
          "Sensor type - temperature inlet";
        tailf:code-name "ENUM_plat_sensor_type_PLAT_SENSOR_TEMP_INLET";
      }
      enum "sensor-temp-outlet" {
        value 4;
        description
          "Sensor type - temperature outlet";
        tailf:code-name "ENUM_plat_sensor_type_PLAT_SENSOR_TEMP_OUTLET";
      }
      enum "sensor-temp-hotspot" {
        value 5;
        description
          "Sensor type - temperature hotspot";
        tailf:code-name "ENUM_plat_sensor_type_PLAT_SENSOR_TEMP_HOTSPOT";
      }
      enum "sensor-pfu-redundancy" {
        value 6;
        description
          "Sensor type - power supply redundancy";
        tailf:code-name "ENUM_plat_sensor_type_PLAT_SENSOR_PFU_REDUNDANCY";
      }
    }
    description
      "Temperature sensor type";
  }

  typedef plat-sensor-state {
    type enumeration {
      enum "green" {
        value 0;
        description
          "Sensor state - green";
        tailf:code-name "ENUM_plat_sensor_state_PLAT_SENSOR_STATE_GREEN";
      }
      enum "yellow" {
        value 1;
        description
          "Sensor state - yellow";
        tailf:code-name "ENUM_plat_sensor_state_PLAT_SENSOR_STATE_YELLOW";
      }
      enum "red" {
        value 2;
        description
          "Sensor state - red";
        tailf:code-name "ENUM_plat_sensor_state_PLAT_SENSOR_STATE_RED";
      }
    }
    description
      "Platform sensor state";
  }

  grouping plat-sensor-data {
    description
      "Sensor state data for device components";
    leaf value-instant {
      type decimal64 {
        fraction-digits 2;
      }
      description
        "Instantaneous sensor reading 
         value of a component";
    }
    leaf value-avg {
      type decimal64 {
        fraction-digits 2;
      }
      description
        "Arithmetic mean value of the statistic over a
         sampling period";
    }
    leaf value-max {
      type decimal64 {
        fraction-digits 2;
      }
      description
        "High water mark value of the statistic over a
         sampling period";
    }
    leaf value-min {
      type decimal64 {
        fraction-digits 2;
      }
      description
        "Low water mark value of the statistic over a
         sampling period";
    }
    leaf sampling-period-sec {
      type uint32;
      description
        "Sampling period in seconds";
    }
  }

  grouping plat-sensor-alarm-data {
    description
      "Sensor alarm data of a component";
    leaf alarm-status {
      type boolean;
      description
        "Alarm status";
    }
    leaf alarm-threshold-high {
      type uint32;
      description
        "High threshold limit of a generated alarm";
    }
    leaf alarm-threshold-low {
      type uint32;
      description
        "Low threshold limit of a generated alarm";
    }
    leaf severity {
      type platform-common-ios-xe-oper:plat-sensor-alarm-severity;
      description
        "Alarm Severity";
    }
  }

  grouping __yangpp_metadata {
    description
      "Internal metadata for this module and imported modules";
  }

  container gnmi-model-data {
    description
      "This container makes accessible the information necessary to respond to a GNMI Capabilities RPC";
    tailf:hidden "full";
    tailf:meta-data "module-name" {
      tailf:meta-value "Cisco-IOS-XE-platform-common-oper";
    }
    tailf:meta-data "organization" {
      tailf:meta-value "Cisco Systems, Inc.";
    }
    tailf:meta-data "semver" {
      tailf:meta-value "2019-11-01";
    }
  }
}
