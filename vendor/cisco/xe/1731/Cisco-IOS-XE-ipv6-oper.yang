module Cisco-IOS-XE-ipv6-oper {
  yang-version 1;
  namespace "http://cisco.com/ns/yang/Cisco-IOS-XE-ipv6-oper";
  prefix ipv6-ios-xe-oper;
  import ietf-inet-types {
    prefix inet;
  }
  import ietf-yang-types {
    prefix yang;
  }
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for IPv6 operational data.
     Copyright (c) 2017, 2019 by Cisco Systems, Inc.
     All rights reserved.";

  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2017-11-01 {
    description
      "Initial revision";
    reference "1.0.0";
    cisco-semver:module-version "1.0.0";
  }

  typedef ipv6-nd-tdl-state {
    type enumeration {
      enum "ipv6-nd-incomplete" {
        value 0;
        description
          "Address resolution is in progress and the 
           link-layer address of the neighbor has not
           yet been determined.";
        tailf:code-name "ENUM_ipv6_nd_tdl_state_IPV6_ND_TDL_INCOMPLETE";
      }
      enum "ipv6-nd-reachable" {
        value 1;
        description
          "The neighbor is known to have been reachable
           recently (within tens of seconds ago).";
        tailf:code-name "ENUM_ipv6_nd_tdl_state_IPV6_ND_TDL_REACHABLE";
      }
      enum "ipv6-nd-stale" {
        value 2;
        description
          "The neighbor is no longer known to be reachable
           but until traffic is sent to the neighbor, no 
           attempt should be made to verify its reachability";
        tailf:code-name "ENUM_ipv6_nd_tdl_state_IPV6_ND_TDL_STALE";
      }
      enum "ipv6-nd-glean" {
        value 3;
        description
          "Received updated link-layer information. 
           Behaviour like STALE.";
        tailf:code-name "ENUM_ipv6_nd_tdl_state_IPV6_ND_TDL_GLEAN";
      }
      enum "ipv6-nd-delay" {
        value 4;
        description
          "The neighbor is no longer known to be reachable, and traffic
           has recently been sent to the neighbor. Rather than probe the
           neighbor immediately, however, delay sending probes for a short
           while in order to give upper layer protocols a chance to provide
           reachability confirmation.";
        tailf:code-name "ENUM_ipv6_nd_tdl_state_IPV6_ND_TDL_DELAY";
      }
      enum "ipv6-nd-probe" {
        value 5;
        description
          "The neighbor is no longer known to be reachable, and unicast
           Neighbor Solicitation probes are being sent to verify 
           reachability.";
        tailf:code-name "ENUM_ipv6_nd_tdl_state_IPV6_ND_TDL_PROBE";
      }
      enum "ipv6-nd-delete" {
        value 6;
        description
          "Entry is deleted.";
        tailf:code-name "ENUM_ipv6_nd_tdl_state_IPV6_ND_TDL_DELETE";
      }
    }
    description
      "Indicate the current state of 
       the Neighbor-Discovery entry.";
  }

  grouping nd6-info-key {
    description
      "Key for IPv6 neighbor information table";
    leaf vrf-name {
      type string;
      description
        "The Virtual Router and Forwarding instance that 
         this neighbor information is associated with";
    }
    leaf if-name {
      type string;
      description
        "The Interface name.";
    }
    leaf ip {
      type inet:ip-address;
      description
        "IPv6 address of this neighbor entry";
    }
  }

  grouping nd6-info {
    description
      "Value for IPv6 neighbor info table entry";
    leaf mac-address {
      type yang:mac-address;
      description
        "MAC address";
    }
    leaf state {
      type ipv6-ios-xe-oper:ipv6-nd-tdl-state;
      description
        "State of the entry";
    }
    leaf idle-timer {
      type uint32;
      description
        "Time before expiration, in seconds.";
    }
    leaf uptime {
      type uint32;
      description
        "Indicates how long this neighbor entry has 
         been active, in seconds";
    }
  }

  container ipv6-data {
    config false;
    description
      "Operational state of IPv6";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list nd6-info {
      key "vrf-name if-name ip";
      description
        "List of IPv6 neighbors";
      uses ipv6-ios-xe-oper:nd6-info-key;
      uses ipv6-ios-xe-oper:nd6-info;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWc8FZ08AAMFfgEAAEAYBED7n3Wq+598qMADNtBilB6j0mjNTIPUBoZNGnoQaCTExE00AGg0ZAMQZQk2kMCDTA0EeU0NMMcPFqN33rPvQEbvLbK8aE8FJMJQTJc7wZ1sqptAmSAEnYgNJQsEsfajDzaKFicLJUSgMWHOTiEBTrTtOBFRPLst8SLNNdORUyUXsQiN7kPYhFAMIqVhZDI8CECWGYmS+hrZbxp9Mj395WWVOa6salgHACkyCLxcaRGcTMDfJ0SACJYKKlOK4LF7am04xIjbIUzI9rnitZwQiIKkWBWOraK8mPBA8OIGNkAYy/i7kinChIZ4Kzp4=";
      }
      tailf:meta-data "uncompressed_size" {
        tailf:meta-value "397";
      }
    }
  }

  container schema-metadata-Cisco-IOS-XE-ipv6-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-ipv6-oper";
    }
    tailf:meta-data "organization" {
      tailf:meta-value "Cisco Systems, Inc.";
    }
    tailf:meta-data "semver" {
      tailf:meta-value "2019-05-01";
    }
  }
}
