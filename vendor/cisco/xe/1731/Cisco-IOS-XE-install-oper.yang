module Cisco-IOS-XE-install-oper {
  yang-version 1;
  namespace "http://cisco.com/ns/yang/Cisco-IOS-XE-install-oper";
  prefix install-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for install manager operational data.
     Copyright (c) 2020 by Cisco Systems, Inc.
     All rights reserved.";

  revision 2020-07-01 {
    description
      "Initial revision";
    reference "1.0.0";
    cisco-semver:module-version "1.0.0";
  }

  typedef install-package-type {
    type enumeration {
      enum "install-pkg-unknown" {
        value 0;
        description
          "Install package type unknown";
      }
      enum "install-pkg-img" {
        value 1;
        description
          "Install package of type Super Image";
      }
      enum "install-pkg-smu" {
        value 2;
        description
          "Install package of type Software Maintenance Upgrade";
      }
      enum "install-pkg-subpkg" {
        value 3;
        description
          "Install package of type sub-package";
      }
      enum "install-pkg-dmp" {
        value 4;
        description
          "Install package of type Data Model Package";
      }
      enum "install-pkg-apsp" {
        value 5;
        description
          "Install package of type Access Point Service Pack";
      }
      enum "install-pkg-apdp" {
        value 6;
        description
          "Install package of type Access Point Device Pack";
      }
    }
    description
      "Install package type";
  }

  typedef install-package-state {
    type enumeration {
      enum "install-state-new" {
        value 0;
        description
          "Install state for file is new";
      }
      enum "install-state-added" {
        value 1;
        description
          "Image has been added";
      }
      enum "install-state-act-uncommitted" {
        value 2;
        description
          "Install state is activated but not committed";
      }
      enum "install-state-dact-uncommitted" {
        value 3;
        description
          "Install state is deactivated and uncommitted";
      }
      enum "install-state-committed" {
        value 4;
        description
          "Install image is in committed state";
      }
      enum "install-state-unknown" {
        value 5;
        description
          "Install state is not known";
      }
    }
    description
      "Install package state";
  }

  typedef install-package-verify-status {
    type enumeration {
      enum "install-package-verify-unknown" {
        value 0;
        description
          "Install package verification status is unknown";
      }
      enum "install-package-verify-ok" {
        value 1;
        description
          "Install package is verified";
      }
      enum "install-package-verify-fail" {
        value 2;
        description
          "Install package verification failed";
      }
      enum "install-package-verify-deferred" {
        value 3;
        description
          "Install package verification is deferred";
      }
      enum "install-package-verify-not-done" {
        value 4;
        description
          "Install package verification is not done";
      }
    }
    description
      "Install package verification status";
  }

  typedef install-pkg-reload-condition {
    type enumeration {
      enum "install-reload-cond-device-reload" {
        value 0;
        description
          "Install restart condition is restart required";
      }
      enum "install-reload-cond-non-reload" {
        value 1;
        description
          "Install restart condition is no restart required";
      }
      enum "install-reload-cond-restart" {
        value 2;
        description
          "Install restart condition is restart";
      }
      enum "install-reload-cond-issu" {
        value 3;
        description
          "Install restart condition is ISSU dependent";
      }
      enum "install-reload-cond-unknown" {
        value 4;
        description
          "Reload condition is not known";
      }
    }
    description
      "Install package restart condition";
  }

  typedef install-smu-subcategory {
    type enumeration {
      enum "install-smu-subcategory-apsp" {
        value 0;
        description
          "Install Software Maintenance Upgrade sub-category is Access Point Service Pack";
      }
      enum "install-smu-subcategory-apdp" {
        value 1;
        description
          "Install Software Maintenance Upgrade sub-category is Access Point Device Pack";
      }
      enum "install-smu-subcategory-unknown" {
        value 2;
        description
          "Install Software Maintenance Upgrade sub-category is unknown";
      }
    }
    description
      "Install Software Maintenance Upgrade sub-category";
  }

  typedef install-mode {
    type enumeration {
      enum "install-mode-bundle" {
        value 0;
        description
          "install mode is bundle";
      }
      enum "install-mode-install" {
        value 1;
        description
          "Install boot mode is install";
      }
      enum "install-mode-install-bundle" {
        value 2;
        description
          "Install boot mode is bundle";
      }
      enum "install-mode-unknown" {
        value 3;
        description
          "Install boot mode is not known";
      }
    }
    description
      "Install mode type";
  }

  typedef install-smu-class {
    type enumeration {
      enum "install-smu-class-recommended" {
        value 0;
        description
          "Install Software Maintenance Upgrade class is recommended";
      }
      enum "install-smu-class-optional" {
        value 1;
        description
          "Install Software Maintenance Upgrade class is optional";
      }
      enum "install-smu-class-unknown" {
        value 2;
        description
          "Install Software Maintenance Upgrade class is unknown";
      }
    }
    description
      "Install Software Maintenance Upgrade class type";
  }

  typedef install-crdu-attr {
    type enumeration {
      enum "install-crdu-attr-unrevertable" {
        value 0;
        description
          "Install hot patch type is not reversible";
      }
      enum "install-crdu-attr-revertable" {
        value 1;
        description
          "Install hot patch type is reversible";
      }
      enum "install-crdu-attr-unknown" {
        value 2;
        description
          "Install hot patch attribute is unknown";
      }
    }
    description
      "Install hot patch attributes";
  }

  typedef install-version-state {
    type enumeration {
      enum "install-version-state-provisioned-committed" {
        value 0;
        description
          "Install version state is provisioned and committed";
      }
      enum "install-version-state-provisioned-uncommitted" {
        value 1;
        description
          "Install version state is provisioned and uncommitted";
      }
      enum "install-version-state-in-progress" {
        value 2;
        description
          "Install version state is in-progress";
      }
      enum "install-version-state-invalid" {
        value 3;
        description
          "Complete image is not available for this version";
      }
      enum "install-version-state-present" {
        value 4;
        description
          "Install version state is present but not used";
      }
      enum "install-version-state-unknown" {
        value 5;
        description
          "Install version state is not configured";
      }
    }
    description
      "Install version state";
  }

  typedef install-smu-license-level {
    type enumeration {
      enum "install-smu-lic-name-base-network-essentials" {
        value 0;
        description
          "Install Software Maintenance Upgrade license level is base-network-essentials";
      }
      enum "install-smu-lic-name-base-network-advantage" {
        value 1;
        description
          "Install Software Maintenance Upgrade license level is base-network-advantage";
      }
      enum "install-smu-lic-name-dna-essentials" {
        value 2;
        description
          "Install Software Maintenance Upgrade license level is dna-essentials";
      }
      enum "install-smu-lic-name-dna-advantage" {
        value 3;
        description
          "Install Software Maintenance Upgrade license level is dna-advantage";
      }
      enum "install-smu-lic-name-unknown" {
        value 4;
        description
          "Install Software Maintenance Upgrade license level is not known";
      }
    }
    description
      "Install Software Maintenance Upgrade license level";
  }

  typedef install-smu-impact-type {
    type enumeration {
      enum "install-smu-impact-ap-images" {
        value 0;
        description
          "Install Software Maintenance Upgrade impacts AP images";
      }
      enum "install-smu-impact-unknown" {
        value 1;
        description
          "Install Software Maintenance Upgrade impact is unknown";
      }
    }
    description
      "Install Software Maintenance Upgrade impact type";
  }

  typedef install-header-package-type {
    type enumeration {
      enum "install-header-package-type-invalid" {
        value 0;
        description
          "Install header package type is invalid";
      }
      enum "install-header-package-type-rommon" {
        value 1;
        description
          "Install header package is for ROMMON";
      }
      enum "install-header-package-type-cc-base" {
        value 2;
        description
          "Install header package is for CC Base";
      }
      enum "install-header-package-type-cc-spa" {
        value 3;
        description
          "Install header package is for CC supervisor card";
      }
      enum "install-header-package-type-cc-srdriver" {
        value 4;
        description
          "Install header package is for CC SR driver";
      }
      enum "install-header-package-type-cc-spawma" {
        value 5;
        description
          "Install header package is for CC shared port adaptor";
      }
      enum "install-header-package-type-cc-iomd-sup" {
        value 6;
        description
          "Install header package is for CC supervisor card daemon";
      }
      enum "install-header-package-type-cc-mips-base" {
        value 7;
        description
          "Install header package is for MIPS";
      }
      enum "install-header-package-type-elc-base" {
        value 8;
        description
          "Install header package is for line card base";
      }
      enum "install-header-package-type-elc-spa" {
        value 9;
        description
          "Install header package is for shared port adaptor card";
      }
      enum "install-header-package-type-fp-base" {
        value 10;
        description
          "Install header package is for FP base";
      }
      enum "install-header-package-type-rp-super" {
        value 11;
        description
          "Install header package is for RP super";
      }
      enum "install-header-package-type-rp-base" {
        value 12;
        description
          "Install header package is for RP base";
      }
      enum "install-header-package-type-rp-daemons" {
        value 13;
        description
          "Install header package is for RP daemons";
      }
      enum "install-header-package-type-rp-iosd" {
        value 14;
        description
          "Install header package is for RP IOS daemon";
      }
      enum "install-header-package-type-rp-security" {
        value 15;
        description
          "Install header package is for RP security";
      }
      enum "install-header-package-type-firmware" {
        value 16;
        description
          "Install header package is for firmware";
      }
    }
    description
      "Install header package type";
  }

  typedef install-timer-state {
    type enumeration {
      enum "install-timer-state-unknown" {
        value 0;
        description
          "Install timer state is not known";
      }
      enum "install-timer-state-active" {
        value 1;
        description
          "Install timer is running";
      }
      enum "install-timer-state-inactive" {
        value 2;
        description
          "Install timer is not running";
      }
    }
    description
      "Install timer state";
  }

  grouping install-generic-pkg-info {
    description
      "Install common package generic info";
    leaf name {
      type string;
      description
        "Internal package name";
    }
    leaf build-time {
      type yang:date-and-time;
      description
        "Package build time";
    }
    leaf release-date {
      type yang:date-and-time;
      description
        "Package release date";
    }
    leaf user-name {
      type string;
      description
        "Name of the user that built the package";
    }
    leaf package-name {
      type string;
      description
        "Extended internal package name info for variants";
    }
    leaf build-name {
      type string;
      description
        "Release Name tag used for Package Build";
    }
  }

  grouping install-common-pkg-info {
    description
      "Install package info applicable to all package types";
    container generic-info {
      description
        "Install package generic information applicable to all package types";
      uses install-ios-xe-oper:install-generic-pkg-info;
    }
  }

  grouping install-common-smu-pkg-info {
    description
      "Software Maintenance Upgrade package information";
    leaf smu-id {
      type uint32;
      description
        "Software Maintenance Upgrade identifier";
    }
    leaf smu-mode {
      type install-ios-xe-oper:install-mode;
      description
        "Software Maintenance Upgrade mode";
    }
    leaf-list smu-supersedes-list {
      type uint32;
      max-elements "64";
      ordered-by user;
      description
        "Software Maintenance Upgrade supersede list";
    }
    leaf smu-subcategory {
      type install-ios-xe-oper:install-smu-subcategory;
      description
        "Software Maintenance Upgrade sub-category";
    }
    leaf smu-compatible-with {
      type string;
      description
        "Software Maintenance Upgrade compatible with";
    }
    leaf smu-type {
      type install-ios-xe-oper:install-pkg-reload-condition;
      description
        "Software Maintenance Upgrade type";
    }
    leaf activation-type {
      type install-ios-xe-oper:install-pkg-reload-condition;
      description
        "Activation type";
    }
    leaf deactivation-type {
      type install-ios-xe-oper:install-pkg-reload-condition;
      description
        "De-activation type";
    }
    leaf smu-impact {
      type install-ios-xe-oper:install-smu-impact-type;
      description
        "Software Maintenance Upgrade impact type";
    }
    leaf smu-class {
      type install-ios-xe-oper:install-smu-class;
      description
        "Software Maintenance Upgrade class";
    }
    leaf-list smu-fixes-list {
      type string;
      max-elements "64";
      ordered-by user;
      description
        "Software Maintenance Upgrade fixes";
    }
    leaf smu-license-level {
      type install-ios-xe-oper:install-smu-license-level;
      description
        "Software Maintenance Upgrade license level";
    }
    leaf crdu-attr {
      type install-ios-xe-oper:install-crdu-attr;
      description
        "Hot patch attribute";
    }
  }

  grouping install-smu-pkg-info {
    description
      "Install Software Maintenance Upgrade package information";
    container common-data {
      description
        "Common package data which is applicable to all types of packages";
      uses install-ios-xe-oper:install-common-pkg-info;
    }
    leaf defect {
      type string;
      description
        "Defect identifier fixed by this package";
    }
    container smu-data {
      description
        "Software Maintenance Upgrade data";
      uses install-ios-xe-oper:install-common-smu-pkg-info;
    }
  }

  grouping install-smu-attr {
    description
      "Software Maintenance Upgrade package attributes";
    leaf package-state {
      type install-ios-xe-oper:install-package-state;
      description
        "Package state";
    }
    container pkg-info-data {
      description
        "Package info data";
      uses install-ios-xe-oper:install-smu-pkg-info;
    }
  }

  grouping install-subpkg-pkg-info {
    description
      "Sub-package information";
    container common-data {
      description
        "Common package data which is applicable to all types of packages";
      uses install-ios-xe-oper:install-common-pkg-info;
    }
    leaf subpkg-type {
      type string;
      description
        "Sub-package type";
    }
    container smu-data {
      description
        "Software Maintenance Upgrade data";
      uses install-ios-xe-oper:install-common-smu-pkg-info;
    }
  }

  grouping install-subpkg-attr {
    description
      "Sub-package attribute";
    leaf package-state {
      type install-ios-xe-oper:install-package-state;
      description
        "Package state";
    }
    container pkg-info-data {
      description
        "Package information data";
      uses install-ios-xe-oper:install-subpkg-pkg-info;
    }
  }

  grouping install-img-pkg-info {
    description
      "Package information for image";
    container common-data {
      description
        "Common package data which is applicable to all types of packages";
      uses install-ios-xe-oper:install-common-pkg-info;
    }
  }

  grouping install-img-attr {
    description
      "Install image attributes";
    leaf timestamp {
      type yang:date-and-time;
      description
        "Timestamp of the package file";
    }
    leaf header-size {
      type uint32;
      units "bytes";
      description
        "Header size in bytes";
    }
    leaf header-package-type {
      type install-ios-xe-oper:install-header-package-type;
      description
        "Package header type";
    }
    container pkg-info-data {
      description
        "Package info data";
      uses install-ios-xe-oper:install-img-pkg-info;
    }
  }

  grouping install-auto-abort-timer {
    description
      "Install auto abort timer information";
    leaf state {
      type install-ios-xe-oper:install-timer-state;
      description
        "Install auto abort timer state";
    }
    leaf end-time {
      when "(../state = 'install-timer-state-active')";
      type yang:date-and-time;
      description
        "Install auto abort timer end time";
    }
  }

  grouping install-oper-state {
    description
      "Install operational state information";
    container auto-abort-timer {
      description
        "Install auto abort timer information";
      uses install-ios-xe-oper:install-auto-abort-timer;
    }
  }

  grouping install-location-info {
    description
      "Install operational information for install location";
    list install-packages {
      key "pkg-dir pkg-name";
      description
        "Install package information";
      uses install-ios-xe-oper:install-package-path;
      uses install-ios-xe-oper:install-package-info;
    }
    list install-version-info {
      key "version version-extension";
      description
        "Install version information";
      uses install-ios-xe-oper:install-version-key;
      uses install-ios-xe-oper:install-version-file;
    }
    list install-version-state-info {
      key "version-state";
      description
        "Install version state information";
      uses install-ios-xe-oper:install-version-state-key;
      uses install-ios-xe-oper:install-version-key;
    }
    container oper-state {
      description
        "Install operational state information";
      uses install-ios-xe-oper:install-oper-state;
    }
  }

  grouping install-package-path {
    description
      "Install package path";
    leaf pkg-dir {
      type string;
      description
        "Package directory";
    }
    leaf pkg-name {
      type string;
      description
        "Package name";
    }
  }

  grouping install-package-data {
    description
      "Package data";
    leaf pkg-name {
      type string;
      description
        "Package name";
    }
    leaf version {
      type string;
      description
        "Version";
    }
    leaf checksum {
      type string;
      description
        "Checksum";
    }
    leaf pkg-size {
      type uint64;
      units "bytes";
      description
        "Package size in bytes";
    }
    leaf verify-status {
      type install-ios-xe-oper:install-package-verify-status;
      description
        "Package verification status";
    }
    choice pkg-type-choice {
      description
        "Package type";
      case install-pkg-img {
        container img-attr {
          when "(../verify-status = 'install-package-verify-ok')";
          description
            "Image attributes";
          uses install-ios-xe-oper:install-img-attr;
        }
      }
      case install-pkg-smu {
        container smu-attr {
          when "(../verify-status = 'install-package-verify-ok')";
          description
            "Software Maintenance Upgrade attributes";
          uses install-ios-xe-oper:install-smu-attr;
        }
      }
      case install-pkg-subpkg {
        container subpkg-attr {
          when "(../verify-status = 'install-package-verify-ok')";
          description
            "Sub-package attributes";
          uses install-ios-xe-oper:install-subpkg-attr;
        }
      }
      case install-pkg-dmp {
        container dmp-attr {
          when "(../verify-status = 'install-package-verify-ok')";
          description
            "Data Model Package attributes";
          uses install-ios-xe-oper:install-smu-attr;
        }
      }
      case install-pkg-apsp {
        container apsp-attr {
          when "(../verify-status = 'install-package-verify-ok')";
          description
            "Access Point Service Pack attributes";
          uses install-ios-xe-oper:install-smu-attr;
        }
      }
      case install-pkg-apdp {
        container apdp-attr {
          when "(../verify-status = 'install-package-verify-ok')";
          description
            "Access Point Device Pack attributes";
          uses install-ios-xe-oper:install-smu-attr;
        }
      }
    }
  }

  grouping install-packages {
    description
      "Install package info";
    container pkg-data {
      description
        "Package data";
      uses install-ios-xe-oper:install-package-data;
    }
    list install-included-packages {
      key "inc-version inc-pkg-name";
      description
        "Included package information";
      uses install-ios-xe-oper:install-include-pkg-key;
      uses install-ios-xe-oper:install-package-data;
    }
  }

  grouping install-package-data-key {
    description
      "Package data key";
    leaf version {
      type string;
      description
        "Version";
    }
    leaf pkg-name {
      type string;
      description
        "Package name";
    }
  }

  grouping install-include-pkg-key {
    description
      "Package data";
    leaf inc-version {
      type string;
      description
        "Version";
    }
    leaf inc-pkg-name {
      type string;
      description
        "Package name";
    }
  }

  grouping install-package-info {
    description
      "Install top package info";
    leaf ios-dir {
      type string;
      description
        "IOS directory path of package";
    }
    container pkg-data {
      description
        "Package data";
      uses install-ios-xe-oper:install-package-data;
    }
    list install-related-packages {
      key "version pkg-name";
      description
        "Included package information";
      uses install-ios-xe-oper:install-package-data-key;
      uses install-ios-xe-oper:install-packages;
    }
  }

  grouping install-pkg-state-key {
    description
      "Install package state key";
    leaf package-type {
      type install-ios-xe-oper:install-package-type;
      description
        "Package type";
    }
    leaf pkg-dir {
      type string;
      description
        "Package directory";
    }
    leaf pkg-name {
      type string;
      description
        "Package name";
    }
  }

  grouping install-pkg-state-info {
    description
      "Install package state information";
    leaf package-state {
      type install-ios-xe-oper:install-package-state;
      description
        "Package state";
    }
  }

  grouping install-version-key {
    description
      "Install version key";
    leaf version {
      type string;
      description
        "Software image version";
    }
    leaf version-extension {
      type string;
      description
        "Extended version octet to differentiate base images with same release version";
    }
  }

  grouping install-version-file {
    description
      "Install version file information";
    leaf is-default {
      type boolean;
      description
        "Is this default version";
    }
    leaf previous {
      type install-ios-xe-oper:install-version-state;
      description
        "Is this previous version";
    }
    leaf current {
      type install-ios-xe-oper:install-version-state;
      description
        "Is this current version";
    }
    leaf src-filename {
      type string;
      description
        "Source file name";
    }
    leaf src-checksum {
      type string;
      description
        "Source file checksum";
    }
    list install-package-state-info {
      key "package-type pkg-dir pkg-name";
      description
        "Install package state information";
      uses install-ios-xe-oper:install-pkg-state-key;
      uses install-ios-xe-oper:install-pkg-state-info;
    }
  }

  grouping install-version-state-key {
    description
      "Install version state key";
    leaf version-state {
      type install-ios-xe-oper:install-version-state;
      description
        "Version state";
    }
  }

  container install-oper-data {
    config false;
    description
      "Install manager operational data";
    list install-location-information {
      key "fru slot bay chassis";
      description
        "Table of locations which contain install specific details";
      uses common-types-ios-xe:internal-location;
      uses install-ios-xe-oper:install-location-info;
    }
  }
}
