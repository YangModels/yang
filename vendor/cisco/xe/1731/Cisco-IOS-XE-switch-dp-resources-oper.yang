module Cisco-IOS-XE-switch-dp-resources-oper {
  yang-version 1;
  namespace "http://cisco.com/ns/yang/Cisco-IOS-XE-switch-dp-resources-oper";
  prefix dp-resources-oper;

  import Cisco-IOS-XE-common-types {
    prefix common-types-ios-xe;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring the usage of switching data path resources.
     Copyright (c) 2020 by Cisco Systems, Inc.
     All rights reserved.";

  revision 2020-07-01 {
    description
      "Initial revision";
    reference "1.0.0";
    cisco-semver:module-version "1.0.0";
    cisco-semver-internal:os-version "17.3.1";
  }

  typedef dp-proto {
    type enumeration {
      enum "dp-proto-ipv4" {
        value 0;
        description
          "IPV4 protocol";
        tailf:code-name "ENUM_dp_proto_DP_PROTO_IPV4";
      }
      enum "dp-proto-ipv6" {
        value 1;
        description
          "IPV6 protocol";
        tailf:code-name "ENUM_dp_proto_DP_PROTO_IPV6";
      }
      enum "dp-proto-mpls" {
        value 2;
        description
          "MPLS protocol";
        tailf:code-name "ENUM_dp_proto_DP_PROTO_MPLS";
      }
      enum "dp-proto-other" {
        value 3;
        description
          "Protocol other than IPV4/IPV6/MPLS";
        tailf:code-name "ENUM_dp_proto_DP_PROTO_OTHER";
      }
    }
    description
      "Data path protocol";
  }

  typedef dp-feature {
    type enumeration {
      enum "dp-feature-mac-address-table" {
        value 0;
        description
          "Unicast MAC address";
        tailf:code-name "ENUM_dp_feature_DP_FEATURE_MAC_ADDRESS_TABLE";
      }
      enum "dp-feature-l3-multicast" {
        value 1;
        description
          "L3 Multicast";
        tailf:code-name "ENUM_dp_feature_DP_FEATURE_L3_MULTICAST";
      }
      enum "dp-feature-l2-multicast" {
        value 2;
        description
          "L2 Multicast";
        tailf:code-name "ENUM_dp_feature_DP_FEATURE_L2_MULTICAST";
      }
      enum "dp-feature-ip-route-table" {
        value 3;
        description
          "L3/MPLS routes";
        tailf:code-name "ENUM_dp_feature_DP_FEATURE_IP_ROUTE_TABLE";
      }
      enum "dp-feature-qos-acl" {
        value 4;
        description
          "QOS ACL";
        tailf:code-name "ENUM_dp_feature_DP_FEATURE_QOS_ACL";
      }
      enum "dp-feature-security-acl" {
        value 5;
        description
          "Security ACL";
        tailf:code-name "ENUM_dp_feature_DP_FEATURE_SECURITY_ACL";
      }
      enum "dp-feature-netflow-acl" {
        value 6;
        description
          "Netflow ACL";
        tailf:code-name "ENUM_dp_feature_DP_FEATURE_NETFLOW_ACL";
      }
      enum "dp-feature-pbr-acl" {
        value 7;
        description
          "Policy based routing ACL";
        tailf:code-name "ENUM_dp_feature_DP_FEATURE_PBR_ACL";
      }
      enum "dp-feature-flow-span-acl" {
        value 8;
        description
          "Flow span ACL";
        tailf:code-name "ENUM_dp_feature_DP_FEATURE_FLOW_SPAN_ACL";
      }
      enum "dp-feature-control-plane" {
        value 9;
        description
          "Control plane";
        tailf:code-name "ENUM_dp_feature_DP_FEATURE_CONTROL_PLANE";
      }
      enum "dp-feature-tunnel-termination" {
        value 10;
        description
          "Tunnel termination";
        tailf:code-name "ENUM_dp_feature_DP_FEATURE_TUNNEL_TERMINATION";
      }
      enum "dp-feature-lisp-inst-mapping" {
        value 11;
        description
          "Lisp instance mapping";
        tailf:code-name "ENUM_dp_feature_DP_FEATURE_LISP_INST_MAPPING";
      }
      enum "dp-feature-security-association" {
        value 12;
        description
          "Security association";
        tailf:code-name "ENUM_dp_feature_DP_FEATURE_SECURITY_ASSOCIATION";
      }
      enum "dp-feature-cts-cell-matrix" {
        value 13;
        description
          "CTS cell matrix";
        tailf:code-name "ENUM_dp_feature_DP_FEATURE_CTS_CELL_MATRIX";
      }
      enum "dp-feature-vpn-label" {
        value 14;
        description
          "VPN label";
        tailf:code-name "ENUM_dp_feature_DP_FEATURE_VPN_LABEL";
      }
      enum "dp-feature-client-table" {
        value 15;
        description
          "Client table";
        tailf:code-name "ENUM_dp_feature_DP_FEATURE_CLIENT_TABLE";
      }
      enum "dp-feature-group-table" {
        value 16;
        description
          "Group table";
        tailf:code-name "ENUM_dp_feature_DP_FEATURE_GROUP_TABLE";
      }
      enum "dp-feature-macsec-spd" {
        value 17;
        description
          "MACSec";
        tailf:code-name "ENUM_dp_feature_DP_FEATURE_MACSEC_SPD";
      }
    }
    description
      "Data path features";
  }

  typedef dp-table {
    type enumeration {
      enum "dp-table-exact-match" {
        value 0;
        description
          "Exact Match table";
        tailf:code-name "ENUM_dp_table_DP_TABLE_EXACT_MATCH";
      }
      enum "dp-table-tcam" {
        value 1;
        description
          "TCAM table";
        tailf:code-name "ENUM_dp_table_DP_TABLE_TCAM";
      }
      enum "dp-table-acl-ids" {
        value 2;
        description
          "ACL Identifiers";
        tailf:code-name "ENUM_dp_table_DP_TABLE_ACL_IDS";
      }
      enum "dp-table-lpm" {
        value 3;
        description
          "Longest Prefix Match table";
        tailf:code-name "ENUM_dp_table_DP_TABLE_LPM";
      }
    }
    description
      "Data path table type";
  }

  typedef dp-direction {
    type enumeration {
      enum "dp-direction-ingress" {
        value 0;
        description
          "Ingress direction";
        tailf:code-name "ENUM_dp_direction_DP_DIRECTION_INGRESS";
      }
      enum "dp-direction-egress" {
        value 1;
        description
          "Egress direction";
        tailf:code-name "ENUM_dp_direction_DP_DIRECTION_EGRESS";
      }
    }
    description
      "Data path direction";
  }

  grouping dp-oper-feature-key {
    description
      "Data path oper feature key";
    leaf feature {
      type dp-resources-oper:dp-feature;
      description
        "Feature";
    }
    leaf protocol {
      type dp-resources-oper:dp-proto;
      description
        "Protocol";
    }
    leaf direction {
      type dp-resources-oper:dp-direction;
      description
        "Direction";
    }
  }

  grouping dp-shared-ftr {
    description
      "Datapath shared feature";
    container ftr-info {
      description
        "Feature information";
      uses dp-resources-oper:dp-oper-feature-key;
    }
  }

  grouping dp-resource-usage {
    description
      "Resource usage for a given feature, protocol and direction.";
    leaf max-entries {
      type uint32;
      description
        "Maximum number of physical entries available. It is a cumulative maximum 
         for all shared features of the physical resource.";
    }
    leaf entries-used {
      type uint32;
      description
        "Number of entries used by the given feature, protocol and direction.";
    }
    leaf total-entries-free {
      type uint32;
      description
        "Total entries free";
    }
    leaf percentage-used {
      type decimal64 {
        fraction-digits 2;
      }
      description
        "Percentage of physical entries used by all shared features.";
    }
  }

  grouping dp-pipes {
    description
      "Data path pipelines";
    leaf pipeline {
      type uint8;
      description
        "Pipeline number represents the physical partition in a given ASIC.
         Pipeline can be a core or a slice based on the asic type.";
    }
  }

  grouping dp-phy-location {
    description
      "Physical location of resource";
    leaf asic {
      type uint8;
      description
        "ASIC number";
    }
    list pipeline-list {
      description
        "List of pipelines in a given asic.";
      uses dp-resources-oper:dp-pipes;
    }
  }

  grouping dp-table-data {
    description
      "Provides resource usage for a given instance of the feature, protocol and direction.";
    leaf table {
      type dp-resources-oper:dp-table;
      description
        "Type of the data path table";
    }
    container resource-usage {
      description
        "Summary of resource usage";
      uses dp-resources-oper:dp-resource-usage;
    }
  }

  grouping dp-feature-resource-instance {
    description
      "Data path feature resource instance";
    leaf id {
      type uint32;
      description
        "Instance identifier";
    }
    container physical-location {
      description
        "Physical location of the resource";
      uses dp-resources-oper:dp-phy-location;
    }
    list table-data {
      description
        "Provides resource usage for a given instance of the feature, protocol and direction.";
      uses dp-resources-oper:dp-table-data;
    }
  }

  grouping dp-feature-resource {
    description
      "Data path feature resource";
    leaf max-tcam-percentage-used {
      type decimal64 {
        fraction-digits 2;
      }
      description
        "Maximum TCAM percentage used for the feature. A feature can have one or more instance, 
         and this value is the maximum percentage used for the TCAM table among all the instances";
    }
    leaf max-em-percentage-used {
      type decimal64 {
        fraction-digits 2;
      }
      description
        "Maximum Exact Match percentage used for the feature. A feature can have one or more instance, 
         and this value is the maximum percentage used for the Exact Match table among all the instances";
    }
    leaf max-acl-ids-percentage-used {
      type decimal64 {
        fraction-digits 2;
      }
      description
        "Maximum ACL Identifiers percentage used for the feature. A feature can have one or more instance, 
         and this value is the maximum percentage used for the ACL Identifiers table among all the instances";
    }
    leaf max-lpm-percentage-used {
      type decimal64 {
        fraction-digits 2;
      }
      description
        "Maximum Longest Prefix Match percentage used for the feature. A feature can have one or more instance, 
         and this value is the maximum percentage used for the Longest Prefix Match table among all the instances";
    }
    list instance-list {
      description
        "Feature can have one of more instances in datapath. Instance list is the list of instances 
         on which the feature resources are available.";
      uses dp-resources-oper:dp-feature-resource-instance;
    }
    list shared-ftr-list {
      description
        "List of features sharing the same physical resource.";
      uses dp-resources-oper:dp-shared-ftr;
    }
  }

  container switch-dp-resources-oper-data {
    config false;
    description
      "Switching datapath resources operational data";
    tailf:callpoint "fed-common-db";
    tailf:meta-data "callpoint" {
      tailf:meta-value "fed-common-db";
    }
    tailf:meta-data "greenprefix" {
      tailf:meta-value "//locations/services;serviceName=fedpi_oper";
    }
    tailf:meta-data "emulated" {
      tailf:meta-value "false";
    }
    tailf:meta-data "name" {
      tailf:meta-value "Cisco-IOS-XE-switch-dp-resources-oper";
    }
    list location {
      key "fru slot bay chassis node";
      description
        "A list of data provider locations";
      uses common-types-ios-xe:extended-location;
      list dp-feature-resource {
        key "feature protocol direction";
        description
          "Data path feature resource provides resource usage for features. 
           User can query based on feature name, protocol and direction";
        uses dp-resources-oper:dp-feature-resource;
        uses dp-resources-oper:dp-oper-feature-key;
      }
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWaT8EqQAA1FfgEAAEAYdED/n/+q/5//qQAMCxHTroDCVPSKYUep6mJo00PU0b1MSekZMj0htQShMgRMCnqQ0AAaZDJ6gNAkSKj2QKaaADQeoABkAAamqN6p+pMm1NNqZBpoMjJo000DIGBYcP5Xm0f8scjfufAPoWTLPyXH7ffsKj4ixcam9YBYKmme5V2lZ7UrQZThVm7+L2WEQRawOczkzgBmQyZNN+zVgBrraozFHOX0wjjaiENKJLSJ0QlgOBmX3O8uQpJfeqeMnSfX858h2ncGVKMaaZ4TizBFHg46G/72b3BIKMCfcByCy53GWtlOcyNPbGcQPzuQwKWab6lpGqxEm3aREDdVWUyQJeNMMGsS8Qd5kq6s1K+GzRTsukmxNpTiC6aQTaUaK1nVRqbayxQWA7xg0KYpZDCEtYB5PoNHMivRSOigl1SDZ9HkXUSKzYrvaZgoc8EGwgTE1DKVoW7bU8WThc2BCqg2rA+rnePAIZQuIDQLUGOB5xgwBh3g9iCyIQIslBCIIoAyxoboMXJA1pUkIFyzxqYVUQHG2Q1LyLXx6CLHadhLl+Mc/zfNtndNCrPIQGZ0G2iPhsQjqGZOsfL5TesU4MpGKeqfFChgaVD9enJdjiapJrICA3aByvbZ11pMhztl4Ucl2CBm3MQvHhsj0yuanI7kcJTEfOmQWEMucSxgtATGGOxfm12GCbE2lhEGQgcmFKX8Krpa/RokhxluJSvtVECamaD6rKgQqjZ73kawIyZnUlO5Mkuhir8SqcM2GO4FXjRuBZ94rlnLKGOGskYIUoscYRvRzBYWmHI3BV0OnF6CZNnif5ZoURamrcAg6iXzYNVeq5pz3fPHnZwwF3TfhskEIINv6aQcUFyCKG6GxnbatiFMU4sO6PIZNE6Za6UGFrE5oC1TTyvF8cioWJBWU3pIQLDYdKHBncFECo1dysjNHvkVTqL045pbTrcgwP8XckU4UJCk/BKkA";
      }
      tailf:meta-data "uncompressed_size" {
        tailf:meta-value "1716";
      }
    }
    container Cisco-IOS-XE-common-types {
      description
        "Hidden internal container used for metadata";
      uses common-types-ios-xe:__yangpp_metadata;
    }
  }

  container schema-metadata-Cisco-IOS-XE-switch-dp-resources-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-switch-dp-resources-oper";
    }
    tailf:meta-data "organization" {
      tailf:meta-value "Cisco Systems, Inc.";
    }
    tailf:meta-data "semver" {
      tailf:meta-value "2020-07-01";
    }
  }
}
