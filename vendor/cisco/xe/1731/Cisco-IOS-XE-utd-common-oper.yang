module Cisco-IOS-XE-utd-common-oper {
  yang-version 1;
  namespace "http://cisco.com/ns/yang/Cisco-IOS-XE-utd-common-oper";
  prefix utd-common-ios-xe-oper;
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     common for all UTD operational data.
     Copyright (c) 2018-2019 by Cisco Systems, Inc.
     All rights reserved.";

  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2018-04-04 {
    description
      "Initial revision";
    reference "1.0.0";
    cisco-semver:module-version "1.0.0";
  }

  typedef utd-update-status-val {
    type enumeration {
      enum "utd-update-status-unknown" {
        value 0;
        description
          "Unified Threat Defense (UTD) update status is unknown";
        tailf:code-name "ENUM_utd_update_status_val_UTD_UPDATE_STATUS_UNKNOWN";
      }
      enum "utd-update-status-success" {
        value 1;
        description
          "Unified Threat Defense (UTD) update successful";
        tailf:code-name "ENUM_utd_update_status_val_UTD_UPDATE_STATUS_SUCCESS";
      }
      enum "utd-update-status-failure" {
        value 2;
        description
          "Unified Threat Defense (UTD) update failed";
        tailf:code-name "ENUM_utd_update_status_val_UTD_UPDATE_STATUS_FAILURE";
      }
      enum "utd-update-status-no-update" {
        value 3;
        description
          "Unified Threat Defense (UTD) update attempted but not required";
        tailf:code-name "ENUM_utd_update_status_val_UTD_UPDATE_STATUS_NO_UPDATE";
      }
    }
    description
      "Unified Threat Defense (UTD) update status";
  }

  grouping __yangpp_metadata {
    description
      "Internal metadata for this module and imported modules";
  }

  container gnmi-model-data {
    description
      "This container makes accessible the information necessary to respond to a GNMI Capabilities RPC";
    tailf:hidden "full";
    tailf:meta-data "module-name" {
      tailf:meta-value "Cisco-IOS-XE-utd-common-oper";
    }
    tailf:meta-data "organization" {
      tailf:meta-value "Cisco Systems, Inc.";
    }
    tailf:meta-data "semver" {
      tailf:meta-value "2019-05-01";
    }
  }
}
