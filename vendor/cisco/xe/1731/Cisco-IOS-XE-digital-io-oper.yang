module Cisco-IOS-XE-digital-io-oper {
  yang-version 1;
  namespace "http://cisco.com/ns/yang/Cisco-IOS-XE-digital-io-oper";
  prefix digital-io-ios-xe-oper;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Digital Input and Output port operational data.
     Copyright (c) 2020 by Cisco Systems, Inc.
     All rights reserved.";

  revision 2020-07-01 {
    description
      "Initial revision";
    reference "1.0.0";
    cisco-semver:module-version "1.0.0";
    cisco-semver-internal:os-version "17.3.1";
  }

  typedef dio-port-severity {
    type enumeration {
      enum "port-severity-none" {
        value 0;
        description
          "Port Severity None";
        tailf:code-name "ENUM_dio_port_severity_PORT_SEV_NONE";
      }
      enum "port-severity-critical" {
        value 1;
        description
          "Port Severity Critical";
        tailf:code-name "ENUM_dio_port_severity_PORT_SEV_CRITICAL";
      }
      enum "port-severity-major" {
        value 2;
        description
          "Port Severity Major";
        tailf:code-name "ENUM_dio_port_severity_PORT_SEV_MAJOR";
      }
      enum "port-severity-minor" {
        value 3;
        description
          "Port Severity Minor";
        tailf:code-name "ENUM_dio_port_severity_PORT_SEV_MINOR";
      }
      enum "port-severity-info" {
        value 4;
        description
          "Port Severity Informational";
        tailf:code-name "ENUM_dio_port_severity_PORT_SEV_INFO";
      }
    }
    description
      "Port Severity";
  }

  typedef dio-port-state {
    type enumeration {
      enum "port-state-closed" {
        value 0;
        description
          "Port State Closed";
        tailf:code-name "ENUM_dio_port_state_PORT_STATE_CLOSED";
      }
      enum "port-state-open" {
        value 1;
        description
          "Port State Open";
        tailf:code-name "ENUM_dio_port_state_PORT_STATE_OPEN";
      }
    }
    description
      "Port State";
  }

  typedef dio-port-status {
    type enumeration {
      enum "port-status-not-triggered" {
        value 0;
        description
          "Port Status Not Triggered";
        tailf:code-name "ENUM_dio_port_status_PORT_STATUS_NOT_TRIGGERED";
      }
      enum "port-status-triggered" {
        value 1;
        description
          "Port Status Triggered";
        tailf:code-name "ENUM_dio_port_status_PORT_STATUS_TRIGGERED";
      }
    }
    description
      "Port Status";
  }

  typedef dio-port-mode {
    type enumeration {
      enum "port-mode-input" {
        value 0;
        description
          "Port Mode Input";
        tailf:code-name "ENUM_dio_port_mode_PORT_MODE_INPUT";
      }
      enum "port-mode-output" {
        value 1;
        description
          "Port Mode Output";
        tailf:code-name "ENUM_dio_port_mode_PORT_MODE_OUTPUT";
      }
      enum "port-mode-output-relay-temp" {
        value 2;
        description
          "Port Mode Output Relay Temperature";
        tailf:code-name "ENUM_dio_port_mode_PORT_MODE_OUTPUT_RELAY_TEMP";
      }
      enum "port-mode-output-relay-input" {
        value 3;
        description
          "Port Mode Output Relay Input";
        tailf:code-name "ENUM_dio_port_mode_PORT_MODE_OUTPUT_RELAY_INPUT";
      }
    }
    description
      "Port Mode";
  }

  typedef dio-port-application {
    type enumeration {
      enum "port-app-dry" {
        value 0;
        description
          "Port Application Dry";
        tailf:code-name "ENUM_dio_port_application_PORT_APP_DRY";
      }
      enum "port-app-wet" {
        value 1;
        description
          "Port Application Wet";
        tailf:code-name "ENUM_dio_port_application_PORT_APP_WET";
      }
    }
    description
      "Port Application";
  }

  typedef dio-port-output-source {
    type enumeration {
      enum "port-out-src-input0" {
        value 0;
        description
          "Port Output Source Input 0";
        tailf:code-name "ENUM_dio_port_output_source_PORT_OUT_SRC_INPUT0";
      }
      enum "port-out-src-input1" {
        value 1;
        description
          "Port Output Source Input 1";
        tailf:code-name "ENUM_dio_port_output_source_PORT_OUT_SRC_INPUT1";
      }
      enum "port-out-src-input2" {
        value 2;
        description
          "Port Output Source Input 2";
        tailf:code-name "ENUM_dio_port_output_source_PORT_OUT_SRC_INPUT2";
      }
      enum "port-out-src-input3" {
        value 3;
        description
          "Port Output Source Input 3";
        tailf:code-name "ENUM_dio_port_output_source_PORT_OUT_SRC_INPUT3";
      }
      enum "port-out-src-input4" {
        value 4;
        description
          "Port Output Source Input 4";
        tailf:code-name "ENUM_dio_port_output_source_PORT_OUT_SRC_INPUT4";
      }
      enum "port-out-src-temp-minor" {
        value 5;
        description
          "Port Output Source Temperature Minor";
        tailf:code-name "ENUM_dio_port_output_source_PORT_OUT_SRC_TEMP_MINOR";
      }
      enum "port-out-src-temp-major" {
        value 6;
        description
          "Port Output Source Temperature Major";
        tailf:code-name "ENUM_dio_port_output_source_PORT_OUT_SRC_TEMP_MAJOR";
      }
      enum "port-out-src-temp-critical" {
        value 7;
        description
          "Port Output Source Temperature Critical";
        tailf:code-name "ENUM_dio_port_output_source_PORT_OUT_SRC_TEMP_CRITICAL";
      }
    }
    description
      "Port Output Source";
  }

  grouping digital-io-port {
    description
      "Digital IO port";
    leaf port-num {
      type uint16;
      description
        "Port number";
    }
    leaf attached-to-iox {
      type boolean;
      description
        "Attached to IOX";
    }
    leaf enabled {
      type boolean;
      description
        "Enabled";
    }
    leaf desc {
      type string;
      description
        "Description";
    }
    leaf severity {
      type digital-io-ios-xe-oper:dio-port-severity;
      description
        "Severity";
    }
    leaf port-value {
      type uint16;
      description
        "Port value";
    }
    leaf trigger {
      type digital-io-ios-xe-oper:dio-port-state;
      description
        "Trigger";
    }
    leaf status {
      type digital-io-ios-xe-oper:dio-port-status;
      description
        "Port status";
    }
    leaf mode {
      type digital-io-ios-xe-oper:dio-port-mode;
      description
        "Port mode";
    }
    leaf app {
      type digital-io-ios-xe-oper:dio-port-application;
      description
        "Application";
    }
    leaf source {
      type digital-io-ios-xe-oper:dio-port-output-source;
      description
        "Output source";
    }
    leaf voltage {
      type uint16;
      units "millivolts";
      description
        "Voltage";
    }
    leaf threshold {
      type uint16;
      units "millivolts";
      description
        "Threshold";
    }
  }

  container digital-io-oper-data {
    config false;
    description
      "Operational state of Digital IO";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list digital-io-port {
      key "port-num";
      description
        "Digital IO port";
      uses digital-io-ios-xe-oper:digital-io-port;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWQoE3NcAAkBfgEAAEAZ8EC+33+q/t9+qQAHl1LJmEohDTSeqeo0aGR6ntKeppkHqaNlHlBIoTIpsp5T9U9QMg0ANNAADAADQABk0AAAaASSMiAhHqAwgAA0A0NM8g5vphVq5Yi4sMMMVa7j6B5xjGMbbxb2Fll6mzH518vrS5ZCIKqowBGd88hELV3e0Sy2T+trXLWhIc1XQH9z3CQEE0glRQsnDobbbbvElsO44CQajxJrUBU0LWD69vDULg6/I2wh+hmVbKGJBaXZDS8XE2BiVkBBGV0WNpeVwXy2wbqkiebjCRSzgSRgRnYTEWsNQMgMS0oZiEkZMOgPUlSQFQcLzEdTJm8JTGQwDBW4vAgmMC5FKudp1a5XFLvRuG3JGuyxuYPKgRSFRQjHTr47IPhci2M4EhqYN7De4KaDjV6gZD94pwRegFnpZGrUqo+BzUcHUGRmg3ShCmYrQmHkEq1jSwY+MtU0qgVsZnW0kxSRPfwkxsD8pbEe7DAMaaGfsW80kcMJJEyTHjgF6SIE9DY0OGchsgGLShmJiokjL+NBOqAh1bviUhkMAwRJGFVeEiwMHICY5NGBiiwBkPJKkJ4Tkyov9IM7qxTT/F3JFOFCQCgTc1w==";
      }
      tailf:meta-data "uncompressed_size" {
        tailf:meta-value "1163";
      }
    }
  }

  container schema-metadata-Cisco-IOS-XE-digital-io-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-digital-io-oper";
    }
    tailf:meta-data "organization" {
      tailf:meta-value "Cisco Systems, Inc.";
    }
    tailf:meta-data "semver" {
      tailf:meta-value "2020-07-01";
    }
  }
}
