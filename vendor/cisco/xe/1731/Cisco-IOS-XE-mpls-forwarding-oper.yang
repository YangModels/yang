module Cisco-IOS-XE-mpls-forwarding-oper {
  yang-version 1;
  namespace "http://cisco.com/ns/yang/Cisco-IOS-XE-mpls-forwarding-oper";
  prefix mpls-forwarding-ios-xe-oper;
  import ietf-inet-types {
    prefix inet;
  }
  import ietf-yang-types {
    prefix yang;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for mpls forwarding operational data.
     Copyright (c) 2018-2019 by Cisco Systems, Inc.
     All rights reserved.";

  revision 2020-03-01 {
    description
      "Added new model for MPLS MFI";
    reference "1.3.0";
    cisco-semver:module-version "1.3.0";
    cisco-semver-internal:os-version "17.2.1";
  }
  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2017-11-01 {
    description
      "Initial revision";
    reference "1.0.0";
    cisco-semver:module-version "1.0.0";
  }

  typedef outgoing-interface-type {
    type enumeration {
      enum "drop" {
        value 0;
        description
          "Outgoing interface is not found";
        tailf:code-name "ENUM_outgoing_interface_type_enum_OUTGOING_INT_DROP";
      }
      enum "punt" {
        value 1;
        description
          "Punt packets to cpu";
        tailf:code-name "ENUM_outgoing_interface_type_enum_OUTGOING_INT_PUNT";
      }
      enum "aggregate" {
        value 2;
        description
          "Aggregate interface (e.g., used for VPN label allocation)";
        tailf:code-name "ENUM_outgoing_interface_type_enum_OUTGOING_INT_AGGREGATE";
      }
      enum "exception" {
        value 3;
        description
          "Exception";
        tailf:code-name "ENUM_outgoing_interface_type_enum_OUTGOING_INT_EXCEPTION";
      }
      enum "none" {
        value 4;
        description
          "No outgoing interface";
        tailf:code-name "ENUM_outgoing_interface_type_enum_OUTGOING_INT_NONE";
      }
    }
    description
      "Describes supported outgoing interface types";
  }

  typedef outgoing-interface-description-type {
    type enumeration {
      enum "interface-type" {
        value 0;
        description
          "Forwarding path's outgoing interface type";
        tailf:code-name "ENUM_outgoing_interface_disc_OUTGOING_INTERFACE_TYPE";
      }
      enum "interface-value" {
        value 1;
        description
          "Forwarding path's outgoing interface value";
        tailf:code-name "ENUM_outgoing_interface_disc_OUTGOING_INTERFACE_VALUE";
      }
    }
    description
      "Describes outgoing interface information types";
  }

  typedef outgoing-label-type {
    type enumeration {
      enum "no-label" {
        value 0;
        description
          "A label is not present";
        tailf:code-name "ENUM_outgoing_label_disc_NO_LABEL";
      }
      enum "pop-label" {
        value 1;
        description
          "Label is popped";
        tailf:code-name "ENUM_outgoing_label_disc_POP_LABEL";
      }
      enum "ipv4-explicit-null" {
        value 2;
        description
          "IPv4 explicit NULL label is present";
        tailf:code-name "ENUM_outgoing_label_disc_IPV4_EXPLICIT_NULL";
      }
      enum "ipv6-explicit-null" {
        value 3;
        description
          "IPv6 explicit NULL label is present";
        tailf:code-name "ENUM_outgoing_label_disc_IPV6_EXPLICIT_NULL";
      }
      enum "regular-label" {
        value 4;
        description
          "A regular MPLS label is present";
        tailf:code-name "ENUM_outgoing_label_disc_REGULAR_LABEL";
      }
      enum "invalid-label" {
        value 5;
        description
          "An invalid label is present";
        tailf:code-name "ENUM_outgoing_label_disc_INVALID_LABEL";
      }
    }
    description
      "Describes supported outgoing label types";
  }

  typedef connection-info-type {
    type enumeration {
      enum "information-string" {
        value 0;
        description
          "Connection information string";
        tailf:code-name "ENUM_connection_info_disc_CONNECTION_INFO_STRING";
      }
      enum "ip-prefix" {
        value 1;
        description
          "IP prefix for the connection";
        tailf:code-name "ENUM_connection_info_disc_CONNECTION_INFO_IP_PREFIX";
      }
    }
    description
      "Describes connection information types";
  }

  typedef forwarding-next-hop-type {
    type enumeration {
      enum "point2point" {
        value 0;
        description
          "Next hop is via a P2P link";
        tailf:code-name "ENUM_forwarding_next_hop_disc_FORWARDING_NEXT_HOP_P2P";
      }
      enum "next-hop-ip-address" {
        value 1;
        description
          "Next hop IP address";
        tailf:code-name "ENUM_forwarding_next_hop_disc_FORWARDING_NEXT_HOP_IP_ADDR";
      }
      enum "next-hop-mac-address" {
        value 2;
        description
          "Next hop MAC address";
        tailf:code-name "ENUM_forwarding_next_hop_disc_FORWARDING_NEXT_HOP_MAC_ADDR";
      }
    }
    description
      "Describes supported next hop types";
  }

  grouping outgoing-interface-info {
    description
      "Outgoing interface information";
    leaf discrim {
      type mpls-forwarding-ios-xe-oper:outgoing-interface-description-type;
      config false;
      description
        "DO NOT USE!  -- hidden internal";
      tailf:hidden "full";
      tailf:meta-data "hidden" {
        tailf:meta-value "true";
      }
    }
    choice discrim-choice {
      description
        "Type of interface information";
      case interface-type {
        leaf interface-type {
          type mpls-forwarding-ios-xe-oper:outgoing-interface-type;
          description
            "Outgoing interface type";
        }
      }
      case interface-value {
        leaf interface-value {
          type string;
          description
            "Outgoing interface value";
        }
      }
    }
  }

  grouping outgoing-label-info {
    description
      "Outgoing label information";
    leaf discrim {
      type mpls-forwarding-ios-xe-oper:outgoing-label-type;
      config false;
      description
        "DO NOT USE!  -- hidden internal";
      tailf:hidden "full";
      tailf:meta-data "hidden" {
        tailf:meta-value "true";
      }
    }
    choice discrim-choice {
      description
        "Type of label";
      case no-label {
        leaf no-label {
          type boolean;
          description
            "True if a label is not present";
        }
      }
      case pop-label {
        leaf pop-label {
          type uint32;
          description
            "Pop label value";
        }
      }
      case ipv4-explicit-null {
        leaf ipv4-explicit-null {
          type uint32;
          description
            "IPv4 explicit null label value";
        }
      }
      case ipv6-explicit-null {
        leaf ipv6-explicit-null {
          type uint32;
          description
            "IPv6 explicit null label value";
        }
      }
      case regular-label {
        leaf regular-label {
          type uint32;
          description
            "Regular label value";
        }
      }
      case invalid-label {
        leaf invalid-label {
          type boolean;
          description
            "True if a label with a value that is outside IETF acceptable label range is present";
        }
      }
    }
  }

  grouping connection-info {
    description
      "Connection information";
    leaf discrim {
      type mpls-forwarding-ios-xe-oper:connection-info-type;
      config false;
      description
        "DO NOT USE!  -- hidden internal";
      tailf:hidden "full";
      tailf:meta-data "hidden" {
        tailf:meta-value "true";
      }
    }
    choice discrim-choice {
      description
        "Type of connection information";
      case information-string {
        leaf info-str {
          type string;
          description
            "Connection information string";
        }
      }
      case ip-prefix {
        leaf ip-prefix {
          type inet:ip-prefix;
          description
            "IP prefix for the connection";
        }
      }
    }
  }

  grouping forwarding-next-hop {
    description
      "Forwarding next hop information";
    leaf discrim {
      type mpls-forwarding-ios-xe-oper:forwarding-next-hop-type;
      config false;
      description
        "DO NOT USE!  -- hidden internal";
      tailf:hidden "full";
      tailf:meta-data "hidden" {
        tailf:meta-value "true";
      }
    }
    choice discrim-choice {
      description
        "Next hop type";
      case point2point {
        leaf p2p {
          type boolean;
          description
            "True if next hop is via a p2p link";
        }
      }
      case next-hop-ip-address {
        leaf ip-address {
          type inet:ip-address;
          description
            "Next hop ip address";
        }
      }
      case next-hop-mac-address {
        leaf mac-address {
          type yang:mac-address;
          description
            "Next hop mac address";
        }
      }
    }
  }

  grouping local-label-forwarding-info {
    description
      "Information of a given forwarding path";
    container outgoing-interface {
      description
        "Outgoing interface information";
      uses mpls-forwarding-ios-xe-oper:outgoing-interface-info;
    }
    container outgoing-label {
      description
        "Outgoing label information";
      uses mpls-forwarding-ios-xe-oper:outgoing-label-info;
    }
    container next-hop {
      description
        "Next hop information";
      uses mpls-forwarding-ios-xe-oper:forwarding-next-hop;
    }
  }

  grouping local-label-entry {
    description
      "Local label entry";
    container connection-information {
      description
        "Connection information for the local label";
      uses mpls-forwarding-ios-xe-oper:connection-info;
    }
    list forwarding-paths {
      description
        "ECMP paths for the local label";
      uses mpls-forwarding-ios-xe-oper:local-label-forwarding-info;
    }
  }

  grouping local-label-key {
    description
      "Key for the local label";
    leaf local-label {
      type uint32;
      description
        "Value of local label";
    }
  }

  grouping local-label-forwarding-path-statistics {
    description
      "Statistics for the forwarding path";
    leaf label-switched-bytes {
      type uint64;
      description
        "Number of bytes switched to a particular ECMP path";
    }
    leaf label-switched-packets {
      type uint64;
      description
        "Number of packets switched to a particular ECMP path";
    }
  }

  grouping local-label-forwarding-path-key {
    description
      "Key for the forwarding path";
    leaf local-label {
      type uint32;
      description
        "Value of local label";
    }
    leaf forwarding-path-index {
      type uint8;
      description
        "Path index among ECMP paths for the same local label";
    }
  }

  grouping ecmp-local-label-entry {
    description
      "Details of an ECMP path";
    container connection-information {
      description
        "Connection information for a local label";
      uses mpls-forwarding-ios-xe-oper:connection-info;
    }
    container outgoing-interface {
      description
        "Outgoing interface information";
      uses mpls-forwarding-ios-xe-oper:outgoing-interface-info;
    }
    container outgoing-label {
      description
        "Outgoing label information";
      uses mpls-forwarding-ios-xe-oper:outgoing-label-info;
    }
    container next-hop {
      description
        "Next hop information";
      uses mpls-forwarding-ios-xe-oper:forwarding-next-hop;
    }
    container label-stats {
      description
        "Statistics of a label";
      uses mpls-forwarding-ios-xe-oper:local-label-forwarding-path-statistics;
    }
  }

  grouping ecmp-index-key {
    description
      "Key for an ECMP path";
    leaf ecmp-idx {
      type uint64;
      description
        "Number of an ECMP path";
    }
  }

  grouping ecmp-stats-summary {
    description
      "Total data of all the ECMP paths for a label";
    leaf total-label-switched-bytes {
      type uint64;
      units "bytes";
      description
        "Total number of bytes switched of all ECMP paths for a label";
    }
    leaf total-label-switched-packets {
      type uint64;
      units "packets";
      description
        "Total number of packets switched of all ECMP paths for a label";
    }
  }

  grouping ecmp-stats {
    description
      "Statistics of all the ECMP paths for a label";
    container stats-summary {
      description
        "Total number of bytes and packets switched of all ECMP paths for a label";
      uses mpls-forwarding-ios-xe-oper:ecmp-stats-summary;
    }
    list ecmp-index {
      key "ecmp-idx";
      description
        "Reference to the index of a ECMP path";
      uses mpls-forwarding-ios-xe-oper:ecmp-index-key;
      uses mpls-forwarding-ios-xe-oper:ecmp-local-label-entry;
    }
  }

  container mpls-forwarding-oper-data {
    config false;
    description
      "MPLS forwarding operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list mpls-local-label {
      key "local-label";
      description
        "Local label information";
      uses mpls-forwarding-ios-xe-oper:local-label-key;
      uses mpls-forwarding-ios-xe-oper:local-label-entry;
    }
    list mpls-local-label-statistics {
      key "local-label forwarding-path-index";
      description
        "Statistics for forwarding paths of the local labels";
      uses mpls-forwarding-ios-xe-oper:local-label-forwarding-path-key;
      uses mpls-forwarding-ios-xe-oper:local-label-forwarding-path-statistics;
    }
    list ecmp-local-label {
      key "local-label";
      description
        "Native MPLS MFI model";
      uses mpls-forwarding-ios-xe-oper:local-label-key;
      uses mpls-forwarding-ios-xe-oper:ecmp-stats;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWVNZcjgAA4xfgCwAEAYVED/n3+q/59/qQAMF1a2GwouEkRGiaYQ0gGg0MCD1Gmg0EiQmQE00p+lNomgeoAAAAw0NAAABoAAAAARSIU2jGpDQADQA0aNAxOSP3f9HHAPVfXB4xOM5Dj06fDRA79rE55DPGUIaqUOwuKR7fCVl92YbJlg+H9ka26pTsMSmd3meIctDJaXhgDhgoYQ1EOHAQ1AQIZBA0MTEkkhkN2DriAiOoOeEY6COmUgmly+y33vnhiHX0QbAdEq+Yf5yi4vaUVY340qqw0EqMz8xyE7DZ8xG+ilwwonWGg05wsNSV+HqHjBgYi8g4DLzR7qqfbm+d9STFC9wwkUqZECecrrRWyvxLhOoG1KMGLUuVJrjtfhZzIbzgyYyGYa8ThA5ZGhCNklIjG6aUhzNUouyINfsYtWIiBUk8mp+So4XkoXNSEhNesiK7qKC+ehEmSpayDGVLFlNkplYhrBr7XKKkmHleiVudKLpXeqRuSI02tMtmx0YyxLXOW52e5pkSTpo2GbTztbrXjXHUtY1LvMwBt/DoMTVbxG5tpKjkgPTHZNWGPgAXAEZVNsj8yzNI5kJE6w3tKBbQIw1YWZmi6t2X9AMQpegsqBha4vAmaQpE8CAI4qYgpnypOeVUq47bkPKivjNAaVCZZ2KwSZ1ArTA7MshguCBtMwWDEM2zKQTMnxcRFxchXUSOVKa5ClRiYT1KXRMompCQx4MWIVEqkvLV3YpRTbQMRZfUNUGGQDGIV4BogtOyBpxBpxlO37hBt0LIV5eq8ovIIQ8GJoDh4Z8wob76SndJATDoN+CJ1nLmhZILwz3ZJ81mkbJTJEa4A5JxrBylMJK1hY6ULa1glXdAXYAyCnFrhBNiRA+Y0gNslJDJgYX8XckU4UJBTWXI4A=";
      }
      tailf:meta-data "uncompressed_size" {
        tailf:meta-value "1920";
      }
    }
  }

  container schema-metadata-Cisco-IOS-XE-mpls-forwarding-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-mpls-forwarding-oper";
    }
    tailf:meta-data "organization" {
      tailf:meta-value "Cisco Systems, Inc.";
    }
    tailf:meta-data "semver" {
      tailf:meta-value "2020-03-01";
    }
  }
}
