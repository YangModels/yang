module Cisco-IOS-XE-mdt-cfg {
  yang-version 1;
  namespace "http://cisco.com/ns/yang/Cisco-IOS-XE-mdt-cfg";
  prefix mdt-cfg;

  import Cisco-IOS-XE-mdt-common-defs {
    prefix mdt-common-defs;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG 
     definitions for configuration of streaming telemetry.
     Copyright (c) 2016-2019 by Cisco Systems, Inc.
     All rights reserved.";

  revision 2020-03-01 {
    description
      "Support for Histogram transform operation";
    reference "3.3.0";
    cisco-semver:module-version "3.3.0";
    cisco-semver-internal:os-version "17.2.1";
  }
  revision 2019-05-01 {
    description
      "- Support for new transform operations
       - Flattening the structure of new transform operations
       - Support for Division transform operation
       - Added semantic version";
    reference "3.2.0";
    cisco-semver:module-version "3.2.0";
  }
  revision 2018-10-29 {
    description
      "Cleaned up spelling errors in descriptions.";
    reference "3.1.0";
    cisco-semver:module-version "3.1.0";
  }
  revision 2018-08-24 {
    description
      "Make a receiver's protocol mandatory and
       remove its default.";
    reference "3.0.0";
    cisco-semver:module-version "3.0.0";
  }
  revision 2018-02-12 {
    description
      "Transform support for Native stream.";
    reference "2.1.0";
    cisco-semver:module-version "2.1.0";
  }
  revision 2018-02-07 {
    description
      "Fix top level name.";
    reference "2.0.0";
    cisco-semver:module-version "2.0.0";
  }
  revision 2017-09-20 {
    description
      "TLS support for Native stream";
    reference "1.1.0";
    cisco-semver:module-version "1.1.0";
  }
  revision 2017-03-02 {
    description
      "Initial revision";
    reference "1.0.0";
    cisco-semver:module-version "1.0.0";
  }

  typedef mdt-xfrm-attr-type {
    type enumeration {
      enum "mdt-xfrm-attr-none" {
        value 0;
        description
          "Indicates that no filter has been 
           specified.";
        tailf:code-name "ENUM_mdt_xfrm_attr_type_MDT_XFRM_ATTR_NONE";
      }
      enum "mandatory" {
        value 1;
        description
          "Indicates that mandatory filter is set.";
        tailf:code-name "ENUM_mdt_xfrm_attr_type_MDT_XFRM_ATTR_MANDATORY";
      }
      enum "primary" {
        value 2;
        description
          "Indicates that primary filter is set.";
        tailf:code-name "ENUM_mdt_xfrm_attr_type_MDT_XFRM_ATTR_PRIMARY";
      }
    }
    description
      "Types of subscription transform attribute type";
  }

  typedef mdt-xfrm-op-type {
    type enumeration {
      enum "sub-record" {
        value 0;
        description
          "Indicates that operation type is 
           sub-record";
        tailf:code-name "ENUM_mdt_xfrm_op_type_MDT_XFRM_SUBREC";
      }
      enum "delta" {
        value 1;
        description
          "Indicates that operation type is delta";
        tailf:code-name "ENUM_mdt_xfrm_op_type_MDT_XFRM_DELTA";
      }
    }
    description
      "Types of subscription transform operations.";
  }

  typedef mdt-xfrm-logic-op {
    type enumeration {
      enum "mdt-xfrm-lop-none" {
        value 0;
        description
          "Indicates that no logical operation 
           is selected";
        tailf:code-name "ENUM_mdt_xfrm_logic_op_MDT_XFRM_LOP_NONE";
      }
      enum "and" {
        value 1;
        description
          "Indicates that logical operation 
           is 'and' ";
        tailf:code-name "ENUM_mdt_xfrm_logic_op_MDT_XFRM_LOP_AND";
      }
      enum "or" {
        value 2;
        description
          "Indicates that logical operation is 'or' ";
        tailf:code-name "ENUM_mdt_xfrm_logic_op_MDT_XFRM_LOP_OR";
      }
    }
    description
      "Types of subscription transform 
       logical operations.";
  }

  typedef mdt-xfrm-operator {
    type enumeration {
      enum "operator-none" {
        value 0;
        description
          "Default operator";
        tailf:code-name "ENUM_mdt_xfrm_operator_MDT_XFRM_OP_NONE";
      }
      enum "eq" {
        value 1;
        description
          "Equal operator";
        tailf:code-name "ENUM_mdt_xfrm_operator_MDT_XFRM_OP_EQUAL";
      }
      enum "ne" {
        value 2;
        description
          "Not equal operator";
        tailf:code-name "ENUM_mdt_xfrm_operator_MDT_XFRM_OP_NOT_EQUAL";
      }
      enum "gt" {
        value 3;
        description
          "Greater than operator";
        tailf:code-name "ENUM_mdt_xfrm_operator_MDT_XFRM_OP_GREATER";
      }
      enum "ge" {
        value 4;
        description
          "Greater than or equal operator";
        tailf:code-name "ENUM_mdt_xfrm_operator_MDT_XFRM_OP_GREATER_OR_EQUAL";
      }
      enum "lt" {
        value 5;
        description
          "Less than operator";
        tailf:code-name "ENUM_mdt_xfrm_operator_MDT_XFRM_OP_LESSER";
      }
      enum "le" {
        value 6;
        description
          "Less than or equal operator";
        tailf:code-name "ENUM_mdt_xfrm_operator_MDT_XFRM_OP_LESSER_OR_EQUAL";
      }
    }
    description
      "Supported operator types";
  }

  typedef mdt-xfrm-condition-check-with {
    type enumeration {
      enum "condition-check-wth-argument-value" {
        value 0;
        description
          "Indicates that conditional check should happen with provided value";
        tailf:code-name "ENUM_mdt_xfrm_condition_check_with_MDT_XFRM_CONDITION_CHECK_WITH_ARGUMENT_VALUE";
      }
      enum "condition-check-wth-previous-value" {
        value 1;
        description
          "Indicates that conditional check should happen with
           previous value of the field";
        tailf:code-name "ENUM_mdt_xfrm_condition_check_with_MDT_XFRM_CONDITION_CHECK_WITH_PREVIOUS_VALUE";
      }
    }
    description
      "Specifies the kind of value 
       this condition check should happen with. 
       This way conditional operation can compare with either the
       user provided value or the previously cached value of
       the same field";
  }

  typedef mdt-xfrm-operation-type {
    type enumeration {
      enum "xfrm-oper-none" {
        value 0;
        description
          "Indicates operation has not been specified.";
        tailf:code-name "ENUM_mdt_xfrm_operation_type_MDT_XFRM_OPER_NONE";
      }
      enum "xfrm-oper-mean" {
        value 1;
        description
          "Mean of the cached values";
        tailf:code-name "ENUM_mdt_xfrm_operation_type_MDT_XFRM_OPER_MEAN";
      }
      enum "xfrm-oper-mean-window" {
        value 2;
        description
          "Mean over a specified window";
        tailf:code-name "ENUM_mdt_xfrm_operation_type_MDT_XFRM_OPER_MEAN_WIN";
      }
      enum "xfrm-oper-rate" {
        value 3;
        description
          "Rate of change in value";
        tailf:code-name "ENUM_mdt_xfrm_operation_type_MDT_XFRM_OPER_RATE";
      }
      enum "xfrm-oper-ewma" {
        value 4;
        description
          "Exponentially Weighted Moving Average";
        tailf:code-name "ENUM_mdt_xfrm_operation_type_MDT_XFRM_OPER_EWMA";
      }
      enum "xfrm-oper-delta" {
        value 5;
        description
          "Delta with previously known value";
        tailf:code-name "ENUM_mdt_xfrm_operation_type_MDT_XFRM_OPER_DELTA";
      }
      enum "xfrm-oper-div" {
        value 6;
        description
          "Division operation";
        tailf:code-name "ENUM_mdt_xfrm_operation_type_MDT_XFRM_OPER_DIV";
      }
      enum "xfrm-oper-div-of-delta" {
        value 7;
        description
          "Division operation is performed on Delta of field values";
        tailf:code-name "ENUM_mdt_xfrm_operation_type_MDT_XFRM_OPER_DIV_OF_DELTA";
      }
      enum "xfrm-oper-hist" {
        value 8;
        description
          "Histogram operation is performed over field values";
        tailf:code-name "ENUM_mdt_xfrm_operation_type_MDT_XFRM_OPER_HIST";
      }
    }
    description
      "Operation to be performed";
  }

  typedef mdt-xfrm-window-size-type {
    type enumeration {
      enum "time-based" {
        value 0;
        description
          "Time based windowing";
        tailf:code-name "ENUM_mdt_xfrm_window_size_type_MDT_XFRM_WINDOW_SIZE_TIME_BASED";
      }
      enum "count-based" {
        value 1;
        description
          "Count based windowing";
        tailf:code-name "ENUM_mdt_xfrm_window_size_type_MDT_XFRM_WINDOW_SIZE_COUNT_BASED";
      }
    }
    description
      "Type of window size (eg. time, count based)";
  }

  typedef mdt-xfrm-window-segment-type {
    type enumeration {
      enum "sliding-window" {
        value 0;
        description
          "Sliding window";
        tailf:code-name "ENUM_mdt_xfrm_window_segment_type_MDT_XFRM_WINDOW_SEGMENT_TYPE_SLIDING";
      }
      enum "tumbling-window" {
        value 1;
        description
          "Tumbling window";
        tailf:code-name "ENUM_mdt_xfrm_window_segment_type_MDT_XFRM_WINDOW_SEGMENT_TYPE_TUMBLING";
      }
    }
    description
      "Type of window segment (eg. sliding, tumbling etc)";
  }

  typedef mdt-operand-ref-type {
    type enumeration {
      enum "operand-ref-const" {
        value 0;
        description
          "Indicates that the operand is a constant";
        tailf:code-name "ENUM_mdt_operand_ref_type_MDT_XFRM_OPERAND_TYPE_CONST";
      }
      enum "operand-ref-field" {
        value 1;
        description
          "Indicates that the operand is the value of the specified field";
        tailf:code-name "ENUM_mdt_operand_ref_type_MDT_XFRM_OPERAND_TYPE_FIELD";
      }
    }
    description
      "Type operand reference
       (eg whether it is constant, other field etc)";
  }

  typedef mdt-div-operand-role {
    type enumeration {
      enum "operand-role-dividend" {
        value 0;
        description
          "Indicates that the operand is a dividend";
        tailf:code-name "ENUM_mdt_div_operand_role_MDT_XFRM_DIV_OPERAND_ROLE_DIVIDEND";
      }
      enum "operand-role-divisor" {
        value 1;
        description
          "Indicates that the operand is a divisor";
        tailf:code-name "ENUM_mdt_div_operand_role_MDT_XFRM_DIV_OPERAND_ROLE_DIVISOR";
      }
    }
    description
      "Role of operand in division operation";
  }

  typedef mdt-xfrm-alert-type {
    type enumeration {
      enum "noop" {
        value 0;
        description
          "No alert based operation";
        tailf:code-name "ENUM_mdt_xfrm_alert_type_MDT_XFRM_ALERT_TYPE_NOOP";
      }
      enum "limit-threshold" {
        value 1;
        description
          "Limit threshold based alerting";
        tailf:code-name "ENUM_mdt_xfrm_alert_type_MDT_XFRM_ALERT_TYPE_LIM_THRESH";
      }
    }
    description
      "Type of alert";
  }

  typedef mdt-xfrm-alert-size-type {
    type enumeration {
      enum "duration" {
        value 0;
        description
          "Time based alerting";
        tailf:code-name "ENUM_mdt_xfrm_alert_size_type_MDT_XFRM_TIME_BASED";
      }
      enum "frequency" {
        value 1;
        description
          "Count based alerting";
        tailf:code-name "ENUM_mdt_xfrm_alert_size_type_MDT_XFRM_COUNT_BASED";
      }
    }
    description
      "Type of alerting (eg. time, count based)";
  }

  grouping mdt-xfrm-op-event-type {
    description
      "Types of subscription 
       transform operation event type.";
    leaf onchange {
      type boolean;
      description
        "Indicates that onchange filter is set.";
    }
  }

  grouping mdt-xfrm-field-condition {
    description
      "Per field filter condition (e.g. f1 gt '5')";
    leaf operator {
      type mdt-cfg:mdt-xfrm-operator;
      description
        "Type of operator";
    }
    leaf value {
      type string;
      description
        "Field value to operate on";
    }
    leaf check-with {
      type mdt-cfg:mdt-xfrm-condition-check-with;
      description
        "Specifies the kind of value 
         this condition check should happen with. 
         This way conditional operation can compare with either the
         user provided value or the previously cached value of
         the same field";
    }
  }

  grouping mdt-xfrm-input-field {
    description
      "Configuration information for transform input uri table fields.";
    leaf field {
      type string;
      description
        "Transform input URI table field name";
    }
  }

  grouping mdt-xfrm-input {
    description
      "Configuration information for transform input.";
    leaf table-name {
      type string;
      description
        "Transform input URI table name";
    }
    leaf uri {
      type string;
      description
        "Transform input URI full-path";
    }
    list mdt-xfrm-input-field {
      key "field";
      description
        "Transform input URI table fields";
      uses mdt-cfg:mdt-xfrm-input-field;
    }
    leaf join-key {
      type string;
      description
        "Transform input table join-key";
    }
    leaf attr-type {
      type mdt-cfg:mdt-xfrm-attr-type;
      description
        "Transform input table attribute type 
         e.g. table is mandatory for join record";
    }
    leaf lop {
      type mdt-cfg:mdt-xfrm-logic-op;
      description
        "Logical operation with next
         input table event";
    }
    leaf key {
      type string;
      description
        "Transform input table key";
    }
  }

  grouping mdt-xfrm-operation-window-data {
    description
      "Data specifying Window parameters";
    leaf window-size-type {
      type mdt-cfg:mdt-xfrm-window-size-type;
      description
        "Type of window size (eg. time, count based)";
    }
    leaf window-size {
      type uint32;
      units "centiseconds";
      description
        "Window duration in case of time-based. Count in case of count-based";
    }
    leaf window-segment-type {
      type mdt-cfg:mdt-xfrm-window-segment-type;
      description
        "Type of window segment (eg. sliding, tumbling etc)";
    }
  }

  grouping mdt-xfrm-operation-ewma-data {
    description
      "Data specifying Exponentially Weighted Moving Average parameters";
    leaf lambda {
      type string;
      description
        "Lambda (weight factor) used in Exponentially Weighted Moving Average calculation";
    }
  }

  grouping mdt-xfrm-op-div-data {
    description
      "Data specifying Division parameters";
    leaf operand-ref-type {
      type mdt-cfg:mdt-operand-ref-type;
      description
        "Specify whether the operand specified is a constant 
         or a filed. If it is field, it's value shall be used
         in division operation";
    }
    leaf operand-role {
      type mdt-cfg:mdt-div-operand-role;
      description
        "Role of operand in division operation";
    }
    leaf operand {
      type string;
      description
        "Operand value to be used in division operation. It can be
         either a constant or name of another field";
    }
  }

  grouping mdt-xfrm-op-hist-data {
    description
      "Data specifying Histogram parameters";
    leaf bin-size {
      type uint64;
      description
        "Specify the bin size";
    }
    leaf min {
      type uint64;
      description
        "Specify the min value";
    }
    leaf max {
      type uint64;
      description
        "Specify the max value";
    }
  }

  grouping mdt-xfrm-alert-data {
    description
      "Data specifying alerting  parameters";
    leaf alert-type {
      type mdt-cfg:mdt-xfrm-alert-type;
      description
        "Type of alert";
    }
    leaf alert-size-type {
      type mdt-cfg:mdt-xfrm-alert-size-type;
      description
        "Window duration in case of time-based. Count in case of count-based";
    }
    leaf alert-size {
      type uint32;
      units "centiseconds";
      description
        "Window duration in case of time-based. Count in case of count-based";
    }
  }

  grouping mdt-xfrm-op-filter {
    description
      "Configuration information for transform 
       operation filters.";
    leaf filter-id {
      type uint32;
      description
        "filters will be evaluated in sequence based 
         on filter ID";
    }
    leaf field {
      type string;
      description
        "Transform operation filter field name";
    }
    container op-event {
      description
        "Transform operation event flag (e.g. onchange)";
      uses mdt-cfg:mdt-xfrm-op-event-type;
    }
    leaf lop {
      type mdt-cfg:mdt-xfrm-logic-op;
      description
        "logical operation with condition";
    }
    container condition {
      description
        "Per field condition (e.g. f1 eq 'name')";
      uses mdt-cfg:mdt-xfrm-field-condition;
    }
    leaf next-lop {
      type mdt-cfg:mdt-xfrm-logic-op;
      description
        "logical operation with next filter condition";
    }
    leaf operation-type {
      type mdt-cfg:mdt-xfrm-operation-type;
      default "xfrm-oper-none";
      config false;
      description
        "DO NOT USE!  -- hidden internal";
      tailf:hidden "full";
      tailf:meta-data "hidden" {
        tailf:meta-value "true";
      }
    }
    choice operation-type-choice {
      default "xfrm-oper-none";
      description
        "Operation to be performed on input value";
      case xfrm-oper-none {
        description
          "Indicates operation has not been specified. Value will be passed as-is";
        leaf operation-no-op {
          type boolean;
          default "false";
          description
            "Indicates operation has not been specified. Value will be passed as-is";
        }
      }
      case xfrm-oper-mean {
        description
          "Mean of the cached values";
        leaf operation-mean {
          type empty;
          description
            "Mean of the cached values";
        }
      }
      case xfrm-oper-mean-window {
        description
          "Mean over a specified window";
        container operation-mean-window {
          description
            "Data specifying Window parameters";
          uses mdt-cfg:mdt-xfrm-operation-window-data;
        }
      }
      case xfrm-oper-rate {
        description
          "Rate of change in value";
        leaf operation-rate {
          type empty;
          description
            "Rate of change in value";
        }
      }
      case xfrm-oper-ewma {
        description
          "Exponentially Weighted Moving Average";
        container operation-ewma {
          description
            "Data specifying Exponentially Weighted Moving Average parameters";
          uses mdt-cfg:mdt-xfrm-operation-ewma-data;
        }
      }
      case xfrm-oper-delta {
        description
          "Delta with previously known value";
        leaf operation-delta {
          type empty;
          description
            "Delta with previously known value";
        }
      }
      case xfrm-oper-div {
        description
          "Division operation";
        container operation-div {
          description
            "Data specifying Division parameters";
          uses mdt-cfg:mdt-xfrm-op-div-data;
        }
      }
      case xfrm-oper-div-of-delta {
        description
          "Division operation is performed on Delta of field values";
        container operation-div-of-delta {
          description
            "Data specifying Division of Delta parameters";
          uses mdt-cfg:mdt-xfrm-op-div-data;
        }
      }
    }
  }

  grouping mdt-xfrm-op-field {
    description
      "Configuration information for transform operations";
    leaf field-id {
      type uint32;
      description
        "Transform operation response field-id, part of response record.
         It is used to uniquely identify response record field";
    }
    leaf field {
      type string;
      description
        "Subscription transform field name on 
         which transform operation is performed";
    }
    leaf op-type {
      type mdt-cfg:mdt-xfrm-op-type;
      description
        "Subscription transform operation type";
    }
    leaf operation-type {
      type mdt-cfg:mdt-xfrm-operation-type;
      default "xfrm-oper-none";
      config false;
      description
        "DO NOT USE!  -- hidden internal";
      tailf:hidden "full";
      tailf:meta-data "hidden" {
        tailf:meta-value "true";
      }
    }
    leaf name {
      type string;
      description
        "Name of the field to be returned in output";
    }
    choice operation-type-choice {
      default "xfrm-oper-none";
      description
        "Operation to be performed on field before output";
      case xfrm-oper-none {
        description
          "Indicates operation has not been specified. Value will be passed as-is";
        leaf operation-no-op {
          type boolean;
          default "false";
          description
            "Indicates operation has not been specified. Value will be passed as-is";
        }
      }
      case xfrm-oper-mean {
        description
          "Mean of the cached values";
        leaf operation-mean {
          type empty;
          description
            "Mean of the cached values";
        }
      }
      case xfrm-oper-mean-window {
        description
          "Mean over a specified window";
        container operation-mean-window {
          description
            "Data specifying Window parameters";
          uses mdt-cfg:mdt-xfrm-operation-window-data;
        }
      }
      case xfrm-oper-rate {
        description
          "Rate of change in value";
        leaf operation-rate {
          type empty;
          description
            "Rate of change in value";
        }
      }
      case xfrm-oper-ewma {
        description
          "Exponentially Weighted Moving Average";
        container operation-ewma {
          description
            "Data specifying Exponentially Weighted Moving Average parameters";
          uses mdt-cfg:mdt-xfrm-operation-ewma-data;
        }
      }
      case xfrm-oper-delta {
        description
          "Delta with previously known value";
        leaf operation-delta {
          type empty;
          description
            "Delta with previously known value";
        }
      }
      case xfrm-oper-div {
        description
          "Division operation";
        container operation-div {
          description
            "Data specifying Division parameters";
          uses mdt-cfg:mdt-xfrm-op-div-data;
        }
      }
      case xfrm-oper-div-of-delta {
        description
          "Division operation is performed on Delta of field values";
        container operation-div-of-delta {
          description
            "Data specifying Division of Delta parameters";
          uses mdt-cfg:mdt-xfrm-op-div-data;
        }
      }
      case xfrm-oper-hist {
        description
          "Histogram operation is performed field values";
        container operation-hist {
          description
            "Data specifying Histogram parameters";
          uses mdt-cfg:mdt-xfrm-op-hist-data;
        }
      }
    }
  }

  grouping mdt-xfrm-op {
    description
      "Configuration information for transform operation.";
    leaf id {
      type uint32;
      description
        "Unique transform operation id";
    }
    list mdt-xfrm-op-filters {
      key "filter-id";
      description
        "Transform operation filters. 
         These are evaluated before performing
         transform action (e.g. sub record)
         on the response record";
      uses mdt-cfg:mdt-xfrm-op-filter;
    }
    list mdt-xfrm-op-fields {
      key "field-id";
      description
        "Transform operation fields. 
         Default operation is sub record.
         It is performed on each field";
      uses mdt-cfg:mdt-xfrm-op-field;
    }
    container alert-data {
      description
        "Transform alert data.
         It sets the alerting mechanism";
      uses mdt-cfg:mdt-xfrm-alert-data;
    }
  }

  grouping mdt-xfrm {
    description
      "Configuration information for 
       subscription transform.";
    leaf name {
      type string;
      description
        "Unique transform identifier.";
    }
    leaf fully-specify {
      type boolean;
      description
        "When fully-specify is set, 
         fully-specify field identifier is sent 
         in the response record along with field value";
    }
    list mdt-xfrm-input {
      key "table-name";
      description
        "Transform input information";
      uses mdt-cfg:mdt-xfrm-input;
    }
    list mdt-xfrm-op {
      key "id";
      description
        "Transform operations information";
      uses mdt-cfg:mdt-xfrm-op;
    }
  }

  grouping mdt-subscription-cnfg {
    description
      "Subscription configuration information.";
    leaf subscription-id {
      type uint32 {
        range "0 .. 2147483647";
      }
      description
        "Unique subscription identifier.";
    }
    container base {
      description
        "Common subscription information.";
      uses mdt-common-defs:mdt-subscription-base;
    }
    list mdt-receivers {
      key "address port";
      description
        "Configuration of receivers of configured 
         subscriptions.";
      uses mdt-cfg:mdt-receiver-cnfg;
      uses mdt-common-defs:mdt-receiver-id;
    }
  }

  grouping mdt-receiver-cnfg {
    description
      "Configuration information for subscription receiver.";
    leaf protocol {
      type string;
      mandatory true;
      description
        "Receiver transport protocol.";
    }
    leaf profile {
      type string;
      description
        "Name of protocol profile used by receiver.";
    }
  }

  container mdt-config-data {
    description
      "MDT configuration data";
    tailf:callpoint "mdt-config-db";
    tailf:meta-data "callpoint" {
      tailf:meta-value "mdt-config-db";
    }
    tailf:meta-data "greenprefix" {
      tailf:meta-value "/services;serviceName=mdt";
    }
    list mdt-subscription {
      key "subscription-id";
      description
        "List of subscriptions";
      uses mdt-cfg:mdt-subscription-cnfg;
    }
    list mdt-xfrm {
      key "name";
      description
        "List of subscription transforms";
      uses mdt-cfg:mdt-xfrm;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWbIrtUYABMJfgAQAEAYAED/v//q/7//qUAQme5SoK7NUqrhqekJogaGgAA0yD1NBppoBJAkyU8mkyRoNAGg000MRpoEkVNANAAaaA0GQAAAw0NAAABoAAAAASIppkalPNT00FI9AAaI9RiN6g/cO/3iSDMyksSpbKyF0/HD2xCVOa0IPLKkpWKa682cHKdpM52JRAHNn5wh0BdIN8rZktSsBigcq48i1xEIxI8LveeO/ggyM8dAn/gmaVCQzsh2cB2Bh07Ow6GGSBx04lBIfVMhIlQxnDmElu1hssQhrtrJullBx2RBXmEFH8mRbweKB3pcy5g4XG8YVIpPE8+7B4kmOAhKxToDoXx7w9R7TmefmHS0zP5CZPr8rJWwgr6SnGRojphdTu0qu5ySLgQGQkDLplcyEeDx+4VN60PUFGbtAstQqtUbDARDujEnI9si3hYcB2NKFhxIN+FvKM9Vlp1qnVG7m3d8pkNRHgizzJ+wvc42LAXLn+BvZY0KR1aotEYljfnjTp1Egk6kyWQAzIu7YbQgHBxZQQ4DRYpOoqrGpsJzgTjKFxaGx8I22gqitiNAy5b1AVaD/UiCBHATGGc6HHbpxzKqbZaCQZkk1hQMxY2mxQEhgdx3UlaQTETsBe1TiqGUslDmwxkQGahQCzK7ELiJB2DNBmZa2MkO8D3sISiQ6hICNxVIxPFH9Ip3m3KFW7fKoHGM/I0DQZOWafKiSOtybKU7QPvh46JYoQTQwvByO8LVYx7YKGbsRjG9ymmHLhYOwtgUoCJ+eTfJMIFgdCud4nEXQBz0TWXgPZGQjY6FBiF24lEi7tDLJDjHYhihiHhG29htKLyGqi8MXYri0kBwHWqSs+oxPZpAPqZSaIc1NR0LQdx9DjwleR5b63RswzQxOJ4PTXV7yg8HZG2f+SLHaG8Mh6dmbPRZrPOJNp145lJkNaP/VY0544gWhH0RHPbINRnAZ1nPlGsGsdOMUXJFzaUMkcXzrnuE9TDMzFNUlPobGbiGz5BxQUmC7F9h5KaRVMtjK1GSOMX5cyiVLByEHQTlxfnigzRq716RF89lmade5dkYCXkl7rI1KIHA0aGEPVomEa8PPpkXUX2Ri6RGD0POOPLS9jejqioVy4UlzKC4c9i/KiLckjKIDBZ5DXhFR5irxwMDLaDjYHs6GWYlmeFteOSbc4+NxI1o8FKlhdA+Jtmj8fwgPyjxswaH+kxn8XckU4UJCyK7VGA==";
      }
      tailf:meta-data "uncompressed_size" {
        tailf:meta-value "2481";
      }
    }
    container Cisco-IOS-XE-mdt-common-defs {
      description
        "Hidden internal container used for metadata";
      uses mdt-common-defs:__yangpp_metadata;
    }
  }

  container schema-metadata-Cisco-IOS-XE-mdt-cfg {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-mdt-cfg";
    }
    tailf:meta-data "organization" {
      tailf:meta-value "Cisco Systems, Inc.";
    }
    tailf:meta-data "semver" {
      tailf:meta-value "2020-03-01";
    }
  }
}
