module Cisco-IOS-XE-vrrp-oper {
  yang-version 1;
  namespace "http://cisco.com/ns/yang/Cisco-IOS-XE-vrrp-oper";
  prefix vrrp-ios-xe-oper;

  import Cisco-IOS-XE-common-types {
    prefix common-types-ios-xe;
  }
  import ietf-inet-types {
    prefix inet;
  }
  import ietf-yang-types {
    prefix yang;
  }
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG
     definitions for VRRP operational data.
     Copyright (c) 2017-2019 by Cisco Systems, Inc.
     All rights reserved.";

  revision 2019-05-01 {
    description
      "Added semantic version";
    reference "2.1.0";
    cisco-semver:module-version "2.1.0";
  }
  revision 2018-05-10 {
    description
      "New leaf for secondary addresses";
    reference "2.0.0";
    cisco-semver:module-version "2.0.0";
  }
  revision 2017-12-01 {
    description
      "Initial revision";
    reference "1.0.0";
    cisco-semver:module-version "1.0.0";
  }

  typedef proto-version {
    type enumeration {
      enum "vrrp-v3" {
        value 1;
        tailf:code-name "ENUM_proto_version_VRRP_V3";
      }
    }
    description
      "VRRP protocol version";
  }

  typedef master-reason {
    type enumeration {
      enum "reason-not-master" {
        value 0;
        description
          "Router is not in master state";
        tailf:code-name "ENUM_master_reason_REASON_NOT_MASTER";
      }
      enum "reason-priority" {
        value 1;
        description
          "Won the Master election due to higher priority";
        tailf:code-name "ENUM_master_reason_REASON_PRIORITY";
      }
      enum "reason-preempt" {
        value 2;
        description
          "Preempted a lower priority Master router";
        tailf:code-name "ENUM_master_reason_REASON_PREEMPT";
      }
      enum "reason-master-no-response" {
        value 3;
        description
          "Master router stopped responding";
        tailf:code-name "ENUM_master_reason_REASON_MASTER_NO_RESPONSE";
      }
    }
    description
      "Indicates why this router became master of the VRRP group";
  }

  typedef vrrp-proto-state {
    type enumeration {
      enum "proto-state-init" {
        value 1;
        description
          "Indicates that the virtual router group is waiting for a startup event";
        tailf:code-name "ENUM_vrrp_proto_state_PROTO_STATE_INIT";
      }
      enum "proto-state-backup" {
        value 2;
        description
          "Indicates that the virtual router is monitoring the availability of a master";
        tailf:code-name "ENUM_vrrp_proto_state_PROTO_STATE_BACKUP";
      }
      enum "proto-state-master" {
        value 3;
        description
          "Indicates that the virtual router is forwarding packets for IP addresses that are associated with this router";
        tailf:code-name "ENUM_vrrp_proto_state_PROTO_STATE_MASTER";
      }
      enum "proto-state-recover" {
        value 4;
        description
          "Indicates that the virtual router is under recovery";
        tailf:code-name "ENUM_vrrp_proto_state_PROTO_STATE_RECOVER";
      }
    }
    description
      "VRRP group state";
  }

  typedef omp-state-updown {
    type enumeration {
      enum "omp-up" {
        value 0;
        description
          "Indicates OMP track is up";
        tailf:code-name "ENUM_omp_state_updown_OMP_UP";
      }
      enum "omp-down" {
        value 1;
        description
          "Indicates OMP track is down";
        tailf:code-name "ENUM_omp_state_updown_OMP_DOWN";
      }
    }
    description
      "Indicates the state of the Overlay Management Protocol tracking";
  }

  typedef track-state {
    type enumeration {
      enum "vrrp-track-state-resolved" {
        value 0;
        description
          "Track is resolved";
        tailf:code-name "ENUM_track_st_VRRP_TRACK_STATE_RESOLVED";
      }
      enum "vrrp-track-state-unresolved" {
        value 1;
        description
          "Track is unresolved";
        tailf:code-name "ENUM_track_st_VRRP_TRACK_STATE_UNRESOLVED";
      }
    }
    description
      "Indicates whether the track is resolved";
  }

  grouping vrrp-tracking-object {
    description
      "VRRP tracking object state";
    leaf track-name {
      type string;
      description
        "Name of the tracking object";
    }
    leaf track-obj-state {
      type vrrp-ios-xe-oper:track-state;
      description
        "State of the tracking object";
    }
  }

  grouping vrrp-group-state {
    description
      "VRRP group state";
    leaf version {
      type vrrp-ios-xe-oper:proto-version;
      description
        "VRRP version";
    }
    leaf virtual-ip {
      type inet:ip-address;
      description
        "Primary Virtual IP address for the VRRP group";
    }
    leaf if-name {
      type string;
      description
        "Name for the interface on which VRRP group is hosted";
    }
    leaf vrrp-state {
      type vrrp-ios-xe-oper:vrrp-proto-state;
      description
        "VRRP group state";
    }
    leaf virtual-mac {
      type yang:mac-address;
      description
        "Virtual MAC address for the VRRP group";
    }
    leaf master-ip {
      type inet:ip-address;
      description
        "IP address of the Master router for the VRRP group";
    }
    leaf is-owner {
      type boolean;
      description
        "Whether the router owns the VRRP Primary virtual IP address. When Interface IP address and VRRP Primary virtual IP address are the same for this router, its priority is bumped up to 255";
    }
    leaf priority {
      type uint32;
      description
        "Specifies the priority value used for VRRP master election process. Valid values are 0 to 255. 0 is used by a current master router to gracefully retire from the vrrp group. 255 indicates the master router also owns the VRRP virtual IP address";
    }
    leaf advertisement-timer {
      type uint32;
      description
        "Time interval between hello packets sent by the master router in milliseconds";
    }
    leaf master-down-timer {
      type uint32;
      description
        "Time after which a backup router declares the current master to be down in milliseconds";
    }
    leaf skew-time {
      type uint32;
      description
        "Time to skew Master Down Interval in milliseconds";
    }
    leaf preempt {
      type boolean;
      description
        "Controls whether a higher priority virtual router will preempt a lower priority master";
    }
    leaf master-transitions {
      type uint32;
      description
        "Number of master transitions that have happened in the VRRP group";
    }
    leaf new-master-reason {
      type vrrp-ios-xe-oper:master-reason;
      description
        "Indicates why this router became master of the VRRP group";
    }
    leaf last-state-change-time {
      type yang:date-and-time;
      description
        "Time when state of the VRRP group last changed";
    }
    leaf adv-interval-errors {
      type uint32;
      description
        "Total number of VRRP packets that arrived with advertisement interval different to the configured value";
    }
    leaf ip-ttl-errors {
      type uint32;
      description
        "Total number of VRRP packets received by the virtual router with IPv4 TTL (for VRRP over IPv4) or IPv6 Hop Limit (for VRRP over IPv6) not equal to 255";
    }
    leaf rcvd-pri-zero-pak {
      type uint32;
      description
        "Total number of VRRP packets received with priority 0";
    }
    leaf sent-pri-zero-pak {
      type uint32;
      description
        "Total number of VRRP packets sent with priority 0";
    }
    leaf rcvd-invalid-type-pak {
      type uint32;
      description
        "Total number of VRRP packets received with invalid Type field";
    }
    leaf addr-list-errors {
      type uint32;
      description
        "Total number of VRRP packets received with address not matching the address list locally configured on the router";
    }
    leaf pak-len-errors {
      type uint32;
      description
        "Total number of VRRP packets received with length less that VRRP header length";
    }
    leaf discontinuity-time {
      type yang:date-and-time;
      description
        "Indicates the last time when a discontinuity happened in gathering statistics";
    }
    leaf advertisement-sent {
      type uint32;
      description
        "Total number of VRRP packets sent";
    }
    leaf advertisement-rcvd {
      type uint32;
      description
        "Total number of VRRP packets received";
    }
    list track-list {
      description
        "Status of list of tracking objects in the group";
      uses vrrp-ios-xe-oper:vrrp-tracking-object;
    }
    leaf omp-state {
      type vrrp-ios-xe-oper:omp-state-updown;
      description
        "Indicates the state of the Overlay Management protocol tracking";
    }
    leaf-list secondary-vip-addresses {
      type inet:ip-address;
      ordered-by user;
      description
        "Contains the list of secondary address configured on the group";
    }
  }

  grouping vrrp-key {
    description
      "VRRP key";
    leaf if-number {
      type uint32;
      description
        "IfIndex for the interface on which VRRP group is hosted";
    }
    leaf group-id {
      type uint32;
      description
        "VRRP group number";
    }
    leaf addr-type {
      type common-types-ios-xe:addr-type;
      description
        "Address family of VRRP group. IPv4 or IPv6 are the two valid values";
    }
  }

  container vrrp-oper-data {
    config false;
    description
      "VRRP operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list vrrp-oper-state {
      key "if-number group-id addr-type";
      description
        "VRRP operational state";
      uses vrrp-ios-xe-oper:vrrp-key;
      uses vrrp-ios-xe-oper:vrrp-group-state;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWQPV/KgAAZFfgEAAEAYNED4v3+q+L9+qQAGriyZhKaRASeptJo0aME9qgbEJmglNI1R5NNU02poaZBkAAaNDAANGmgDJoDQZAaAkUEankCmgAaADR6gDL65c0sOQ/MmT9ryHTVv4Jbd4/ArneH3sNXTjZfjkbvhgHd0DiZh3dqZtrAbFq1dnal1Z9jnRt6yE8CINiPokRZz7/1MYzJAvDqOYI3B4nqtwpwPJTuGQRLcju5dbIxHS0WRAYpUj5wsGyWK9iaKwNXvktYoyKlfSIXqwStpDMKl9iobag6jeSoQGbFYKzEroKNpauJFJGQIZFRk0NCL1dgiNEJiZ3MFOGJGxlpmzyuhdclnzLcqdGhlpREsYtKSCJ9ltmbqRolCR/+YVSvkHEdsaxvGnCqcdvUq0SYVGMIqNix6CvWc1ysiAK3e4eJaWhuS2fIo9WJE+LhRf0NxlKmFrg60kxBPRfApOwVywOGQN6PJYVMQusGiIszIBPN5PFEa3wCwtosEWNlxiDEyompk6WrOYmJqkQyoUZ70PUHoUQrDyhb89UdlKgRl3F3JFOFCQA9X8qA==";
      }
      tailf:meta-data "uncompressed_size" {
        tailf:meta-value "812";
      }
    }
    container Cisco-IOS-XE-common-types {
      description
        "Hidden internal container used for metadata";
      uses common-types-ios-xe:__yangpp_metadata;
    }
  }

  container schema-metadata-Cisco-IOS-XE-vrrp-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-vrrp-oper";
    }
    tailf:meta-data "organization" {
      tailf:meta-value "Cisco Systems, Inc.";
    }
    tailf:meta-data "semver" {
      tailf:meta-value "2019-05-01";
    }
  }
}
