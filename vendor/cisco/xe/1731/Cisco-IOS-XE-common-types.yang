module Cisco-IOS-XE-common-types {
  yang-version 1;
  namespace "http://cisco.com/ns/yang/Cisco-IOS-XE-common-types";
  prefix common-types-ios-xe;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains type definitions common to all Cisco IOS XE native models
     
     Copyright (c) 2016-2020 by Cisco Systems, Inc.
     All rights reserved.";

  revision 2020-07-01 {
    description
      "Added extended location type and FC FRU type";
    reference "2.2.0";
    cisco-semver:module-version "2.2.0";
  }
  revision 2019-05-01 {
    description
      "Added semantic version";
    reference "2.1.0";
    cisco-semver:module-version "2.1.0";
  }
  revision 2019-01-02 {
    description
      "Remove mcp-bytestr type
       Added the high availability states";
    reference "2.0.0";
    cisco-semver:module-version "2.0.0";
  }
  revision 2018-05-25 {
    description
      "Add internal location types";
    reference "1.2.0";
    cisco-semver:module-version "1.2.0";
  }
  revision 2017-12-01 {
    description
      "- Properly indicate leaf-list ordering
       - Add addr-type to represent IP address types";
    reference "1.1.0";
    cisco-semver:module-version "1.1.0";
  }
  revision 2017-05-05 {
    description
      "Initial revision";
    reference "1.0.0";
    cisco-semver:module-version "1.0.0";
  }

  typedef addr-type {
    type enumeration {
      enum "address-none" {
        value 0;
      }
      enum "ipv4-address" {
        value 1;
      }
      enum "ipv6-address" {
        value 2;
      }
      enum "ipv4-address-mcast" {
        value 3;
      }
      enum "ipv6-address-mcast" {
        value 4;
      }
    }
    description
      "IP address type";
  }

  typedef fru-type {
    type enumeration {
      enum "fru-rp" {
        value 0;
        description
          "A Route Processor FRU";
      }
      enum "fru-fp" {
        value 1;
        description
          "An Embedded Services Processor FRU";
      }
      enum "fru-cc" {
        value 2;
        description
          "A Carrier Card FRU";
      }
      enum "fru-max" {
        value 3;
        description
          "An illegal value for FRU type";
      }
      enum "fru-fc" {
        value 4;
        description
          "A Fabric Card FRU";
      }
    }
    description
      "FRU type";
  }

  typedef high-availability-role {
    type enumeration {
      enum "ha-role-active" {
        value 0;
        description
          "The role is Active";
      }
      enum "ha-role-standby" {
        value 1;
        description
          "The role is Standby";
      }
      enum "ha-role-unknown" {
        value 2;
        description
          "The role is unknown";
      }
    }
    description
      "The High Availability role";
  }

  grouping internal-location {
    description
      "Service location details";
    leaf fru {
      type common-types-ios-xe:fru-type;
      description
        "Field replaceable unit type";
    }
    leaf slot {
      type int16;
      description
        "Slot number";
    }
    leaf bay {
      type int16;
      description
        "Bay number";
    }
    leaf chassis {
      type int16;
      description
        "Chassis number";
    }
  }

  grouping extended-location {
    description
      "Extended service location details";
    leaf fru {
      type common-types-ios-xe:fru-type;
      description
        "Field replaceable unit (FRU) type";
    }
    leaf slot {
      type int16;
      description
        "Slot number";
    }
    leaf bay {
      type int16;
      description
        "Bay number";
    }
    leaf chassis {
      type int16;
      description
        "Chassis number";
    }
    leaf node {
      type uint16;
      description
        "Node number";
    }
  }
}
