module Cisco-IOS-XE-yang-interfaces-cfg {
  yang-version 1;
  namespace "http://cisco.com/ns/yang/Cisco-IOS-XE-yang-interfaces-cfg";
  prefix yang-interfaces-cfg;
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Configuration for YANG model-based interfaces.
     Copyright (c) 2018-2019 by Cisco Systems, Inc.
     All rights reserved.";

  revision 2019-05-21 {
    description
      "- Add semantic version
       - Add SNMP to NETCONF/YANG configuration";
    reference "1.1.0";
    cisco-semver:module-version "1.1.0";
  }
  revision 2018-11-01 {
    description
      "Initial revision";
    reference "1.0.0";
    cisco-semver:module-version "1.0.0";
  }

  grouping dmi-acl-nbi-type {
    description
      "Configure an access-list for the selected service";
    leaf ipv4-acl-name {
      type string {
        length "1..32";
        pattern "[0-9a-zA-Z_]+";
      }
      description
        "Validate access using an IPv4 access-list";
    }
    leaf ipv6-acl-name {
      type string {
        length "1..32";
        pattern "[0-9a-zA-Z_]+";
      }
      description
        "Validate access using an IPv6 access-list";
    }
  }

  grouping dmi-acl {
    description
      "Service ACLs for YANG Interfaces";
    container netconf-yang-ssh {
      description
        "NETCONF-YANG SSH service";
      uses yang-interfaces-cfg:dmi-acl-nbi-type;
    }
    container restconf {
      description
        "RESTCONF service";
      uses yang-interfaces-cfg:dmi-acl-nbi-type;
    }
  }

  grouping dmi-snmp-trap {
    description
      "SNMP trap to NETCONF translation";
    leaf trap-oid {
      type string {
        pattern "(([0-1](\\.[1-3]?[0-9]))|(2\\.(0|([1-9]\\d*))))(\\.(0|([1-9]\\d*)))*";
        pattern "\\d*(\\.\\d*){1,127}";
      }
      description
        "The OID for this trap";
    }
    leaf description {
      type string;
      default "";
      description
        "A description for this trap";
    }
    leaf forward {
      type boolean;
      default "true";
      description
        "Enables or disables forwarding for this trap";
    }
  }

  grouping dmi-general {
    description
      "Configuration applicable to all YANG model-based interfaces";
    leaf snmp-global-forwarding {
      type boolean;
      default "true";
      description
        "Enables or disables forwarding for all SNMP traps";
    }
    list snmp-trap {
      key "trap-oid";
      description
        "List of SNMP traps considered for automatic translation to NETCONF
         notifications";
      uses yang-interfaces-cfg:dmi-snmp-trap;
    }
    leaf snmp-community {
      type string;
      default "private";
      description
        "The community string for communication with the SNMP agent";
    }
  }

  container yang-interfaces-cfg-data {
    description
      "Configuration for YANG model-based interfaces";
    tailf:callpoint "dmi-config-db";
    tailf:meta-data "callpoint" {
      tailf:meta-value "dmi-config-db";
    }
    tailf:meta-data "greenprefix" {
      tailf:meta-value "/services;serviceName=dmi";
    }
    container acl {
      description
        "Optionally configure an access-list to validate access
         to the device";
      uses yang-interfaces-cfg:dmi-acl;
    }
    container general {
      description
        "Configuration applicable to all YANG model-based interfaces";
      uses yang-interfaces-cfg:dmi-general;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWXDYeIQAAK3fgBAAEAYQEAogiEq/p96qMADZbQ0o9QAyfqj1AADQSKSb1T0RpkwhoaNMgkSkeowBDajTQ0003wmaajGGiJmknLVwcDcvaGnbDUChNQnD+8W9otC9O4mWKznqbUKZeVCVDSWayPWa8qgKyAoCSbHnPwAsnQgBAevEwTcC9kVSi1CRrlurQ8BAMK53Q22m6qEyWhHQ8wp6q0h6jLitFJXupkgfRhJUrwYGOPySqVQwtyHAVqlKmwJRUX0O/92EbJvZy+btTE5Jv+LuSKcKEg4bDxCA";
      }
      tailf:meta-data "uncompressed_size" {
        tailf:meta-value "384";
      }
    }
  }

  container schema-metadata-Cisco-IOS-XE-yang-interfaces-cfg {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-yang-interfaces-cfg";
    }
    tailf:meta-data "organization" {
      tailf:meta-value "Cisco Systems, Inc.";
    }
    tailf:meta-data "semver" {
      tailf:meta-value "2019-05-21";
    }
  }
}
