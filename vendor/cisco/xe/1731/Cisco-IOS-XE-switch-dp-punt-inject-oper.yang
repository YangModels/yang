module Cisco-IOS-XE-switch-dp-punt-inject-oper {
  yang-version 1;
  namespace "http://cisco.com/ns/yang/Cisco-IOS-XE-switch-dp-punt-inject-oper";
  prefix switch-dp-punt-inject-oper;

  import Cisco-IOS-XE-common-types {
    prefix common-types-ios-xe;
  }
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for switching device datapath punt and inject operational data.
     Copyright (c) 2019-2020 by Cisco Systems, Inc.
     All rights reserved.";

  revision 2020-07-01 {
    description
      "Initial revision";
    reference "1.0.0";
    cisco-semver:module-version "1.0.0";
    cisco-semver-internal:os-version "17.3.1";
  }

  grouping brief-punt-cpuq-statistics {
    description
      "Brief punt CPU queue statistics";
    leaf cpuq-id {
      type uint8;
      description
        "CPU queue identification";
    }
    leaf rx-recv-prev {
      type uint64;
      description
        "Previous count of packets received from ASIC";
    }
    leaf rx-recv-cur {
      type uint64;
      description
        "Current count of packets received from ASIC";
    }
    leaf rx-recv-delta {
      type uint64;
      description
        "Delta of counts of packets received from ASIC";
    }
    leaf rx-dropped-prev {
      type uint64;
      description
        "Previous count of dropped RX packets";
    }
    leaf rx-dropped-cur {
      type uint64;
      description
        "Current count of dropped RX packets";
    }
    leaf rx-dropped-delta {
      type uint64;
      description
        "Delta of counts of dropped RX packets";
    }
    leaf cpu-punt-queue-name {
      type string;
      description
        "Name of CPU punt queue";
    }
  }

  container switch-dp-punt-inject-oper-data {
    config false;
    description
      "Switching device datapath punt and inject operational data";
    tailf:callpoint "fed-emul-oper-db";
    tailf:meta-data "callpoint" {
      tailf:meta-value "fed-emul-oper-db";
    }
    tailf:meta-data "greenprefix" {
      tailf:meta-value "//locations/services;serviceName=fed_emul_oper";
    }
    tailf:meta-data "emulated" {
      tailf:meta-value "true";
    }
    tailf:meta-data "name" {
      tailf:meta-value "Cisco-IOS-XE-switch-dp-punt-inject-oper";
    }
    list location {
      key "fru slot bay chassis node";
      description
        "A list of data provider locations";
      uses common-types-ios-xe:extended-location;
      list punt-inject-cpuq-brief-stats {
        key "cpuq-id";
        description
          "This list contains brief punt CPU queue statistics";
        uses switch-dp-punt-inject-oper:brief-punt-cpuq-statistics;
      }
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWVg1MhgAALtfgEAAEAYAEDsj2kq/d97qMADsmhiSjNDRGg09QaaDTTTEGimmgaNAAAAABJTSmagDT0jTaTEeoADQcxflhhSOEViMBbO/7c5lpWAhvRZiGZBkybZk+sI1tExKbYeB5E7MxoGpqziPjgMXItwsepJksEXjGKXJDoTyMiYD0TgUXFw3RSRcw1lVEoy5BpIs6Pnr4E7vLsaTAbqDaWxAUEKMjT+fWUrJRAiosJhILjmYGuqSZ6DNt3I+5MzeU+o1WBtQmooFipgs1l80G4Qswh0gwokMpMRCAGami8ZQI3G1kJyTEqG+wfURmlcJygNB/F3JFOFCQWDUyGA=";
      }
      tailf:meta-data "uncompressed_size" {
        tailf:meta-value "392";
      }
    }
    container Cisco-IOS-XE-common-types {
      description
        "Hidden internal container used for metadata";
      uses common-types-ios-xe:__yangpp_metadata;
    }
  }

  container schema-metadata-Cisco-IOS-XE-switch-dp-punt-inject-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-switch-dp-punt-inject-oper";
    }
    tailf:meta-data "organization" {
      tailf:meta-value "Cisco Systems, Inc.";
    }
    tailf:meta-data "semver" {
      tailf:meta-value "2020-07-01";
    }
  }
}
