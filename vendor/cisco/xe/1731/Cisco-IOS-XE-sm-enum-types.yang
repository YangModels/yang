module Cisco-IOS-XE-sm-enum-types {
  yang-version 1;
  namespace "http://cisco.com/ns/yang/Cisco-IOS-XE-sm-enum-types";
  prefix sm-enum-types;
  import tailf-common {
    prefix tailf;
  }
  import cisco-semver {
    prefix cisco-semver;
  }
  import cisco-semver-internal {
    prefix cisco-semver-internal;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for session data types.
     Copyright (c) 2019 by Cisco Systems, Inc.
     All rights reserved.";

  revision 2019-11-01 {
    description
      "Initial revision";
    reference "1.0.0";
    cisco-semver:module-version "1.0.0";
    cisco-semver-internal:os-version "17.1.1";
  }

  typedef session-events {
    type enumeration {
      enum "session-event-invalid" {
        value 0;
        description
          "Session event type invalid";
        tailf:code-name "ENUM_session_events_SESSION_EVENT_INVALID";
      }
      enum "session-event-internal" {
        value 1;
        description
          "Session event type internal";
        tailf:code-name "ENUM_session_events_SESSION_EVENT_INTERNAL";
      }
      enum "session-event-session-create" {
        value 2;
        description
          "Session event type session create";
        tailf:code-name "ENUM_session_events_SESSION_EVENT_SESSION_CREATE";
      }
      enum "session-event-session-authc-success" {
        value 3;
        description
          "Session event type authentication success";
        tailf:code-name "ENUM_session_events_SESSION_EVENT_SESSION_AUTHC_SUCCESS";
      }
      enum "session-event-session-authc-failed" {
        value 4;
        description
          "Session event type authentication failed";
        tailf:code-name "ENUM_session_events_SESSION_EVENT_SESSION_AUTHC_FAILED";
      }
      enum "session-event-session-authz-success" {
        value 5;
        description
          "Session event type authorization success";
        tailf:code-name "ENUM_session_events_SESSION_EVENT_SESSION_AUTHZ_SUCCESS";
      }
      enum "session-event-session-authz-failed" {
        value 6;
        description
          "Session event type authorization failed";
        tailf:code-name "ENUM_session_events_SESSION_EVENT_SESSION_AUTHZ_FAILED";
      }
      enum "session-event-start-method" {
        value 7;
        description
          "Session event type start method";
        tailf:code-name "ENUM_session_events_SESSION_EVENT_START_METHOD";
      }
      enum "session-event-terminate-method" {
        value 8;
        description
          "Session event type terminate method";
        tailf:code-name "ENUM_session_events_SESSION_EVENT_TERMINATE_METHOD";
      }
      enum "session-event-aaa-request" {
        value 9;
        description
          "Event raised when a request is initiated to a AAA server.";
        tailf:code-name "ENUM_session_events_SESSION_EVENT_AAA_REQUEST";
      }
      enum "session-event-aaa-success" {
        value 10;
        description
          "Session event type AAA success";
        tailf:code-name "ENUM_session_events_SESSION_EVENT_AAA_SUCCESS";
      }
      enum "session-event-aaa-success-no-author-data" {
        value 11;
        description
          "Event raised when a success is received from AAA server without any authorization data";
        tailf:code-name "ENUM_session_events_SESSION_EVENT_AAA_SUCCESS_NO_AUTHOR_DATA";
      }
      enum "session-event-aaa-challenge" {
        value 12;
        description
          "Event raised when access-challenge is raised for a AAA server";
        tailf:code-name "ENUM_session_events_SESSION_EVENT_AAA_CHALLENGE";
      }
      enum "session-event-eap-req-tx" {
        value 13;
        description
          "Session event type EAP request transmitted";
        tailf:code-name "ENUM_session_events_SESSION_EVENT_EAP_REQ_TX";
      }
      enum "session-event-eap-resp-rx" {
        value 14;
        description
          "Session event type EAP response received";
        tailf:code-name "ENUM_session_events_SESSION_EVENT_EAP_RESP_RX";
      }
      enum "session-event-eapol-start-rx" {
        value 15;
        description
          "Session event type EAPOL start received";
        tailf:code-name "ENUM_session_events_SESSION_EVENT_EAPOL_START_RX";
      }
      enum "session-event-eapol-logoff-rx" {
        value 16;
        description
          "Session event type EAPOL logoff received";
        tailf:code-name "ENUM_session_events_SESSION_EVENT_EAPOL_LOGOFF_RX";
      }
      enum "session-event-wa-get-request" {
        value 17;
        description
          "Event raised when a web-auth session received a HTTP GET request.";
        tailf:code-name "ENUM_session_events_SESSION_EVENT_WA_GET_REQUEST";
      }
      enum "session-event-wa-post-request" {
        value 18;
        description
          "Event raised when a web-auth session received a HTTP POST request.";
        tailf:code-name "ENUM_session_events_SESSION_EVENT_WA_POST_REQUEST";
      }
      enum "session-event-bm-set-client-to-orig" {
        value 19;
        description
          "Event raised when message is sent to put client into original state.";
        tailf:code-name "ENUM_session_events_SESSION_EVENT_BM_SET_CLIENT_TO_ORIG";
      }
      enum "session-event-bm-set-client-to-fwd" {
        value 20;
        description
          "Event raised when a message is sent to put client into forwarding state.";
        tailf:code-name "ENUM_session_events_SESSION_EVENT_BM_SET_CLIENT_TO_FWD";
      }
      enum "session-event-policy-change" {
        value 21;
        description
          "Event raised when authorization policy changes for a session.";
        tailf:code-name "ENUM_session_events_SESSION_EVENT_POLICY_CHANGE";
      }
      enum "session-event-session-disconnect" {
        value 22;
        description
          "Event raised when session disconnect request is received.";
        tailf:code-name "ENUM_session_events_SESSION_EVENT_SESSION_DISCONNECT";
      }
      enum "session-event-policy-update" {
        value 23;
        description
          "Event raised when change of policy attributes.";
        tailf:code-name "ENUM_session_events_SESSION_EVENT_SESSION_POLICY_UPDATE";
      }
      enum "session-event-coa-start" {
        value 24;
        description
          "Event raised when change of authorization is received.";
        tailf:code-name "ENUM_session_events_SESSION_EVENT_COA_START";
      }
      enum "session-event-security-violation" {
        value 25;
        description
          "Event raised on security violation for a port.";
        tailf:code-name "ENUM_session_events_SESSION_EVENT_SECURITY_VIOLATION";
      }
    }
    description
      "Enumeration for session event type";
  }

  typedef session-event-failure-reason {
    type enumeration {
      enum "session-event-reason-none" {
        value 0;
        description
          "Session event reason none";
        tailf:code-name "ENUM_session_event_failure_reason_SESSION_EVENT_REASON_NONE";
      }
      enum "session-event-reason-authc-cred-fail" {
        value 1;
        description
          "Session event reason authentication credential fail";
        tailf:code-name "ENUM_session_event_failure_reason_SESSION_EVENT_REASON_AUTHC_CRED_FAIL";
      }
      enum "session-event-reason-authc-aaa-server-fail" {
        value 2;
        description
          "Session event reason authentication AAA server fail";
        tailf:code-name "ENUM_session_event_failure_reason_SESSION_EVENT_REASON_AUTHC_AAA_SERVER_FAIL";
      }
      enum "session-event-reason-authc-no-response-fail" {
        value 3;
        description
          "Session event reason authentication no response fail";
        tailf:code-name "ENUM_session_event_failure_reason_SESSION_EVENT_REASON_AUTHC_NO_RESPONSE_FAIL";
      }
      enum "session-event-reason-authc-timeout-fail" {
        value 4;
        description
          "Session event reason authentication timeout fail";
        tailf:code-name "ENUM_session_event_failure_reason_SESSION_EVENT_REASON_AUTHC_TIMEOUT_FAIL";
      }
      enum "session-event-reason-authc-no-config-fail" {
        value 5;
        description
          "Session event reason authentication no configuration fail";
        tailf:code-name "ENUM_session_event_failure_reason_SESSION_EVENT_REASON_AUTHC_NO_CONFIG_FAIL";
      }
      enum "session-event-reason-aaa-not-ready" {
        value 6;
        description
          "Session event reason AAA server not ready";
        tailf:code-name "ENUM_session_event_failure_reason_SESSION_EVENT_REASON_AAA_NOT_READY";
      }
      enum "session-event-reason-authz-vlan-fail" {
        value 7;
        description
          "Session event reason authorization VLAN fail";
        tailf:code-name "ENUM_session_event_failure_reason_SESSION_EVENT_REASON_AUTHZ_VLAN_FAIL";
      }
      enum "session-event-reason-authz-acl-fail" {
        value 8;
        description
          "Session event reason authorization ACL fail";
        tailf:code-name "ENUM_session_event_failure_reason_SESSION_EVENT_REASON_AUTHZ_ACL_FAIL";
      }
      enum "session-event-reason-authz-punt-acl-fail" {
        value 9;
        description
          "Session event reason authorization punt ACL fail";
        tailf:code-name "ENUM_session_event_failure_reason_SESSION_EVENT_REASON_AUTHZ_PUNT_ACL_FAIL";
      }
      enum "session-event-reason-authz-qos-policy-fail" {
        value 10;
        description
          "Session event reason authorization QOS policy fail";
        tailf:code-name "ENUM_session_event_failure_reason_SESSION_EVENT_REASON_AUTHZ_QOS_POLICY_FAIL";
      }
      enum "session-event-reason-authz-accounting-fail" {
        value 11;
        description
          "Session event reason authorization accounting fail";
        tailf:code-name "ENUM_session_event_failure_reason_SESSION_EVENT_REASON_AUTHZ_ACCOUNTING_FAIL";
      }
      enum "session-event-reason-authz-cfg-macro-fail" {
        value 12;
        description
          "Session event reason authorization config macro fail";
        tailf:code-name "ENUM_session_event_failure_reason_SESSION_EVENT_REASON_AUTHZ_CFG_MACRO_FAIL";
      }
      enum "session-event-reason-authz-cts-fail" {
        value 13;
        description
          "Session event reason authorization CTS fail";
        tailf:code-name "ENUM_session_event_failure_reason_SESSION_EVENT_REASON_AUTHZ_CTS_FAIL";
      }
      enum "session-event-reason-authz-fqdn-fail" {
        value 14;
        description
          "Session event reason authorization FQDN fail";
        tailf:code-name "ENUM_session_event_failure_reason_SESSION_EVENT_REASON_AUTHZ_FQDN_FAIL";
      }
      enum "session-event-reason-authz-mdns-fail" {
        value 15;
        description
          "Session event reason authorization MDNS fail";
        tailf:code-name "ENUM_session_event_failure_reason_SESSION_EVENT_REASON_AUTHZ_MDNS_FAIL";
      }
      enum "session-event-reason-authz-idle-timeout-fail" {
        value 16;
        description
          "Session event reason authorization IAF fail";
        tailf:code-name "ENUM_session_event_failure_reason_SESSION_EVENT_REASON_AUTHZ_IDLE_TIMEOUT_FAIL";
      }
      enum "session-event-reason-authz-interface-template-fail" {
        value 17;
        description
          "Session event reason authorization interface template fail";
        tailf:code-name "ENUM_session_event_failure_reason_SESSION_EVENT_REASON_AUTHZ_INTERFACE_TEMPLATE_FAIL";
      }
      enum "session-event-reason-authz-umbrella-fail" {
        value 18;
        description
          "Session event reason authorization umbrella fail";
        tailf:code-name "ENUM_session_event_failure_reason_SESSION_EVENT_REASON_AUTHZ_UMBRELLA_FAIL";
      }
      enum "session-event-reason-authz-linksec-fail" {
        value 19;
        description
          "Session event reason authorization link security fail";
        tailf:code-name "ENUM_session_event_failure_reason_SESSION_EVENT_REASON_AUTHZ_LINKSEC_FAIL";
      }
      enum "session-event-reason-authz-misc-fail" {
        value 20;
        description
          "Session event reason authorization miscellaneous fail";
        tailf:code-name "ENUM_session_event_failure_reason_SESSION_EVENT_REASON_AUTHZ_MISC_FAIL";
      }
      enum "session-event-reason-authz-autoconf-fail" {
        value 21;
        description
          "Session event reason authorization autoconf fail";
        tailf:code-name "ENUM_session_event_failure_reason_SESSION_EVENT_REASON_AUTHZ_AUTOCONF_FAIL";
      }
      enum "session-event-reason-authz-tag-fail" {
        value 22;
        description
          "Session event reason authorization tag fail";
        tailf:code-name "ENUM_session_event_failure_reason_SESSION_EVENT_REASON_AUTHZ_TAG_FAIL";
      }
      enum "session-event-reason-authz-tunnel-fail" {
        value 23;
        description
          "Session event reason authorization tunnel fail";
        tailf:code-name "ENUM_session_event_failure_reason_SESSION_EVENT_REASON_AUTHZ_TUNNEL_FAIL";
      }
      enum "session-event-reason-authz-voice-vlan-fail" {
        value 24;
        description
          "Session event reason authorization voice VLAN fail";
        tailf:code-name "ENUM_session_event_failure_reason_SESSION_EVENT_REASON_AUTHZ_VOICE_VLAN_FAIL";
      }
      enum "session-event-reason-authz-reauth-fail" {
        value 25;
        description
          "Session event reason authorization reauthentication fail";
        tailf:code-name "ENUM_session_event_failure_reason_SESSION_EVENT_REASON_AUTHZ_REAUTH_FAIL";
      }
      enum "session-event-reason-authz-supplicant-name-fail" {
        value 26;
        description
          "Session event reason authorization supplicant name fail";
        tailf:code-name "ENUM_session_event_failure_reason_SESSION_EVENT_REASON_AUTHZ_SUPPLICANT_NAME_FAIL";
      }
      enum "session-event-reason-authz-user-name-fail" {
        value 27;
        description
          "Session event reason authorization user name fail";
        tailf:code-name "ENUM_session_event_failure_reason_SESSION_EVENT_REASON_AUTHZ_USER_NAME_FAIL";
      }
      enum "session-event-reason-authz-service-set-id-fail" {
        value 28;
        description
          "Session event reason authorization service set id fail";
        tailf:code-name "ENUM_session_event_failure_reason_SESSION_EVENT_REASON_AUTHZ_SERVICE_SET_ID_FAIL";
      }
      enum "session-event-reason-authz-interim-interval-fail" {
        value 29;
        description
          "Session event reason authorization interim interval fail";
        tailf:code-name "ENUM_session_event_failure_reason_SESSION_EVENT_REASON_AUTHZ_INTERIM_INTERVAL_FAIL";
      }
      enum "session-event-reason-authz-unknown-fail" {
        value 30;
        description
          "Session event reason authorization unknown fail";
        tailf:code-name "ENUM_session_event_failure_reason_SESSION_EVENT_REASON_AUTHZ_UNKNOWN_FAIL";
      }
    }
    description
      "Enumeration for session event reason";
  }

  typedef session-eap-method {
    type enumeration {
      enum "session-eap-method-unknown" {
        value 0;
        description
          "Session EAP method unknown";
        tailf:code-name "ENUM_session_eap_method_SESSION_EAP_METHOD_UNKNOWN";
      }
      enum "session-eap-method-md5" {
        value 4;
        description
          "Session EAP method MD5";
        tailf:code-name "ENUM_session_eap_method_SESSION_EAP_METHOD_MD5";
      }
      enum "session-eap-method-gtc" {
        value 6;
        description
          "Session EAP method GTC";
        tailf:code-name "ENUM_session_eap_method_SESSION_EAP_METHOD_GTC";
      }
      enum "session-eap-method-tls" {
        value 13;
        description
          "Session EAP method TLS";
        tailf:code-name "ENUM_session_eap_method_SESSION_EAP_METHOD_TLS";
      }
      enum "session-eap-method-leap" {
        value 17;
        description
          "Session EAP method LEAP";
        tailf:code-name "ENUM_session_eap_method_SESSION_EAP_METHOD_LEAP";
      }
      enum "session-eap-method-peap" {
        value 25;
        description
          "Session EAP method PEAP";
        tailf:code-name "ENUM_session_eap_method_SESSION_EAP_METHOD_PEAP";
      }
      enum "session-eap-method-mschapv2" {
        value 26;
        description
          "Session EAP method MSCHAPV2";
        tailf:code-name "ENUM_session_eap_method_SESSION_EAP_METHOD_MSCHAPV2";
      }
      enum "session-eap-method-fast" {
        value 43;
        description
          "Session EAP method FAST";
        tailf:code-name "ENUM_session_eap_method_SESSION_EAP_METHOD_FAST";
      }
    }
    description
      "Enumeration for EAP method for a session";
  }

  typedef session-auth-method-id {
    type enumeration {
      enum "session-auth-method-no-method-id" {
        value 0;
        description
          "Session method ID is none";
        tailf:code-name "ENUM_session_auth_method_id_SESSION_AUTH_METHOD_NO_METHOD_ID";
      }
      enum "session-auth-method-dot1x-method-id" {
        value 1;
        description
          "Session method ID is DOT1X";
        tailf:code-name "ENUM_session_auth_method_id_SESSION_AUTH_METHOD_DOT1X_METHOD_ID";
      }
      enum "session-auth-method-mab-method-id" {
        value 2;
        description
          "Session method ID is MAB";
        tailf:code-name "ENUM_session_auth_method_id_SESSION_AUTH_METHOD_MAB_METHOD_ID";
      }
      enum "session-auth-method-webauth-method-id" {
        value 3;
        description
          "Session method ID is Web-Auth";
        tailf:code-name "ENUM_session_auth_method_id_SESSION_AUTH_METHOD_WEBAUTH_METHOD_ID";
      }
      enum "session-auth-method-static-method-id" {
        value 4;
        description
          "Session method ID is static";
        tailf:code-name "ENUM_session_auth_method_id_SESSION_AUTH_METHOD_STATIC_METHOD_ID";
      }
      enum "session-auth-method-eou-method-id" {
        value 5;
        description
          "Session method ID is EOU";
        tailf:code-name "ENUM_session_auth_method_id_SESSION_AUTH_METHOD_EOU_METHOD_ID";
      }
      enum "session-auth-method-dot1x-supp-method-id" {
        value 6;
        description
          "Session method ID is DOT1X Supplicant";
        tailf:code-name "ENUM_session_auth_method_id_SESSION_AUTH_METHOD_DOT1X_SUPP_METHOD_ID";
      }
    }
    description
      "Enumeration for Authentication method  type for a session";
  }

  typedef session-security-violation-action {
    type enumeration {
      enum "session-violation-action-shutdown" {
        value 0;
        description
          "Session violation action shutdown";
        tailf:code-name "ENUM_session_security_violation_action_SESSION_VIOLATION_ACTION_SHUTDOWN";
      }
      enum "session-violation-action-restrict" {
        value 1;
        description
          "Session violation action restrict";
        tailf:code-name "ENUM_session_security_violation_action_SESSION_VIOLATION_ACTION_RESTRICT";
      }
      enum "session-violation-action-protect" {
        value 2;
        description
          "Session violation action protect";
        tailf:code-name "ENUM_session_security_violation_action_SESSION_VIOLATION_ACTION_PROTECT";
      }
      enum "session-violation-action-replace" {
        value 3;
        description
          "Session violation action replace";
        tailf:code-name "ENUM_session_security_violation_action_SESSION_VIOLATION_ACTION_REPLACE";
      }
    }
    description
      "Enumeration for security violation action";
  }

  typedef session-coa-request-type {
    type enumeration {
      enum "coa-request" {
        value 32530;
        description
          "Session COA request";
        tailf:code-name "ENUM_session_coa_request_type_COA_REQUEST";
      }
      enum "coa-pod-request" {
        value 32539;
        description
          "Session COA pod request";
        tailf:code-name "ENUM_session_coa_request_type_COA_POD_REQUEST";
      }
      enum "coa-bounce-host-port-request" {
        value 32534;
        description
          "Session COA bounce host port";
        tailf:code-name "ENUM_session_coa_request_type_COA_BOUNCE_HOST_PORT_REQUEST";
      }
      enum "coa-disable-host-port-request" {
        value 32535;
        description
          "Session COA disable host port";
        tailf:code-name "ENUM_session_coa_request_type_COA_DISABLE_HOST_PORT_REQUEST";
      }
      enum "coa-update-service-template-request" {
        value 32543;
        description
          "Session COA update service template";
        tailf:code-name "ENUM_session_coa_request_type_COA_UPDATE_SERVICE_TEMPLATE_REQUEST";
      }
    }
    description
      "Enumeration for COA request type";
  }

  grouping __yangpp_metadata {
    description
      "Internal metadata for this module and imported modules";
  }

  container gnmi-model-data {
    description
      "This container makes accessible the information necessary to respond to a GNMI Capabilities RPC";
    tailf:hidden "full";
    tailf:meta-data "module-name" {
      tailf:meta-value "Cisco-IOS-XE-sm-enum-types";
    }
    tailf:meta-data "organization" {
      tailf:meta-value "Cisco Systems, Inc.";
    }
    tailf:meta-data "semver" {
      tailf:meta-value "2019-11-01";
    }
  }
}
