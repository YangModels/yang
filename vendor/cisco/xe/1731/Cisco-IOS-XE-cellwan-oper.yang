module Cisco-IOS-XE-cellwan-oper {
  yang-version 1;
  namespace "http://cisco.com/ns/yang/Cisco-IOS-XE-cellwan-oper";
  prefix cellwan-ios-xe-oper;
  import ietf-inet-types {
    prefix inet;
  }
  import ietf-yang-types {
    prefix yang;
  }
  import tailf-common {
    prefix tailf;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for cellwan operational data.
     Copyright (c) 2018-2019 by Cisco Systems, Inc.
     All rights reserved.";

  revision 2019-05-01 {
    description
      "Added semantic version";
    reference "1.3.0";
    cisco-semver:module-version "1.3.0";
  }
  revision 2018-10-29 {
    description
      "Cleaned up spelling errors in descriptions.";
    reference "1.2.0";
    cisco-semver:module-version "1.2.0";
  }
  revision 2018-05-18 {
    description
      "Addition of Cellular Sim Security, GPS and SMS data";
    reference "1.1.0";
    cisco-semver:module-version "1.1.0";
  }
  revision 2018-05-01 {
    description
      "Initial revision";
    reference "1.0.0";
    cisco-semver:module-version "1.0.0";
  }

  typedef modem-status {
    type enumeration {
      enum "modem-status-offline" {
        value 0;
        description
          "Modem is in Offline state";
        tailf:code-name "ENUM_modem_status_CELLWAN_MODEM_STATUS_OFFLINE";
      }
      enum "modem-status-online" {
        value 1;
        description
          "Modem is in Online state";
        tailf:code-name "ENUM_modem_status_CELLWAN_MODEM_STATUS_ONLINE";
      }
      enum "modem-status-low-power" {
        value 2;
        description
          "Modem is in Low Power Mode state";
        tailf:code-name "ENUM_modem_status_CELLWAN_MODEM_STATUS_LOW_POWER";
      }
      enum "modem-status-power-off" {
        value 3;
        description
          "Modem is in power off state";
        tailf:code-name "ENUM_modem_status_CELLWAN_MODEM_STATUS_POWER_OFF";
      }
      enum "modem-status-boot-ready" {
        value 4;
        description
          "Modem is in boot ready state";
        tailf:code-name "ENUM_modem_status_CELLWAN_MODEM_STATUS_BOOT_READY";
      }
      enum "modem-status-unknown" {
        value 5;
        description
          "Modem is in unknown state";
        tailf:code-name "ENUM_modem_status_CELLWAN_MODEM_STATUS_UNKNOWN";
      }
    }
    description
      "Modem status indicates the current state of cellular modem";
  }

  typedef cw-radio-power-status {
    type enumeration {
      enum "radio-power-mode-online" {
        value 0;
        description
          "Cellular modem is in online radio mode";
        tailf:code-name "ENUM_cw_radio_power_status_CELLWAN_RADIO_POWER_MODE_ONLINE";
      }
      enum "radio-power-mode-low-power" {
        value 1;
        description
          "Cellular modem is in low power radio mode";
        tailf:code-name "ENUM_cw_radio_power_status_CELLWAN_RADIO_POWER_MODE_LOW_POWER";
      }
      enum "radio-power-mode-factory-test" {
        value 2;
        description
          "Cellular modem is in factory test radio mode";
        tailf:code-name "ENUM_cw_radio_power_status_CELLWAN_RADIO_POWER_MODE_FACTORY_TEST";
      }
      enum "radio-power-mode-offline" {
        value 3;
        description
          "Cellular modem is in offline radio mode";
        tailf:code-name "ENUM_cw_radio_power_status_CELLWAN_RADIO_POWER_MODE_OFFLINE";
      }
      enum "radio-power-mode-reset" {
        value 4;
        description
          "Cellular modem is in reset radio mode";
        tailf:code-name "ENUM_cw_radio_power_status_CELLWAN_RADIO_POWER_MODE_RESET";
      }
      enum "radio-power-mode-off" {
        value 5;
        description
          "Cellular modem is in off radio mode";
        tailf:code-name "ENUM_cw_radio_power_status_CELLWAN_RADIO_POWER_MODE_OFF";
      }
      enum "radio-power-mode-persistent-low-power" {
        value 6;
        description
          "Cellular modem is in persistent low power radio mode";
        tailf:code-name "ENUM_cw_radio_power_status_CELLWAN_RADIO_POWER_MODE_PERSISTENT_LOW_POWER";
      }
    }
    description
      "Radio power status indicates the current radio power mode of cellular modem";
  }

  typedef radio-bandwidth {
    type enumeration {
      enum "bandwidth-1-dot-4-mhz" {
        value 0;
        description
          "Cellular radio bandwidth is 1.4 MHz";
        tailf:code-name "ENUM_radio_bandwidth_CELLWAN_BAND_WIDTH_1_DOT_4_MHz";
      }
      enum "bandwidth-3-mhz" {
        value 1;
        description
          "Cellular radio bandwidth is 3 MHz";
        tailf:code-name "ENUM_radio_bandwidth_CELLWAN_BAND_WIDTH_3_MHz";
      }
      enum "bandwidth-5-mhz" {
        value 2;
        description
          "Cellular radio bandwidth is 5 MHz";
        tailf:code-name "ENUM_radio_bandwidth_CELLWAN_BAND_WIDTH_5_MHz";
      }
      enum "bandwidth-10-mhz" {
        value 3;
        description
          "Cellular radio bandwidth is 10 MHz";
        tailf:code-name "ENUM_radio_bandwidth_CELLWAN_BAND_WIDTH_10_MHz";
      }
      enum "bandwidth-15-mhz" {
        value 4;
        description
          "Cellular radio bandwidth is 15 MHz";
        tailf:code-name "ENUM_radio_bandwidth_CELLWAN_BAND_WIDTH_15_MHz";
      }
      enum "bandwidth-20-mhz" {
        value 5;
        description
          "Cellular radio bandwidth is 20 MHz";
        tailf:code-name "ENUM_radio_bandwidth_CELLWAN_BAND_WIDTH_20_MHz";
      }
      enum "bandwidth-invalid" {
        value 6;
        description
          "Cellular radio bandwidth is invalid";
        tailf:code-name "ENUM_radio_bandwidth_CELLWAN_BAND_WIDTH_INVALID";
      }
      enum "bandwidth-unknown" {
        value 7;
        description
          "Cellular radio bandwidth is unknown";
        tailf:code-name "ENUM_radio_bandwidth_CELLWAN_BAND_WIDTH_UNKNOWN";
      }
    }
    description
      "Radio bandwidth indicates the current cellular radio bandwidth selected in MHz";
  }

  typedef modem-technology {
    type enumeration {
      enum "cdma-evdo-1x-rtt" {
        value 0;
        description
          "Modem technology selected is CDMA (Code Division Multiple Access) / 
             EVDO (Evolution-Data Optimized) / 
             1xRTT (Single carrier (1x) radio transmission technology)";
        tailf:code-name "ENUM_modem_technology_CELLWAN_CDMA_EVDO_1xRTT";
      }
      enum "gsm-umts-gprs" {
        value 1;
        description
          "Modem technology selected is GSM (Global System for Mobile Communications) 
             / UMTS (Universal Mobile Telecommunications Service) 
             / GPRS (General Packet Radio Service)";
        tailf:code-name "ENUM_modem_technology_CELLWAN_GSM_UMTS_GPRS";
      }
      enum "tech-unknown" {
        value 2;
        description
          "Modem technology selected is unknown";
        tailf:code-name "ENUM_modem_technology_CELLWAN_TECH_UNKNOWN";
      }
    }
    description
      "Modem technology indicates the current cellular technology selected";
  }

  typedef rat-preference {
    type enumeration {
      enum "lte-radio-tech-no-svc" {
        value 0;
        description
          "Radio technology preference is no svc";
        tailf:code-name "ENUM_rat_preference_CELLWAN_LTE_RADIO_TECH_NO_SVC";
      }
      enum "lte-radio-tech-cdma-1-xrtt" {
        value 1;
        description
          "Radio technology preference is CDMA (Code Division Multiple Access) 
           / 1xRTT (Single carrier (1x) radio transmission technology)";
        tailf:code-name "ENUM_rat_preference_CELLWAN_LTE_RADIO_TECH_CDMA_1XRTT";
      }
      enum "lte-radio-tech-cdma-evdo" {
        value 2;
        description
          "Radio technology preference is CDMA (Code Division Multiple Access) 
           / EVDO (Evolution-Data Optimized) ";
        tailf:code-name "ENUM_rat_preference_CELLWAN_LTE_RADIO_TECH_CDMA_EVDO";
      }
      enum "lte-radio-tech-amps" {
        value 3;
        description
          "Radio technology preference is AMPS (Advanced Mobile Phone Service)";
        tailf:code-name "ENUM_rat_preference_CELLWAN_LTE_RADIO_TECH_AMPS";
      }
      enum "lte-radio-tech-gsm" {
        value 4;
        description
          "Radio technology preference is GSM (Global System for Mobile Communications)";
        tailf:code-name "ENUM_rat_preference_CELLWAN_LTE_RADIO_TECH_GSM";
      }
      enum "lte-radio-tech-umts" {
        value 5;
        description
          "Radio technology preference is UMTS (Universal Mobile Telecommunications Service)";
        tailf:code-name "ENUM_rat_preference_CELLWAN_LTE_RADIO_TECH_UMTS";
      }
      enum "lte-radio-tech-wlan" {
        value 6;
        description
          "Radio technology preference is WLAN (wireless local area network)";
        tailf:code-name "ENUM_rat_preference_CELLWAN_LTE_RADIO_TECH_WLAN";
      }
      enum "lte-radio-tech-gprs" {
        value 7;
        description
          "Radio technology preference is GPRS (General Packet Radio Service)";
        tailf:code-name "ENUM_rat_preference_CELLWAN_LTE_RADIO_TECH_GPRS";
      }
      enum "lte-radio-tech-lte" {
        value 8;
        description
          "Radio technology preference is LTE (Long-Term Evolution)";
        tailf:code-name "ENUM_rat_preference_CELLWAN_LTE_RADIO_TECH_LTE";
      }
      enum "lte-radio-tech-auto" {
        value 9;
        description
          "Radio technology preference is AUTO ";
        tailf:code-name "ENUM_rat_preference_CELLWAN_LTE_RADIO_TECH_AUTO";
      }
      enum "lte-radio-tech-hybrid-cdma" {
        value 10;
        description
          "Radio technology preference is Hybrid CDMA (Hybrid Code Division Multiple Access)";
        tailf:code-name "ENUM_rat_preference_CELLWAN_LTE_RADIO_TECH_HYBRID_CDMA";
      }
      enum "lte-radio-tech-wcdma" {
        value 11;
        description
          "Radio technology preference is WCDMA (Wideband Code Division Multiplexing Access)";
        tailf:code-name "ENUM_rat_preference_CELLWAN_LTE_RADIO_TECH_WCDMA";
      }
      enum "lte-radio-tech-gwl" {
        value 12;
        description
          "Radio technology preference is GWL ";
        tailf:code-name "ENUM_rat_preference_CELLWAN_LTE_RADIO_TECH_GWL";
      }
      enum "lte-radio-tech-edge" {
        value 13;
        description
          "Radio technology preference is EDGE (Enhanced Data rates for GSM Evolution)";
        tailf:code-name "ENUM_rat_preference_CELLWAN_LTE_RADIO_TECH_EDGE";
      }
      enum "lte-radio-tech-hsdpa-n-wcdma" {
        value 14;
        description
          "Radio technology preference is HSDPA (High Speed Downlink Packet Access)
           & WCDMA (Wideband Code Division Multiplexing Access)";
        tailf:code-name "ENUM_rat_preference_CELLWAN_LTE_RADIO_TECH_HSDPA_N_WCDMA";
      }
      enum "lte-radio-tech-wcdma-n-hsupa" {
        value 15;
        description
          "Radio technology preference is WCDMA (Wideband Code Division Multiplexing Access)
             & HSUPA (High Speed Uplink Packet Access)";
        tailf:code-name "ENUM_rat_preference_CELLWAN_LTE_RADIO_TECH_WCDMA_N_HSUPA";
      }
      enum "lte-radio-tech-hsdpa-n-hsupa" {
        value 16;
        description
          "Radio technology preference is HSDPA (High Speed Downlink Packet Access)
             & HSUPA (High Speed Uplink Packet Access)";
        tailf:code-name "ENUM_rat_preference_CELLWAN_LTE_RADIO_TECH_HSDPA_N_HSUPA";
      }
      enum "lte-radio-tech-hsdpa-plus-n-wcdma" {
        value 17;
        description
          "Radio technology preference is HSDPA+ (High Speed Downlink Packet Access plus) 
             & WCDMA (Wideband Code Division Multiplexing Access)";
        tailf:code-name "ENUM_rat_preference_CELLWAN_LTE_RADIO_TECH_HSDPA_PLUS_N_WCDMA";
      }
      enum "lte-radio-tech-hsdpa-plus-n-hsupa" {
        value 18;
        description
          "Radio technology preference is HSDPA+ (High Speed Downlink Packet Access plus)
             & HSUPA (High Speed Uplink Packet Access)";
        tailf:code-name "ENUM_rat_preference_CELLWAN_LTE_RADIO_TECH_HSDPA_PLUS_N_HSUPA";
      }
      enum "lte-radio-tech-dc-hsdpa-plus-n-wcdma" {
        value 19;
        description
          "Radio technology preference is 
             DC HSDPA+ (Dual Carrier High Speed Downlink Packet Access plus) 
             & WCDMA (Wideband Code Division Multiplexing Access)";
        tailf:code-name "ENUM_rat_preference_CELLWAN_LTE_RADIO_TECH_DC_HSDPA_PLUS_N_WCDMA";
      }
      enum "lte-radio-tech-dc-hsdpa-plus-n-hsupa" {
        value 20;
        description
          "Radio technology preference is 
             DC HSDPA+ (Dual Carrier High Speed Downlink Packet Access plus) 
             & HSUPA (High Speed Uplink Packet Access)";
        tailf:code-name "ENUM_rat_preference_CELLWAN_LTE_RADIO_TECH_DC_HSDPA_PLUS_N_HSUPA";
      }
      enum "lte-radio-tech-null-bearer" {
        value 21;
        description
          "Radio technology preference is Null Bearer ";
        tailf:code-name "ENUM_rat_preference_CELLWAN_LTE_RADIO_TECH_NULL_BEARER";
      }
      enum "lte-radio-tech-unknown" {
        value 22;
        description
          "Radio technology preference is Unknown ";
        tailf:code-name "ENUM_rat_preference_CELLWAN_LTE_RADIO_TECH_UNKNOWN";
      }
      enum "lte-radio-tech-no-change" {
        value 23;
        description
          "Radio technology preference is unchanged ";
        tailf:code-name "ENUM_rat_preference_CELLWAN_LTE_RADIO_TECH_NO_CHANGE";
      }
    }
    description
      "RAT preference indicates the current radio technology preference";
  }

  typedef rat-technology {
    type enumeration {
      enum "system-mode-none" {
        value 0;
        description
          "Radio technology selected is none";
        tailf:code-name "ENUM_rat_technology_CELLWAN_SYSTEM_MODE_NONE";
      }
      enum "system-mode-gprs" {
        value 1;
        description
          "Radio technology selected is GPRS (General Packet Radio Service)";
        tailf:code-name "ENUM_rat_technology_CELLWAN_SYSTEM_MODE_GPRS";
      }
      enum "system-mode-edge" {
        value 2;
        description
          "Radio technology selected is EDGE (Enhanced Data rates for GSM Evolution)";
        tailf:code-name "ENUM_rat_technology_CELLWAN_SYSTEM_MODE_EDGE";
      }
      enum "system-mode-umts" {
        value 3;
        description
          "Radio technology selected is UMTS (Universal Mobile Telecommunications System)";
        tailf:code-name "ENUM_rat_technology_CELLWAN_SYSTEM_MODE_UMTS";
      }
      enum "system-mode-hsdpa" {
        value 4;
        description
          "Radio technology selected is HSDPA (High Speed Downlink Packet Access)";
        tailf:code-name "ENUM_rat_technology_CELLWAN_SYSTEM_MODE_HSDPA";
      }
      enum "system-mode-hsupa" {
        value 5;
        description
          "Radio technology selected is HSUPA (High Speed Uplink Packet Access)";
        tailf:code-name "ENUM_rat_technology_CELLWAN_SYSTEM_MODE_HSUPA";
      }
      enum "system-mode-hspa" {
        value 6;
        description
          "Radio technology selected is HSPA (High Speed Packet Access)";
        tailf:code-name "ENUM_rat_technology_CELLWAN_SYSTEM_MODE_HSPA";
      }
      enum "system-mode-hspa-plus" {
        value 7;
        description
          "Radio technology selected is HSPA+ (Evolved High Speed Packet Access)";
        tailf:code-name "ENUM_rat_technology_CELLWAN_SYSTEM_MODE_HSPA_PLUS";
      }
      enum "system-mode-lte-fdd" {
        value 8;
        description
          "Radio technology selected is LTE-FDD (Long Term Evolution-Frequency Division Duplex)";
        tailf:code-name "ENUM_rat_technology_CELLWAN_SYSTEM_MODE_LTE_FDD";
      }
      enum "system-mode-lte-tdd" {
        value 9;
        description
          "Radio technology selected is LTE-TDD(Long Term Evolution-Time Division Duplex)";
        tailf:code-name "ENUM_rat_technology_CELLWAN_SYSTEM_MODE_LTE_TDD";
      }
      enum "system-mode-lte-e-hrpd-1x-rtt" {
        value 10;
        description
          "Radio technology selected is LTE (Long Term Evolution) /
             eHRPD (Evolved High Rate Packet Data) /
             1xRTT (Single carrier (1x) radio transmission technology)";
        tailf:code-name "ENUM_rat_technology_CELLWAN_SYSTEM_MODE_LTE_eHRPD_1xRTT";
      }
      enum "system-mode-lte-e-hrpd-evdo" {
        value 11;
        description
          "Radio technology selected is LTE (Long Term Evolution) / 
             eHRPD (Evolved High Rate Packet Data) / 
             EVDO (Evolution-Data Optimized) ";
        tailf:code-name "ENUM_rat_technology_CELLWAN_SYSTEM_MODE_LTE_eHRPD_EVDO";
      }
      enum "system-mode-evdo" {
        value 12;
        description
          "Radio technology selected is EVDO (Evolution-Data Optimized)";
        tailf:code-name "ENUM_rat_technology_CELLWAN_SYSTEM_MODE_EVDO";
      }
      enum "system-mode-evdo-reva" {
        value 13;
        description
          "Radio technology selected is EVDO (Evolution-Data Optimized) / 
             REVA (Evolution Data Optimized - Rev A)";
        tailf:code-name "ENUM_rat_technology_CELLWAN_SYSTEM_MODE_EVDO_REVA";
      }
      enum "system-mode-hsdpa-n-wcdma" {
        value 14;
        description
          "Radio technology selected is HSDPA (High Speed Downlink Packet Access) 
             & WCDMA (Wideband Code Division Multiple Access)";
        tailf:code-name "ENUM_rat_technology_CELLWAN_SYSTEM_MODE_HSDPA_N_WCDMA";
      }
      enum "system-mode-wcdma-n-hsupa" {
        value 15;
        description
          "Radio technology selected is WCDMA (Wideband Code Division Multiple Access)
             & HSUPA (High Speed Uplink Packet Access) ";
        tailf:code-name "ENUM_rat_technology_CELLWAN_SYSTEM_MODE_WCDMA_N_HSUPA";
      }
      enum "system-mode-hsdpa-n-hsupa" {
        value 16;
        description
          "Radio technology selected is HSDPA (High Speed Downlink Packet Access) 
             & HSUPA (High Speed Uplink Packet Access) ";
        tailf:code-name "ENUM_rat_technology_CELLWAN_SYSTEM_MODE_HSDPA_N_HSUPA";
      }
      enum "system-mode-hsdpa-plus-n-wcdma" {
        value 17;
        description
          "Radio technology selected is HSDPA+ (High Speed Downlink Packet Access plus) 
             & WCDMA (Wideband Code Division Multiple Access)";
        tailf:code-name "ENUM_rat_technology_CELLWAN_SYSTEM_MODE_HSDPA_PLUS_N_WCDMA";
      }
      enum "system-mode-hsdpa-plus-n-hsupa" {
        value 18;
        description
          "Radio technology selected is HSDPA+ (High Speed Downlink Packet Access plus) 
             & HSUPA (High Speed Uplink Packet Access) ";
        tailf:code-name "ENUM_rat_technology_CELLWAN_SYSTEM_MODE_HSDPA_PLUS_N_HSUPA";
      }
      enum "system-mode-dc-hsdpa-plus-n-wcdma" {
        value 19;
        description
          "Radio technology selected is 
             DC HSDPA+ (Dual Carrier High Speed Downlink Packet Access plus) 
             & WCDMA (Wideband Code Division Multiple Access)";
        tailf:code-name "ENUM_rat_technology_CELLWAN_SYSTEM_MODE_DC_HSDPA_PLUS_N_WCDMA";
      }
      enum "system-mode-dc-hsdpa-plus-n-hsupa" {
        value 20;
        description
          "Radio technology selected is 
             DC HSDPA+ (Dual Carrier High Speed Downlink Packet Access plus)
             & HSUPA (High Speed Uplink Packet Access)";
        tailf:code-name "ENUM_rat_technology_CELLWAN_SYSTEM_MODE_DC_HSDPA_PLUS_N_HSUPA";
      }
      enum "sysyem-mode-null-bearer" {
        value 21;
        description
          "Radio technology selected is null bearer";
        tailf:code-name "ENUM_rat_technology_CELLWAN_SYSYEM_MODE_NULL_BEARER";
      }
      enum "system-mode-unknown" {
        value 22;
        description
          "Radio technology selected is unknown";
        tailf:code-name "ENUM_rat_technology_CELLWAN_SYSTEM_MODE_UNKNOWN";
      }
    }
    description
      "RAT technology indicates the current radio technology selected";
  }

  typedef service-status {
    type enumeration {
      enum "service-status-normal" {
        value 0;
        description
          "Cellular Network status is in normal state";
        tailf:code-name "ENUM_service_status_CELLWAN_SERVICE_STATUS_NORMAL";
      }
      enum "service-status-emergency" {
        value 1;
        description
          "Cellular Network status is in emergency state";
        tailf:code-name "ENUM_service_status_CELLWAN_SERVICE_STATUS_EMERGENCY";
      }
      enum "service-status-no-service" {
        value 2;
        description
          "Cellular Network status is in no service state";
        tailf:code-name "ENUM_service_status_CELLWAN_SERVICE_STATUS_NO_SERVICE";
      }
      enum "service-status-unknown" {
        value 3;
        description
          "Cellular Network status is in unknown state";
        tailf:code-name "ENUM_service_status_CELLWAN_SERVICE_STATUS_UNKNOWN";
      }
    }
    description
      "Service status indicates the current network service for cellular modem";
  }

  typedef modem-service {
    type enumeration {
      enum "service-type-circuit-switched" {
        value 0;
        description
          "Cellular Network service type is circuit-switched";
        tailf:code-name "ENUM_modem_service_CELLWAN_SERVICE_TYPE_CIRCUIT_SWITCHED";
      }
      enum "service-type-packet-switched" {
        value 1;
        description
          "Cellular Network service type is packet-switched";
        tailf:code-name "ENUM_modem_service_CELLWAN_SERVICE_TYPE_PACKET_SWITCHED";
      }
      enum "service-type-combined" {
        value 2;
        description
          "Cellular Network service type is combined";
        tailf:code-name "ENUM_modem_service_CELLWAN_SERVICE_TYPE_COMBINED";
      }
      enum "service-type-invalid" {
        value 3;
        description
          "Cellular Network service type is invalid";
        tailf:code-name "ENUM_modem_service_CELLWAN_SERVICE_TYPE_INVALID";
      }
      enum "service-type-unknown" {
        value 4;
        description
          "Cellular Network service type is unknown";
        tailf:code-name "ENUM_modem_service_CELLWAN_SERVICE_TYPE_UNKNOWN";
      }
    }
    description
      "Modem service indicates the current network service type for cellular modem";
  }

  typedef lte-ca {
    type enumeration {
      enum "lte-ca-deconfigured" {
        value 0;
        description
          "LTE carrier aggregation is deconfigured";
        tailf:code-name "ENUM_lte_ca_CELLWAN_LTE_CA_DECONFIGURED";
      }
      enum "lte-ca-deactivated" {
        value 1;
        description
          "LTE carrier aggregation is deactivated";
        tailf:code-name "ENUM_lte_ca_CELLWAN_LTE_CA_DEACTIVATED";
      }
      enum "lte-ca-activated" {
        value 2;
        description
          "LTE carrier aggregation is activated";
        tailf:code-name "ENUM_lte_ca_CELLWAN_LTE_CA_ACTIVATED";
      }
      enum "lte-ca-unsupported" {
        value 3;
        description
          "LTE carrier aggregation is unsupported";
        tailf:code-name "ENUM_lte_ca_CELLWAN_LTE_CA_UNSUPPORTED";
      }
    }
    description
      "LTE CA indicates the LTE carrier aggregation status for cellular modem";
  }

  typedef reg-state {
    type enumeration {
      enum "reg-status-not-registered" {
        value 0;
        description
          "Cellular Network is in not registered state";
        tailf:code-name "ENUM_reg_state_CELLWAN_REG_STATUS_NOT_REGISTERED";
      }
      enum "reg-status-registered" {
        value 1;
        description
          "Cellular Network is in registered state";
        tailf:code-name "ENUM_reg_state_CELLWAN_REG_STATUS_REGISTERED";
      }
      enum "reg-status-searching" {
        value 2;
        description
          "Cellular Network is in searching state";
        tailf:code-name "ENUM_reg_state_CELLWAN_REG_STATUS_SEARCHING";
      }
      enum "reg-status-registration-denied" {
        value 3;
        description
          "Cellular Network is in registration denied state";
        tailf:code-name "ENUM_reg_state_CELLWAN_REG_STATUS_REGISTRATION_DENIED";
      }
      enum "reg-status-unsupported" {
        value 4;
        description
          "Cellular Network is in unsupported state";
        tailf:code-name "ENUM_reg_state_CELLWAN_REG_STATUS_UNSUPPORTED";
      }
    }
    description
      "Registration state indicates the current cellular network registration state";
  }

  typedef packet-sess-status {
    type enumeration {
      enum "packet-session-status-inactive" {
        value 0;
        description
          "Cellular packet session status is inactive";
        tailf:code-name "ENUM_packet_sess_status_CELLWAN_PACKET_SESSION_STATUS_INACTIVE";
      }
      enum "packet-session-status-active" {
        value 1;
        description
          "Cellular packet session status is active";
        tailf:code-name "ENUM_packet_sess_status_CELLWAN_PACKET_SESSION_STATUS_ACTIVE";
      }
    }
    description
      "Packet Session Status indicates the Cellular packet session state";
  }

  typedef profile-scope {
    type enumeration {
      enum "scope-global" {
        value 0;
        description
          "IP address scope is Global";
        tailf:code-name "ENUM_profile_scope_CELLWAN_SCOPE_GLOBAL";
      }
      enum "scope-link" {
        value 1;
        description
          "IP address scope is Link";
        tailf:code-name "ENUM_profile_scope_CELLWAN_SCOPE_LINK";
      }
    }
    description
      "Profile Scope indicates the IP address scope";
  }

  typedef cellwan-chv1-sim-status {
    type enumeration {
      enum "chv1-verify-disabled" {
        value 0;
        description
          "SIM card holder verification (CHV1) disabled";
        tailf:code-name "ENUM_cellwan_chv1_sim_status_CELLWAN_CHV1_VERIFY_DISABLED";
      }
      enum "chv1-verify-enabled" {
        value 1;
        description
          "SIM card holder verification (CHV1) enabled";
        tailf:code-name "ENUM_cellwan_chv1_sim_status_CELLWAN_CHV1_VERIFY_ENABLED";
      }
      enum "chv1-verify-pending" {
        value 2;
        description
          "SIM card holder verification (CHV1) pending";
        tailf:code-name "ENUM_cellwan_chv1_sim_status_CELLWAN_CHV1_VERIFY_PENDING";
      }
    }
    description
      "Cellular modem SIM card holder verification (CHV1) status";
  }

  typedef cellwan-sim-status {
    type enumeration {
      enum "sim-status-ok" {
        value 0;
        description
          "Cellular modem SIM status is inserted";
        tailf:code-name "ENUM_cellwan_sim_status_CELLWAN_SIM_STATUS_OK";
      }
      enum "sim-status-not-inserted" {
        value 1;
        description
          "Cellular modem SIM is not inserted";
        tailf:code-name "ENUM_cellwan_sim_status_CELLWAN_SIM_STATUS_NOT_INSERTED";
      }
      enum "sim-status-removed" {
        value 2;
        description
          "Cellular modem SIM is in removed state";
        tailf:code-name "ENUM_cellwan_sim_status_CELLWAN_SIM_STATUS_REMOVED";
      }
      enum "sim-status-init-failure" {
        value 3;
        description
          "Cellular modem SIM is in initialization failure state";
        tailf:code-name "ENUM_cellwan_sim_status_CELLWAN_SIM_STATUS_INIT_FAILURE";
      }
      enum "sim-status-general-failure" {
        value 4;
        description
          "Cellular modem SIM is in general failure state";
        tailf:code-name "ENUM_cellwan_sim_status_CELLWAN_SIM_STATUS_GENERAL_FAILURE";
      }
      enum "sim-status-locked" {
        value 5;
        description
          "Cellular modem SIM is in locked state";
        tailf:code-name "ENUM_cellwan_sim_status_CELLWAN_SIM_STATUS_LOCKED";
      }
      enum "sim-status-chv1-blocked" {
        value 6;
        description
          "Cellular modem SIM is in chv1 (Card Holder Verification) blocked state";
        tailf:code-name "ENUM_cellwan_sim_status_CELLWAN_SIM_STATUS_CHV1_BLOCKED";
      }
      enum "sim-status-chv2-blocked" {
        value 7;
        description
          "Cellular modem SIM is in chv2 (Card Holder Verification) blocked state";
        tailf:code-name "ENUM_cellwan_sim_status_CELLWAN_SIM_STATUS_CHV2_BLOCKED";
      }
      enum "sim-status-chv1-rejected" {
        value 8;
        description
          "Cellular modem SIM is in chv1 (Card Holder Verification) rejected state";
        tailf:code-name "ENUM_cellwan_sim_status_CELLWAN_SIM_STATUS_CHV1_REJECTED";
      }
      enum "sim-status-chv2-rejected" {
        value 9;
        description
          "Cellular modem SIM is in chv2 (Card Holder Verification) rejected state";
        tailf:code-name "ENUM_cellwan_sim_status_CELLWAN_SIM_STATUS_CHV2_REJECTED";
      }
      enum "sim-status-mep-locked" {
        value 10;
        description
          "Cellular modem SIM is in MEP (Mobile Equipment Personalization) locked state";
        tailf:code-name "ENUM_cellwan_sim_status_CELLWAN_SIM_STATUS_MEP_LOCKED";
      }
      enum "sim-status-network-reject" {
        value 11;
        description
          "Cellular modem SIM is in network reject state";
        tailf:code-name "ENUM_cellwan_sim_status_CELLWAN_SIM_STATUS_NETWORK_REJECT";
      }
      enum "sim-status-unknown" {
        value 12;
        description
          "Cellular modem SIM is in unknown state";
        tailf:code-name "ENUM_cellwan_sim_status_CELLWAN_SIM_STATUS_UNKNOWN";
      }
    }
    description
      "Cellular modem SIM status";
  }

  typedef cellwan-sim-user-op {
    type enumeration {
      enum "sim-user-op-none" {
        value 0;
        description
          "Cellular modem SIM user operation is in None state";
        tailf:code-name "ENUM_cellwan_sim_user_op_CELLWAN_SIM_USER_OP_NONE";
      }
      enum "sim-user-op-chv1" {
        value 1;
        description
          "Cellular modem SIM user is in CHV1 (Card Holder Verification) state";
        tailf:code-name "ENUM_cellwan_sim_user_op_CELLWAN_SIM_USER_OP_CHV1";
      }
      enum "sim-user-op-chv2" {
        value 2;
        description
          "Cellular modem SIM user is in CHV2 (Card Holder Verification) state";
        tailf:code-name "ENUM_cellwan_sim_user_op_CELLWAN_SIM_USER_OP_CHV2";
      }
      enum "sim-user-op-unblock-chv1" {
        value 3;
        description
          "Cellular modem SIM user is in Unblocked CHV1 (Card Holder Verification) state";
        tailf:code-name "ENUM_cellwan_sim_user_op_CELLWAN_SIM_USER_OP_UNBLOCK_CHV1";
      }
      enum "sim-user-op-unblock-chv2" {
        value 4;
        description
          "Cellular modem SIM user is in Unblocked CHV2 (Card Holder Verification) state";
        tailf:code-name "ENUM_cellwan_sim_user_op_CELLWAN_SIM_USER_OP_UNBLOCK_CHV2";
      }
      enum "sim-user-op-mep" {
        value 5;
        description
          "Cellular modem SIM user is in MEP (Mobile Equipment Personalization) state";
        tailf:code-name "ENUM_cellwan_sim_user_op_CELLWAN_SIM_USER_OP_MEP";
      }
      enum "sim-user-op-unknown" {
        value 6;
        description
          "Cellular modem SIM user operation is in Unknown state";
        tailf:code-name "ENUM_cellwan_sim_user_op_CELLWAN_SIM_USER_OP_UNKNOWN";
      }
    }
    description
      "Cellular modem SIM user operation status";
  }

  typedef cwan-gps-feature-state {
    type enumeration {
      enum "gps-disabled" {
        value 0;
        description
          "Cellular modem GPS feature state is Disabled";
        tailf:code-name "ENUM_cwan_gps_feature_state_CELLWAN_GPS_DISABLED";
      }
      enum "gps-enabled" {
        value 1;
        description
          "Cellular modem GPS feature state is Enabled";
        tailf:code-name "ENUM_cwan_gps_feature_state_CELLWAN_GPS_ENABLED";
      }
    }
    description
      "Cellular modem GPS feature state status";
  }

  typedef cwan-gps-port-selected {
    type enumeration {
      enum "dedicated-gps-port" {
        value 0;
        description
          "Cellular modem dedicated GPS port selected";
        tailf:code-name "ENUM_cwan_gps_port_selected_CELLWAN_DEDICATED_GPS_PORT";
      }
      enum "div-gps-port" {
        value 1;
        description
          "Cellular modem DIV port selected for GPS";
        tailf:code-name "ENUM_cwan_gps_port_selected_CELLWAN_DIV_GPS_PORT";
      }
      enum "voltage-no-bias-gps-port" {
        value 2;
        description
          "Cellular modem voltage no-bias port selected for GPS";
        tailf:code-name "ENUM_cwan_gps_port_selected_CELLWAN_VOLTAGE_NO_BIAS_GPS_PORT";
      }
      enum "gps-port-none" {
        value 3;
        description
          "Cellular modem none port selected for GPS";
        tailf:code-name "ENUM_cwan_gps_port_selected_CELLWAN_GPS_PORT_NONE";
      }
    }
    description
      "Cellular modem GPS port selection status";
  }

  typedef cwan-gps-state {
    type enumeration {
      enum "gps-state-disabled" {
        value 1;
        description
          "Cellular modem is in GPS disabled state";
        tailf:code-name "ENUM_cwan_gps_state_CELLWAN_GPS_STATE_DISABLED";
      }
      enum "gps-state-acquiring" {
        value 2;
        description
          "Cellular modem is in GPS acquiring state";
        tailf:code-name "ENUM_cwan_gps_state_CELLWAN_GPS_ACQUIRING";
      }
      enum "gps-state-enabled" {
        value 3;
        description
          "Cellular modem is in GPS enabled state";
        tailf:code-name "ENUM_cwan_gps_state_CELLWAN_GPS_STATE_ENABLED";
      }
      enum "gps-loc-error" {
        value 4;
        description
          "Cellular modem is in GPS location error state";
        tailf:code-name "ENUM_cwan_gps_state_CELLWAN_GPS_LOC_ERROR";
      }
    }
    description
      "Cellular modem GPS state";
  }

  typedef cwan-gps-mode-selected {
    type enumeration {
      enum "gps-mode-disable" {
        value 0;
        description
          "Cellular modem GPS mode is disabled";
        tailf:code-name "ENUM_cwan_gps_mode_selected_CELLWAN_GPS_MODE_DISABLE";
      }
      enum "gps-mode-standalone" {
        value 1;
        description
          "Cellular modem GPS mode is standalone";
        tailf:code-name "ENUM_cwan_gps_mode_selected_CELLWAN_GPS_MODE_STANDALONE";
      }
      enum "gps-mode-mbased" {
        value 2;
        description
          "Cellular modem GPS mode is ms-based";
        tailf:code-name "ENUM_cwan_gps_mode_selected_CELLWAN_GPS_MODE_MSBASED";
      }
      enum "gps-mode-msassist" {
        value 3;
        description
          "Cellular modem GPS mode is ms-assist";
        tailf:code-name "ENUM_cwan_gps_mode_selected_CELLWAN_GPS_MODE_MSASSIST";
      }
    }
    description
      "Cellular modem GPS mode selection status";
  }

  grouping cellwan-hardware-entry {
    description
      "Cellular modem hardware status entry details";
    leaf cellular-interface {
      type string;
      description
        "Cellular interface";
    }
    leaf cellular-firmware-version {
      type string;
      description
        "Cellular Modem firmware version";
    }
    leaf cellular-firmware-build-time {
      type string;
      description
        "Cellular Modem firmware build time";
    }
    leaf cellular-hardware-version {
      type string;
      description
        "Cellular Modem hardware version";
    }
    leaf cellular-device-model {
      type string;
      description
        "Cellular Modem device model type";
    }
    leaf cellular-imsi {
      type string;
      description
        "Cellular Modem IMSI";
    }
    leaf cellular-imei {
      type string;
      description
        "Cellular Modem IMEI";
    }
    leaf cellular-iccid {
      type string;
      description
        "Cellular Modem ICCID";
    }
    leaf cellular-msisdn {
      type string;
      description
        "Cellular Modem MSISDN";
    }
    leaf cellular-fsn {
      type string;
      description
        "Cellular Modem FSN";
    }
    leaf cellular-modem-status {
      type cellwan-ios-xe-oper:modem-status;
      description
        "Cellular Modem Status";
    }
    leaf cellular-modem-temperature {
      type int16;
      description
        "Cellular Modem temperature";
    }
    leaf cellular-pri-skuid {
      type string;
      description
        "Cellular Modem PRI sku id";
    }
    leaf cellular-pri-version {
      type string;
      description
        "Cellular Modem PRI version";
    }
    leaf cellular-carrier {
      type string;
      description
        "Cellular Modem carrier";
    }
    leaf cellular-oem-pri-version {
      type string;
      description
        "Cellular Modem OEM PRI version";
    }
  }

  grouping cellwan-radio-entry {
    description
      "Cellular modem radio status entry details";
    leaf cellular-interface {
      type string;
      description
        "Cellular interface";
    }
    leaf technology {
      type cellwan-ios-xe-oper:modem-technology;
      description
        "Cellular modem technology";
    }
    leaf radio-power-mode {
      type cellwan-ios-xe-oper:cw-radio-power-status;
      description
        "Cellular modem radio power mode";
    }
    leaf radio-rx-channel {
      type uint32;
      description
        "Cellular radio receive (Rx) channel number";
    }
    leaf radio-tx-channel {
      type uint32;
      description
        "Cellular radio transmit (Tx) channel number";
    }
    leaf radio-band {
      type uint32;
      description
        "Cellular radio band number";
    }
    leaf bandwidth {
      type cellwan-ios-xe-oper:radio-bandwidth;
      description
        "Cellular radio bandwidth in MHz";
    }
    leaf radio-rssi {
      type int16;
      description
        "Cellular RSSI - Received Signal Strength Indication in dBm";
    }
    leaf radio-rsrp {
      type int16;
      description
        "Cellular RSRP - Reference Signal Received Power in dBm";
    }
    leaf radio-rsrq {
      type int8;
      description
        "Cellular RSRQ - Reference Signal Received Quality in dB";
    }
    leaf radio-snr {
      type decimal64 {
        fraction-digits 2;
      }
      description
        "Cellular SNR - Signal to Noise Ratio in dB";
    }
    leaf radio-rat-preference {
      type cellwan-ios-xe-oper:rat-preference;
      description
        "Cellular Radio Access Technology preference";
    }
    leaf radio-rat-selected {
      type cellwan-ios-xe-oper:rat-technology;
      description
        "Cellular Radio Access Technology selected";
    }
  }

  grouping cellwan-network-entry {
    description
      "Cellular modem network status entry details";
    leaf cellular-interface {
      type string;
      description
        "Cellular interface";
    }
    leaf cellular-modem-time {
      type yang:date-and-time;
      description
        "Current Cellular modem time";
    }
    leaf radio-access-technology-selected {
      type cellwan-ios-xe-oper:rat-technology;
      description
        "Cellular Radio Access Technology selected";
    }
    leaf current-service-status {
      type cellwan-ios-xe-oper:service-status;
      description
        "Cellular network current service status";
    }
    leaf current-system-identifier {
      type uint16;
      description
        "Cellular modem current system identifier";
    }
    leaf current-network-identifier {
      type uint16;
      description
        "Cellular modem current network identifier";
    }
    leaf current-service-type {
      type cellwan-ios-xe-oper:modem-service;
      description
        "Cellular network current service type";
    }
    leaf current-roaming-status {
      type string;
      description
        "Cellular network current roaming status";
    }
    leaf network-selection-mode {
      type string;
      description
        "Cellular network selection mode";
    }
    leaf network-name {
      type string;
      description
        "Cellular current network name";
    }
    leaf mobile-country-code {
      type uint16;
      description
        "Cellular network mobile country code";
    }
    leaf mobile-network-code {
      type uint16;
      description
        "Cellular modem mobile network code";
    }
    leaf packet-switch-domain-state {
      type string;
      description
        "Cellular packet switched (PS) domain state";
    }
    leaf lte-carrier-aggregation {
      type cellwan-ios-xe-oper:lte-ca;
      description
        "Cellular LTE carrier aggregation (CA) state";
    }
    leaf registration-state {
      type cellwan-ios-xe-oper:reg-state;
      description
        "Cellular network registration state";
    }
    leaf emm-state {
      type string;
      description
        "Cellular network EMM registration state";
    }
    leaf emm-substate {
      type string;
      description
        "Cellular network EMM sub-state";
    }
    leaf location-area-code {
      type uint16;
      description
        "Cellular network location area code";
    }
    leaf tracking-area-code {
      type uint16;
      description
        "Cellular network tracking area code";
    }
    leaf cell-id {
      type uint64;
      description
        "Cellular network cell ID";
    }
    leaf negotiated-network-mtu {
      type uint16;
      description
        "Cellular modem negotiated network MTU size";
    }
  }

  grouping cellwan-connection-entry {
    description
      "Cellular modem connection status entry details";
    leaf cellular-interface {
      type string;
      description
        "Cellular interface";
    }
    leaf active-profile {
      type uint64;
      description
        "Cellular modem active profile number";
    }
    leaf cellular-packet-status {
      type cellwan-ios-xe-oper:packet-sess-status;
      description
        "Cellular modem packet session status";
    }
    leaf tx-packets {
      type uint64;
      description
        "Cellular data packets transmitted";
    }
    leaf rx-packets {
      type uint64;
      description
        "Cellular data packets received";
    }
    leaf tx-bytes {
      type uint64;
      description
        "Cellular data bytes transmitted";
    }
    leaf rx-bytes {
      type uint64;
      description
        "Cellular data bytes received";
    }
    leaf ipv4-addr {
      type inet:ip-address;
      description
        "Cellular interface IPv4 Address";
    }
    leaf ipv6-addr {
      type inet:ip-address;
      description
        "Cellular interface IPv6 Address";
    }
    leaf ipv4-dns-pri {
      type inet:ip-address;
      description
        "Cellular interface primary IPv4 DNS Address";
    }
    leaf ipv4-dns-sec {
      type inet:ip-address;
      description
        "Cellular interface secondary IPv4 DNS Address";
    }
    leaf ipv6-dns-pri {
      type inet:ip-address;
      description
        "Cellular interface primary IPv6 DNS Address";
    }
    leaf ipv6-dns-sec {
      type inet:ip-address;
      description
        "Cellular interface secondary IPv6 DNS Address";
    }
    leaf scope {
      type cellwan-ios-xe-oper:profile-scope;
      description
        "Cellular interface profile IP address scope";
    }
  }

  grouping cellwan-security-entry {
    description
      "Cellular modem SIM security status entry details";
    leaf cellular-interface {
      type string;
      description
        "Cellular interface";
    }
    leaf active-sim {
      type int8;
      description
        "Cellular modem active SIM slot status";
    }
    leaf sim-num-switchover {
      type uint32;
      description
        "Cellular modem SIM switchover attempts";
    }
    leaf chv1-status {
      type cellwan-ios-xe-oper:cellwan-chv1-sim-status;
      description
        "Cellular SIM Card Holder Verification (CHV1) status";
    }
    leaf sim-status {
      type cellwan-ios-xe-oper:cellwan-sim-status;
      description
        "Cellular SIM status";
    }
    leaf sim-oper {
      type cellwan-ios-xe-oper:cellwan-sim-user-op;
      description
        "Cellular SIM user operation";
    }
    leaf num-retries {
      type int8;
      description
        "Cellular SIM number of CHV1 retries remaining";
    }
  }

  grouping cellwan-sms-entry {
    description
      "Cellular modem SMS entry details";
    leaf cellular-interface {
      type string;
      description
        "Cellular interface";
    }
    leaf in-sms-count {
      type uint16;
      description
        "Number of incoming SMS stored in Cellular modem";
    }
    leaf in-sms-archived {
      type uint16;
      description
        "Number of incoming SMS archived in Cellular modem";
    }
    leaf in-sms-deleted {
      type uint16;
      description
        "Number of incoming SMS deleted in Cellular modem";
    }
    leaf in-sms-max {
      type uint16;
      description
        "Number of SIM/modem SMS record allocated";
    }
    leaf in-sms-used {
      type uint16;
      description
        "Number of SIM/modem SMS record used";
    }
    leaf sms-callback-count {
      type uint16;
      description
        "Number of SMS triggered data callback";
    }
    leaf in-sms-arch-count {
      type uint16;
      description
        "Number of successful archive on in SMS";
    }
    leaf in-sms-arch-error-count {
      type uint16;
      description
        "Number of failed archive on in SMS";
    }
    leaf out-sms-count {
      type uint16;
      description
        "Number of outgoing SMS successfully sent";
    }
    leaf out-sms-error-count {
      type uint16;
      description
        "Number of outgoing SMS send failure";
    }
    leaf out-sms-pending {
      type uint16;
      description
        "Number of outgoing SMS pending";
    }
    leaf out-sms-arch-count {
      type uint16;
      description
        "Number of successful archive out in SMS";
    }
    leaf out-sms-arch-error-count {
      type uint16;
      description
        "Number of failed archive on out SMS";
    }
  }

  grouping cellwan-gps-entry {
    description
      "Cellular modem GPS status entry details";
    leaf cellular-interface {
      type string;
      description
        "Cellular interface";
    }
    leaf gps-feature-state {
      type cellwan-ios-xe-oper:cwan-gps-feature-state;
      description
        "Cellular modem GPS feature state status";
    }
    leaf port-selected {
      type cellwan-ios-xe-oper:cwan-gps-port-selected;
      description
        "Cellular modem GPS port selection status";
    }
    leaf state {
      type cellwan-ios-xe-oper:cwan-gps-state;
      description
        "Cellular modem GPS state status";
    }
    leaf mode-selected {
      type cellwan-ios-xe-oper:cwan-gps-mode-selected;
      description
        "Cellular modem GPS mode selection status";
    }
    leaf latitude {
      type string;
      description
        "Cellular modem GPS latitude details";
    }
    leaf longitude {
      type string;
      description
        "Cellular modem GPS longitude details";
    }
    leaf timestamp {
      type yang:date-and-time;
      description
        "Cellular modem GPS timestamp details";
    }
  }

  container cellwan-oper-data {
    config false;
    description
      "Cellwan operational data";
    tailf:callpoint "ios-emul-oper-db";
    tailf:meta-data "callpoint" {
      tailf:meta-value "ios-emul-oper-db";
    }
    tailf:meta-data "greenprefix" {
      tailf:meta-value "/services;serviceName=ios_emul_oper";
    }
    tailf:meta-data "emulated" {
      tailf:meta-value "true";
    }
    list cellwan-hardware {
      key "cellular-interface";
      description
        "Cellwan modem hardware data";
      uses cellwan-ios-xe-oper:cellwan-hardware-entry;
    }
    list cellwan-radio {
      key "cellular-interface";
      description
        "Cellwan modem radio data";
      uses cellwan-ios-xe-oper:cellwan-radio-entry;
    }
    list cellwan-network {
      key "cellular-interface";
      description
        "Cellwan modem network data";
      uses cellwan-ios-xe-oper:cellwan-network-entry;
    }
    list cellwan-connection {
      key "cellular-interface";
      description
        "Cellwan modem connection data";
      uses cellwan-ios-xe-oper:cellwan-connection-entry;
    }
    list cellwan-security {
      key "cellular-interface";
      description
        "Cellwan modem sim security data";
      uses cellwan-ios-xe-oper:cellwan-security-entry;
    }
    list cellwan-sms {
      key "cellular-interface";
      description
        "Cellwan modem sms data";
      uses cellwan-ios-xe-oper:cellwan-sms-entry;
    }
    list cellwan-gps {
      key "cellular-interface";
      description
        "Cellwan modem gps data";
      uses cellwan-ios-xe-oper:cellwan-gps-entry;
    }
  }

  grouping __yangpp_metadata {
    description
      "Internal metadata for this module and imported modules";
    leaf json-metadata-leaf {
      type empty;
      description
        "Hidden internal leaf that holds this module's metadata";
      tailf:hidden "full";
      tailf:meta-data "compressed" {
        tailf:meta-value "QlpoMTFBWSZTWesi1FEADn/fgEAAEAZ+ED///+q////6YAjrrah9IUoAAdjVbGg6aFBhKECTSZ6RAxANqNAB6hoPU0HlBomRqm9CU000yBoAMQ0yG1NAAOYBNMAmQwABMEwAAASnpQSGk0EnqfqIbU0Gj0amzVNpNMmQA5gE0wCZDAAEwTAAABEoIAI0Q1IjQAAGjCMgC+4Tu9tjFjCsfVj3MKbFBbXrYQfba9B5rwRwwFuWQ9FgJqqCCUKpz97INZEAzAgDDHI1xY/hkRahemc6Uuw3XxjOeEcdRXo9fKHphDw9MtC9jkg9+HqEl0aFIKMzynEHrWQ7VgN2kYqIJUrTp4OyPEAzA4UksVfnz+UnOfjH5WqURVpdgIQjHG0tPxv16L+pAAHvUCMaKoUpaKAieXPqoADtflsTkrYkrstca4Gojo0QkFMjNLo1SGZiRVJlXaNTdMWxJltdn06TmkOfpmV2TP+XuXpV2RjGVrVLa5pLljgy95Re/s5cpyt5zDXU0ChBJRJWydCqqopN0ddb3q80bKMqt5Ol2UGA/2uuqlwK3EOvr42xn/i00L2rXnosxog+CCKxphgWoA70TmYdipmWlaV5tdd3VvGYSpvJ7nxHxQT71LKEIWLCWtYkXEZ2UFAerkq0jmEVr0H5KsrJ9zbw7aqqv22Pdt3Hdpt79mgH1/cIAatePt1PqyNYK672YdpJFKfTYDON/pWh0T+uu1Q5ZAjCnkQAiFdziinZBm4asKV3LUYl9sPAaGmKBIhUvmHnWjkMggYN9FWydkeGkN0dQL96TLIDzD6t7DaJr0Eu/LovzdZtoKv8a1DCXMqcJx3PvsqTjo1rkpyIAWpVQ+I3Gz26lbejH0zexbVzz7KZARcoYzLdtilwxNGkkZSiEIBqhGwFJzBGiWTyXOJoHENbHVUrRdc8eNUBMJRNg+gqA0Umo0VkSRPA+tPInwewG/EeeT2BN8Q00x+L3jxifPXFV5++gXPh5Ob5hh4be2a0Qhxl2J2Wh3wk4zEANjfEsQmMdYgHsfCHQIBfv2A5iZZG0FSYUNmoDosjJCSZReTCLZrcpaQDEsEJXGtW1qF0LFx9IQLWL1KmCOERqBFUKEQaD1o7Ae4CWT3828NLGj1Uqvfth0O2Rtbib4KUQ2b0MFpQoA89ktDqG7UKwDcqfI2khQHUgOJ5d4LgaRO0omCrOfHGZeXKA2IU6jfE3+C27LJP2fNK1EkVwvNptS+YcmxqjN/FBMlhrATw69zIuZaUxQDoUqF0NCzaKnGoyScZ0awgQAgRIQOLbG9Jt1W3m6AcGtYg6lzElMEG1wqQF8gUwDWYd3JuK65ptrOcKFy0+/TAxANFNzqVXkQoBAdulNMjUzqlDbN3EldBACiFlIBga0qhrH5q/R1zxnkkVPnKt1zsMB1nAObxOAwAC+Gt55bgD3hebHxsFJEQMMq6mSebEtrm18M8mk1kObhMrsm4DTsxasLhV2xjGVaqW1zSX9bfgkxjIWQKaxjx8fa+M0K7DLXmaBQgkokraTXda1OsSTpVVZCTGtJCUXIp1LoXD8z7rTBbgOhUqnv78b50yWkoNBCi9ycKLMaI+eQIKxmcl1S9USkdqpxMeSpmWlaV4tddnMLxmHwBM+z8/rzXl953Z/RVpHuhFa5T9qSyrVEz4GiZmpdY7zT2uIiJXQfU4yoNllNhPYAPN6F9rtOxTF+2orv468gb2PslKL0Vft1wx2C4c9NIEL0KiVrr3Qa7nFAuxMx3exXGhWjEw40sgSIbHtWVtknttqIFTag0wcNVWoX6R7JXhHeBoBp1w+G9hsE29BLuKOc6KlK0ybxAhFvEpLAMMQpEpWHcmW/sYoNv+O4XhYwkOafHE+6skJ2nY1yU25bqHxG44YR795a/ow9MwaAd15wMN2mmOCmULThytgnogegtU6aPpOKT4yyuwPSxgSY02HwrIkiFBGKTsPnTuJ7mvgDijzydAmuIaaY+97z1C6ok6Cd7w8R5mScKiNAbqQ3qSaojkCWQmKSm/IjY6xk78GTzXEIYx3nuEYAz3PSHD4voA3WRkhJKxfCPXfPSGMATIaa14e5WLhYCxCFTFbtuha6gZMAjbNrVe8MUFzBR6QtYvSxDzs6zz4LrWhQBrfsB6ATJPV8G+LW55i0OqHfrDyO29epxs4KVQ7XJE8dJlDzCgUgHg44PkZSQrRgupFMj3eIL1huukAIuIDTtx50Ly5glVuQr5jhkU4+RTim5Tp8GFFs4d7viVZWaws0ggCDQsDQOYbmyOuOC+K3QhtQE8O3czLmelMhA6FKhdDQs20VONDWkz6re/bWaVoYlpt50ECxtW0CQkEaImcamRqSmKDpfyBbAOxMO7k3Fdsk/9joVAMlNjqdkYBECy5nPSmuZUzqlDvi7id6urZCincDI3tZAxaQdGfAmGdNCCoiDCcomv+VLvfIKX/4u5IpwoSHWRaii";
      }
      tailf:meta-data "uncompressed_size" {
        tailf:meta-value "7433";
      }
    }
  }

  container schema-metadata-Cisco-IOS-XE-cellwan-oper {
    description
      "Hidden internal container used for metadata";
    tailf:hidden "full";
    uses __yangpp_metadata;
  }
  container gnmi-model-data {
    description
      "This container makes accessible the information necessary to respond to a GNMI Capabilities RPC";
    tailf:hidden "full";
    tailf:meta-data "module-name" {
      tailf:meta-value "Cisco-IOS-XE-cellwan-oper";
    }
    tailf:meta-data "organization" {
      tailf:meta-value "Cisco Systems, Inc.";
    }
    tailf:meta-data "semver" {
      tailf:meta-value "2019-05-01";
    }
  }
}
