module Cisco-IOS-XE-atm {
  yang-version 1.1;
  namespace "http://cisco.com/ns/yang/Cisco-IOS-XE-atm";
  prefix ios-atm;

  import cisco-semver {
    prefix cisco-semver;
  }
  import ietf-inet-types {
    prefix inet;
  }
  import Cisco-IOS-XE-l2vpn {
    prefix ios-l2vpn;
  }
  import Cisco-IOS-XE-native {
    prefix ios;
  }
  import Cisco-IOS-XE-pppoe {
    prefix ios-pppoe;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native ATM Interfaces Yang model.
     Copyright (c) 2020 by Cisco Systems, Inc.
     All rights reserved.";

  revision 2022-11-01 {
    description
      "- Update yang-version to 1.1";
    cisco-semver:module-version "2.2.0";
  }
  revision 2020-11-01 {
    description
      "When condition is added in protocol ppp
       - pppoe-client support added for encapsulation
       - Added default condition for enable-ilmi-trap leaf";
    cisco-semver:module-version "2.1.0";
  }
  revision 2020-07-01 {
    description
      "Virtual template range is added, is same as IOS";
    cisco-semver:module-version "2.0.0";
  }
  revision 2019-07-01 {
    description
      "Establish semantic version baseline";
    cisco-semver:module-version "1.0.0";
  }
  revision 2018-05-19 {
    description
      "Enhancement for vbr-rt";
  }
  revision 2018-04-30 {
    description
      "Enhancement for oam-retry, service-policy";
  }
  revision 2018-04-19 {
    description
      "Enhancements done to ATM as part of CSCvh91982 & CSCvj06187";
  }
  revision 2018-04-17 {
    description
      "imported pppoe groupings";
  }
  revision 2018-03-28 {
    description
      "Enhancements for configuring PVCs under ATM";
  }
  revision 2017-02-07 {
    description
      "Initial revision";
  }

  grouping config-interface-atm-grouping {
    container ip {
      description
        "IP address";
      leaf address {
        type inet:ipv4-address;
      }
      leaf split-horizon {
        type empty;
      }
    }
    container atm {
      description
        "ATM";
      leaf bandwidth {
        description
          "ATM bandwith";
        type enumeration {
          enum dynamic;
        }
      }
      leaf enable-ilmi-trap {
        description
          "Enable-ilmi-trap";
        type boolean;
        default "false";
      }
      leaf ilmi-keepalive {
        description
          "Keepalive polling configuration";
        type empty;
      }
      leaf route-bridged {
        description
          "Route IP/IPv6 over RFC 1483 Ethernet";
        type enumeration {
          enum ip;
          enum ipv6;
        }
      }
      list pvp {
        description
          "PVP";
        key "pvp-number";
        leaf pvp-number {
          description
            "PVP number";
          type uint16;
        }
        leaf l2transport {
          type empty;
        }
        uses ios-l2vpn:config-interface-efp-xconnect-grouping;
      }
    }
    leaf load-interval {
      description
        "Load interval";
      type uint32;
    }
    leaf cdp {
      type enumeration {
        enum enable;
      }
    }
    list cem {
      description
        "CEM";
      key "number";
      leaf number {
        type uint32;
      }
      uses ios-l2vpn:config-interface-efp-xconnect-grouping;
    }
    list pvc {
      description
        "PVC";
      key "local-vpi-vci";
      leaf local-vpi-vci {
        description
          "Vpi and vci";
        type string;
      }
      leaf remote-vpi-vci {
        description
          "Vpi and vci";
        type string;
      }
      leaf l2transport {
        type empty;
      }
      leaf ubr {
        description
          "UBR";
        type uint32;
      }
      container ubrplus {
        leaf PCR {
          type uint32;
        }
        leaf MCR {
          type uint32;
        }
      }
      leaf cbr {
        description
          "CBR";
        type uint32;
      }
      leaf vbr {
        description
          "VBR";
        type uint32;
      }
      container vbr-rt {
        description
          "Enter Variable Bit Rate (pcr)(average)";
        leaf PCR {
          description
            "Peak Cell Rate in Kbps";
          type uint32 {
            range "48..25000";
          }
        }
        leaf ACR {
          description
            "Average cell rate in kbps";
          type uint32;
        }
        leaf Burst-cell-size {
          description
            " Burst cell size in number of cells";
          type uint32 {
            range "1..65535";
          }
        }
      }
      container vbr-nrt {
        leaf PCR {
          description
            "Peak Cell Rate(PCR) in Kbps";
          type uint32 {
            range "48..25000";
          }
        }
        leaf SCR {
          description
            "Sustainable Cell Rate(SCR) in Kbps";
          type uint32;
        }
        leaf MCR {
          description
            "Maximum Burst Size(MBS) in Cells";
          type uint32 {
            range "1..65535";
          }
        }
      }
      container oam-pvc {
        presence "true";
        description
          "Send oam cells on this pvc";
        leaf loopback-frequency {
          description
            "OAM loopback frequency(seconds)";
          type uint32 {
            range "0..600";
          }
        }
        container manage {
          presence "true";
          description
            "Enable VC management";
          leaf loopback-freq {
            description
              " OAM loopback frequency(seconds)";
            type uint32 {
              range "0..600";
            }
          }
        }
      }
      container oam {
        description
          "Configure oam parameters";
        container retry {
          presence "true";
          leaf retry-count-UP {
            description
              "OAM retry count before declaring a VC is up";
            type uint32 {
              range "1..600";
            }
          }
          leaf retry-count-DOWN {
            description
              "OAM retry count before declaring a VC is down";
            type uint32 {
              range "1..600";
            }
          }
          leaf retry-poll-freq {
            description
              "OAM retry polling frequency";
            type uint32 {
              range "1..1000";
            }
          }
        }
      }
      container pvc-encapsulation {
        description
          "pvc encapsulation types";
        choice encapsulation-choice {
          container aal5autoppp {
            description
              "Cisco AUTO PPP over AAL5 Encapsulation";
            leaf Virtual-Template {
              description
                "Virtual-Template interface number";
              type uint32 {
                range "0..4095";
              }
            }
          }
          container aal5ciscoppp {
            description
              "Cisco PPP over AAL5 Encapsulation";
            leaf Virtual-Template {
              description
                "Virtual-Template interface number";
              type uint32 {
                range "0..4095";
              }
            }
          }
          container aal5mux {
            description
              "AAL5+MUX Encapsulation";
            container ppp {
              description
                "VC MUX PPP over AAL5 Encapsulation";
              choice ppp {
                leaf Virtual-Template {
                  description
                    "Virtual-Template interface number";
                  type uint32 {
                    range "0..4095";
                  }
                }
                leaf dialer {
                  description
                    "pvc is part of dialer profile";
                  type empty;
                }
              }
            }
            leaf pppoe-client {
              description
                "PPPoE client over ATM";
              type empty;
            }
            leaf ip {
              description
                "IP";
              type empty;
            }
          }
          leaf aal5nlpid {
            description
              "AAL5+NLPID Encapsulation";
            type empty;
          }
          leaf aal5snap {
            description
              "AAL5+LLC/SNAP Encapsulation";
            type empty;
          }
        }
      }
      container encapsulation {
        status deprecated;
        description
          "encapsulation type for pvc, has been DEPRECATED.
           Use pvc-encapsulation container";
        container aal5autoppp {
          status deprecated;
          description
            "Cisco AUTO PPP over AAL5 Encapsulation";
          leaf Virtual-Template {
            status deprecated;
            description
              "Virtual-Template interface number";
            type uint32;
          }
        }
        container aal5ciscoppp {
          status deprecated;
          description
            "Cisco PPP over AAL5 Encapsulation";
          leaf Virtual-Template {
            status deprecated;
            description
              "Virtual-Template interface number";
            type uint32;
          }
        }
        container aal5mux {
          status deprecated;
          description
            "AAL5+MUX Encapsulation";
          container ppp {
            status deprecated;
            description
              "VC MUX PPP over AAL5 Encapsulation";
            leaf Virtual-Template {
              status deprecated;
              description
                "Virtual-Template interface number";
              type uint32 {
                range "0..4095";
              }
            }
            leaf dialer {
              status deprecated;
              description
                "pvc is part of dialer profile";
              type empty;
            }
          }
          leaf ip {
            status deprecated;
            description
              "IP";
            type empty;
          }
        }
        leaf aal5nlpid {
          status deprecated;
          description
            " AAL5+NLPID Encapsulation";
          type empty;
        }
        leaf aal5snap {
          status deprecated;
          description
            "AAL5+LLC/SNAP Encapsulation";
          type empty;
        }
      }
      container bridge-dot1q {
        description
          "Bridge packets received on vlanid1 and add dot1 header with vlanid2";
        leaf encap {
          description
            "Encapsulation of 802.1q header";
          type uint32 {
            range "1..4094";
          }
        }
      }
      container protocol {
        description
          "Map an upper layer protocol to this connection";
        container ppp {
          description
            "'protocol ppp' is only valid with AAL5 SNAP Encapsulation";
          when 'not (../../pvc-encapsulation/aal5autoppp or ../../pvc-encapsulation/aal5ciscoppp or ../../pvc-encapsulation/aal5mux or ../../pvc-encapsulation/aal5nlpid)';
          leaf Virtual-Template {
            description
              "Virtual Template interface";
            type uint32 {
              range "1..4095";
            }
          }
          leaf dialer {
            description
              "pvc is part of dialer profile";
            type empty;
          }
        }
      }
      container dialer {
        description
          "set dialer pool this pvc belongs to";
        leaf pool-member {
          description
            "Specify dialer pool membership";
          type uint16 {
            range "1..255";
          }
        }
      }
      uses ios-l2vpn:config-interface-efp-xconnect-grouping;
      uses ios-pppoe:config-pppoe-grouping;
      uses ios-pppoe:config-pppoe-client-grouping;
    }
    uses ios-pppoe:config-pppoe-session-grouping;
    uses ios-l2vpn:config-interface-efp-xconnect-grouping;
  }

  grouping config-acr-grouping {
    list acr {
      description
        "ACR";
      key "number";
      leaf number {
        type uint8;
      }
      leaf type {
        type enumeration {
          enum CH-OC3;
        }
      }
    }
  }

  augment "/ios:native/ios:interface/ios:ATM" {
    uses config-interface-atm-grouping;
  }

  augment "/ios:native/ios:interface/ios:ATM-subinterface/ios:ATM" {
    uses config-interface-atm-grouping;
  }

  augment "/ios:native/ios:interface/ios:ATM-ACR" {
    uses config-interface-atm-grouping;
  }

  augment "/ios:native/ios:interface/ios:ATM-ACRsubinterface/ios:ATM-ACR" {
    uses config-interface-atm-grouping;
  }

  augment "/ios:native/ios:interface/ios:CEM" {
    uses config-interface-atm-grouping;
  }

  augment "/ios:native/ios:interface/ios:CEM-ACR" {
    uses config-interface-atm-grouping;
  }
}
