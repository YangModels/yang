module Cisco-IOS-XE-wireless-access-point-cmd-rpc {
  yang-version 1.1;
  namespace "http://cisco.com/ns/yang/Cisco-IOS-XE-wireless-access-point-cmd-rpc";
  prefix wireless-access-point-cmd-rpc;

  import Cisco-IOS-XE-wireless-enum-types {
    prefix wireless-enum-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Copyright (c) 2019-2022 by Cisco Systems, Inc.
     All rights reserved.";

  revision 2022-11-01 {
    description
      "- Update yang-version to 1.1
       - Added support for AP geolocation RPC";
    reference
      "2.6.0";
    cisco-semver:module-version "2.6.0";
  }
  revision 2022-07-01 {
    description
      "- Modified channels for 6 Ghz Open RRM
       - Added RPC support for AP Meraki conversion
       - Slot 3 support for Open RRM RPC
       - Added RPC support for AP features
       - Added RPC support for AP TFTP downgrade and AP reset features
       - Added support for AP Upgrade RPC";
    reference
      "2.5.0";
    cisco-semver:module-version "2.5.0";
  }
  revision 2021-03-01 {
    description
      "- Added support for on-demand Office Extended AP link test
       - Modified the description of clear personal SSID";
    reference
      "2.4.0";
    cisco-semver:module-version "2.4.0";
  }
  revision 2020-11-01 {
    description
      " - Added Open RRM Tx Power set RPC
        - Added Open RRM Channel change set RPC
        - Added RPC support for AP image predownload and abort
        - Added RPC support for clear AP CAPWAP session";
    reference
      "2.3.0";
    cisco-semver:module-version "2.3.0";
  }
  revision 2020-07-01 {
    description
      "- Added AP clear predownload statistics exec command";
    reference
      "2.2.0";
    cisco-semver:module-version "2.2.0";
  }
  revision 2020-03-01 {
    description
      "- Added AP reset and other exec command support.";
    reference
      "2.1.0";
    cisco-semver:module-version "2.1.0";
  }
  revision 2019-11-01 {
    description
      "- Add mandatory constraints for mandatory inputs";
    reference
      "2.0.0";
    cisco-semver:module-version "2.0.0";
  }
  revision 2019-03-01 {
    description
      "Initial revision";
    reference
      "1.0.0";
    cisco-semver:module-version "1.0.0";
  }

  typedef ap-identifier {
    type enumeration {
      enum ap-identifier-name {
        value 0;
        description
          "AP name";
      }
      enum ap-identifier-mac-address {
        value 1;
        description
          "AP MAC address";
      }
    }
    description
      "Access point identifier";
  }

  grouping set-rad-predownload-all {
    description
      "AP Image Predownload for all";
    leaf uuid {
      type string;
      mandatory true;
      description
        "UUID for AP Image Predownload";
    }
  }

  grouping convert-ap-to-meraki {
    description
      "AP conversion from CAPWAP to Meraki mode";
    leaf force-convert {
      type boolean;
      mandatory true;
      description
        "Force convert ignoring pre validation failures";
    }
    choice alternative-choice {
      mandatory true;
      description
        "AP name or AP radio MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-ap-tags {
    description
      "Write tags to AP";
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping ap-capwap-reset {
    description
      "AP capwap session reset";
    choice alternative-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ap-reset {
    description
      "AP reset data";
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ap-image-predownload-abort {
    description
      "AP Image Predownload abort";
    leaf uuid {
      type string;
      mandatory true;
      description
        "UUID for AP Image Predownload abort";
    }
  }

  grouping image-site-filter-add {
    description
      "Add a new site to site filters for AP Upgrade";
    leaf image-name {
      type string;
      mandatory true;
      description
        "Install file name";
    }
    leaf site-name {
      type string;
      mandatory true;
      description
        "Site name";
    }
  }

  grouping image-site-filter-remove {
    description
      "Remove a site from AP upgrade site filters";
    leaf image-name {
      type string;
      mandatory true;
      description
        "Install file name";
    }
    leaf site-name {
      type string;
      mandatory true;
      description
        "Site name";
    }
  }

  grouping image-site-filter-clear {
    description
      "Clear the site filters and apply selected operation on all remaining sites. If no operation has been performed, only existing site filters are deleted.";
    leaf image-name {
      type string;
      mandatory true;
      description
        "Install file name";
    }
    leaf uuid {
      type string;
      mandatory true;
      description
        "Netconf UUID for clearing AP image site filters";
    }
  }

  grouping image-site-filter-apply {
    description
      "Apply the selected upgrade operation on all newly added sites";
    leaf image-name {
      type string;
      mandatory true;
      description
        "Install file name";
    }
    leaf uuid {
      type string;
      mandatory true;
      description
        "Netconf UUID for applying upgrade for newly added sites";
    }
  }

  grouping image-site-filter-remove-all {
    description
      "Remove all sites from AP upgrade site filters. This will only work for N+1 upgrade/move";
    leaf image-name {
      type string;
      mandatory true;
      description
        "Install file name";
    }
  }

  grouping ap-move-destination {
    description
      "Move APs to a destination controller using rolling AP upgrade";
    leaf uuid {
      type string;
      mandatory true;
      description
        "Netconf UUID for AP image move to destination";
    }
    leaf controller-name {
      type string;
      mandatory true;
      description
        "Destination controller hostname";
    }
    leaf controller-ip {
      type inet:ip-address;
      mandatory true;
      description
        "Destination controller IP address";
    }
    leaf report-name {
      type string;
      description
        "Optionally specify an existing upgrade report name from a previous upgrade to get the list of APs";
    }
  }

  grouping ap-upgrade-destination {
    description
      "Start N+1 AP image upgrade to destination";
    leaf uuid {
      type string;
      mandatory true;
      description
        "Netconf UUID for AP image upgrade to destination";
    }
    leaf controller-name {
      type string;
      mandatory true;
      description
        "Destination controller hostname";
    }
    leaf controller-ip {
      type inet:ip-address;
      mandatory true;
      description
        "Destination controller IP address";
    }
    leaf reset {
      type boolean;
      description
        "Reload the controller after upgrade operation is complete";
    }
    leaf fallback {
      type boolean;
      description
        "Move the APs back to source controller after the source controller reloads with new image";
    }
    leaf secondary-wlc-name {
      type string;
      description
        "Optionally configure secondary controller on the APs";
    }
    leaf secondary-wlc-ip {
      type inet:ip-address;
      description
        "Secondary controller IP address";
    }
    leaf tertiary-wlc-name {
      type string;
      description
        "Optionally configure tertiary controller on the APs";
    }
    leaf tertiary-wlc-ip {
      type inet:ip-address;
      description
        "Tertiary controller IP address";
    }
  }

  grouping clear-ap-personal-ssid {
    description
      "Clear local configuration of Office Extended AP";
    choice alternative-choice {
      mandatory true;
      description
        "Alternative choice between AP name and MAC address";
      case ap-identifier-name {
        leaf ap-name {
          type string;
          mandatory true;
          description
            "AP name to clear local configuration of Office Extended AP";
        }
      }
      case ap-identifier-mac-address {
        leaf mac-addr {
          type yang:mac-address;
          mandatory true;
          description
            "MAC address to clear configuration of Office Extended AP";
        }
      }
    }
  }

  grouping set-ap-reset-button {
    description
      "Set AP reset button state";
    leaf reset-button-state {
      type boolean;
      mandatory true;
      description
        "Reset button state";
    }
    choice alternative-choice {
      mandatory true;
      description
        "Alternative choice";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping set-ap-tftp-downgrade {
    description
      "Set AP TFTP downgrade";
    leaf ip-addr {
      type inet:ip-address;
      mandatory true;
      description
        "IP address";
    }
    leaf file-name {
      type string;
      mandatory true;
      description
        "File name";
    }
    choice alternative-choice {
      mandatory true;
      description
        "Alternative choice";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-ap-static-ip-enable {
    description
      "Set static IP address for AP";
    leaf ip-addr {
      type inet:ip-address;
      mandatory true;
      description
        "Enter static IP address";
    }
    leaf net-mask {
      type inet:ip-address;
      description
        "Enter subnet mask (i.e 255.255.255.0)";
    }
    leaf prefix {
      type uint32;
      description
        "Enter network prefix according to subnet mask (i.e 24)";
    }
    leaf gateway {
      type inet:ip-address;
      mandatory true;
      description
        "Enter static IP Gateway";
    }
    choice alternative-choice {
      mandatory true;
      description
        "Alternative choice between AP name and MAC address";
      case ap-identifier-name {
        leaf ap-name {
          type string;
          mandatory true;
          description
            "AP name to enable static IP configuration";
        }
      }
      case ap-identifier-mac-address {
        leaf mac-addr {
          type yang:mac-address;
          mandatory true;
          description
            "MAC address of AP to enable static IP configuration";
        }
      }
    }
  }

  grouping rad-static-ip-domain-set {
    description
      "Static IP domain configuration";
    leaf domain {
      type string;
      mandatory true;
      description
        "Domain name";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-ap-static-ip-namesrvr {
    description
      "AP static IP name server configuration";
    leaf nameserver {
      type inet:ip-address;
      mandatory true;
      description
        "Name server IP address";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping get-rad-crash-data-file {
    description
      "Starts the transfer of AP and radio crash data file from AP to controller";
    leaf opcode {
      type wireless-types:ap-rad-crash-data-file;
      mandatory true;
      description
        "Type of AP and radio crash data file";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping network-diagnostics {
    description
      "Initiate Office Extended AP link test";
    choice alternative-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping set-ap-static-ip-disable {
    description
      "Unset Cisco AP static IP address configuration";
    choice alternative-choice {
      mandatory true;
      description
        "Choice between AP name and MAC address";
      case ap-identifier-name {
        leaf ap-name {
          type string;
          mandatory true;
          description
            "AP name to disable static IP configuration";
        }
      }
      case ap-identifier-mac-address {
        leaf mac-addr {
          type yang:mac-address;
          mandatory true;
          description
            "MAC address of AP to disable static IP configuration";
        }
      }
    }
  }

  grouping set-ap-predownload {
    description
      "Instruct the AP to start image predownload";
    choice alternative-choice {
      mandatory true;
      description
        "Choice between AP name and MAC address";
      case ap-identifier-name {
        leaf ap-name {
          type string;
          mandatory true;
          description
            "AP name to perform predownload";
        }
      }
      case ap-identifier-mac-address {
        leaf mac-addr {
          type yang:mac-address;
          mandatory true;
          description
            "MAC address of AP to perform predownload";
        }
      }
    }
  }

  grouping swap-ap-image {
    description
      "Instruct the AP to swap the image";
    leaf enable {
      type boolean;
      mandatory true;
      description
        "When enabled, it is an instruction to AP to swap the current image with the backup image";
    }
    choice alternative-choice {
      mandatory true;
      description
        "Alternative choice between AP name and MAC address";
      case ap-identifier-name {
        leaf ap-name {
          type string;
          mandatory true;
          description
            "AP name to swap the current image with the backup image";
        }
      }
      case ap-identifier-mac-address {
        leaf mac-addr {
          type yang:mac-address;
          mandatory true;
          description
            "MAC address of AP to swap the current image with the backup image";
        }
      }
    }
  }

  grouping clear-ap-config {
    description
      "Clear AP config";
    leaf operation-type {
      type wireless-types:ap-clear-config-op-type;
      mandatory true;
      description
        "Clear config operation type";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping set-ap-usb {
    description
      "Enable/Disable AP USB option";
    leaf ap-usb-enable {
      type boolean;
      mandatory true;
      description
        "Enable/Disable AP USB option";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-ap-usb-override {
    description
      "Set AP USB override option";
    leaf ap-usb-override {
      type boolean;
      mandatory true;
      description
        "Override state";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-role-ap {
    description
      "Set AP role";
    leaf role {
      type wireless-types:ap-role;
      mandatory true;
      description
        "AP role to be set";
    }
    leaf rebootcheck {
      type boolean;
      mandatory true;
      description
        "Checks for the action if it is coming either from prime or from the CLI";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-ap-keepalive-state {
    description
      "AP keepalive configuration";
    leaf enable {
      type boolean;
      mandatory true;
      description
        "Enable/Disable";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-open-rrm-tx-power-auto {
    description
      "Configure Open RRM TX Power Parameters";
    leaf slot-id {
      type uint8;
      mandatory true;
      description
        "Slot ID for the Radio to which TX Power has to be applied";
    }
    leaf band {
      type wireless-enum-types:enm-radio-band;
      mandatory true;
      description
        "Band ID, 2.4GHz or 5 GHz of the Radio Slot, to which Tx Parameters to be changed";
    }
    leaf tx-power {
      type int8;
      units "dBm";
      description
        "Transmit Power in dBm specific to the Radio slot";
    }
    leaf power-change-reason {
      type wireless-types:tx-power-change-reason;
      mandatory true;
      description
        "Tx Power Change reason";
    }
    choice ap-identifier-choice {
      mandatory true;
      description
        "Alternative choice between AP name and Radio MAC address";
      case ap-identifier-name {
        leaf ap-name {
          type string;
          mandatory true;
          description
            "AP name that holds this radio which TX Power parameters to be changed ";
        }
      }
      case ap-identifier-mac-address {
        leaf mac-addr {
          type yang:mac-address;
          mandatory true;
          description
            "Radio MAC address of AP to which TX Power parameters to be changed";
        }
      }
    }
  }

  grouping set-open-rrm-channel-auto {
    description
      "Configure Open RRM Channel Parameters";
    leaf slot-id {
      type uint8 {
        range "0..3";
      }
      mandatory true;
      description
        "Slot ID for the Radio to which channel change has to be applied";
    }
    leaf band {
      type wireless-enum-types:enm-radio-band;
      mandatory true;
      description
        "Band ID, 2.4GHz, 5 GHz or 6 Ghz of the Radio Slot, to which channel has to be changed";
    }
    leaf primary-chan {
      type uint8 {
        range "0..233";
      }
      mandatory true;
      description
        "channel number to be applied";
    }
    leaf extension-chan {
      type uint8 {
        range "0..233";
      }
      mandatory true;
      description
        "Extension channel number when the channel width is greater than 20MHz channel";
    }
    leaf curr-cost-metric {
      type int8 {
        range "-128..127";
      }
      mandatory true;
      description
        "DCA cost metric for the current channel";
    }
    leaf new-cost-metric {
      type int8 {
        range "-128..127";
      }
      mandatory true;
      description
        "DCA cost metric for the new channel";
    }
    leaf secondary-chan-1 {
      type uint8 {
        range "0..233";
      }
      mandatory true;
      description
        "Extended 40MHz third channel when the channel width is greater than 40MHz channel";
    }
    leaf secondary-chan-2 {
      type uint8;
      mandatory true;
      description
        "Extended 40MHz fourth channel when the channel width is greater than 40MHz channel";
    }
    leaf chan-width {
      type wireless-enum-types:rrm-chan-width;
      mandatory true;
      description
        "Channel width number 20 for 20MHz, 40 for 40MHz, 80 for 80MHz, 160 for 160 MHz and 188 for 80 plus 80MHz";
    }
    leaf second-best-chan {
      type uint8 {
        range "0..233";
      }
      mandatory true;
      description
        "Second best channel number as recommended by DCA";
    }
    leaf second-best-width {
      type wireless-enum-types:rrm-chan-width;
      mandatory true;
      description
        "Second best channel width number 20 for 20MHz, 40 for 40MHz, 80 for 80MHz, 160 for 160 MHz and 188 for 80 plus 80MHz";
    }
    leaf second-best-metric {
      type int8 {
        range "-128..127";
      }
      mandatory true;
      description
        "DCA Cost metric for the second best channel";
    }
    leaf is-redundant {
      type boolean;
      mandatory true;
      description
        "is Radio redundant";
    }
    leaf rrf-metric {
      type uint8 {
        range "0..100";
      }
      mandatory true;
      description
        "Radios's coverage overlap rate(%) by FRA, 0 to 100";
    }
    leaf rrf-contributing {
      type boolean;
      mandatory true;
      description
        "Radio is contributing to redundant radio";
    }
    leaf dca-chan-width {
      type wireless-enum-types:rrm-chan-width;
      mandatory true;
      description
        "Configured RRM DCA Channel width number 20 for 20MHz, 40 for 40MHz, 80 for 80MHz, 160 for 160 MHz and 188 for 80 plus 80MHz";
    }
    leaf slave-chan {
      type uint16 {
        range "0..233";
      }
      mandatory true;
      description
        "The current channel of the slave radio";
    }
    leaf slave-metric {
      type int8 {
        range "-128..127";
      }
      mandatory true;
      description
        "DCA cost metric of the slave channel";
    }
    choice ap-identifier-choice {
      mandatory true;
      description
        "Alternative choice between AP name and Radio MAC address";
      case ap-identifier-name {
        leaf ap-name {
          type string;
          mandatory true;
          description
            "AP name that holds this radio to which channel parameters to be changed ";
        }
      }
      case ap-identifier-mac-address {
        leaf mac-addr {
          type yang:mac-address;
          mandatory true;
          description
            "Radio MAC address of AP to which channel parameters to be changed";
        }
      }
    }
  }

  grouping set-lrad-geolocation-height {
    description
      "Set AP geolocation height and uncertainty";
    leaf height {
      type int16 {
        range "-100 .. 1000";
      }
      units "meters";
      mandatory true;
      description
        "AP geolocation height";
    }
    leaf height-uncertainty {
      type uint16 {
        range "0 .. 100";
      }
      units "meters";
      mandatory true;
      description
        "AP geolocation height uncertainty";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping clear-lrad-geolocation-height {
    description
      "Clear AP geolocation height and uncertainty";
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  grouping set-lrad-geolocation-gnss {
    description
      "Set AP GNSS configuration";
    leaf cable-len {
      type uint16 {
        range "1 .. 100";
      }
      units "meters";
      mandatory true;
      description
        "AP GNSS external antenna cable length";
    }
    choice alternative-choice {
      mandatory true;
      description
        "Alternative choice between AP name and MAC address";
      case ap-identifier-name {
        leaf ap-name {
          type string;
          mandatory true;
          description
            "AP name";
        }
      }
      case ap-identifier-mac-address {
        leaf mac-addr {
          type yang:mac-address;
          mandatory true;
          description
            "AP radio MAC address";
        }
      }
    }
  }

  rpc set-rad-predownload-all {
    description
      "AP Image Predownload for all";
    input {
      uses wireless-access-point-cmd-rpc:set-rad-predownload-all;
    }
  }

  rpc convert-ap-to-meraki {
    description
      "AP conversion from CAPWAP to Meraki mode";
    input {
      uses wireless-access-point-cmd-rpc:convert-ap-to-meraki;
    }
  }

  rpc set-ap-tags {
    description
      "Write existing tags config to the AP";
    input {
      uses wireless-access-point-cmd-rpc:set-ap-tags;
    }
  }

  rpc set-rad-capwap-reset {
    description
      "Instruct the AP to reset the CAPWAP session";
    input {
      uses wireless-access-point-cmd-rpc:ap-capwap-reset;
    }
  }

  rpc ap-reset {
    description
      "AP reset";
    input {
      uses wireless-access-point-cmd-rpc:ap-reset;
    }
  }

  rpc ap-image-upgrade-dry-run {
    description
      "Run the AP image upgrade algorithm in dry-run mode";
  }

  rpc ap-image-predownload-abort {
    description
      "AP Image Predownload abort";
    input {
      uses wireless-access-point-cmd-rpc:ap-image-predownload-abort;
    }
  }

  rpc image-site-filter-add {
    description
      "Add a new site to site filters for AP Upgrade";
    input {
      uses wireless-access-point-cmd-rpc:image-site-filter-add;
    }
  }

  rpc image-site-filter-remove {
    description
      "Remove a site from AP upgrade site filters";
    input {
      uses wireless-access-point-cmd-rpc:image-site-filter-remove;
    }
  }

  rpc image-site-filter-clear {
    description
      "Clear the site filters and apply selected operation on all remaining sites. If no operation has been performed, only existing site filters are deleted.";
    input {
      uses wireless-access-point-cmd-rpc:image-site-filter-clear;
    }
  }

  rpc image-site-filter-apply {
    description
      "Apply the selected upgrade operation on all newly added sites";
    input {
      uses wireless-access-point-cmd-rpc:image-site-filter-apply;
    }
  }

  rpc image-site-filter-remove-all {
    description
      "Remove all sites from AP upgrade site filters. This will only work for N+1 upgrade/move";
    input {
      uses wireless-access-point-cmd-rpc:image-site-filter-remove-all;
    }
  }

  rpc ap-move-destination {
    description
      "Move APs to a destination controller using rolling AP upgrade";
    input {
      uses wireless-access-point-cmd-rpc:ap-move-destination;
    }
  }

  rpc ap-upgrade-destination {
    description
      "Start N+1 AP image upgrade to destination controller. Instruct all the APs to swap their image and join the given controller after reboot";
    input {
      uses wireless-access-point-cmd-rpc:ap-upgrade-destination;
    }
  }

  rpc clear-ap-personal-ssid {
    description
      "Clear local configuration of Office Extended AP";
    input {
      uses wireless-access-point-cmd-rpc:clear-ap-personal-ssid;
    }
  }

  rpc set-ap-reset-button {
    description
      "Set AP reset button state";
    input {
      uses wireless-access-point-cmd-rpc:set-ap-reset-button;
    }
  }

  rpc set-ap-tftp-downgrade {
    description
      "Set AP TFTP downgrade";
    input {
      uses wireless-access-point-cmd-rpc:set-ap-tftp-downgrade;
    }
  }

  rpc set-ap-static-ip-enable {
    description
      "Configure static IP address for AP";
    input {
      uses wireless-access-point-cmd-rpc:set-ap-static-ip-enable;
    }
  }

  rpc rad-static-ip-domain-set {
    description
      "Set static IP domain name";
    input {
      uses wireless-access-point-cmd-rpc:rad-static-ip-domain-set;
    }
  }

  rpc set-ap-static-ip-namesrvr {
    description
      "Set static ip Name Server";
    input {
      uses wireless-access-point-cmd-rpc:set-ap-static-ip-namesrvr;
    }
  }

  rpc get-rad-crash-data-file {
    description
      "Starts the transfer of AP and radio crash data file from AP to controller";
    input {
      uses wireless-access-point-cmd-rpc:get-rad-crash-data-file;
    }
  }

  rpc network-diagnostics {
    description
      "Initiate Office Extended AP link test";
    input {
      uses wireless-access-point-cmd-rpc:network-diagnostics;
    }
  }

  rpc set-ap-static-ip-disable {
    description
      "Unset Cisco AP static IP address configuration";
    input {
      uses wireless-access-point-cmd-rpc:set-ap-static-ip-disable;
    }
  }

  rpc set-ap-predownload {
    description
      "Instruct the AP to start image predownload";
    input {
      uses wireless-access-point-cmd-rpc:set-ap-predownload;
    }
  }

  rpc swap-ap-image {
    description
      "Instruct the AP to swap the image";
    input {
      uses wireless-access-point-cmd-rpc:swap-ap-image;
    }
  }

  rpc clear-ap-config {
    description
      "Clear AP config";
    input {
      uses wireless-access-point-cmd-rpc:clear-ap-config;
    }
  }

  rpc set-ap-usb {
    description
      "AP USB data";
    input {
      uses wireless-access-point-cmd-rpc:set-ap-usb;
    }
  }

  rpc set-ap-usb-override {
    description
      "Set AP USB override";
    input {
      uses wireless-access-point-cmd-rpc:set-ap-usb-override;
    }
  }

  rpc clear-ap-predownload-statistics {
    description
      "Clear the AP predownload statistics";
  }

  rpc clear-ap-meraki-stats {
    description
      "Clear AP Meraki conversion statistics";
  }

  rpc set-role-ap {
    description
      "Set AP role";
    input {
      uses wireless-access-point-cmd-rpc:set-role-ap;
    }
  }

  rpc set-ap-keepalive-state {
    description
      "Set AP keepalive state";
    input {
      uses wireless-access-point-cmd-rpc:set-ap-keepalive-state;
    }
  }

  rpc set-open-rrm-tx-power-auto {
    description
      "Configure Open RRM Tx Power Parameters for AP Radio";
    input {
      uses wireless-access-point-cmd-rpc:set-open-rrm-tx-power-auto;
    }
  }

  rpc set-open-rrm-channel-auto {
    description
      "Configure Open RRM Channel Parameters for AP Radio";
    input {
      uses wireless-access-point-cmd-rpc:set-open-rrm-channel-auto;
    }
  }

  rpc ap-image-upgrade-abort {
    description
      "Abort the current AP upgrade algorithm";
  }

  rpc set-lrad-geolocation-height {
    description
      "Set AP height";
    input {
      uses wireless-access-point-cmd-rpc:set-lrad-geolocation-height;
    }
  }

  rpc clear-lrad-geolocation-height {
    description
      "Clear AP height";
    input {
      uses wireless-access-point-cmd-rpc:clear-lrad-geolocation-height;
    }
  }

  rpc set-lrad-geolocation-gnss {
    description
      "Set AP GNSS parameters";
    input {
      uses wireless-access-point-cmd-rpc:set-lrad-geolocation-gnss;
    }
  }
}
