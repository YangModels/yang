module Cisco-IOS-XE-endpoint-tracker-events {
  yang-version 1.1;
  namespace "http://cisco.com/ns/yang/Cisco-IOS-XE-endpoint-tracker-events";
  prefix endpoint-tracker-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for endpoint tracker events.
     Copyright (c) 2021-2022 by Cisco Systems, Inc.
     All rights reserved.";

  revision 2022-11-01 {
    description
      "Update yang-version to 1.1";
    reference
      "1.1.0";
    cisco-semver:module-version "1.1.0";
  }
  revision 2021-11-01 {
    description
      "Initial revision";
    reference
      "1.0.0";
    cisco-semver:module-version "1.0.0";
  }

  typedef endpoint-tracker-notif-state {
    type enumeration {
      enum tracker-notif-state-up {
        value 0;
        description
          "Tracker Notification State UP";
      }
      enum tracker-notif-state-down {
        value 1;
        description
          "Tracker Notification State DOWN";
      }
    }
    description
      "Endpoint tracker notification state";
  }

  grouping endpoint-tracker-state-change {
    description
      "Endpoint tracker state change notification";
    leaf severity-level {
      type ios-common-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf attach-point-name {
      type string;
      description
        "Attach point name";
    }
    leaf tracker-name {
      type string;
      description
        "Tracker name";
    }
    leaf new-state {
      type endpoint-tracker-ios-xe-events:endpoint-tracker-notif-state;
      description
        "New tracker state";
    }
  }

  notification tracker-state-change {
    description
      "Endpoint tracker state change notification";
    uses endpoint-tracker-ios-xe-events:endpoint-tracker-state-change;
  }
}
