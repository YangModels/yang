module Cisco-IOS-XE-utd-oper {
  yang-version 1.1;
  namespace "http://cisco.com/ns/yang/Cisco-IOS-XE-utd-oper";
  prefix utd-ios-xe-oper;

  import Cisco-IOS-XE-utd-common-oper {
    prefix utd-common-ios-xe-oper;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring Unified Threat Defense (UTD).
     Copyright (c) 2018-2020, 2022 by Cisco Systems, Inc.
     All rights reserved.";

  revision 2022-11-01 {
    description
      "Update yang-version to 1.1";
    reference
      "1.6.0";
    cisco-semver:module-version "1.6.0";
  }
  revision 2021-03-01 {
    description
      "Added Unified Threat Defense (UTD) connectivity status";
    reference
      "1.5.0";
    cisco-semver:module-version "1.5.0";
  }
  revision 2019-11-01 {
    description
      "Added Unified Threat Defense (UTD) Routing Table
       and UTD Domain Name System (DNS) Configurations";
    reference
      "1.4.0";
    cisco-semver:module-version "1.4.0";
  }
  revision 2019-05-01 {
    description
      "Added semantic version";
    reference
      "1.3.0";
    cisco-semver:module-version "1.3.0";
  }
  revision 2018-11-05 {
    description
      "- Add UTD file reputation/analysis status
       - Cleaned up spelling errors in descriptions.";
    reference
      "1.2.0";
    cisco-semver:module-version "1.2.0";
  }
  revision 2018-06-18 {
    description
      "Add UTD version status";
    reference
      "1.1.0";
    cisco-semver:module-version "1.1.0";
  }
  revision 2018-04-04 {
    description
      "Initial revision";
    reference
      "1.0.0";
    cisco-semver:module-version "1.0.0";
  }

  typedef utd-oper-status-val {
    type enumeration {
      enum utd-oper-status-unknown {
        value 0;
        description
          "Unified Threat Defense (UTD) operational status is unknown - Unable to determine status";
      }
      enum utd-oper-status-green {
        value 1;
        description
          "Unified Threat Defense (UTD) operational status is green - Working as expected";
      }
      enum utd-oper-status-yellow {
        value 2;
        description
          "Unified Threat Defense (UTD) operational status is yellow - Minor problem";
      }
      enum utd-oper-status-red {
        value 3;
        description
          "Unified Threat Defense (UTD) operational status is red - Major problem";
      }
      enum utd-oper-status-down {
        value 4;
        description
          "Unified Threat Defense (UTD) operational status is down - Communication has been lost";
      }
    }
    description
      "Unified Threat Defense (UTD) operational status";
  }

  typedef utd-file-reputation-status-states {
    type enumeration {
      enum utd-file-repu-stat-process-unknown {
        value 0;
        description
          "UTD Integration Advanced Malware Protection beaker process down";
      }
      enum utd-file-repu-stat-process-up {
        value 1;
        description
          "UTD Integration Advanced Malware Protection beaker process up";
      }
      enum utd-file-repu-stat-process-down {
        value 2;
        description
          "UTD Integration Advanced Malware Protection beaker process down";
      }
      enum utd-file-repu-stat-amp-module-load-fail {
        value 3;
        description
          "UTD Integration Advanced Malware Protection beaker AMP module load fail";
      }
      enum utd-file-repu-stat-connected {
        value 4;
        description
          "UTD Integration Advanced Malware Protection beaker connected";
      }
      enum utd-file-repu-stat-not-connected {
        value 5;
        description
          "UTD Integration Advanced Malware Protection beaker not connected";
      }
    }
    description
      "UTD Integration Advanced Malware Protection AMP status";
  }

  typedef utd-file-analysis-states {
    type enumeration {
      enum tg-client-stat-unknown {
        value 0;
        description
          "UTD Integration Advanced Malware Protection TG health status client unknown";
      }
      enum tg-client-stat-down {
        value 1;
        description
          "UTD Integration Advanced Malware Protection TG health status client down";
      }
      enum tg-client-stat-up {
        value 2;
        description
          "UTD Integration Advanced Malware Protection TG health status client up";
      }
      enum api-key-stat-not-present {
        value 3;
        description
          "UTD Integration Advanced Malware Protection TG health status apikey not present";
      }
      enum api-key-stat-invalid {
        value 4;
        description
          "UTD Integration Advanced Malware Protection TG health status apikey invalid";
      }
      enum file-upload-stat-limit-reached {
        value 5;
        description
          "UTD Integration Advanced Malware Protection TG health status file upload limit reached";
      }
    }
    description
      "UTD Integration Advanced Malware Protection TG health status";
  }

  typedef utd-con-state {
    type enumeration {
      enum utd-con-unknown {
        value 0;
        description
          "UTD Connectivity status unknown";
      }
      enum utd-con-down {
        value 1;
        description
          "UTD Connectivity status down";
      }
      enum utd-con-up {
        value 2;
        description
          "UTD Connectivity status up";
      }
    }
    description
      "UTD Connectivity status";
  }

  typedef utd-con-reason {
    type enumeration {
      enum utd-con-unknown-err {
        value 0;
        description
          "Unknown error occurred while running connectivity status";
      }
      enum utd-con-none {
        value 1;
        description
          "Connectivity test ran successfully without an error";
      }
      enum utd-con-connection-err {
        value 2;
        description
          "Connection error occurred while running connectivity status";
      }
      enum utd-con-http-err {
        value 3;
        description
          "HTTP error occurred while running connectivity status";
      }
      enum utd-con-proxy-err {
        value 4;
        description
          "Proxy error occurred while running connectivity status";
      }
      enum utd-con-ssl-err {
        value 5;
        description
          "SSL error occurred while running connectivity status";
      }
      enum utd-con-timeout-err {
        value 6;
        description
          "Timeout error occurred while running connectivity status";
      }
    }
    description
      "Reason for UTD Connectivity status to go down";
  }

  typedef utd-route-flag {
    type bits {
      bit utd-route-flag-route-up {
        position 0;
        description
          "Route is up";
      }
      bit utd-route-flag-target-is-host {
        position 1;
        description
          "Target is a host";
      }
      bit utd-route-flag-gateway-used {
        position 2;
        description
          "Route uses gateway";
      }
      bit utd-route-flag-route-reinstated {
        position 3;
        description
          "Reinstate route for dynamic routing";
      }
      bit utd-route-flag-dynamic-install {
        position 4;
        description
          "Route dynamically installed by daemon or redirect";
      }
      bit utd-route-flag-modified {
        position 5;
        description
          "Route modified from routing daemon or redirect";
      }
      bit utd-route-flag-installed-by-address-configuration {
        position 6;
        description
          "Route installed by address configuration";
      }
      bit utd-route-flag-cache-entry {
        position 7;
        description
          "Route is a cached entry";
      }
      bit utd-route-flag-route-rejected {
        position 8;
        description
          "Route Rejected";
      }
    }
    description
      "UTD route's flag description";
  }

  grouping utd-update-status {
    description
      "Unified Threat Defense (UTD) update status";
    leaf version {
      type string;
      description
        "Version";
    }
    leaf last-update-time {
      type yang:date-and-time;
      description
        "Time of last attempted update";
    }
    leaf last-update-status {
      type utd-common-ios-xe-oper:utd-update-status-val;
      description
        "Status of last attempted update";
    }
    leaf last-update-reason {
      type string;
      description
        "Reason for last attempted update failure";
    }
    leaf last-successful-update-time {
      type yang:date-and-time;
      description
        "Time of last successful update";
    }
  }

  grouping utd-ips-update-status {
    description
      "Unified Threat Defense (UTD) Intrusion Prevention System (IPS) update status";
    container ips-update-status {
      description
        "Intrusion Prevention System (IPS) update status";
      uses utd-ios-xe-oper:utd-update-status;
    }
  }

  grouping utd-urlf-update-status {
    description
      "Unified Threat Defense (UTD) URL-Filtering (URLF) update status";
    container urlf-update-status {
      description
        "URL-Filtering (URLF) update status";
      uses utd-ios-xe-oper:utd-update-status;
    }
  }

  grouping utd-engine-instance-status {
    description
      "Unified Threat Defense (UTD) engine instance status";
    leaf id {
      type uint32;
      description
        "Engine instance ID";
    }
    leaf running {
      type boolean;
      description
        "Engine instance running";
    }
    leaf status {
      type utd-ios-xe-oper:utd-oper-status-val;
      description
        "Engine instance status";
    }
    leaf reason {
      type string;
      description
        "Engine instance status reason";
    }
  }

  grouping utd-engine-status {
    description
      "Unified Threat Defense (UTD) engine status";
    leaf version {
      type string;
      description
        "Engine version";
    }
    leaf profile {
      type string;
      description
        "Profile";
    }
    leaf status {
      type utd-ios-xe-oper:utd-oper-status-val;
      description
        "Overall status";
    }
    leaf reason {
      type string;
      description
        "Overall status reason";
    }
    leaf memory-usage {
      type decimal64 {
        fraction-digits 2;
      }
      units "percent";
      description
        "Percentage of memory used";
    }
    leaf memory-status {
      type utd-ios-xe-oper:utd-oper-status-val;
      description
        "Status of memory usage";
    }
    list utd-engine-instance-status {
      key "id";
      description
        "Status of engine instances";
      uses utd-ios-xe-oper:utd-engine-instance-status;
    }
  }

  grouping utd-version-status {
    description
      "Unified Threat Defense (UTD) version status";
    leaf recommended-version {
      type string;
      description
        "Unified Threat Defense (UTD) version recommended to run";
    }
    leaf supported-regex {
      type string;
      description
        "Unified Threat Defense (UTD) version regular expression- describes version support";
    }
    leaf installed-version {
      type string;
      description
        "Unified Threat Defense (UTD) version currently installed";
    }
    leaf supported {
      type boolean;
      description
        "Unified Threat Defense (UTD) supported flag - indicates if the installed UTD version is compatible with the supported version";
    }
  }

  grouping utd-file-reputation-status {
    description
      "UTD Integration Advanced Malware Protection beaker general status";
    leaf version {
      type string;
      description
        "UTD Integration Advanced Malware Protection beaker version";
    }
    leaf status {
      type utd-ios-xe-oper:utd-file-reputation-status-states;
      description
        "UTD Integration Advanced Malware Protection beaker status";
    }
    leaf message {
      type string;
      description
        "UTD Integration Advanced Malware Protection beaker status messages";
    }
  }

  grouping utd-file-analysis-status {
    description
      "UTD Integration Advanced Malware Protection TG status";
    leaf status {
      type utd-ios-xe-oper:utd-file-analysis-states;
      description
        "UTD Integration Advanced Malware Protection TG status health status";
    }
    leaf backoff-interval {
      type uint64;
      description
        "UTD Integration Advanced Malware Protection TG status number of seconds for backoff";
    }
    leaf message {
      type string;
      description
        "UTD Integration Advanced Malware Protection TG status messages";
    }
  }

  grouping utd-route {
    description
      "Unified Threat Defense (UTD) Routing Table's individual routes";
    leaf id {
      type uint32;
      description
        "ID to distinguish the routes";
    }
    leaf destination {
      type inet:ip-address;
      description
        "The destination address or destination host";
    }
    leaf gateway {
      type inet:ip-address;
      description
        "The gateway address";
    }
    leaf genmask {
      type inet:ip-address;
      description
        "The netmask for the destination net,
         255.255.255.255 for a host destination
         and 0.0.0.0 for the default route";
    }
    leaf flags {
      type utd-ios-xe-oper:utd-route-flag;
      description
        "The route's flags";
    }
    leaf metric {
      type int16;
      description
        "The 'distance' to the target (usually counted in hops)
         It is not used by recent kernels, but may be needed by routing daemons";
    }
    leaf use {
      type int16;
      description
        "Count of lookups for the route. In our case, it is route cache misses";
    }
    leaf ref {
      type int16;
      description
        "Number of references to the route";
    }
    leaf interface {
      type string;
      description
        "Interface to which packets for this route will be sent";
    }
  }

  grouping utd-dns {
    description
      "Domain Name System (DNS) Configuration of Unified Threat Defense (UTD) Container";
    leaf domain {
      type string;
      description
        "Local domain name";
    }
    leaf-list name-server {
      type inet:ip-address;
      max-elements 32;
      ordered-by user;
      description
        "Name servers in Domain Name System (DNS) configurations";
    }
  }

  grouping utd-con-feat {
    description
      "Unified Threat Defense (UTD) connectivity feature";
    leaf status {
      type utd-ios-xe-oper:utd-con-state;
      description
        "UTD connectivity status";
    }
    leaf attempt-once {
      type empty;
      description
        "This field indicates if the connectivity status has been attempted at least once";
    }
    leaf last-attempt-time {
      when 'boolean(../attempt-once)';
      type yang:date-and-time;
      description
        "Timestamp of last UTD connectivity attempt";
    }
    leaf up-once {
      type empty;
      description
        "This field indicates if the connectivity status has been up at least once";
    }
    leaf last-up-time {
      when 'boolean(../up-once)';
      type yang:date-and-time;
      description
        "Timestamp of last successful UTD connectivity attempt";
    }
    leaf down-once {
      type empty;
      description
        "This field indicates if the connectivity status has been down at least once";
    }
    leaf last-down-time {
      when 'boolean(../down-once)';
      type yang:date-and-time;
      description
        "Timestamp of last failed UTD connectivity attempt";
    }
    leaf last-down-reason {
      when 'boolean(../down-once)';
      type utd-ios-xe-oper:utd-con-reason;
      description
        "Last known reason for the UTD connectivity status to go down";
    }
  }

  grouping utd-urlf-con {
    description
      "Unified Threat Defense (UTD) connectivity to URL-Filtering Server";
    container con-status {
      description
        "UTD connectivity status to URL-Filtering server";
      uses utd-ios-xe-oper:utd-con-feat;
    }
  }

  container utd-oper-data {
    config false;
    description
      "Unified Threat Defense (UTD) operational data";
    container utd-engine-status {
      presence "utd-engine-status";
      description
        "Unified Threat Defense (UTD) engine status";
      uses utd-ios-xe-oper:utd-engine-status;
    }
    container utd-ips-update-status {
      presence "utd-ips-update-status";
      description
        "Unified Threat Defense (UTD) Intrusion Prevention System (IPS) update status";
      uses utd-ios-xe-oper:utd-ips-update-status;
    }
    container utd-urlf-update-status {
      presence "utd-urlf-update-status";
      description
        "Unified Threat Defense (UTD) URL-Filtering (URLF) update status";
      uses utd-ios-xe-oper:utd-urlf-update-status;
    }
    container utd-version-status {
      presence "utd-version-status";
      description
        "Unified Threat Defense (UTD) version status";
      uses utd-ios-xe-oper:utd-version-status;
    }
    container utd-file-reputation-status {
      presence "utd-file-reputation-status";
      description
        "UTD Integration Advanced Malware Protection beaker status";
      uses utd-ios-xe-oper:utd-file-reputation-status;
    }
    container utd-file-analysis-status {
      presence "utd-file-analysis-status";
      description
        "UTD Integration Advanced Malware Protection TG status";
      uses utd-ios-xe-oper:utd-file-analysis-status;
    }
    list utd-route {
      key "id";
      description
        "UTD Routing Table";
      uses utd-ios-xe-oper:utd-route;
    }
    container utd-dns {
      presence "utd-dns";
      description
        "UTD Domain Name System (DNS) Configuration";
      uses utd-ios-xe-oper:utd-dns;
    }
    container utd-urlf-con {
      presence "utd-urlf-con";
      description
        "UTD container connectivity status";
      uses utd-ios-xe-oper:utd-urlf-con;
    }
  }
}
