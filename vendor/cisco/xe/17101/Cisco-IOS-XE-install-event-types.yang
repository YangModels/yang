module Cisco-IOS-XE-install-event-types {
  yang-version 1.1;
  namespace "http://cisco.com/ns/yang/Cisco-IOS-XE-install-event-types";
  prefix install-event-types-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for install status notification for image install events.
     Copyright (c) 2021-2022 by Cisco Systems, Inc.
     All rights reserved.";

  revision 2022-11-01 {
    description
      "- Update yang-version to 1.1
       - Added install sub status for deactivate SMU, install RPC, unsupported platforms, install downgrade and unsupported rollback
       - Added install sub-state enum for invalid install image, missing upgrade confirm timer and rejecting add for uncommitted sub-package
       - Added install sub-state enum for same filename used";
    reference
      "1.2.0";
    cisco-semver:module-version "1.2.0";
  }
  revision 2022-07-01 {
    description
      "- Added install sub-state enum for image downgrade and boot parameter update
       - Added support for set default install operation";
    reference
      "1.1.0";
    cisco-semver:module-version "1.1.0";
  }
  revision 2022-03-01 {
    description
      "Initial revision";
    reference
      "1.0.0";
    cisco-semver:module-version "1.0.0";
  }

  typedef installation-status {
    type enumeration {
      enum download-start {
        value 0;
        description
          "Download Start";
      }
      enum download-complete {
        value 1;
        description
          "Download Complete";
      }
      enum verification-complete {
        value 2;
        description
          "Verification Complete";
      }
      enum upgrade-apply-complete {
        value 3;
        description
          "Upgrade Apply Complete";
      }
      enum sync-partition-start {
        value 4;
        description
          "Sync Partition Start";
      }
      enum sync-partition-complete {
        value 5;
        description
          "Sync Partition Start";
      }
      enum install-complete {
        value 6;
        description
          "Install Complete";
      }
      enum install-fail {
        value 7;
        description
          "Install Fail";
      }
      enum reboot {
        value 8;
        description
          "Reboot";
      }
      enum install-start {
        value 9;
        description
          "Install Start";
      }
      enum uninstall-complete {
        value 10;
        description
          "Uninstall Complete";
      }
      enum uninstall-fail {
        value 11;
        description
          "Uninstall Fail";
      }
      enum reset-complete {
        value 12;
        description
          "Reset Complete";
      }
      enum reset-fail {
        value 13;
        description
          "Reset Fail";
      }
      enum config-commit-confirm-complete {
        value 14;
        description
          "Confirmation for configuration commit complete";
      }
      enum config-commit-confirm-fail {
        value 15;
        description
          "Confirmation for configuration commit fail";
      }
      enum rollback-complete {
        value 16;
        description
          "Rollback Complete";
      }
      enum rollback-fail {
        value 17;
        description
          "Rollback Fail";
      }
      enum download-fail {
        value 18;
        description
          "Download Fail";
      }
      enum download-success {
        value 19;
        description
          "Download Success";
      }
      enum set-default-fail {
        value 20;
        description
          "Set Default Fail";
      }
      enum set-default-success {
        value 21;
        description
          "Set Default Success";
      }
    }
    description
      "Installation Status";
  }

  typedef install-sub-state {
    type enumeration {
      enum none {
        value 0;
        description
          "None or not applicable";
      }
      enum install-adding-pkg {
        value 1;
        description
          "Install add package in progress";
      }
      enum install-expanding-pkg {
        value 2;
        description
          "Install expand package in progress";
      }
      enum install-expand-pkg-done {
        value 3;
        description
          "Install completes successful expand package";
      }
      enum install-activating-pkg {
        value 4;
        description
          "Activating package in progress";
      }
      enum install-activate-dev-boot {
        value 5;
        description
          "Activate or deactivate complete and starting device boot";
      }
      enum install-error-msg {
        value 6;
        description
          "Action failed error";
      }
      enum install-oper-invoked {
        value 7;
        description
          "Operation is invoked in install infra for the action";
      }
      enum install-inprogress {
        value 8;
        description
          "Operation is in progress";
      }
      enum install-ewc-predwnld-none {
        value 9;
        description
          "Predownload for Embedded Wireless Controller not started";
      }
      enum install-ewc-ctrl-img-dwnld-initiated {
        value 10;
        description
          "Embedded Wireless Controller - Controller image download initiated";
      }
      enum install-ewc-ctrl-img-dwnld-in-progress {
        value 11;
        description
          "Embedded Wireless Controller - Controller image download in progress";
      }
      enum install-ewc-ctrl-img-dwnld-completed {
        value 12;
        description
          "Embedded Wireless Controller - Controller image download completed";
      }
      enum install-ewc-ctrl-img-dwnld-failed {
        value 13;
        description
          "Embedded Wireless Controller - Controller image download failed";
      }
      enum install-ewc-ap-img-predwnld-initiated {
        value 14;
        description
          "Embedded Wireless Controller - AP image predownload initiated";
      }
      enum install-ewc-ap-img-predwnld-in-progress {
        value 15;
        description
          "Embedded Wireless Controller - AP image predownload in progress";
      }
      enum install-ewc-ap-img-predwnld-completed {
        value 16;
        description
          "Embedded Wireless Controller - AP image predownload completed";
      }
      enum install-ewc-ap-img-predwnld-not-supported {
        value 17;
        description
          "Embedded Wireless Controller - AP image predownload not supported";
      }
      enum install-ewc-ap-img-predwnld-failed {
        value 18;
        description
          "Embedded Wireless Controller - AP image predownload failed";
      }
      enum install-ewc-ctrl-img-predwnld-in-progress {
        value 19;
        description
          "Embedded Wireless Controller - Controller image predownload in progress";
      }
      enum install-ewc-ctrl-img-predwnld-completed {
        value 20;
        description
          "Embedded Wireless Controller - Controller image predownload completed";
      }
      enum install-ewc-ctrl-img-predwnld-failed {
        value 21;
        description
          "Embedded Wireless Controller - Controller image predownload failed";
      }
      enum install-ewc-activated {
        value 22;
        description
          "Embedded Wireless Controller - install activate successful";
      }
      enum install-ewc-activate-failed {
        value 23;
        description
          "Embedded Wireless Controller - install activate failed";
      }
      enum install-status-bundle-boot-error {
        value 24;
        description
          "Install is not allowed in bundle boot use one shot install";
      }
      enum install-status-invalid-image-file {
        value 25;
        description
          "RPC action failed because either image file specified is not present or invalid";
      }
      enum install-earlier-added-image-present {
        value 26;
        description
          "Install action detected image already installed on device with same version waiting for
           activation. Either remove this earlier installed image to install new image or use
           activate RPC action to proceed image activation";
      }
      enum install-activate-trigg-without-add {
        value 27;
        description
          "Activate image is triggered before image is installed on device.
           Use install RPC to install image and trigger activate on device";
      }
      enum install-status-no-trans-to-commit {
        value 28;
        description
          "Commit action could not find any activate transaction to commit. Either activate
           installed image first or remove installed image to start fresh Workflow";
      }
      enum install-status-activate-pend-commit {
        value 29;
        description
          "Rollback to base is not allowed while image is pending commit. Either use abort action to abort
           activated image transaction or use install rollback action to commit to go back to previous image";
      }
      enum install-status-nothing-to-rollback {
        value 30;
        description
          "No Rollback points present from the current image to rollback";
      }
      enum install-status-already-at-base {
        value 31;
        description
          "Rollback to base is not required as device is already at the base image";
      }
      enum install-remove-rejected-by-platform {
        value 32;
        description
          "Remove of the file is not allowed currently. The file is likely in use at this moment. Retry again";
      }
      enum install-status-no-trans-to-abort {
        value 33;
        description
          "There is no activate or deactivate operation detected on device that needs to be aborted.";
      }
      enum install-status-no-platform-response {
        value 34;
        description
          "Action failed due to no response from other platform or access device.
           Please check device operation status";
      }
      enum install-rem-of-activated-img-reject {
        value 35;
        description
          "Install remove can not remove activated image. Please use install commit
           to commit activated image.";
      }
      enum install-ap-img-predwnld-initiated {
        value 36;
        description
          "AP Image Predownload Initiated";
      }
      enum install-ap-img-predwnld-inprogress {
        value 37;
        description
          "AP Image Predownload is In progress";
      }
      enum install-ap-img-predwnld-complete {
        value 38;
        description
          "AP Image Predownload Completed";
      }
      enum install-ap-img-predwnld-failed {
        value 39;
        description
          "AP Image Predownload Failed";
      }
      enum install-ap-img-predwnld-abort {
        value 40;
        description
          "AP Image Predownload Aborted";
      }
      enum install-act-on-stby {
        value 41;
        description
          "Start of install activation on standby";
      }
      enum install-act-on-active {
        value 42;
        description
          "Start of install activation on active";
      }
      enum install-act-on-stby-done {
        value 43;
        description
          "Install activation on standby is completed";
      }
      enum install-act-on-active-done {
        value 44;
        description
          "Install activation on active is completed";
      }
      enum install-abort-on-stby {
        value 45;
        description
          "Start of install abort on standby";
      }
      enum install-abort-on-active {
        value 46;
        description
          "Start of install abort on active";
      }
      enum install-abort-on-stby-done {
        value 47;
        description
          "Install abort on standby is completed";
      }
      enum install-abort-on-active-done {
        value 48;
        description
          "Install abort on active is completed";
      }
      enum install-sys-precheck-failed {
        value 49;
        description
          "System does not satisfy all criteria to perform given operation";
      }
      enum install-stale-sys-upgrade-state {
        value 50;
        description
          "System is in stale state after previous failed upgrade.
           Perform abort operation and then restart upgrade";
      }
      enum install-auto-abort-failed {
        value 51;
        description
          "Auto abort operation failed because system recovery is beyond the scope of
           installation process. User needs to manually review system status and
           decide best action to bring system back to normal state. One of the reason
           for this to happen is standby keep reloading or never became online";
      }
      enum install-mcl-error {
        value 52;
        description
          "Installation failed because configuration commands on active and standby do not match.
           Installation abort will start automatically. After abort is completed, use
           following command to see list of mismatch commands - show redundancy config-sync failures historic mcl";
      }
      enum install-stby-act-role-change-failed {
        value 53;
        description
          "Failure during change of role of standby from standby to active.
           User needs to invoke installation abort";
      }
      enum install-act-to-stby-hover-failed {
        value 54;
        description
          "Failed to handover control of the installation process from active to
           standby before active reloads. User needs to invoke installation abort";
      }
      enum install-stby-up-old-sw {
        value 55;
        description
          "After restart, standby came up with old software. Installation will be aborted automatically.
           User does not need to invoke install abort";
      }
      enum install-status-no-disk-space {
        value 56;
        description
          "RPC action failed due to no disk space left on device. Please use
           install remove RPC with inactive option to clean all unused
           non active files";
      }
      enum install-ap-img-upg-initiated {
        value 57;
        description
          "AP image upgrade initiated";
      }
      enum install-ap-img-upg-in-progress {
        value 58;
        description
          "AP image upgrade is in progress";
      }
      enum install-ap-img-upg-complete {
        value 59;
        description
          "AP image upgrade completed";
      }
      enum install-ap-img-upg-failed {
        value 60;
        description
          "AP image upgrade failed";
      }
      enum install-ap-img-upg-interrupted {
        value 61;
        description
          "AP image upgrade is interrupted";
      }
      enum install-ap-img-upg-continued {
        value 62;
        description
          "AP image upgrade continued";
      }
      enum install-ap-img-upg-paused {
        value 63;
        description
          "AP image upgrade paused";
      }
      enum install-ap-img-upg-resumed {
        value 64;
        description
          "AP image upgrade resumed";
      }
      enum install-ap-img-upg-aborted {
        value 65;
        description
          "AP image upgrade aborted";
      }
      enum install-verify-pkg-start {
        value 66;
        description
          "Install package verification in progress";
      }
      enum install-verify-pkg-done {
        value 67;
        description
          "Install package verification complete";
      }
      enum install-verify-pkg-fail {
        value 68;
        description
          "Install package verification failed";
      }
      enum install-smu-add-start {
        value 69;
        description
          "SMU install is in progress";
      }
      enum install-smu-add-done {
        value 70;
        description
          "SMU install operation is Complete";
      }
      enum install-smu-add-fail {
        value 71;
        description
          "SMU install operation failed";
      }
      enum install-pkg-add-start {
        value 72;
        description
          "Sub-package install is in progress";
      }
      enum install-pkg-add-done {
        value 73;
        description
          "Sub-package install operation is Complete";
      }
      enum install-pkg-add-fail {
        value 74;
        description
          "Sub-package install operation failed";
      }
      enum install-pkg-extract-start {
        value 75;
        description
          "Install Package extraction is in progress";
      }
      enum install-pkg-extract-done {
        value 76;
        description
          "Install package extraction is Complete";
      }
      enum install-pkg-extract-fail {
        value 77;
        description
          "Install package extraction failed";
      }
      enum install-sub-state-undef {
        value 78;
        description
          "Install operation sub state not set";
      }
      enum install-add-clnup-start {
        value 79;
        description
          "Install add failure cleanup is in progress";
      }
      enum install-add-clnup-done {
        value 80;
        description
          "Install add failure cleanup is Complete";
      }
      enum install-add-clnup-fail {
        value 81;
        description
          "Install add failure cleanup failed";
      }
      enum install-add-prechk-start {
        value 82;
        description
          "Install check before starting add operation is in progress";
      }
      enum install-add-prechk-done {
        value 83;
        description
          "Install check before starting add operation is complete";
      }
      enum install-add-prechk-fail {
        value 84;
        description
          "Install check before starting add operation failed";
      }
      enum install-add-postchk-start {
        value 85;
        description
          "Install check after finishing add operation is in progress";
      }
      enum install-add-postchk-done {
        value 86;
        description
          "Install check after finishing add operation is complete";
      }
      enum install-add-postchk-fail {
        value 87;
        description
          "Install check after finishing add operation failed";
      }
      enum install-add-wlc-query-start {
        value 88;
        description
          "Install wireless query during add operation is in progress";
      }
      enum install-add-wlc-query-done {
        value 89;
        description
          "Install wireless query during add operation is complete";
      }
      enum install-add-wlc-query-fail {
        value 90;
        description
          "Install wireless query during add operation failed";
      }
      enum install-add-mount-ap-img-start {
        value 91;
        description
          "Install mount AP image for wireless is in progress";
      }
      enum install-add-mount-ap-img-done {
        value 92;
        description
          "Install mount AP image for wireless is complete";
      }
      enum install-add-mount-ap-img-fail {
        value 93;
        description
          "Install mount AP image for wireless failed";
      }
      enum install-add-wlc-ntfy-start {
        value 94;
        description
          "Install wireless notify during add operation is in progress";
      }
      enum install-add-wlc-ntfy-done {
        value 95;
        description
          "Install wireless notify during add operation is complete";
      }
      enum install-add-wlc-ntfy-fail {
        value 96;
        description
          "Install wireless notify during add operation failed";
      }
      enum install-rej-for-act-smu {
        value 97;
        description
          "SMU Install operation is rejected as SMU is already activated";
      }
      enum install-rej-for-deactv-smu {
        value 98;
        description
          "SMU install operation is not required as SMU is in deactivated state.
           Trigger commit for finishing deactivate operation or
           abort to bring it back to activated state";
      }
      enum install-rej-in-bundle-mode {
        value 99;
        description
          "Install of input package is allowed only for device booted in Install Mode";
      }
      enum install-rej-issu-in-progress {
        value 100;
        description
          "Install operation is rejected as device already has in-progress ISSU operation";
      }
      enum install-same-img-install {
        value 101;
        description
          "Install of same image as running image. No change in install state ";
      }
      enum install-same-pkg-install {
        value 102;
        description
          "Install of same package as running package, No change in install state ";
      }
      enum install-pkg-startup-fail {
        value 103;
        description
          "Package startup failed on activation";
      }
      enum install-remove-user-reject {
        value 104;
        description
          "Install Remove rejected by user at prompt";
      }
      enum install-rej-smu-conflict {
        value 105;
        description
          "Install SMU operation rejected because of conflict with existing SMU on device";
      }
      enum install-rej-smu-improper-state {
        value 106;
        description
          "Install SMU operation rejected as earlier SMU is not in proper state";
      }
      enum install-rej-pkg-lic-mismatch {
        value 107;
        description
          "Install operation rejected as device license do not match with package license";
      }
      enum install-int-sw-err {
        value 108;
        description
          "Install operation internal software error";
      }
      enum install-inv-path-err {
        value 109;
        description
          "Install operation invalid file path";
      }
      enum install-pkgtype-not-found {
        value 110;
        description
          "Install operation package type not found";
      }
      enum install-download-start {
        value 111;
        description
          "Install download is in progress";
      }
      enum install-download-done {
        value 112;
        description
          "Install download is Complete";
      }
      enum install-download-fail {
        value 113;
        description
          "Install download failed";
      }
      enum install-smu-add-clnup-start {
        value 114;
        description
          "Install SMU add failure cleanup is in progress";
      }
      enum install-smu-add-clnup-done {
        value 115;
        description
          "Install SMU add failure cleanup is Complete";
      }
      enum install-smu-add-clnup-fail {
        value 116;
        description
          "Install SMU add failure cleanup failed";
      }
      enum install-act-prechk-start {
        value 117;
        description
          "Install check before starting activate operation is in progress";
      }
      enum install-act-prechk-done {
        value 118;
        description
          "Install check before starting activate operation is complete";
      }
      enum install-act-prechk-fail {
        value 119;
        description
          "Install check before starting activate operation failed";
      }
      enum install-smu-act-start {
        value 120;
        description
          "SMU install activate operation is in progress";
      }
      enum install-smu-act-done {
        value 121;
        description
          "SMU install activate operation is Complete";
      }
      enum install-smu-act-fail {
        value 122;
        description
          "SMU install activate operation failed";
      }
      enum install-pkg-act-start {
        value 123;
        description
          "Sub-package install activation operation is in progress";
      }
      enum install-pkg-act-done {
        value 124;
        description
          "Sub-package install activation operation is Complete";
      }
      enum install-pkg-act-fail {
        value 125;
        description
          "Sub-package install activation operation failed";
      }
      enum install-act-postchk-start {
        value 126;
        description
          "Install check after activate operation is in progress";
      }
      enum install-act-postchk-done {
        value 127;
        description
          "Install check after activate operation is complete";
      }
      enum install-act-postchk-fail {
        value 128;
        description
          "Install check after activate operation failed";
      }
      enum install-act-clnup-start {
        value 129;
        description
          "Install activation failure cleanup is in progress";
      }
      enum install-act-clnup-done {
        value 130;
        description
          "Install activation failure cleanup is Complete";
      }
      enum install-act-clnup-fail {
        value 131;
        description
          "Install activation failure cleanup failed";
      }
      enum install-issu-incomp-ver {
        value 132;
        description
          "Install ISSU comp check failed. Added image is not ISSU compatible";
      }
      enum install-pkg-in-use {
        value 133;
        description
          "Install Package is in use";
      }
      enum install-img-cncl-start {
        value 134;
        description
          "Cancel of image operation has started";
      }
      enum install-img-cncl-done {
        value 135;
        description
          "Cancel of image operation has completed";
      }
      enum install-img-cncl-fail {
        value 136;
        description
          "Cancel of image operation has failed";
      }
      enum install-smu-cncl-start {
        value 137;
        description
          "Cancel of SMU operation has started";
      }
      enum install-smu-cncl-done {
        value 138;
        description
          "Cancel of SMU operation has completed";
      }
      enum install-smu-cncl-fail {
        value 139;
        description
          "Cancel of SMU operation has failed";
      }
      enum install-img-commit-start {
        value 140;
        description
          "Commit of image operation has started";
      }
      enum install-img-commit-done {
        value 141;
        description
          "Commit of image operation has completed";
      }
      enum install-img-commit-fail {
        value 142;
        description
          "Commit of image operation has failed";
      }
      enum install-smu-commit-start {
        value 143;
        description
          "Commit of SMU operation has started";
      }
      enum install-smu-commit-done {
        value 144;
        description
          "Commit of SMU operation has completed";
      }
      enum install-smu-commit-fail {
        value 145;
        description
          "Commit of SMU operation has failed";
      }
      enum install-remove-usr-cnfrm {
        value 146;
        description
          "Install remove operation waiting for user confirmation";
      }
      enum install-reload-usr-cnfrm {
        value 147;
        description
          "Install operation waiting confirmation for reload";
      }
      enum install-reload-fast-usr-cnfrm {
        value 148;
        description
          "Install operation waiting confirmation for reload fast";
      }
      enum install-rbk-db-chk-start {
        value 149;
        description
          "Coherence check of rollback points across device";
      }
      enum install-rbk-db-chk-done {
        value 150;
        description
          "Coherence check of rollback points across device completed with success";
      }
      enum install-rbk-db-chk-fail {
        value 151;
        description
          "Coherence check of rollback points across device failed";
      }
      enum install-rbk-boot-mode-chk-start {
        value 152;
        description
          "Checking of boot mode compatibility for rollback point";
      }
      enum install-rbk-boot-mode-chk-done {
        value 153;
        description
          "Boot mode compatibility check for rollback point completed with success";
      }
      enum install-rbk-boot-mode-chk-fail {
        value 154;
        description
          "Boot mode compatibility check for rollback point failed";
      }
      enum install-rbk-lbl-not-found {
        value 155;
        description
          "Rollback label provided by the user is not present in the rollback database";
      }
      enum install-get-rbk-type-start {
        value 156;
        description
          "Identifying type of packages involved in rollback operation";
      }
      enum install-get-rbk-type-done {
        value 157;
        description
          "Identification of packages involved in rollback operation completed with success";
      }
      enum install-get-rbk-type-fail {
        value 158;
        description
          "Identification of packages involved in rollback operation failed";
      }
      enum install-img-rbk-start {
        value 159;
        description
          "Rollback of image operation has started";
      }
      enum install-img-rbk-fail {
        value 160;
        description
          "Rollback of image operation has failed";
      }
      enum install-img-rbk-done {
        value 161;
        description
          "Rollback of image operation has completed";
      }
      enum install-smu-rbk-start {
        value 162;
        description
          "Rollback of SMU operation has started";
      }
      enum install-smu-rbk-fail {
        value 163;
        description
          "Rollback of SMU operation has failed";
      }
      enum install-smu-rbk-done {
        value 164;
        description
          "Rollback of SMU operation has completed";
      }
      enum install-autoupg-start {
        value 165;
        description
          "Install auto upgrade operation has been started";
      }
      enum install-autoupg-fail {
        value 166;
        description
          "Install auto upgrade operation has failed or aborted";
      }
      enum install-autoupg-done {
        value 167;
        description
          "Install auto upgrade operation has completed successfully";
      }
      enum install-img-act-start {
        value 168;
        description
          "Package install activation operation is in progress";
      }
      enum install-img-act-done {
        value 169;
        description
          "Package install activation operation is Complete";
      }
      enum install-img-act-fail {
        value 170;
        description
          "Package install activation operation failed";
      }
      enum install-img-not-added {
        value 171;
        description
          "Image required for install operation has not been added";
      }
      enum install-smu-not-added {
        value 172;
        description
          "SMU file required for install operation has not been added";
      }
      enum install-same-smu-install {
        value 173;
        description
          "Install of same SMU as running SMU, No change in install state";
      }
      enum install-unsaved-cfg-chg {
        value 174;
        description
          "Install operation is rejected because config changes are not saved";
      }
      enum install-missing-file-for-rbk-id {
        value 175;
        description
          "Required file is missing from the rollback database";
      }
      enum install-invalid-rbk-id {
        value 176;
        description
          "Invalid rollback id for rollback operation";
      }
      enum install-hot-smu-act-fail {
        value 177;
        description
          "Hot SMU activation has failed";
      }
      enum install-hot-smu-deact-fail {
        value 178;
        description
          "Hot SMU de-activation has failed";
      }
      enum install-nothing-to-activate {
        value 179;
        description
          "Install operation did not detect any package for ready for activation";
      }
      enum install-nothing-to-deactivate {
        value 180;
        description
          "Install operation did not detect package for de-activation";
      }
      enum install-boot-param-update-fail {
        value 181;
        description
          "Failed to update boot parameter in config";
      }
      enum install-exec-script-fail {
        value 182;
        description
          "Execution of pre or post script during an install operation has failed";
      }
      enum install-plat-precheck-fail {
        value 183;
        description
          "Platform specific pre-check failed for the operation";
      }
      enum install-plat-postcheck-fail {
        value 184;
        description
          "Platform specific post-check failed for the operation";
      }
      enum install-img-downgrade {
        value 185;
        description
          "Image is being downgraded";
      }
      enum install-boot-param-update-start {
        value 186;
        description
          "Package install boot parameter update operation is in progress";
      }
      enum install-boot-param-update-done {
        value 187;
        description
          "Package install boot parameter update operation is Complete";
      }
      enum install-deact-rej-uncommit-smu-fail {
        value 188;
        description
          "Failed to deactivate SMU since a SMU is in activated state but not yet committed.";
      }
      enum install-set-def-succ {
        value 189;
        description
          "Install operation to set default completed successfully.";
      }
      enum install-set-def-fail {
        value 190;
        description
          "Install operation to set default failed.";
      }
      enum install-max-img-cnt-exceeded {
        value 191;
        description
          "Device exceeded limit for maximum allowed installed image versions.";
      }
      enum install-same-img-as-def-ver {
        value 192;
        description
          "Install of same package as default version, No change in install state.";
      }
      enum install-same-img-as-cur-ver {
        value 193;
        description
          "Install of same package as active version, No change in install state.";
      }
      enum install-no-space-in-cfg-partn {
        value 194;
        description
          "Device do not have enough space to store config partition, please cleanup older versions.";
      }
      enum install-op-unsupp-plat {
        value 195;
        description
          "Install operation is not supported on this platform.";
      }
      enum install-downgrade-unsupp {
        value 196;
        description
          "Install downgrade is not supported in this scenario";
      }
      enum install-act-state-rbk-unsupp {
        value 197;
        description
          "Rollback operation is not supported in activated & uncommitted state, please use abort instead.";
      }
      enum install-inval-file {
        value 198;
        description
          "Install operation on invalid install file.";
      }
      enum install-missing-upg-confrm-timer {
        value 199;
        description
          "Upgrade confirm timer is not configured. SMU activate or deactivate operation is not allowed.";
      }
      enum install-add-rej-uncommit-subpkg-fail {
        value 200;
        description
          "Failed to install add since a sub-package is in uncommitted state.";
      }
      enum install-same-filename-used {
        value 201;
        description
          "Device used same filename when installing image, retry after renaming file or removing the existing version.";
      }
    }
    description
      "Install sub state provides the intermediate sub state status during
       install and activate operations. This helps to see the progress during
       long waiting install action operation.";
  }

  typedef install-action {
    type enumeration {
      enum install {
        value 0;
        description
          "Install action type";
      }
      enum activate {
        value 1;
        description
          "Activate action type";
      }
      enum install-commit {
        value 2;
        description
          "Commit action type";
      }
      enum rollback {
        value 3;
        description
          "Rollback action type";
      }
      enum deactivate {
        value 4;
        description
          "Deactivate action type";
      }
      enum remove {
        value 5;
        description
          "Remove action type";
      }
      enum auto-abort-timer {
        value 6;
        description
          "Auto abort timer action type";
      }
      enum abort {
        value 7;
        description
          "Abort action type";
      }
      enum autoupgrade {
        value 8;
        description
          "Auto upgrade action type";
      }
      enum set-default {
        value 9;
        description
          "Set default action type";
      }
    }
    description
      "Install action type";
  }

  grouping common-notification-header {
    description
      "Install notification header";
    leaf host-name {
      type string;
      description
        "Host name";
    }
  }

  grouping install-notification-fields {
    description
      "Install operation state";
    leaf status {
      type install-event-types-ios-xe:installation-status;
      description
        "Installation status";
    }
    leaf action-type {
      type install-event-types-ios-xe:install-action;
      description
        "Action type";
    }
    leaf sub-state {
      type install-event-types-ios-xe:install-sub-state;
      description
        "Intermediate sub state of install status";
    }
    leaf uuid {
      type string;
      description
        "Universally unique identifier 128-bit number UUID is received from action rpc";
    }
    leaf percentage-completed {
      type int8;
      units "percent";
      description
        "Percent of completion for in-progress installations.
         If the value is -1, the field is not applicable";
    }
  }
}
