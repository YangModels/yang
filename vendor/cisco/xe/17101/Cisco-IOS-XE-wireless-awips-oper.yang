module Cisco-IOS-XE-wireless-awips-oper {
  yang-version 1.1;
  namespace "http://cisco.com/ns/yang/Cisco-IOS-XE-wireless-awips-oper";
  prefix wireless-oper-awips;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for AWIPS (Adaptive Wireless Intrusion Prevention
     Service) operational data.
     Copyright (c) 2019-2020, 2022 by Cisco Systems, Inc.
     All rights reserved.";

  revision 2022-11-01 {
    description
      "Update yang-version to 1.1";
    reference
      "1.2.0";
    cisco-semver:module-version "1.2.0";
  }
  revision 2020-11-01 {
    description
      "- Added Forensic and file download status
       - AWIPS WLC Alarm table.
       - Added new file download error codes";
    reference
      "1.1.0";
    cisco-semver:module-version "1.1.0";
  }
  revision 2019-11-01 {
    description
      "Initial revision";
    reference
      "1.0.0";
    cisco-semver:module-version "1.0.0";
  }

  typedef ap-awips-context-id {
    type enumeration {
      enum ap-awips-reserved {
        value 0;
        description
          "Reserved context ID";
      }
      enum ap-awips-src-dst {
        value 1;
        description
          "Src/Dst MAC context";
      }
      enum ap-awips-dot11-hdr {
        value 2;
        description
          "802.11 hdr context";
      }
      enum ap-awips-radio-slot {
        value 3;
        description
          "Radio slot context";
      }
    }
    description
      "Enum for AWIPS Device context.
       This would indicate the type
       of device context in the alarm. The
       device context can be empty, or have
       src/dst MAC information or have 802.11
       header information";
  }

  typedef ap-awips-status {
    type enumeration {
      enum ap-awips-config-not-enabled {
        value 0;
        description
          "Feature config is not enabled";
      }
      enum ap-awips-not-capable {
        value 1;
        description
          "AP does not have feature capability";
      }
      enum ap-awips-enabled {
        value 2;
        description
          "Feature enabled on AP";
      }
      enum ap-awips-failed {
        value 3;
        description
          "Feature enable failed on AP";
      }
    }
    description
      "Enum for AWIPS Status";
  }

  typedef awips-wlc-alarm-type {
    type enumeration {
      enum awips-wlc-alarm-krack {
        value 0;
        description
          "Key-reinstallation attack";
      }
    }
    description
      "AWIPS WLC Alarm Types";
  }

  typedef awips-file-dwld-status {
    type enumeration {
      enum awips-not-initiated {
        value 0;
        description
          "File download not initiated";
      }
      enum awips-file-success {
        value 1;
        description
          "File download successful";
      }
      enum awips-file-failure {
        value 2;
        description
          "File download failed";
      }
      enum awips-dwnld-in-progress {
        value 3;
        description
          "File download in progress";
      }
      enum awips-jwt-token-invalid {
        value 4;
        description
          "JWT token is invalid";
      }
      enum awips-jwt-token-failed {
        value 5;
        description
          "JWT token enrollment failed";
      }
      enum awips-jwt-token-success {
        value 6;
        description
          "JWT token enrollment successful ";
      }
      enum awips-jwt-token-error {
        value 7;
        description
          "JWT token internal error";
      }
      enum awips-cert-error {
        value 8;
        description
          "certificate related error";
      }
      enum awips-file-error {
        value 9;
        description
          "File download error";
      }
      enum awips-file-error-hash {
        value 10;
        description
          "File download failed for invalid SHA hash";
      }
      enum awips-file-error-connection {
        value 11;
        description
          "File download failed for HTTP connection issue";
      }
      enum awips-file-error-cert-chain {
        value 12;
        description
          "File download failed for cert chain validation";
      }
      enum awips-file-error-not-found {
        value 13;
        description
          "File not found during HTTP download";
      }
      enum awips-version-mismatch {
        value 14;
        description
          "Incompatible DNAC version";
      }
      enum awips-forbidden-error {
        value 15;
        description
          "Requested resource is forbidden";
      }
    }
    description
      "Enum for AWIPS File download status.";
  }

  grouping st-device-context {
    description
      "Device context. This context
       is optional and can contain either SRC/DST
       MAC address or 802.11 header";
    leaf context-id {
      type wireless-oper-awips:ap-awips-context-id;
      description
        "Context Identifier";
    }
    leaf context-string {
      type binary;
      description
        "Device context information";
    }
  }

  grouping st-awips-per-ap-alarm {
    description
      "AWIPS alarm operation data";
    leaf version {
      type uint32;
      description
        "Signature version information";
    }
    leaf signature-id {
      type uint32;
      description
        "Signature Identifier";
    }
    leaf alarm-string {
      type string;
      description
        "Alarm description";
    }
    container dev-context {
      description
        "Device context";
      uses wireless-oper-awips:st-device-context;
    }
  }

  grouping awips-alarm-key {
    description
      "Key for AWIPS alarm data";
    leaf alarm-timestamp {
      type yang:date-and-time;
      description
        "Alarm timestamp";
    }
    leaf ap-mac {
      type yang:mac-address;
      description
        "AP MAC Address";
    }
    leaf alarm-id {
      type uint32;
      description
        "Alarm Identifier";
    }
    leaf client-mac-addr {
      type yang:mac-address;
      description
        "Client MAC address";
    }
    leaf msg-indx {
      type uint32;
      description
        "Alarm message index";
    }
  }

  grouping st-awips-per-ap-info {
    description
      "AWIPS Status and per AP alarm stats counter";
    leaf ap-mac {
      type yang:mac-address;
      description
        "AP MAC address";
    }
    leaf awips-status {
      type wireless-oper-awips:ap-awips-status;
      description
        "AWIPS status";
    }
    leaf alarm-count {
      type uint64;
      description
        "Alarm counter";
    }
    leaf forensic-capture-status {
      type wireless-oper-awips:ap-awips-status;
      description
        "AWIPS Forensic capture status";
    }
  }

  grouping st-awips-wlc-alarm-krack {
    description
      "WPA2 Key Reinstallation Attack Alarm details";
    leaf bssid {
      type yang:mac-address;
      description
        "Attacked BSSID";
    }
    leaf client-mac {
      type yang:mac-address;
      description
        "Attacked client MAC";
    }
  }

  grouping st-awips-wlc-alarm {
    description
      "AWIPS WLC alarm operation data";
    leaf alarm-timestamp {
      type yang:date-and-time;
      description
        "Alarm time stamp";
    }
    choice alarm-type-choice {
      description
        "Alarm Type";
      case awips-wlc-alarm-krack {
        container alarm-krack {
          description
            "WPA2 Key Reinstallation Attack Alarm";
          uses wireless-oper-awips:st-awips-wlc-alarm-krack;
        }
      }
    }
  }

  grouping awips-wlc-alarm-key {
    description
      "Key for AWIPS WLC alarm data";
    leaf monotonic-timestamp {
      type yang:timeticks;
      description
        "Alarm timestamp";
    }
    leaf wlc-alarm-index {
      type uint32;
      description
        "WLC Alarm index";
    }
  }

  grouping st-awips-ap-dwld-status {
    description
      "AWIPS per AP file download status";
    leaf ap-mac {
      type yang:mac-address;
      description
        "AP MAC address";
    }
    leaf dwld-status {
      type wireless-oper-awips:awips-file-dwld-status;
      description
        "File download status";
    }
    leaf file-version {
      type uint32;
      description
        "File version at AP";
    }
    leaf file-hash {
      type binary;
      description
        "File content hash value";
    }
  }

  grouping st-awips-dwld-status {
    description
      "AWIPS file download status";
    leaf last-success-timestamp {
      type yang:date-and-time;
      description
        "Last File download success timestamp";
    }
    leaf last-failed-timestamp {
      type yang:date-and-time;
      description
        "Last File download failure timestamp";
    }
    leaf num-of-failure-attempts {
      type uint32;
      description
        "Number of times File download failed";
    }
    leaf last-failure-reason {
      type uint32;
      description
        "Last failure reason";
    }
    leaf wlc-version {
      type string;
      description
        "WLC version information";
    }
    leaf max-file-ver {
      type uint32;
      description
        "Maximum supported file version information";
    }
    leaf latest-file-version {
      type uint32;
      description
        "File version information";
    }
    leaf download-status {
      type wireless-oper-awips:awips-file-dwld-status;
      description
        "File download status";
    }
    leaf file-hash {
      type binary;
      description
        "File content hash value";
    }
  }

  container awips-oper-data {
    config false;
    description
      "AWIPS operational data";
    list awips-alarm {
      key "alarm-timestamp ap-mac alarm-id client-mac-addr msg-indx";
      description
        "List of AWIPS alarms";
      uses wireless-oper-awips:st-awips-per-ap-alarm;
      uses wireless-oper-awips:awips-alarm-key;
    }
    list awips-wlc-alarm {
      key "monotonic-timestamp wlc-alarm-index";
      description
        "List of AWIPS WLC alarms";
      uses wireless-oper-awips:st-awips-wlc-alarm;
      uses wireless-oper-awips:awips-wlc-alarm-key;
    }
    list awips-per-ap-info {
      key "ap-mac";
      description
        "Per AP AWIPS information";
      uses wireless-oper-awips:st-awips-per-ap-info;
    }
    container awips-dwld-status {
      presence "awips-dwld-status";
      description
        "AWIPS File download status";
      uses wireless-oper-awips:st-awips-dwld-status;
    }
    list awips-ap-dwld-status {
      key "ap-mac";
      description
        "Per AP AWIPS File download status";
      uses wireless-oper-awips:st-awips-ap-dwld-status;
    }
  }
}
