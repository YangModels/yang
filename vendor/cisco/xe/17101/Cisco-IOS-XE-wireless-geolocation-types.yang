module Cisco-IOS-XE-wireless-geolocation-types {
  yang-version 1.1;
  namespace "http://cisco.com/ns/yang/Cisco-IOS-XE-wireless-geolocation-types";
  prefix wireless-geolocation-types;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless AP geolocation data types.
     Copyright (c) 2022 by Cisco Systems, Inc.
     All rights reserved.";

  revision 2022-11-01 {
    description
      "Initial revision";
    reference
      "1.0.0";
    cisco-semver:module-version "1.0.0";
  }

  grouping geo-loc-point {
    description
      "Wireless AP geolocation point";
    leaf longitude {
      type decimal64 {
        fraction-digits 6;
      }
      units "degree";
      description
        "Geolocation longitude in WGS 84 format";
    }
    leaf latitude {
      type decimal64 {
        fraction-digits 6;
      }
      units "degree";
      description
        "Geolocation latitude in WGS 84 format";
    }
  }

  grouping geo-loc-elevation-data {
    description
      "Wireless AP elevation data";
    leaf uncertainty {
      type uint16;
      units "meters";
      description
        "Elevation uncertainty";
    }
    leaf height {
      type int16;
      units "meters";
      description
        "AP height";
    }
    leaf source {
      type wireless-enum-types:enm-ap-geolocation-height-source;
      description
        "Elevation source";
    }
  }

  grouping geo-loc-elevation {
    description
      "Wireless AP elevation information";
    leaf last-rcvd-timestamp {
      type yang:date-and-time;
      description
        "Last received height timestamp";
    }
    choice geo-loc-height-type-choice {
      description
        "Type of elevation";
      case ap-height-agl {
        container agl-data {
          description
            "Above Ground Level elevation information";
          uses wireless-geolocation-types:geo-loc-elevation-data;
        }
      }
      case ap-height-msl {
        container msl-data {
          description
            "Mean Sea Level elevation information";
          uses wireless-geolocation-types:geo-loc-elevation-data;
        }
      }
      case ap-height-unknown {
        leaf invalid {
          type boolean;
          description
            "Invalid elevation information";
        }
      }
    }
  }

  grouping geo-loc-ellipse {
    description
      "Wireless AP geolocation ellipse representation";
    container center {
      description
        "Center of the ellipse";
      uses wireless-geolocation-types:geo-loc-point;
    }
    leaf major-axis {
      type uint16;
      units "meters";
      description
        "Major axis of the ellipse";
    }
    leaf minor-axis {
      type uint16;
      units "meters";
      description
        "Minor axis of the ellipse";
    }
    leaf orientation {
      type decimal64 {
        fraction-digits 2;
      }
      units "degree";
      description
        "Orientation of the ellipse measured clockwise from True North";
    }
  }

  grouping geo-loc-info {
    description
      "Wireless AP geolocation information";
    leaf source {
      type wireless-enum-types:enm-ap-geolocation-location-source;
      description
        "AP geolocation source";
    }
    leaf area-of-uncertainty {
      type uint32;
      units "square meters";
      description
        "AP geolocation area of uncertainty";
    }
    leaf hdop {
      type decimal64 {
        fraction-digits 2;
      }
      description
        "AP geolocation GPS Horizontal Dilution of Precision";
    }
    leaf last-rcvd-timestamp {
      type yang:date-and-time;
      description
        "Last received GPS coordinate timestamp";
    }
    choice geo-loc-info-type-choice {
      description
        "AP geolocation type";
      case ap-geoloc-info-ellipse {
        container ellipse {
          description
            "AP geolocation in ellipse format";
          uses wireless-geolocation-types:geo-loc-ellipse;
        }
      }
      case ap-geoloc-info-unknown {
        leaf invalid {
          type boolean;
          description
            "AP invalid geolocation";
        }
      }
    }
  }

  grouping ap-geo-loc-data {
    description
      "Wireless AP geolocation data";
    leaf ap-mac {
      type yang:mac-address;
      description
        "AP MAC address";
    }
    container loc {
      description
        "AP geolocation information";
      uses wireless-geolocation-types:geo-loc-info;
    }
    container elevation {
      description
        "AP elevation information";
      uses wireless-geolocation-types:geo-loc-elevation;
    }
  }

  grouping ap-geo-loc-stats {
    description
      "Wireless AP geolocation statistics";
    leaf num-ap-gnss {
      type uint32;
      description
        "Number of APs with GNSS module";
    }
    leaf num-ap-man-height {
      type uint32;
      description
        "Number of APs with manual elevation configuration";
    }
  }
}
