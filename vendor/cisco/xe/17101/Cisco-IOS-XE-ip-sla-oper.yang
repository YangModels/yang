module Cisco-IOS-XE-ip-sla-oper {
  yang-version 1.1;
  namespace "http://cisco.com/ns/yang/Cisco-IOS-XE-ip-sla-oper";
  prefix ip-sla-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring of IP SLA statistics of a Network Element.
     Copyright (c) 2016-2017, 2019-2022 by Cisco Systems, Inc.
     All rights reserved.";

  revision 2022-11-01 {
    description
      "Update yang-version to 1.1";
    reference
      "5.4.0";
    cisco-semver:module-version "5.4.0";
  }
  revision 2021-11-01 {
    description
      "- Added support for IP SLA service performance latest
       and history interval statistics.
       - Added new enumerations for IP SLA return code type";
    reference
      "5.3.0";
    cisco-semver:module-version "5.3.0";
  }
  revision 2021-07-01 {
    description
      "- Added support for IP SLA Y1731 history interval statistics.";
    reference
      "5.2.0";
    cisco-semver:module-version "5.2.0";
  }
  revision 2021-03-01 {
    description
      "- Extended the model to support aggregated statistics for
         IPSLA DNS, DHCP, FTP, HTTP, HTTPS, ICMP-echo, ICMP-jitter, ICMP path-echo,
         MPLS LSP ping, MPLS LSP trace, multicast UDP-jitter, TCP-connect,
         UDP-echo and UDP-jitter operations.";
    reference
      "5.1.0";
    cisco-semver:module-version "5.1.0";
  }
  revision 2020-11-01 {
    description
      "- Added new enum for IPSLA HTTPS operation type and return codes.
       - Updated existing when statements and added new when statements
         to support IPSLA HTTPS operation statistics.";
    reference
      "5.0.0";
    cisco-semver:module-version "5.0.0";
  }
  revision 2019-05-01 {
    description
      "Added semantic version";
    reference
      "4.2.0";
    cisco-semver:module-version "4.2.0";
  }
  revision 2018-10-29 {
    description
      "- Addition of IPSLA path echo and jitter operation
         statistics
       - Cleaned up spelling errors in descriptions.";
    reference
      "4.1.0";
    cisco-semver:module-version "4.1.0";
  }
  revision 2018-08-13 {
    description
      "- Addition of IPSLA Y1731 delay, loss, http,
       dns, dhcp, ftp, mpls lsp-ping, mpls lsp-trace, ethernet-echo and
       multicast operational types
       - Addition of IPSLA Oper Total statistics
       - Addition of IPSLA Oper Error statistics";
    reference
      "4.0.0";
    cisco-semver:module-version "4.0.0";
  }
  revision 2017-09-25 {
    description
      "Reinstate when clauses";
    reference
      "3.0.0";
    cisco-semver:module-version "3.0.0";
  }
  revision 2017-08-22 {
    description
      "Addition of ICMP echo operational type enumeration";
    reference
      "2.1.0";
    cisco-semver:module-version "2.1.0";
  }
  revision 2017-04-01 {
    description
      "Enumeration name changes. Remove when clauses";
    reference
      "2.0.0";
    cisco-semver:module-version "2.0.0";
  }
  revision 2017-02-07 {
    description
      "Initial revision";
    reference
      "1.0.0";
    cisco-semver:module-version "1.0.0";
  }

  typedef sla-oper-type {
    type enumeration {
      enum oper-type-unknown {
        value 0;
      }
      enum oper-type-udp-echo {
        value 1;
      }
      enum oper-type-udp-jitter {
        value 2;
      }
      enum oper-type-icmp-jitter {
        value 3;
      }
      enum oper-type-ethernet-jitter {
        value 4;
      }
      enum oper-type-ethernet-echo {
        value 5;
      }
      enum oper-type-y1731-delay {
        value 6;
      }
      enum oper-type-y1731-loss {
        value 7;
      }
      enum oper-type-video {
        value 8;
      }
      enum oper-type-mcast {
        value 9;
      }
      enum oper-type-pong {
        value 10;
      }
      enum oper-type-path-jitter {
        value 11;
      }
      enum oper-type-icmp-echo {
        value 12;
      }
      enum oper-type-path-echo {
        value 13;
      }
      enum oper-type-tcp-connect {
        value 14;
      }
      enum oper-type-http {
        value 15;
      }
      enum oper-type-dns {
        value 16;
      }
      enum oper-type-dlsw {
        value 17;
      }
      enum oper-type-dhcp {
        value 18;
      }
      enum oper-type-ftp {
        value 19;
      }
      enum oper-type-voip {
        value 20;
      }
      enum oper-type-rtp {
        value 21;
      }
      enum oper-type-lsp-group {
        value 22;
      }
      enum oper-type-lsp-ping {
        value 23;
      }
      enum oper-type-lsp-trace {
        value 24;
      }
      enum oper-type-ethernet-ping {
        value 25;
      }
      enum oper-type-lsp-ping-pseudowire {
        value 26;
      }
      enum oper-type-udp-app {
        value 27;
      }
      enum oper-type-generic {
        value 28;
      }
      enum oper-type-media-trace {
        value 29;
      }
      enum oper-type-server-performance {
        value 30;
      }
      enum oper-type-fabric-path-echo {
        value 31;
      }
      enum oper-type-https {
        value 32;
        description
          "IPSLA HTTPS operation type";
      }
    }
    description
      "IP SLA operational type";
  }

  typedef sla-return-code {
    type enumeration {
      enum ret-code-unknown {
        value 0;
      }
      enum ret-code-ok {
        value 1;
      }
      enum ret-code-disconnected {
        value 2;
      }
      enum ret-code-busy {
        value 3;
      }
      enum ret-code-timeout {
        value 4;
      }
      enum ret-code-no-connection {
        value 5;
      }
      enum ret-code-internal-error {
        value 6;
      }
      enum ret-code-operation-failure {
        value 7;
      }
      enum ret-code-could-not-find {
        value 8;
      }
      enum ret-code-dns-query-error {
        value 9;
        description
          "DNS query error";
      }
      enum ret-code-dns-timeout {
        value 10;
        description
          "DNS timeout";
      }
      enum ret-code-http-error {
        value 11;
        description
          "HTTP error";
      }
      enum ret-code-over-threshold {
        value 12;
        description
          "Over threshold";
      }
      enum ret-code-no-data {
        value 13;
        description
          "No data in the control message";
      }
      enum ret-code-en-ok {
        value 14;
        description
          "Port enable control message status is ok";
      }
      enum ret-code-en-no-conn {
        value 15;
        description
          "Port enable control message status is no connection";
      }
      enum ret-code-en-ver-fail {
        value 16;
        description
          "Port enable control message status is version error";
      }
      enum ret-code-en-intl-err {
        value 17;
        description
          "Port enable control message status is internal error";
      }
      enum ret-code-en-abort {
        value 18;
        description
          "Port enable control message status is abort";
      }
      enum ret-code-en-fail {
        value 19;
        description
          "Port enable control message status is fail";
      }
      enum ret-code-en-auth-fail {
        value 20;
        description
          "Port enable control message status is authentication failure";
      }
      enum ret-code-en-fmt-err {
        value 21;
        description
          "Port enable control message status is format error";
      }
      enum ret-code-en-port-in-use {
        value 22;
        description
          "Port enable control message status is port in use";
      }
      enum ret-code-stats-ok {
        value 23;
        description
          "Statistics retrieval control message status is ok";
      }
      enum ret-code-stats-no-conn {
        value 24;
        description
          "Statistics retrieval control message status is no connection";
      }
      enum ret-code-stats-ver-fail {
        value 25;
        description
          "Statistics retrieval control message status is version error";
      }
      enum ret-code-stats-intl-err {
        value 26;
        description
          "Statistics retrieval control message status is internal error";
      }
      enum ret-code-stats-abort {
        value 27;
        description
          "Statistics retrieval control message status is abort";
      }
      enum ret-code-stats-fail {
        value 28;
        description
          "Statistics retrieval control message status is failure";
      }
      enum ret-code-stats-auth-fail {
        value 29;
        description
          "Statistics retrieval control message status is authentication failure";
      }
      enum ret-code-stats-fmt-err {
        value 30;
        description
          "Statistics retrieval control message status is format error";
      }
      enum ret-code-stats-port-in-use {
        value 31;
        description
          "Statistics retrieval control message status is port in use";
      }
      enum ret-code-unknown-cmd {
        value 32;
        description
          "Control message status is unknown command";
      }
      enum ret-code-invalid-sess-id {
        value 33;
        description
          "Invalid session identifier";
      }
      enum ret-code-invalid-state {
        value 34;
        description
          "Invalid state";
      }
      enum ret-code-loopback-error {
        value 35;
        description
          "Loopback error";
      }
      enum ret-code-oper-eol {
        value 36;
        description
          "Operation end of life";
      }
      enum ret-code-evc-err {
        value 37;
        description
          "Ethernet evc not found";
      }
      enum ret-code-vlan-err {
        value 38;
        description
          "Ethernet vlan not found";
      }
      enum ret-code-domn-err {
        value 39;
        description
          "Ethernet domain not found";
      }
      enum ret-code-cos-err {
        value 40;
        description
          "Invalid cos specified";
      }
      enum ret-code-malloc-err {
        value 41;
        description
          "Memory allocation error";
      }
    }
    description
      "IP SLA return code";
  }

  typedef accuracy-type {
    type enumeration {
      enum accuracy-milliseconds {
        value 0;
      }
      enum accuracy-microseconds {
        value 1;
      }
      enum accuracy-nanoseconds {
        value 2;
        description
          "nanoseconds accuracy";
      }
    }
    description
      "IP SLA accuracy type";
  }

  typedef rtt-type {
    type enumeration {
      enum rtt-known {
        value 0;
      }
      enum rtt-unknown {
        value 1;
      }
      enum rtt-could-not-find {
        value 2;
      }
    }
    description
      "IP SLA RTT type";
  }

  typedef ttl-type {
    type enumeration {
      enum ttl-finite {
        value 0;
      }
      enum ttl-forever {
        value 1;
      }
    }
    description
      "IP SLA time-to-live type";
  }

  typedef ntp-sync-state {
    type enumeration {
      enum sync {
        value 0;
      }
      enum no-sync {
        value 1;
      }
    }
    description
      "NTP sync state information";
  }

  typedef sla-y1731-delay-bin-type {
    type enumeration {
      enum sla-y1731-fwd-bin {
        value 0;
        description
          "IP SLA Y1731 forward delay statistics bin";
      }
      enum sla-y1731-bwd-bin {
        value 1;
        description
          "IP SLA Y1731 backward delay statistics bin";
      }
      enum sla-y1731-twoway-bin {
        value 2;
        description
          "IP SLA Y1731 two-way delay statistics bin";
      }
      enum sla-y1731-fwd-pos-jitter-bin {
        value 3;
        description
          "IP SLA Y1731 forward positive jitter statistics bin";
      }
      enum sla-y1731-fwd-neg-jitter-bin {
        value 4;
        description
          "IP SLA Y1731 forward negative jitter statistics bin";
      }
      enum sla-y1731-bwd-pos-jitter-bin {
        value 5;
        description
          "IP SLA Y1731 backward positive jitter statistics bin";
      }
      enum sla-y1731-bwd-neg-jitter-bin {
        value 6;
        description
          "IP SLA Y1731 backward negative jitter statistics bin";
      }
      enum sla-y1731-twoway-pos-jitter-bin {
        value 7;
        description
          "IP SLA Y1731 two-way positive jitter statistics bin";
      }
      enum sla-y1731-twoway-neg-jitter-bin {
        value 8;
        description
          "IP SLA Y1731 two-way negative jitter statistics bin";
      }
    }
    description
      "IP SLA Y1731 delay statistics bin types";
  }

  typedef sla-y1731-status {
    type enumeration {
      enum sla-y1731-ok {
        value 0;
        description
          "This indicates IP SLA Y1731 Ethernet PM status is ok";
      }
      enum sla-y1731-suspect {
        value 1;
        description
          "This indicates IP SLA Y1731 Ethernet PM status is suspect";
      }
    }
    description
      "IP SLA Y1731 delay statistics bin types";
  }

  typedef sla-sp-rate-type {
    type enumeration {
      enum rate-pps {
        value 0;
        description
          "Packets per second";
      }
      enum rate-kbps {
        value 1;
        description
          "Kilobytes per second";
      }
    }
    description
      "IP SLA service performance operation rate type";
  }

  typedef sla-sp-oper-mode {
    type enumeration {
      enum sp-unknown-mode {
        value 0;
        description
          "Unknown measurement mode";
      }
      enum sp-pass-mode {
        value 1;
        description
          "Passive measurement mode";
      }
      enum sp-tw-mode {
        value 2;
        description
          "Two way statistics measurement mode";
      }
      enum sp-ow-mode {
        value 3;
        description
          "One way statistics measurement mode";
      }
      enum sp-tgen-mode {
        value 4;
        description
          "Traffic generation mode";
      }
      enum sp-lb-mode {
        value 5;
        description
          "Loopback measurement mode";
      }
    }
    description
      "IP SLA service performance operation mode";
  }

  typedef sla-sp-traffic-class {
    type enumeration {
      enum tc-none {
        value 0;
        description
          "No traffic class";
      }
      enum tc-cir {
        value 1;
        description
          "Committed information rate";
      }
      enum tc-eir {
        value 2;
        description
          "Excess information rate";
      }
      enum tc-abv-eir {
        value 3;
        description
          "Above excess information rate";
      }
    }
    description
      "IP SLA service performance operation traffic class";
  }

  typedef sla-sp-throughput-type {
    type enumeration {
      enum tput-prog {
        value 0;
        description
          "Throughput measurement is in progress";
      }
      enum tput-undef {
        value 1;
        description
          "Throughput measurement is undefined";
      }
      enum tput-val {
        value 2;
        description
          "Throughput value";
      }
    }
    description
      "IP SLA service performance throughput type";
  }

  typedef sla-sp-client-type {
    type enumeration {
      enum clnt-unknown {
        value 0;
        description
          "Unknown client type";
      }
      enum clnt-ip {
        value 1;
        description
          "IP client type";
      }
      enum clnt-eth {
        value 2;
        description
          "Ethernet client type";
      }
    }
    description
      "IP SLA service performance client type";
  }

  typedef sla-sp-duration-type {
    type enumeration {
      enum type-dur {
        value 0;
        description
          "Test duration in seconds";
      }
      enum type-pkts {
        value 1;
        description
          "Test duration in packets";
      }
    }
    description
      "IP SLA service performance duration type";
  }

  grouping sla-time-values {
    description
      "SLA time values";
    leaf min {
      type uint32;
      description
        "Minimum value reading";
    }
    leaf avg {
      type uint32;
      description
        "Average value reading";
    }
    leaf max {
      type uint32;
      description
        "Maximum value reading";
    }
    leaf accuracy {
      type ip-sla-ios-xe-oper:accuracy-type;
      description
        "Reading accuracy";
    }
  }

  grouping sla-time-sum-values {
    description
      "SLA time sum values";
    leaf num {
      type uint32;
      description
        "Number value reading";
    }
    leaf sum {
      type uint32;
      description
        "Sum value reading";
    }
    leaf sum-square {
      type uint64;
      description
        "Sum square value reading";
    }
    leaf accuracy {
      type ip-sla-ios-xe-oper:accuracy-type;
      description
        "Reading accuracy";
    }
  }

  grouping sla-packet-loss-info {
    description
      "SLA packet loss information";
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping voice-score {
    description
      "Voice quality assessment info";
    leaf icpif {
      type uint32;
      description
        "Calculated planning impairment factor";
    }
    leaf mos {
      type uint32;
      description
        "Mean opinion score";
    }
  }

  grouping latest-rtt-type {
    description
      "Latest round-trip-time information";
    choice latestrtt-choice {
      description
        "Last Round Trip Time recorded for this SLA";
      case rtt-known {
        leaf rtt {
          type uint64;
          description
            "Round trip time value";
        }
      }
      case rtt-unknown {
        leaf unknown {
          type empty;
          description
            "Round trip time is unknown";
        }
      }
      case rtt-could-not-find {
        leaf could-not-find {
          type empty;
          description
            "Round trip time could not be determined";
        }
      }
    }
  }

  grouping time-to-live-type {
    description
      "Latest time to live information";
    choice timetolive-choice {
      description
        "For the timetolive-choice item, ip sla items
         can be configured to have a set (finite) time-to-live, or
         they can just be configured to go forever.";
      case ttl-finite {
        leaf ttl {
          type uint64;
          description
            "Time to live value";
        }
      }
      case ttl-forever {
        leaf forever {
          type empty;
          description
            "Time to live unbound";
        }
      }
    }
  }

  grouping rtt-info {
    description
      "Round trip time information";
    container latest-rtt {
      description
        "The last Round Trip Time recorded for this SLA";
      uses ip-sla-ios-xe-oper:latest-rtt-type;
    }
    container time-to-live {
      description
        "Time-to-live for the SLA operation";
      uses ip-sla-ios-xe-oper:time-to-live-type;
    }
  }

  grouping y1731-interval-stats {
    description
      "Y.1731 internal statistics";
    leaf intv-start-time {
      type yang:date-and-time;
      description
        "Interval start time";
    }
    leaf init-count {
      type uint32;
      description
        "Initial count";
    }
    leaf complete-count {
      type uint32;
      description
        "Complete count";
    }
    leaf valid {
      type boolean;
      description
        "Validity";
    }
    leaf intv-end-time {
      type yang:date-and-time;
      description
        "Interval end time";
    }
  }

  grouping rtt {
    description
      "RTT information";
    leaf rtt-count {
      type uint32;
      description
        "RTT count";
    }
    container sla-time-values {
      description
        "Timing information";
      uses ip-sla-ios-xe-oper:sla-time-values;
    }
  }

  grouping oneway-latency {
    description
      "Latency information";
    leaf sample-count {
      type uint32;
      description
        "Sample count";
    }
    container sd {
      description
        "Source to Destination one way latency
         information";
      uses ip-sla-ios-xe-oper:sla-time-values;
    }
    container ds {
      description
        "Destination to Source one way latency
         information";
      uses ip-sla-ios-xe-oper:sla-time-values;
    }
    container sum-ow-sd {
      description
        "Source to Destination one way latency
         sum information";
      uses ip-sla-ios-xe-oper:sla-time-sum-values;
    }
    container sum-ow-ds {
      description
        "Destination to Source one way latency
         sum information";
      uses ip-sla-ios-xe-oper:sla-time-sum-values;
    }
  }

  grouping jitter {
    description
      "Jitter information";
    leaf sd-sample-count {
      type uint32;
      description
        "Sample count";
    }
    leaf ds-sample-count {
      type uint32;
      description
        "Sample count";
    }
    container sd {
      description
        "Source to Destination Jitter information";
      uses ip-sla-ios-xe-oper:sla-time-values;
    }
    container ds {
      description
        "Destination to Source Jitter information";
      uses ip-sla-ios-xe-oper:sla-time-values;
    }
    container pos-jitter-sd {
      description
        "Source to Destination Positive Jitter
         information";
      uses ip-sla-ios-xe-oper:sla-time-values;
    }
    container sum-pos-jitter-sd {
      description
        "Source to Destination Positive jitter
         sum information";
      uses ip-sla-ios-xe-oper:sla-time-sum-values;
    }
    container neg-jitter-sd {
      description
        "Source to Destination Negative jitter
         information";
      uses ip-sla-ios-xe-oper:sla-time-values;
    }
    container sum-neg-jitter-sd {
      description
        "Source to Destination Negative jitter
         sum information";
      uses ip-sla-ios-xe-oper:sla-time-sum-values;
    }
    container pos-jitter-ds {
      description
        "Destination to Source Positive jitter
         information";
      uses ip-sla-ios-xe-oper:sla-time-values;
    }
    container sum-pos-jitter-ds {
      description
        "Destination to Source Positive jitter
         sum information";
      uses ip-sla-ios-xe-oper:sla-time-sum-values;
    }
    container neg-jitter-ds {
      description
        "Destination to Source Negative jitter
         information";
      uses ip-sla-ios-xe-oper:sla-time-values;
    }
    container sum-neg-jitter-ds {
      description
        "Destination to Source Negative jitter
         sum information";
      uses ip-sla-ios-xe-oper:sla-time-sum-values;
    }
    leaf inter-arrival-jitter-out {
      type uint32;
      description
        "Interarrival jitterout information";
    }
    leaf inter-arrival-jitter-in {
      type uint32;
      description
        "Interarrival jitterin information";
    }
    leaf avg-jitter {
      type uint32;
      description
        "Average Jitter";
    }
  }

  grouping over-threshold {
    description
      "Over the threshold information";
    leaf rtt-count {
      type uint32;
      description
        "Round Trip Time (RTT) over threshold count
         (the number of times that the RTT was over the configured
         threshold)";
    }
    leaf percent {
      type uint8;
      description
        "Round Trip Time over threshold percentage
         (the percentage that the RTT was over the configured threshold)";
    }
  }

  grouping packet-loss {
    description
      "Packet loss information";
    leaf unprocessed-packets {
      when "(../../../oper-type='oper-type-ethernet-jitter') or (../../../oper-type='oper-type-ethernet-echo')";
      type uint32;
      description
        "Unprocessed packet count";
    }
    leaf sd-count {
      type uint32;
      description
        "Number of packets lost from Source to Destination";
    }
    container sd-loss {
      when "(../../../oper-type!='oper-type-ethernet-jitter') and (../../../oper-type!='oper-type-ethernet-echo')";
      description
        "Source to Destination packet loss details";
      uses ip-sla-ios-xe-oper:sla-packet-loss-info;
    }
    leaf ds-count {
      type uint32;
      description
        "Number of packets lost from Destination to Source";
    }
    container ds-loss {
      when "(../../../oper-type!='oper-type-ethernet-jitter') and (../../../oper-type!='oper-type-ethernet-echo')";
      description
        "Destination to Source packet loss details";
      uses ip-sla-ios-xe-oper:sla-packet-loss-info;
    }
    leaf out-of-sequence {
      type uint32;
      description
        "Out of sequence packet count";
    }
    leaf drops {
      type uint32;
      description
        "Dropped packet count";
    }
    leaf late-arrivals {
      type uint32;
      description
        "Late arrival packet count";
    }
    leaf skipped-packets {
      type uint32;
      description
        "Skipped packet count";
    }
  }

  grouping icmp-packet-loss {
    description
      "ICMP packet loss information";
    leaf late-arrivals {
      type uint32;
      description
        "Late arrival packet count";
    }
    leaf out-of-sequence {
      type uint32;
      description
        "Out of sequence packet count";
    }
    leaf out-of-sequence-sd {
      type uint32;
      description
        "Out of sequence packet count in source to
         destination direction";
    }
    leaf out-of-sequence-ds {
      type uint32;
      description
        "Out of sequence packet count in destination to
         source direction";
    }
    leaf out-of-sequence-both {
      type uint32;
      description
        "Out of sequence packet count in both directions";
    }
    leaf skipped-packets {
      type uint32;
      description
        "Skipped packet count";
    }
    leaf unprocessed-packets {
      type uint32;
      description
        "Unprocessed packet count";
    }
    leaf packet-loss {
      type uint32;
      description
        "Lost packet count";
    }
    leaf loss-period-count {
      type uint32;
      description
        "Loss period count";
    }
    leaf loss-period-len-min {
      type uint32;
      description
        "Shortest loss period length";
    }
    leaf loss-period-len-max {
      type uint32;
      description
        "Longest loss period length";
    }
    leaf inter-loss-period-len-min {
      type uint32;
      description
        "Shortest inter loss period length";
    }
    leaf inter-loss-period-len-max {
      type uint32;
      description
        "Longest inter loss period length";
    }
  }

  grouping http-rtt-stats {
    description
      "HTTP Specific statistics information";
    leaf status-code {
      type uint32;
      description
        "HTTP status code";
    }
    leaf dns-rtt {
      type uint32;
      description
        "Latest DNS RTT";
    }
    leaf tcp-rtt {
      when "(../../../../oper-type!='oper-type-https')";
      type uint32;
      description
        "Latest TCP Connection RTT";
    }
    leaf time-to-first-byte {
      when "(../../../../oper-type!='oper-type-https')";
      type uint32;
      description
        "Latest HTTP time to first byte";
    }
    leaf transaction-rtt {
      type uint32;
      description
        "Latest HTTP Transaction RTT";
    }
    leaf message-size {
      when "(../../../../oper-type!='oper-type-https')";
      type uint32;
      description
        "Latest HTTP Message Size";
    }
    leaf entity-body-size {
      type uint32;
      description
        "Latest HTTP Entity-Body size";
    }
  }

  grouping http-error-stats {
    description
      "HTTP specific error statistics information";
    leaf transaction-error {
      type uint32;
      description
        "Number of HTTP transaction errors occurred";
    }
    leaf tcp-error {
      when "(../../../../oper-type!='oper-type-https')";
      type uint32;
      description
        "Number of TCP errors occurred";
    }
    leaf dns-error {
      type uint32;
      description
        "Number of DNS errors occurred";
    }
    leaf transaction-timeout {
      type uint32;
      description
        "Number of HTTP transaction timeout occurred";
    }
    leaf tcp-timeout {
      when "(../../../../oper-type!='oper-type-https')";
      type uint32;
      description
        "Number of TCP timeout occurred";
    }
    leaf dns-timeout {
      type uint32;
      description
        "Number of DNS timeout occurred";
    }
  }

  grouping http-stats-info {
    description
      "IP SLA HTTP statistics information";
    container http-stats {
      description
        "HTTP specific statistics information";
      uses ip-sla-ios-xe-oper:http-rtt-stats;
    }
    container http-errors {
      description
        "HTTP specific error information";
      uses ip-sla-ios-xe-oper:http-error-stats;
    }
  }

  grouping sla-y1731-delay-time-values {
    description
      "IP SLA Y1731 delay/jitter data information";
    leaf valid-delay-values {
      type boolean;
      description
        "Delay data validity information, when it is
         true, it means that the number of observations,
         minimum, maximum and average values are filled
         with valid values";
    }
    leaf num-of-observations {
      when "(../valid-delay-values='true')";
      type uint32;
      description
        "Number of observations";
    }
    leaf min-value {
      when "(../valid-delay-values='true')";
      type uint64;
      units "microseconds";
      description
        "Minimum delay value observed";
    }
    leaf avg-value {
      when "(../valid-delay-values='true')";
      type uint64;
      units "microseconds";
      description
        "Average delay value observed";
    }
    leaf max-value {
      when "(../valid-delay-values='true')";
      type uint64;
      units "microseconds";
      description
        "Maximum delay value observed";
    }
    leaf time-of-occurrence-of-min-value {
      when "(../valid-delay-values='true')";
      type yang:date-and-time;
      description
        "Time of occurence of the minimum delay value";
    }
    leaf time-of-occurrence-of-max-value {
      when "(../valid-delay-values='true')";
      type yang:date-and-time;
      description
        "Time of occurence of the maximum delay value";
    }
  }

  grouping sla-y1731-delay-bin-range-values {
    description
      "IP SLA Y1731 delay distribution bin
       data information";
    leaf valid-bin-data {
      type boolean;
      description
        "Bin data validity information, when it is
         true, it means that the lower, upper and number of
         observation values are filled with valid values";
    }
    leaf lower-bin-range {
      when "(../valid-bin-data='true')";
      type uint32;
      units "microseconds";
      description
        "Lower bin range";
    }
    leaf upper-bin-range {
      when "(../valid-bin-data='true')";
      type uint32;
      units "microseconds";
      description
        "Upper bin range";
    }
    leaf num-of-bin-observations {
      when "(../valid-bin-data='true')";
      type uint32;
      description
        "Number of observations with in the lower and
         upper bin range";
    }
  }

  grouping sla-y1731-delay-bin-values {
    description
      "IP SLA Y1731 delay bin information";
    leaf valid-bin-values {
      type boolean;
      description
        "Bin values validity information, when it is
         true, it means that all the bin ranges of the particular bin
         are filled with valid values";
    }
    container distribution-bin-range-1 {
      when "(../valid-bin-values='true')";
      description
        "Y1731 Distribution bin range 1, which has the lower, upper
         boundary values and the corresponding observations";
      uses ip-sla-ios-xe-oper:sla-y1731-delay-bin-range-values;
    }
    container distribution-bin-range-2 {
      when "(../valid-bin-values='true')";
      description
        "Y1731 Distribution bin range 2, which has the lower, upper
         boundary values and the corresponding observations";
      uses ip-sla-ios-xe-oper:sla-y1731-delay-bin-range-values;
    }
    container distribution-bin-range-3 {
      when "(../valid-bin-values='true')";
      description
        "Y1731 Distribution bin range 3, which has the lower, upper
         boundary values and the corresponding observations";
      uses ip-sla-ios-xe-oper:sla-y1731-delay-bin-range-values;
    }
    container distribution-bin-range-4 {
      when "(../valid-bin-values='true')";
      description
        "Y1731 Distribution bin range 4, which has the lower, upper
         boundary values and the corresponding observations";
      uses ip-sla-ios-xe-oper:sla-y1731-delay-bin-range-values;
    }
    container distribution-bin-range-5 {
      when "(../valid-bin-values='true')";
      description
        "Y1731 Distribution bin range 5, which has the lower, upper
         boundary values and the corresponding observations";
      uses ip-sla-ios-xe-oper:sla-y1731-delay-bin-range-values;
    }
    container distribution-bin-range-6 {
      when "(../valid-bin-values='true')";
      description
        "Y1731 Distribution bin range 6, which has the lower, upper
         boundary values and the corresponding observations";
      uses ip-sla-ios-xe-oper:sla-y1731-delay-bin-range-values;
    }
    container distribution-bin-range-7 {
      when "(../valid-bin-values='true')";
      description
        "Y1731 Distribution bin range 7, which has the lower, upper
         boundary values and the corresponding observations";
      uses ip-sla-ios-xe-oper:sla-y1731-delay-bin-range-values;
    }
    container distribution-bin-range-8 {
      when "(../valid-bin-values='true')";
      description
        "Y1731 Distribution bin range 8, which has the lower, upper
         boundary values and the corresponding observations";
      uses ip-sla-ios-xe-oper:sla-y1731-delay-bin-range-values;
    }
    container distribution-bin-range-9 {
      when "(../valid-bin-values='true')";
      description
        "Y1731 Distribution bin range 9, which has the lower, upper
         boundary values and the corresponding observations";
      uses ip-sla-ios-xe-oper:sla-y1731-delay-bin-range-values;
    }
    container distribution-bin-range-10 {
      when "(../valid-bin-values='true')";
      description
        "Y1731 Distribution bin range 10, which has the lower, upper
         boundary values and the corresponding observations";
      uses ip-sla-ios-xe-oper:sla-y1731-delay-bin-range-values;
    }
  }

  grouping sla-y1731-delay-stats-delay-type {
    description
      "IP SLA Y1731 Delay operation delay types";
    container forward-delay {
      description
        "Y1731 forward delay type";
      uses ip-sla-ios-xe-oper:sla-y1731-delay-time-values;
    }
    container backward-delay {
      description
        "Y1731 backward delay type";
      uses ip-sla-ios-xe-oper:sla-y1731-delay-time-values;
    }
    container two-way-delay {
      description
        "Y1731 two way delay type";
      uses ip-sla-ios-xe-oper:sla-y1731-delay-time-values;
    }
  }

  grouping sla-y1731-delay-stats-jitter-type {
    description
      "IP SLA Y1731 Delay operation jitter types";
    container forward-positive-jitter {
      description
        "Y1731 forward positive jitter type";
      uses ip-sla-ios-xe-oper:sla-y1731-delay-time-values;
    }
    container forward-negative-jitter {
      description
        "Y1731 forward negative jitter type";
      uses ip-sla-ios-xe-oper:sla-y1731-delay-time-values;
    }
    container backward-positive-jitter {
      description
        "Y1731 backward positive jitter type";
      uses ip-sla-ios-xe-oper:sla-y1731-delay-time-values;
    }
    container backward-negative-jitter {
      description
        "Y1731 backward negative jitter type";
      uses ip-sla-ios-xe-oper:sla-y1731-delay-time-values;
    }
    container two-way-positive-jitter {
      description
        "Y1731 two way positive jitter type";
      uses ip-sla-ios-xe-oper:sla-y1731-delay-time-values;
    }
    container two-way-negative-jitter {
      description
        "Y1731 two way negative jitter type";
      uses ip-sla-ios-xe-oper:sla-y1731-delay-time-values;
    }
  }

  grouping sla-y1731-delay-stats-delay-bin-type {
    description
      "IP SLA Y1731 Delay operation(s) delay
       distribution bin types";
    container forward-delay-bin {
      description
        "Bin which contains the forward delay
         information";
      uses ip-sla-ios-xe-oper:sla-y1731-delay-bin-values;
    }
    container backward-delay-bin {
      description
        "Bin which contains the backward delay
         information";
      uses ip-sla-ios-xe-oper:sla-y1731-delay-bin-values;
    }
    container two-way-delay-bin {
      description
        "Bin which contains the two way delay
         information";
      uses ip-sla-ios-xe-oper:sla-y1731-delay-bin-values;
    }
  }

  grouping sla-y1731-delay-stats-jitter-bin-type {
    description
      "IP SLA Y1731 Delay operation(s) Jitter
       distribution bin types";
    container forward-positive-jitter-bin {
      description
        "Bin which contains the forward positive
         jitter information";
      uses ip-sla-ios-xe-oper:sla-y1731-delay-bin-values;
    }
    container forward-negative-jitter-bin {
      description
        "Bin which contains the forward negative
         jitter information";
      uses ip-sla-ios-xe-oper:sla-y1731-delay-bin-values;
    }
    container backward-positive-jitter-bin {
      description
        "Bin which contains the backward positive
         jitter information";
      uses ip-sla-ios-xe-oper:sla-y1731-delay-bin-values;
    }
    container backward-negative-jitter-bin {
      description
        "Bin which contains the backward negative
         jitter information";
      uses ip-sla-ios-xe-oper:sla-y1731-delay-bin-values;
    }
    container two-way-positive-jitter-bin {
      description
        "Bin which contains the two way positive
         jitter information";
      uses ip-sla-ios-xe-oper:sla-y1731-delay-bin-values;
    }
    container two-way-negative-jitter-bin {
      description
        "Bin which contains the two way negative
         jitter information";
      uses ip-sla-ios-xe-oper:sla-y1731-delay-bin-values;
    }
  }

  grouping sla-y1731-delay-stats {
    description
      "IP SLA Y1731 Delay operation(s) statistics
       information";
    container y1731-delay-stats-delay-info {
      description
        "IP SLA Y1731 Delay operation(s) delay
         related statistics information";
      uses ip-sla-ios-xe-oper:sla-y1731-delay-stats-delay-type;
    }
    container y1731-delay-stats-jitter-info {
      description
        "IP SLA Y1731 Delay operation(s) jitter
         related statistics information";
      uses ip-sla-ios-xe-oper:sla-y1731-delay-stats-jitter-type;
    }
    container y1731-delay-stats-delay-bin-info {
      description
        "IP SLA Y1731 Delay operation(s) delay
         statistics distribution information";
      uses ip-sla-ios-xe-oper:sla-y1731-delay-stats-delay-bin-type;
    }
    container y1731-delay-stats-jitter-bin-info {
      description
        "IP SLA Y1731 Delay operation(s) jitter
         statistics distribution information";
      uses ip-sla-ios-xe-oper:sla-y1731-delay-stats-jitter-bin-type;
    }
  }

  grouping sla-frame-loss-ratio {
    description
      "Frame loss ratio";
    leaf min-frame-loss-numbers {
      type string;
      description
        "Minimum frame loss numbers
         (packets lost : packets transmitted)";
    }
    leaf avg-frame-loss-ratio {
      type string;
      description
        "Average frame ration loss ratio";
    }
    leaf max-frame-loss-numbers {
      type string;
      description
        "Maximum frame loss numbers
         (packets lost : packets transmitted)";
    }
  }

  grouping sla-y1731-loss-stats-values {
    description
      "IP SLA Y1731 loss operation(s) statistics
       types";
    leaf num-of-obs {
      type uint64;
      description
        "Number of observations";
    }
    leaf num-of-available-indicators {
      type uint64;
      description
        "Number of available indicators";
    }
    leaf num-of-unavailable-indicators {
      type uint64;
      description
        "Number of unavailable indicators";
    }
    leaf tx-frames {
      type uint64;
      description
        "Transmitted frames count";
    }
    leaf rx-frames {
      type uint64;
      description
        "Received frames count";
    }
    container frame-loss-ratio {
      description
        "Frame loss minimum/maximum numbers and frame
         loss ratio (FLR) percentage. (min/FLR%/max)";
      uses ip-sla-ios-xe-oper:sla-frame-loss-ratio;
    }
    leaf cum-frame-loss-ratio {
      type string;
      description
        "Cumulative frame loss ratio percentage";
    }
    leaf min-loss-observed-time {
      type yang:date-and-time;
      description
        "Time at which the minimum frame loss
         observed";
    }
    leaf max-loss-observed-time {
      type yang:date-and-time;
      description
        "Time at which the maximum frame loss
         observed";
    }
  }

  grouping sla-y1731-loss-stats {
    description
      "IP SLA Y1731 Loss operation(s) loss statistics
       information";
    container forward-loss-stats {
      description
        "IP SLA Y1731 Loss operation(s) forward loss
         statistics";
      uses ip-sla-ios-xe-oper:sla-y1731-loss-stats-values;
    }
    container backward-loss-stats {
      description
        "IP SLA Y1731 Loss operation(s) backward loss
         statistics";
      uses ip-sla-ios-xe-oper:sla-y1731-loss-stats-values;
    }
  }

  grouping y1731-stats {
    description
      "IPSLA Y1731 operation(s) specific statistics
       information";
    container y1731-delay-stats {
      when "(../../../oper-type='oper-type-y1731-delay')";
      description
        "Y1731 Delay operation(s) specific
         RTT information";
      uses ip-sla-ios-xe-oper:sla-y1731-delay-stats;
    }
    container y1731-loss-stats {
      when "(../../../oper-type='oper-type-y1731-loss')";
      description
        "Y1731 Loss operation(s) specific
         RTT information";
      uses ip-sla-ios-xe-oper:sla-y1731-loss-stats;
    }
  }

  grouping common-err-stats {
    description
      "SLA common errors related information";
    leaf no-of-disconnects {
      type uint32;
      description
        "Number of operations failed due to
         disconnect";
    }
    leaf no-of-timeouts {
      type uint32;
      description
        "Number of operations failed due to
         timeout";
    }
    leaf no-of-busies {
      type uint32;
      description
        "Number of operations failed due to
         resource busy";
    }
    leaf no-of-no-connections {
      type uint32;
      description
        "Number of operations failed due to
         no connection to the destination";
    }
    leaf no-of-internal-errors {
      type uint32;
      description
        "Number of operations failed due to
         internal errors";
    }
    leaf no-of-sequence-errors {
      type uint32;
      description
        "Number of operations failed due to
         sequence number errors";
    }
    leaf no-of-verify-errors {
      type uint32;
      description
        "Number of operations failed due to
         verification errors";
    }
    leaf no-of-ctrl-enable-errors {
      type uint32;
      description
        "Number of operations failed due to
         control enable errors";
    }
    leaf no-of-stats-retrieve-errors {
      type uint32;
      description
        "Number of operations failed due to
         errors during statistics retrieval";
    }
  }

  grouping sla-percentile-value {
    description
      "Percentile values";
    leaf percentile-samples {
      type uint32;
      description
        "Number of percentile samples";
    }
    container percentile-values {
      description
        "Percentile time values";
      uses ip-sla-ios-xe-oper:sla-time-values;
    }
  }

  grouping percentile-ow-latency {
    description
      "Percentile one-way latency information";
    container percentile-ow-sd {
      description
        "Source to destination percentile one-way
         latency information";
      uses ip-sla-ios-xe-oper:sla-percentile-value;
    }
    container percentile-ow-ds {
      description
        "Destination to source percentile one-way
         latency information";
      uses ip-sla-ios-xe-oper:sla-percentile-value;
    }
  }

  grouping percentile-jitter {
    description
      "Percentile jitter information";
    container percentile-jitter-sd {
      description
        "Source to destination percentile jitter
         information";
      uses ip-sla-ios-xe-oper:sla-percentile-value;
    }
    container percentile-jitter-ds {
      description
        "Destination to source percentile jitter
         information";
      uses ip-sla-ios-xe-oper:sla-percentile-value;
    }
  }

  grouping percentile-stats {
    description
      "Percentile statistics information";
    container percentile-rtt-stats {
      description
        "Percentile RTT related information";
      uses ip-sla-ios-xe-oper:sla-percentile-value;
    }
    container percentile-ow-stats {
      description
        "Percentile one way latency related
         information";
      uses ip-sla-ios-xe-oper:percentile-ow-latency;
    }
    container percentile-jitter-stats {
      description
        "Percentile jitter related information";
      uses ip-sla-ios-xe-oper:percentile-jitter;
    }
  }

  grouping mcast-ow-latency {
    description
      "Multicast one-way latency information";
    leaf ow-samples {
      type uint32;
      description
        "Number of multicast one-way samples";
    }
    leaf min-ow-value {
      type uint32;
      description
        "Minimum one-way latency value";
    }
    leaf avg-ow-value {
      type uint32;
      description
        "Average one-way latency value";
    }
    leaf max-ow-value {
      type uint32;
      description
        "Maximum one-way latency value";
    }
    leaf sum-ow-value {
      type uint32;
      description
        "Sum of all the one-way latency values";
    }
    leaf sum-squares-ow-value {
      type uint64;
      description
        "Sum of squares of all the one-way latency values";
    }
    leaf accuracy-type {
      type ip-sla-ios-xe-oper:accuracy-type;
      description
        "Accuracy type of the one-way latency information";
    }
    leaf ntp-sync-state {
      type ip-sla-ios-xe-oper:ntp-sync-state;
      description
        "NTP sync information";
    }
  }

  grouping mcast-rfc-5481-ipdv {
    description
      "Multicast Inter Packet Delay variation RFC 5481
       related information";
    leaf ipdv-samples {
      type uint32;
      description
        "Number of IPDV Samples";
    }
    container ipdv-sd {
      description
        "Minimum/Average/Maximum IPDV values in source to destination
         direction";
      uses ip-sla-ios-xe-oper:sla-time-values;
    }
    container ipdv-pos-sd {
      description
        "Positive Inter Packet Delay Variation information
         in source to destination direction";
      uses ip-sla-ios-xe-oper:sla-time-values;
    }
    container ipdv-pos-sum-sd {
      description
        "Positive Inter Packet Delay Variation Sum/Sum
         square information in source to destination direction";
      uses ip-sla-ios-xe-oper:sla-time-sum-values;
    }
    container ipdv-neg-sd {
      description
        "Negative Inter Packet Delay Variation information
         in source to destination direction";
      uses ip-sla-ios-xe-oper:sla-time-values;
    }
    container ipdv-neg-sum-sd {
      description
        "Negative Inter Packet Delay Variation Sum/Sum
         square information in source to destination direction";
      uses ip-sla-ios-xe-oper:sla-time-sum-values;
    }
  }

  grouping mcast-pkt-loss {
    description
      "Multicast packet loss related information";
    leaf packet-mia {
      type uint32;
      description
        "Number of packets lost for which the direction
         is not known";
    }
    leaf packet-loss-sd {
      type uint32;
      description
        "Packets lost in source to destination
         direction";
    }
    leaf out-of-seq {
      type uint32;
      description
        "Packets which are received in out of
         sequence";
    }
    leaf tail-drop {
      type uint32;
      description
        "Number of Tail drops";
    }
    leaf duplicate-seq-no-count {
      type uint32;
      description
        "Number of packets which are having duplicate
         sequence numbers";
    }
  }

  grouping mcast-stats {
    description
      "Multicast operation specific statistics
       information";
    leaf mcast-id {
      type uint32;
      description
        "Multicast Operation ID";
    }
    leaf mcast-addr {
      type inet:ip-address;
      description
        "IP Multicast address of the operation";
    }
    leaf dest-addr {
      type inet:ip-address;
      description
        "Destination IP address of the Multicast
         operation";
    }
    leaf dest-port {
      type uint32;
      description
        "Destination port number of the Multicast
         operation";
    }
    container mcast-ow-latency {
      description
        "Multicast one-way latency statistics";
      uses ip-sla-ios-xe-oper:mcast-ow-latency;
    }
    container mcast-ipdv {
      description
        "Multicast Inter Packet Delay Variation (IPDV)
         statistics";
      uses ip-sla-ios-xe-oper:mcast-rfc-5481-ipdv;
    }
    leaf mcast-inter-jitter {
      type uint32;
      description
        "Multicast Inter Arrival Jitter statistics";
    }
    container mcast-pkt-loss {
      description
        "Multicast Packet loss statistics";
      uses ip-sla-ios-xe-oper:mcast-pkt-loss;
    }
    container mcast-voice-score {
      description
        "Multicast voice score statistics";
      uses ip-sla-ios-xe-oper:voice-score;
    }
  }

  grouping stats {
    description
      "Statistics";
    container rtt {
      when "(../../oper-type!='oper-type-http')
            and (../../oper-type!='oper-type-https')
            and (../../oper-type!='oper-type-y1731-delay')
            and (../../oper-type!='oper-type-y1731-loss')
            and (../../oper-type!='oper-type-mcast')";
      description
        "RTT information";
      uses ip-sla-ios-xe-oper:rtt;
    }
    container oneway-latency {
      when "(../../oper-type='oper-type-udp-jitter')
            or (../../oper-type='oper-type-icmp-jitter')";
      description
        "One way latency information";
      uses ip-sla-ios-xe-oper:oneway-latency;
    }
    container jitter {
      when "(../../oper-type='oper-type-udp-jitter')
            or (../../oper-type='oper-type-icmp-jitter')";
      description
        "Jitter information";
      uses ip-sla-ios-xe-oper:jitter;
    }
    container over-threshold {
      when "(../../oper-type!='oper-type-ethernet-echo')
            and (../../oper-type!='oper-type-http')
            and (../../oper-type!='oper-type-https')
            and (../../oper-type!='oper-type-mcast')";
      description
        "Over threshold information";
      uses ip-sla-ios-xe-oper:over-threshold;
    }
    container packet-loss {
      when "(../../oper-type='oper-type-udp-jitter')";
      description
        "Packet loss information";
      uses ip-sla-ios-xe-oper:packet-loss;
    }
    container icmp-packet-loss {
      when "(../../oper-type='oper-type-icmp-jitter')";
      description
        "ICMP packet loss information";
      uses ip-sla-ios-xe-oper:icmp-packet-loss;
    }
    container voice-score {
      when "(../../oper-type='oper-type-udp-jitter')";
      description
        "Voice score information";
      uses ip-sla-ios-xe-oper:voice-score;
    }
    container http-specific-stats {
      when "(../../oper-type='oper-type-http')
            or (../../oper-type='oper-type-https')";
      description
        "HTTP specific statistics information";
      uses ip-sla-ios-xe-oper:http-stats-info;
    }
    container y1731-specific-stats {
      when "(../../oper-type='oper-type-y1731-delay')
            or (../../oper-type='oper-type-y1731-loss')";
      description
        "Y1731 specific statistics information";
      uses ip-sla-ios-xe-oper:y1731-stats;
    }
    container multicast-stats {
      when "(../../oper-type='oper-type-mcast')";
      description
        "IP SLA Multicast Jitter statistics
         information";
      uses ip-sla-ios-xe-oper:mcast-stats;
    }
    container percentile-stats {
      when "(../../oper-type='oper-type-udp-jitter')
            or (../../oper-type='oper-type-icmp-jitter')";
      description
        "IP SLA jitter operation(s) percentile
         statistics information";
      uses ip-sla-ios-xe-oper:percentile-stats;
    }
  }

  grouping sla-oper-entry {
    description
      "SLA operational data entry";
    leaf oper-id {
      type uint32;
      description
        "Entry unique identifier";
    }
    leaf oper-type {
      type ip-sla-ios-xe-oper:sla-oper-type;
      description
        "Entry type";
    }
    leaf latest-return-code {
      type ip-sla-ios-xe-oper:sla-return-code;
      description
        "Latest return code";
    }
    leaf success-count {
      when "(../oper-type!='oper-type-y1731-delay')
            and (../oper-type!='oper-type-y1731-loss')
            and (../oper-type!='oper-type-lsp-trace')";
      type uint32;
      description
        "Success count";
    }
    leaf failure-count {
      when "(../oper-type!='oper-type-y1731-delay')
            and (../oper-type!='oper-type-y1731-loss')
            and (../oper-type!='oper-type-lsp-trace')";
      type uint32;
      description
        "Failure count";
    }
    leaf latest-oper-start-time {
      type yang:date-and-time;
      description
        "Latest start time";
    }
    container rtt-info {
      when "(../oper-type!='oper-type-y1731-delay')
            and (../oper-type!='oper-type-y1731-loss')
            and (../oper-type!='oper-type-cast')";
      description
        "Latest RTT information";
      uses ip-sla-ios-xe-oper:rtt-info;
    }
    container measure-stats {
      when "(../oper-type='oper-type-y1731-delay')
            or (../oper-type='oper-type-y1731-loss')";
      description
        "Measured statistics";
      uses ip-sla-ios-xe-oper:y1731-interval-stats;
    }
    container stats {
      when "(../oper-type='oper-type-udp-jitter')
            or (../oper-type='oper-type-icmp-jitter')
            or (../oper-type='oper-type-ethernet-jitter')
            or (../oper-type='oper-type-ethernet-echo')
            or (../oper-type='oper-type-mcast')
            or (../oper-type='oper-type-http')
            or (../oper-type='oper-type-https')
            or (../oper-type='oper-type-y1731-delay')
            or (../oper-type='oper-type-y1731-loss')";
      description
        "Statistics";
      uses ip-sla-ios-xe-oper:stats;
    }
    leaf threshold-occured {
      type boolean;
      description
        "Threshold occured status";
    }
    container common-stats {
      when "(../oper-type!='oper-type-y1731-loss')
            and (../oper-type!='oper-type-y1731-delay')
            and (../oper-type!='oper-type-lsp-trace')
            and (../oper-type!='oper-type-path-echo')
            and (../oper-type!='oper-type-path-jitter')";
      description
        "IP SLA operation(s) common error
         statistics";
      uses ip-sla-ios-xe-oper:common-err-stats;
    }
  }

  grouping sla-err-stats-key {
    description
      "Key for the IPSLA error statistics data.";
    leaf oper-id {
      type uint32;
      description
        "Operation ID";
    }
    leaf start-time-id {
      type uint64;
      description
        "Operation start time.";
    }
    leaf path-index {
      type uint32;
      description
        "Path index of the operation.";
    }
    leaf hop-index {
      type uint32;
      description
        "Hop index of the operation.";
    }
  }

  grouping sla-err-stats {
    description
      "IPSLA Error statistics data entry.";
    leaf num-of-disconnects {
      type uint32;
      description
        "Number of disconnects occurred.";
    }
    leaf num-of-timeouts {
      type uint32;
      description
        "Number of timeouts occurred.";
    }
    leaf num-of-busies {
      type uint32;
      description
        "Number of busies occurred.";
    }
    leaf num-of-no-connections {
      type uint32;
      description
        "Number of no connection errors occurred.";
    }
    leaf num-of-drops {
      type uint32;
      description
        "Number of drops.";
    }
    leaf num-of-sequence-errors {
      type uint32;
      description
        "Number of sequence errors occurred.";
    }
    leaf num-of-verify-errors {
      type uint32;
      description
        "Number of verification errors occurred.";
    }
    leaf target-address {
      type inet:ip-address;
      description
        "Target address of the operation.";
    }
    leaf num-of-ctrl-enable-errors {
      type uint32;
      description
        "Number of control enable errors occured.";
    }
    leaf num-of-stats-retrieve-errors {
      type uint32;
      description
        "Number of statistics retrieve errors occured.";
    }
  }

  grouping sla-total-stats-key {
    description
      "Key for the IPSLA error statistics data.";
    leaf oper-id {
      type uint32;
      description
        "Operation ID";
    }
    leaf start-time-id {
      type uint64;
      description
        "Operation start time.";
    }
  }

  grouping sla-total-stats-entry {
    description
      "IPSLA Error statistics data entry.";
    leaf total-elapsed-time {
      type uint64;
      description
        "Length of the time since this entry was created.";
    }
    leaf total-initiations {
      type uint32;
      description
        "The number of RTT operations that
         have been initiated.";
    }
  }

  grouping path-echo-stats-entry {
    description
      "IPSLA Path Echo operation latest statistics";
    leaf hop-address {
      type inet:ip-address;
      description
        "Hop IPv4/IPv6 address";
    }
    leaf latest-start-time {
      type yang:date-and-time;
      description
        "Latest operation start time. This is the
         time at which the last RTT measurement was initiated";
    }
    leaf latest-return-code {
      type ip-sla-ios-xe-oper:sla-return-code;
      description
        "Latest return code";
    }
    container latest-rtt {
      description
        "Latest RTT information";
      uses ip-sla-ios-xe-oper:rtt-info;
    }
    leaf success-count {
      type uint32;
      description
        "Success count";
    }
    leaf failure-count {
      type uint32;
      description
        "Failure count";
    }
    leaf over-threshold-occurred {
      type boolean;
      description
        "Threshold occurred status";
    }
    container common-error-stats {
      description
        "Common error statistics";
      uses ip-sla-ios-xe-oper:common-err-stats;
    }
  }

  grouping path-echo-stats-key {
    description
      "IPSLA Path Echo operation key information";
    leaf oper-id {
      type uint32;
      description
        "Operation ID";
    }
    leaf path-id {
      type uint8;
      description
        "Path ID";
    }
    leaf hop-id {
      type uint8;
      description
        "Hop ID";
    }
  }

  grouping rtt-stats {
    description
      "Latest RTT statistics";
    container latest-rtt-value {
      description
        "Latest RTT value";
      uses ip-sla-ios-xe-oper:rtt;
    }
    leaf sum-of-rtt {
      type uint32;
      description
        "Sum of RTTs";
    }
    leaf sum-of-square-of-rtt {
      type uint64;
      description
        "Sum of squares of the RTTs";
    }
  }

  grouping jitter-stats-type {
    description
      "Latest jitter statistics";
    leaf count {
      type uint32;
      description
        "Number of jitter samples";
    }
    container jitter-values {
      description
        "Latest minimum, maximum and average jitter";
      uses ip-sla-ios-xe-oper:sla-time-values;
    }
    container jitter-sum-values {
      description
        "Latest sum and sum of squares of the jitter";
      uses ip-sla-ios-xe-oper:sla-time-sum-values;
    }
  }

  grouping path-jitter-stats {
    description
      "Latest jitter statistics";
    leaf jitter-count {
      type uint32;
      description
        "Number of jitter samples";
    }
    container jitter-stats {
      description
        "Latest jitter statistics";
      uses ip-sla-ios-xe-oper:sla-time-values;
    }
    container positive-jitter-stats {
      description
        "Latest positive jitter statistics";
      uses ip-sla-ios-xe-oper:jitter-stats-type;
    }
    container negative-jitter-stats {
      description
        "Latest negative jitter statistics";
      uses ip-sla-ios-xe-oper:jitter-stats-type;
    }
  }

  grouping packet-loss-stats {
    description
      "Latest packet loss statistics";
    leaf timeouts {
      type uint32;
      description
        "Number of timeouts occurred";
    }
    leaf packet-loss-count {
      type uint32;
      description
        "Number of packets lost";
    }
    leaf out-of-sequence-count {
      type uint32;
      description
        "Number of packets received out of
         sequence";
    }
    leaf discarded-sample-count {
      type uint32;
      description
        "Number of discarded packets";
    }
  }

  grouping path-jitter-stats-entry {
    description
      "IPSLA Path Jitter operation latest statistics
       information";
    leaf hop-address {
      type inet:ip-address;
      description
        "Hop IPv4/IPv6 address";
    }
    leaf latest-start-time {
      type yang:date-and-time;
      description
        "Latest operation start time. This is the
         time at which the last RTT measurement was initiated";
    }
    leaf latest-return-code {
      type ip-sla-ios-xe-oper:sla-return-code;
      description
        "Latest return code";
    }
    container latest-rtt {
      description
        "Latest Round Trip Time value";
      uses ip-sla-ios-xe-oper:rtt-info;
    }
    container latest-rtt-stats {
      description
        "Latest minimum, maximum and average RTT values";
      uses ip-sla-ios-xe-oper:rtt-stats;
    }
    container latest-jitter-stats {
      description
        "Latest jitter information";
      uses ip-sla-ios-xe-oper:path-jitter-stats;
    }
    container latest-packet-loss-stats {
      description
        "Latest packet loss information";
      uses ip-sla-ios-xe-oper:packet-loss-stats;
    }
  }

  grouping path-jitter-stats-key {
    description
      "IPSLA Path Jitter operation key information";
    leaf oper-id {
      type uint32;
      description
        "Operation ID";
    }
    leaf hop-id {
      type uint8;
      description
        "Hop ID";
    }
  }

  grouping sla-dist-stats {
    description
      "IPSLA Round-trip time distribution statistics";
    leaf dist-id {
      type uint16;
      description
        "Distribution range identifier";
    }
    leaf lower-limit {
      type uint32;
      description
        "Lower limit of the distribution range";
    }
    leaf upper-limit {
      type uint32;
      description
        "Upper limit of the distribution range";
    }
    leaf avg-latency {
      type uint32;
      description
        "Average latency";
    }
    leaf percent-of-total-comp {
      type uint32;
      description
        "Percent of total completions for this range";
    }
    leaf num-of-comp {
      type uint32;
      description
        "Number of completions with in this range";
    }
    leaf sum-of-rtt {
      type uint32;
      description
        "Sum of round-trip time with in this range";
    }
    leaf sum-of-rtt-squared {
      type uint64;
      description
        "Sum of square of round-trip time with in this range";
    }
    leaf over-thresh {
      type uint32;
      description
        "Number of operations completed with round-trip time over the configured threshold";
    }
    leaf accuracy {
      type ip-sla-ios-xe-oper:accuracy-type;
      description
        "Reading accuracy";
    }
  }

  grouping sla-agg-stats-key {
    description
      "IPSLA aggregated statistics key";
    leaf oper-id {
      type uint32;
      description
        "IPSLA operation identifier";
    }
    leaf hour-id {
      type uint32;
      description
        "IPSLA statistics hour identifier";
    }
  }

  grouping sla-icmp-echo-agg-stats {
    description
      "IPSLA ICMP-echo aggregated statistics";
    leaf dest-addr {
      type inet:ip-address;
      description
        "Destination address of the IPSLA operation";
    }
    leaf vrf-name {
      type string;
      description
        "Name of the VPN routing and forwarding instance
         associated with the IPSLA operation";
    }
    container rtt-stats {
      description
        "IPSLA ICMP-echo operation round-trip time statistics";
      uses ip-sla-ios-xe-oper:rtt;
    }
    leaf over-thresh {
      type uint32;
      description
        "Number of operations completed with round-trip time over the configured threshold";
    }
  }

  grouping voice-score-stats {
    description
      "IPSLA voice score statistics";
    leaf min-of-icpif {
      type uint32;
      description
        "The lowest (minimum) ICPIF value computed for the
         collected statistics";
    }
    leaf max-of-icpif {
      type uint32;
      description
        "The highest (maximum) ICPIF value computed for
         the collected statistics";
    }
    leaf min-of-mos {
      type uint32;
      description
        "The lowest (minimum) MOS (Mean Opinion Score) value computed for the
         collected statistics. MOS values are represented in hundreds. If the
         MOS value is 4.40, then it will be displayed as 440";
    }
    leaf max-of-mos {
      type uint32;
      description
        "The highest (maximum) MOS (Mean Opinion Score) value computed for the
         collected statistics. MOS values are represented in hundreds. If the
         MOS value is 4.40, then it will be displayed as 440";
    }
  }

  grouping out-of-seq-stats {
    description
      "IPSLA out of sequence statistics";
    leaf total-out-of-seq {
      type uint32;
      description
        "The total number of packets returned out of order";
    }
    leaf out-of-seq-sd {
      type uint32;
      description
        "The number of packets returned out of order in source
         to destination direction";
    }
    leaf out-of-seq-ds {
      type uint32;
      description
        "The number of packets returned out of order in destination
         to source direction";
    }
    leaf out-of-seq-both {
      type uint32;
      description
        "The number of packets returned out of order in both
         source to destination and destination to source direction";
    }
  }

  grouping udp-jitter-packet-loss {
    description
      "IPSLA UDP-jitter operation packet loss statistics";
    leaf sd-count {
      type uint32;
      description
        "Number of packets lost from source to destination";
    }
    container sd-loss {
      description
        "Source to destination packet loss details";
      uses ip-sla-ios-xe-oper:sla-packet-loss-info;
    }
    leaf ds-count {
      type uint32;
      description
        "Number of packets lost from destination to source";
    }
    container ds-loss {
      description
        "Destination to source packet loss details";
      uses ip-sla-ios-xe-oper:sla-packet-loss-info;
    }
    leaf out-of-sequence {
      type uint32;
      description
        "Out of sequence packet count";
    }
    leaf drops {
      type uint32;
      description
        "Dropped packet count";
    }
    leaf late-arrivals {
      type uint32;
      description
        "Late arrival packet count";
    }
    leaf skipped-packets {
      type uint32;
      description
        "Skipped packet count";
    }
  }

  grouping icmp-jitter-packet-loss {
    description
      "IPSLA ICMP-jitter operation packet loss statistics";
    leaf count {
      type uint32;
      description
        "Number of packets lost";
    }
    container packet-loss {
      description
        "Packet loss statistics";
      uses ip-sla-ios-xe-oper:sla-packet-loss-info;
    }
  }

  grouping sla-icmp-jitter-agg-stats {
    description
      "IPSLA ICMP-jitter operation aggregated statistics";
    leaf dest-addr {
      type inet:ip-address;
      description
        "Destination address of the IPSLA operation";
    }
    leaf vrf-name {
      type string;
      description
        "Name of the VPN routing and forwarding instance
         associated with the IPSLA operation";
    }
    container rtt-stats {
      description
        "Round-trip time statistics";
      uses ip-sla-ios-xe-oper:rtt;
    }
    container oneway-stats {
      description
        "One-way latency statistics";
      uses ip-sla-ios-xe-oper:oneway-latency;
    }
    container jitter-stats {
      description
        "Jitter statistics";
      uses ip-sla-ios-xe-oper:jitter;
    }
    container over-thresh-stats {
      description
        "Over threshold statistics";
      uses ip-sla-ios-xe-oper:over-threshold;
    }
    container voice-stats {
      description
        "Voice score statistics";
      uses ip-sla-ios-xe-oper:voice-score-stats;
    }
    container loss-stats {
      description
        "Packet loss statistics";
      uses ip-sla-ios-xe-oper:icmp-jitter-packet-loss;
    }
    leaf late-arrivals {
      type uint32;
      description
        "Late arrival packet count";
    }
    leaf packet-skipped {
      type uint32;
      description
        "Number of packets skipped";
    }
    leaf packet-unprocessed {
      type uint32;
      description
        "Number of packets unprocessed";
    }
    container packet-out-of-seq-stats {
      description
        "Packet out of sequence statistics";
      uses ip-sla-ios-xe-oper:out-of-seq-stats;
    }
    leaf over-thresh-occurred {
      type boolean;
      description
        "Over threshold occurred";
    }
    leaf over-thresh {
      type uint32;
      description
        "Number of operations completed with round-trip time over the configured threshold";
    }
  }

  grouping sla-udp-tcp-agg-stats {
    description
      "IPSLA TCP-connect and UDP-echo operations aggregated
       statistics";
    leaf dest-addr {
      type inet:ip-address;
      description
        "Destination address of the IPSLA operation";
    }
    leaf dest-port {
      type uint16;
      description
        "Destination port of the IPSLA operation";
    }
    leaf vrf-name {
      type string;
      description
        "Name of the VPN routing and forwarding instance
         associated with the IPSLA operation";
    }
    leaf over-thresh {
      type uint32;
      description
        "Number of operations completed with round-trip time over the configured threshold";
    }
  }

  grouping sla-udp-jitter-agg-stats {
    description
      "IPSLA UDP-jitter operation aggregated statistics";
    leaf dest-addr {
      type inet:ip-address;
      description
        "Destination address of the IPSLA operation";
    }
    leaf dest-port {
      type uint16;
      description
        "Destination port of the IPSLA operation";
    }
    leaf vrf-name {
      type string;
      description
        "Name of the VPN routing and forwarding instance
         associated with the IPSLA operation";
    }
    container rtt-stats {
      description
        "Round-trip time statistics";
      uses ip-sla-ios-xe-oper:rtt;
    }
    container oneway-stats {
      description
        "One-way latency statistics";
      uses ip-sla-ios-xe-oper:oneway-latency;
    }
    container jitter-stats {
      description
        "Jitter statistics";
      uses ip-sla-ios-xe-oper:jitter;
    }
    container over-thresh-stats {
      description
        "Over threshold statistics";
      uses ip-sla-ios-xe-oper:over-threshold;
    }
    container voice-stats {
      description
        "Voice score statistics";
      uses ip-sla-ios-xe-oper:voice-score-stats;
    }
    container loss-stats {
      description
        "Packet loss statistics";
      uses ip-sla-ios-xe-oper:udp-jitter-packet-loss;
    }
    leaf over-thresh-occurred {
      type boolean;
      description
        "Over threshold occurred status";
    }
    leaf over-thresh {
      type uint32;
      description
        "Number of operations completed with round-trip time over the configured threshold";
    }
  }

  grouping sla-http-agg-stats {
    description
      "IPSLA HTTP operation aggregated statistics";
    leaf url {
      type string;
      description
        "URL of the HTTP operation";
    }
    leaf vrf-name {
      type string;
      description
        "Name of the VPN routing and forwarding instance
         associated with the IPSLA operation";
    }
    leaf dns-rtt {
      type uint32;
      description
        "Sum of round-trip time taken for DNS resolution";
    }
    leaf tcp-connect-rtt {
      type uint32;
      description
        "Sum of round-trip time taken for TCP connection";
    }
    leaf transaction-rtt {
      type uint32;
      description
        "Sum of round-trip time taken for HTTP transaction";
    }
    leaf time-to-first-byte {
      type uint32;
      description
        "Sum of round-trip time taken to receive the first byte";
    }
    leaf dns-timeout {
      type uint32;
      description
        "Number of DNS timeout";
    }
    leaf tcp-timeout {
      type uint32;
      description
        "Number of TCP connection timeout";
    }
    leaf transaction-timeout {
      type uint32;
      description
        "Number of HTTP transaction timeout";
    }
    leaf dns-error {
      type uint32;
      description
        "Number of DNS error";
    }
    leaf tcp-error {
      type uint32;
      description
        "Number of TCP connection error";
    }
    leaf transaction-error {
      type uint32;
      description
        "Number of HTTP transaction error";
    }
    leaf over-thresh {
      type uint32;
      description
        "Number of operations completed with round-trip time over the configured threshold";
    }
  }

  grouping sla-https-agg-stats {
    description
      "IPSLA HTTPs operation aggregated statistics";
    leaf url {
      type string;
      description
        "URL of the HTTPs operation";
    }
    leaf vrf-name {
      type string;
      description
        "Name of the VPN routing and forwarding instance
         associated with the IPSLA operation";
    }
    leaf dns-rtt {
      type uint32;
      description
        "Sum of round-trip time taken for DNS resolution";
    }
    leaf transaction-rtt {
      type uint32;
      description
        "Sum of round-trip time taken for HTTP transaction";
    }
    leaf dns-timeout {
      type uint32;
      description
        "Number of DNS timeout";
    }
    leaf transaction-timeout {
      type uint32;
      description
        "Number of HTTP transaction timeout";
    }
    leaf dns-error {
      type uint32;
      description
        "Number of DNS error";
    }
    leaf transaction-error {
      type uint32;
      description
        "Number of HTTP transaction error";
    }
    leaf over-thresh {
      type uint32;
      description
        "Number of operations completed with round-trip time over the configured threshold";
    }
  }

  grouping sla-dns-agg-stats {
    description
      "IPSLA DNS operation aggregated statistics";
    leaf name-server-addr {
      type inet:ip-address;
      description
        "Name server address";
    }
    leaf vrf-name {
      type string;
      description
        "Name of the VPN routing and forwarding instance
         associated with the IPSLA operation";
    }
    leaf over-thresh {
      type uint32;
      description
        "Number of operations completed with round-trip time over the configured threshold";
    }
  }

  grouping sla-dhcp-agg-stats {
    description
      "IPSLA DHCP operation aggregated statistics";
    leaf dest-addr {
      type inet:ip-address;
      description
        "Destination address of the IPSLA operation";
    }
    leaf over-thresh {
      type uint32;
      description
        "Number of operations completed with round-trip time over the configured threshold";
    }
  }

  grouping sla-path-echo-agg-stats {
    description
      "IPSLA Path-echo operation aggregated statistics";
    leaf dest-addr {
      type inet:ip-address;
      description
        "Destination address of the IPSLA operation";
    }
    leaf vrf-name {
      type string;
      description
        "Name of the VPN routing and forwarding instance
         associated with the IPSLA operation";
    }
  }

  grouping sla-ftp-agg-stats {
    description
      "IPSLA FTP operation aggregated statistics";
    leaf url {
      type string;
      description
        "URL of the operation";
    }
    leaf vrf-name {
      type string;
      description
        "Name of the VPN routing and forwarding instance
         associated with the IPSLA operation";
    }
    leaf over-thresh {
      type uint32;
      description
        "Number of operations completed with round-trip time over the configured threshold";
    }
  }

  grouping sla-lsp-agg-stats {
    description
      "IPSLA MPLS LSP ping and trace operations aggregated
       statistics";
    leaf dest-addr {
      type inet:ip-prefix;
      description
        "Destination address of the IPSLA operation";
    }
    leaf over-thresh {
      type uint32;
      description
        "Number of operations completed with round-trip time over the configured threshold";
    }
  }

  grouping sla-lsp-pseudo-ping-agg-stats {
    description
      "IPSLA MPLS pseudowire ping operation aggregated
       statistics";
    leaf dest-addr {
      type inet:ip-address;
      description
        "Destination address of the IPSLA operation";
    }
    leaf vccv-id {
      type uint32;
      description
        "MPLS LSP pseudowire VCCV ID";
    }
    leaf over-thresh {
      type uint32;
      description
        "Number of operations completed with round-trip time over the configured threshold";
    }
  }

  grouping sla-mcast-agg-stats {
    description
      "IPSLA Multicast UDP-jitter operation aggregated statistics";
    leaf dest-addr {
      type inet:ip-address;
      description
        "Destination address of the IPSLA operation";
    }
    leaf dest-port {
      type uint16;
      description
        "Destination port of the IPSLA operation";
    }
    leaf edpt-list-name {
      type string;
      description
        "Endpoint list name associated with the IPSLA operation";
    }
    leaf vrf-name {
      type string;
      description
        "Name of the VPN routing and forwarding instance
         associated with the IPSLA operation";
    }
    leaf over-thresh {
      type uint32;
      description
        "Number of operations completed with round-trip time over the configured threshold";
    }
  }

  grouping sla-mcast-dist-stats {
    description
      "IPSLA Multicast UDP-jitter Round-trip time distribution statistics";
    leaf dist-id {
      type uint16;
      description
        "Distribution range identifier";
    }
    leaf lower-limit {
      type uint32;
      description
        "Lower limit of the distribution range";
    }
    leaf upper-limit {
      type uint32;
      description
        "Upper limit of the distribution range";
    }
    leaf avg-latency {
      type uint32;
      description
        "Average latency";
    }
    leaf percent-of-total-comp {
      type uint32;
      description
        "Percent of total completions for this range";
    }
    leaf num-of-comp {
      type uint32;
      description
        "Number of completions with in this range";
    }
    leaf sum-of-latency {
      type uint32;
      description
        "Sum of latency with in this range";
    }
    leaf over-thresh {
      type uint32;
      description
        "Number of operations completed with round-trip time over the configured threshold";
    }
    leaf accuracy {
      type ip-sla-ios-xe-oper:accuracy-type;
      description
        "Reading accuracy";
    }
  }

  grouping sla-mcast-stats {
    description
      "IPSLA multicast UDP-jitter operation endpoint aggregated
       statistics";
    leaf mcast-id {
      type uint32;
      description
        "Multicast operation identifier";
    }
    leaf mcast-endpoint-addr {
      type inet:ip-address;
      description
        "Multicast endpoint address";
    }
    leaf start-time {
      type yang:date-and-time;
      description
        "Start time of the aggregated statistics";
    }
    container ow-stats {
      description
        "One-way latency statistics";
      uses ip-sla-ios-xe-oper:mcast-ow-latency;
    }
    container jitter-stats {
      description
        "Jitter statistics";
      uses ip-sla-ios-xe-oper:mcast-rfc-5481-ipdv;
    }
    leaf inter-arrival-jitter {
      type uint32;
      description
        "Inter arrival jitter time";
    }
    container loss-stats {
      description
        "Packet loss statistics";
      uses ip-sla-ios-xe-oper:mcast-pkt-loss;
    }
    container voice-stats {
      description
        "Voice score statistics";
      uses ip-sla-ios-xe-oper:voice-score-stats;
    }
    leaf success-count {
      type uint32;
      description
        "Success count";
    }
    leaf failure-count {
      type uint32;
      description
        "Failure count";
    }
    leaf over-thresh-occurred {
      type boolean;
      description
        "Over threshold occurred";
    }
    leaf over-thresh {
      type uint32;
      description
        "Number of operations completed with round-trip time over the configured threshold";
    }
    container common-failures {
      description
        "Common error statistics";
      uses ip-sla-ios-xe-oper:common-err-stats;
    }
    list sla-mcast-dist-stats {
      key "dist-id";
      description
        "Round-trip time distribution statistics";
      uses ip-sla-ios-xe-oper:sla-mcast-dist-stats;
    }
  }

  grouping sla-path-stats-key {
    description
      "Path specific aggregated statistics key for ICMP path-echo and
       MPLS LSP trace operations";
    leaf path-id {
      type uint8;
      description
        "Path identifier";
    }
    leaf hop-id {
      type uint8;
      description
        "Hop identifier";
    }
  }

  grouping sla-path-stats {
    description
      "Path specific aggregated statistics for ICMP path-echo and
       MPLS LSP trace operations";
    leaf start-time {
      type yang:date-and-time;
      description
        "Start time of the aggregated statistics";
    }
    leaf target-addr {
      type inet:ip-address;
      description
        "Target address";
    }
    leaf success-count {
      type uint32;
      description
        "Success count";
    }
    leaf failure-count {
      type uint32;
      description
        "Failure count";
    }
    leaf over-thresh {
      type uint32;
      description
        "Number of operations completed with round-trip time over the configured threshold";
    }
    container common-failures {
      description
        "Common error statistics";
      uses ip-sla-ios-xe-oper:common-err-stats;
    }
    list sla-path-dist-stats {
      key "dist-id";
      description
        "Round-trip time distribution statistics";
      uses ip-sla-ios-xe-oper:sla-dist-stats;
    }
  }

  grouping sla-agg-stats {
    description
      "IPSLA aggregated statistics";
    leaf oper-type {
      type ip-sla-ios-xe-oper:sla-oper-type;
      description
        "IPSLA operation type";
    }
    leaf start-time {
      type yang:date-and-time;
      description
        "Start time of the aggregated statistics";
    }
    leaf success-count {
      when "(../oper-type!='oper-type-path-echo') and
            (../oper-type!='oper-type-lsp-trace')";
      type uint32;
      description
        "Success count";
    }
    leaf failure-count {
      when "(../oper-type!='oper-type-path-echo') and
            (../oper-type!='oper-type-lsp-trace')";
      type uint32;
      description
        "Failure count";
    }
    container common-failures {
      when "(../oper-type!='oper-type-path-echo') and
            (../oper-type!='oper-type-lsp-trace')";
      description
        "Common error statistics";
      uses ip-sla-ios-xe-oper:common-err-stats;
    }
    list sla-dist-stats {
      when "(../oper-type!='oper-type-path-echo') and
            (../oper-type!='oper-type-lsp-trace')";
      key "dist-id";
      description
        "Round-trip time distribution statistics";
      uses ip-sla-ios-xe-oper:sla-dist-stats;
    }
    list sla-path-agg-stats {
      when "(../oper-type='oper-type-path-echo') or
            (../oper-type='oper-type-lsp-trace')";
      key "path-id hop-id";
      description
        "Path specific aggregated statistics for
         ICMP path-echo and MPLS LSP trace operations";
      uses ip-sla-ios-xe-oper:sla-path-stats;
      uses ip-sla-ios-xe-oper:sla-path-stats-key;
    }
    list sla-mcast-agg-stats {
      when "(../oper-type='oper-type-mcast')";
      key "mcast-id";
      description
        "IPSLA multicast UDP-jitter endpoint
         aggregated statistics";
      uses ip-sla-ios-xe-oper:sla-mcast-stats;
    }
    choice oper-stats-type-choice {
      description
        "IPSLA operation specific statistics";
      case oper-type-icmp-echo {
        container icmp-echo-stats {
          description
            "ICMP-echo operation aggregated statistics";
          uses ip-sla-ios-xe-oper:sla-icmp-echo-agg-stats;
        }
      }
      case oper-type-icmp-jitter {
        container icmp-jitter-stats {
          description
            "ICMP-jitter operation aggregated statistics";
          uses ip-sla-ios-xe-oper:sla-icmp-jitter-agg-stats;
        }
      }
      case oper-type-udp-echo {
        container udp-echo-stats {
          description
            "UDP-echo operation aggregated statistics";
          uses ip-sla-ios-xe-oper:sla-udp-tcp-agg-stats;
        }
      }
      case oper-type-udp-jitter {
        container udp-jitter-stats {
          description
            "UDP-jitter operation aggregated statistics";
          uses ip-sla-ios-xe-oper:sla-udp-jitter-agg-stats;
        }
      }
      case oper-type-tcp-connect {
        container tcp-connect-stats {
          description
            "TCP-connect operation aggregated statistics";
          uses ip-sla-ios-xe-oper:sla-udp-tcp-agg-stats;
        }
      }
      case oper-type-http {
        container http-stats {
          description
            "HTTP operation aggregated statistics";
          uses ip-sla-ios-xe-oper:sla-http-agg-stats;
        }
      }
      case oper-type-https {
        container https-stats {
          description
            "HTTPs operation aggregated statistics";
          uses ip-sla-ios-xe-oper:sla-https-agg-stats;
        }
      }
      case oper-type-dns {
        container dns-stats {
          description
            "DNS operation aggregated statistics";
          uses ip-sla-ios-xe-oper:sla-dns-agg-stats;
        }
      }
      case oper-type-dhcp {
        container dhcp-stats {
          description
            "DHCP operation aggregated statistics";
          uses ip-sla-ios-xe-oper:sla-dhcp-agg-stats;
        }
      }
      case oper-type-ftp {
        container ftp-stats {
          description
            "FTP operation aggregated statistics";
          uses ip-sla-ios-xe-oper:sla-ftp-agg-stats;
        }
      }
      case oper-type-lsp-ping {
        container lsp-ping-stats {
          description
            "MPLS LSP ping operation aggregated statistics";
          uses ip-sla-ios-xe-oper:sla-lsp-agg-stats;
        }
      }
      case oper-type-lsp-trace {
        container lsp-trace-stats {
          description
            "MPLS LSP trace operation aggregated statistics";
          uses ip-sla-ios-xe-oper:sla-lsp-agg-stats;
        }
      }
      case oper-type-lsp-ping-pseudowire {
        container lsp-pw-ping-stats {
          description
            "MPLS pseudowire ping operation aggregated statistics";
          uses ip-sla-ios-xe-oper:sla-lsp-pseudo-ping-agg-stats;
        }
      }
      case oper-type-path-echo {
        container path-echo-stats {
          description
            "Path-echo operation aggregated statistics";
          uses ip-sla-ios-xe-oper:sla-path-echo-agg-stats;
        }
      }
      case oper-type-mcast {
        container mcast-stats {
          description
            "Multicast UDP-jitter aggregated statistics";
          uses ip-sla-ios-xe-oper:sla-mcast-agg-stats;
        }
      }
    }
  }

  grouping y1731-delay-bin-stats {
    description
      "IP SLA Y1731 delay operation bin statistics";
    leaf lower-limit {
      type uint32;
      units "microseconds";
      description
        "Lower limit of the bin";
    }
    leaf upper-limit {
      type uint32;
      units "microseconds";
      description
        "Upper limit of the bin";
    }
    leaf total-obs {
      type uint32;
      description
        "Total number of observations within the lower
         and upper bin limit";
    }
  }

  grouping y1731-delay-bin-stats-key {
    description
      "IP SLA Y1731 delay operation bin statistics key";
    leaf delay-bin-type {
      type ip-sla-ios-xe-oper:sla-y1731-delay-bin-type;
      description
        "IP SLA Y1731 delay operation bin type";
    }
    leaf delay-bin-id {
      type uint8;
      description
        "IP SLA Y1731 delay operation bin identifier";
    }
  }

  grouping sla-y1731-hist-intvl-delay-stats {
    description
      "IP SLA Y1731 delay operation history interval statistics";
    container delay-stats {
      description
        "IP SLA Y1731 delay operation delay statistics";
      uses ip-sla-ios-xe-oper:sla-y1731-delay-stats-delay-type;
    }
    container jitter-stats {
      description
        "IP SLA Y1731 delay operation jitter statistics";
      uses ip-sla-ios-xe-oper:sla-y1731-delay-stats-jitter-type;
    }
  }

  grouping sla-y1731-hist-loss-stats {
    description
      "IP SLA Y1731 loss operation history interval statistics";
    leaf num-obs {
      type uint64;
      description
        "Number of observations";
    }
    leaf num-avail-indic {
      type uint64;
      description
        "Number of available indicators";
    }
    leaf num-unavail-indic {
      type uint64;
      description
        "Number of unavailable indicators";
    }
    leaf tx-frames {
      type uint64;
      description
        "Number of frames transmitted";
    }
    leaf rx-frames {
      type uint64;
      description
        "Number of frames received";
    }
    leaf min-lost-frames {
      type uint64;
      description
        "Minimum lost frames";
    }
    leaf min-tx-frames {
      type uint64;
      description
        "Minimum transmitted frames";
    }
    leaf frame-loss-ratio {
      type decimal64 {
        fraction-digits 2;
      }
      description
        "Frame loss ratio percentage";
    }
    leaf max-lost-frames {
      type uint64;
      description
        "Maximum lost frames";
    }
    leaf max-tx-frames {
      type uint64;
      description
        "Maximum transmitted frames";
    }
    leaf cum-frame-loss-ratio {
      type decimal64 {
        fraction-digits 2;
      }
      description
        "Cumulative frame loss ratio percentage";
    }
    leaf min-loss-obs-time {
      type yang:date-and-time;
      description
        "Time at which the minimum frame loss occurred";
    }
    leaf max-loss-obs-time {
      type yang:date-and-time;
      description
        "Time at which the maximum frame loss occurred";
    }
  }

  grouping sla-y1731-hist-intvl-loss-stats {
    description
      "IP SLA Y1731 history interval loss statistics";
    container forward-stats {
      description
        "IP SLA Y1731 loss operation forward loss statistics";
      uses ip-sla-ios-xe-oper:sla-y1731-hist-loss-stats;
    }
    container backward-stats {
      description
        "IP SLA Y1731 loss operation backward loss statistics";
      uses ip-sla-ios-xe-oper:sla-y1731-hist-loss-stats;
    }
  }

  grouping sla-y1731-hist-intvl-stats-key {
    description
      "IP SLA Y1731 history interval loss statistics key";
    leaf oper-id {
      type uint32;
      description
        "IP SLA Y1731 operation identifier";
    }
    leaf intvl-id {
      type uint8;
      description
        "IP SLA Y1731 operation history interval identifier";
    }
  }

  grouping sla-y1731-hist-intvl-stats {
    description
      "IP SLA Y1731 history interval statistics";
    leaf y1731-type {
      type ip-sla-ios-xe-oper:sla-oper-type;
      description
        "IP SLA Y1731 operation type";
    }
    leaf latest-start-time {
      type yang:date-and-time;
      description
        "IP SLA Y1731 operation latest start time";
    }
    leaf latest-return-code {
      type ip-sla-ios-xe-oper:sla-return-code;
      description
        "IP SLA Y1731 operation latest return code";
    }
    leaf intvl-start-time {
      type yang:date-and-time;
      description
        "IP SLA Y1731 operation history interval start time";
    }
    leaf intvl-end-time {
      type yang:date-and-time;
      description
        "IP SLA Y1731 operation history interval end time";
    }
    leaf init-count {
      type uint64;
      description
        "Number of measurements initiated in the history interval";
    }
    leaf comp-count {
      type uint64;
      description
        "Number of measurements completed in the history interval";
    }
    leaf status-flag {
      type ip-sla-ios-xe-oper:sla-y1731-status;
      description
        "Status flag of the IP SLA Y1731 operation";
    }
    list sla-bin-stats {
      when "(../y1731-type='oper-type-y1731-delay')";
      key "delay-bin-type delay-bin-id";
      description
        "IP SLA Y1731 delay bin statistics";
      uses ip-sla-ios-xe-oper:y1731-delay-bin-stats;
      uses ip-sla-ios-xe-oper:y1731-delay-bin-stats-key;
    }
    choice y1731-stats-type-choice {
      description
        "IP SLA Y1731 operation specific statistics";
      case oper-type-y1731-delay {
        container y1731-delay-stats {
          description
            "IP SLA Y1731 delay operation history interval statistics";
          uses ip-sla-ios-xe-oper:sla-y1731-hist-intvl-delay-stats;
        }
      }
      case oper-type-y1731-loss {
        container y1731-loss-stats {
          description
            "IP SLA Y1731 loss operation history interval statistics";
          uses ip-sla-ios-xe-oper:sla-y1731-hist-intvl-loss-stats;
        }
      }
    }
  }

  grouping sla-sp-loss-stats {
    description
      "IP SLA service performance loss statistics";
    leaf loss {
      type uint64;
      description
        "Frame loss count";
    }
    leaf flr {
      type decimal64 {
        fraction-digits 2;
      }
      description
        "Frame loss ratio percentage";
    }
    leaf avail {
      type decimal64 {
        fraction-digits 2;
      }
      description
        "Service availability in percentage";
    }
  }

  grouping sla-sp-time {
    description
      "SLA time values";
    leaf val {
      type decimal64 {
        fraction-digits 2;
      }
      description
        "Minimum value reading";
    }
    leaf accy {
      type ip-sla-ios-xe-oper:accuracy-type;
      description
        "Reading accuracy";
    }
  }

  grouping sla-sp-delay-stats {
    description
      "IP SLA service performance delay statistics";
    container min {
      description
        "Minimum delay value";
      uses ip-sla-ios-xe-oper:sla-sp-time;
    }
    container avg {
      description
        "Average delay value";
      uses ip-sla-ios-xe-oper:sla-sp-time;
    }
    container max {
      description
        "Maximum delay value";
      uses ip-sla-ios-xe-oper:sla-sp-time;
    }
  }

  grouping sla-sp-out-of-seq-stats {
    description
      "IP SLA service performance out-of-sequence packet statistics";
    leaf oos {
      type uint64;
      description
        "Number of out-of-sequence packets";
    }
    leaf oos-evts {
      type uint64;
      description
        "Number of out-of-sequence events";
    }
    leaf oos-max {
      type uint64;
      description
        "Maximum out-of-sequence packets";
    }
  }

  grouping sla-sp-pkt-stats {
    description
      "IP SLA service performance packet statistics";
    leaf pkts {
      type uint64;
      description
        "Number of packets";
    }
    leaf bytes {
      type uint64;
      description
        "Number of bytes";
    }
  }

  grouping sla-sp-rate-step-stats-key {
    description
      "IP SLA service performance rate step statistics key information";
    leaf step-id {
      type uint16;
      description
        "IP SLA service performance step identifier";
    }
    leaf tclass {
      type ip-sla-ios-xe-oper:sla-sp-traffic-class;
      description
        "IP SLA service performance traffic class type";
    }
  }

  grouping sla-sp-rate-step-stats {
    description
      "IP SLA service performance per rate step statistics";
    leaf rate {
      type uint32;
      description
        "Traffic rate";
    }
    leaf rtype {
      type ip-sla-ios-xe-oper:sla-sp-rate-type;
      description
        "Traffic rate type";
    }
    leaf mode {
      type ip-sla-ios-xe-oper:sla-sp-oper-mode;
      description
        "Operation mode";
    }
    leaf ir {
      type empty;
      description
        "Information rate measurement";
    }
    leaf loss {
      type empty;
      description
        "Packet loss measurement";
    }
    leaf delay {
      type empty;
      description
        "Delay measurement";
    }
    leaf dly-var {
      type empty;
      description
        "Delay variance measurement";
    }
    leaf oos {
      type empty;
      description
        "Out-of-sequence measurement";
    }
    leaf ir-val {
      when '(../ir)';
      type uint64;
      units "Kilobytes per second";
      description
        "Information rate";
    }
    container loss-stats {
      when '(../loss)';
      description
        "Frame loss statistics";
      uses ip-sla-ios-xe-oper:sla-sp-loss-stats;
    }
    container dly-stats {
      when '(../delay)';
      description
        "Frame delay statistics";
      uses ip-sla-ios-xe-oper:sla-sp-delay-stats;
    }
    container dv-stats {
      when '(../dly-var)';
      description
        "Frame delay variance statistics";
      uses ip-sla-ios-xe-oper:sla-sp-delay-stats;
    }
    container oos-stats {
      when '(../oos)';
      description
        "Frame out-of-sequence statistics";
      uses ip-sla-ios-xe-oper:sla-sp-out-of-seq-stats;
    }
    container tx-stats {
      when "(../mode!='sp-pass-mode')";
      description
        "Transmitted packets statistics";
      uses ip-sla-ios-xe-oper:sla-sp-pkt-stats;
    }
    container rx-stats {
      when "(../mode!='sp-tgen-mode')";
      description
        "Received packets statistics";
      uses ip-sla-ios-xe-oper:sla-sp-pkt-stats;
    }
    leaf dur {
      type uint32;
      description
        "Test duration";
    }
  }

  grouping sla-serv-perf-stats {
    description
      "IP SLA service performance statistics";
    leaf sp-type {
      type ip-sla-ios-xe-oper:sla-sp-client-type;
      description
        "IP SLA operation type";
    }
    leaf sp-mode {
      type ip-sla-ios-xe-oper:sla-sp-oper-mode;
      description
        "IP SLA service performance operation mode";
    }
    leaf rem-addr {
      when "(../sp-mode='sp-ow-mode')";
      type inet:ip-address;
      description
        "IP SLA service performance operation remote address";
    }
    leaf meas-time {
      type yang:date-and-time;
      description
        "IP SLA service performance measurement time";
    }
    choice dur-type-choice {
      description
        "IP SLA service performance test duration choice";
      case type-dur {
        leaf dur {
          type uint32;
          description
            "Test duration in seconds";
        }
      }
      case type-pkts {
        leaf pkts {
          type uint32;
          description
            "Test duration in packets";
        }
      }
    }
    choice tput-type-choice {
      description
        "IP SLA service performance throughput choice";
      case tput-prog {
        leaf tp-inprog {
          type empty;
          description
            "Throughput measurement in progress";
        }
      }
      case tput-undef {
        leaf tp-undef {
          type empty;
          description
            "Throughput measurement undefined - All steps have loss";
        }
      }
      case tput-val {
        leaf tput {
          type uint64;
          description
            "Throughput value";
        }
      }
    }
  }

  grouping sla-sp-stats {
    description
      "IP SLA service performance latest statistics ";
    leaf oper-id {
      type uint32;
      description
        "IP SLA service performance operation identifier";
    }
    leaf ret-code {
      type ip-sla-ios-xe-oper:sla-return-code;
      description
        "IP SLA service performance operation return code";
    }
    leaf supprsd {
      type boolean;
      description
        "This indicates IP SLA service performance statistics is suppressed";
    }
    container sp-stats {
      when "(../supprsd='false')";
      description
        "IP SLA service performance statistics";
      uses ip-sla-ios-xe-oper:sla-serv-perf-stats;
    }
    list step-stats {
      when "(../supprsd='false')";
      key "step-id tclass";
      description
        "IP SLA service performance rate step statistics";
      uses ip-sla-ios-xe-oper:sla-sp-rate-step-stats;
      uses ip-sla-ios-xe-oper:sla-sp-rate-step-stats-key;
    }
  }

  grouping sla-sp-hist-stats-key {
    description
      "IP SLA service performance history interval statistics key information";
    leaf oper-id {
      type uint32;
      description
        "IP SLA service performance operation identifier";
    }
    leaf intvl-id {
      type uint8;
      description
        "IP SLA service performance history interval identifier";
    }
  }

  grouping sla-sp-hist-stats {
    description
      "IP SLA service performance history interval statistics";
    leaf ret-code {
      type ip-sla-ios-xe-oper:sla-return-code;
      description
        "IP SLA service performance operation return code";
    }
    container sp-stats {
      description
        "IP SLA service performance statistics";
      uses ip-sla-ios-xe-oper:sla-serv-perf-stats;
    }
    list hist-step-stats {
      key "step-id tclass";
      description
        "IP SLA service performance history rate step statistics";
      uses ip-sla-ios-xe-oper:sla-sp-rate-step-stats;
      uses ip-sla-ios-xe-oper:sla-sp-rate-step-stats-key;
    }
  }

  container ip-sla-stats {
    config false;
    description
      "Data nodes for All IP SLA Statistics";
    list sla-oper-entry {
      key "oper-id";
      description
        "The list of IP SLA operations with statistics
         info";
      uses ip-sla-ios-xe-oper:sla-oper-entry;
    }
    list sla-oper-error-statistics {
      key "oper-id start-time-id path-index hop-index";
      description
        "The list of IP SLA operations error statistics";
      uses ip-sla-ios-xe-oper:sla-err-stats;
      uses ip-sla-ios-xe-oper:sla-err-stats-key;
    }
    list sla-oper-total-statistics {
      key "oper-id start-time-id";
      description
        "The list of IP SLA operations total statistics";
      uses ip-sla-ios-xe-oper:sla-total-stats-entry;
      uses ip-sla-ios-xe-oper:sla-total-stats-key;
    }
    list sla-path-echo-stats {
      key "oper-id path-id hop-id";
      description
        "The list of IP SLA path echo operations with latest
         statistics information";
      uses ip-sla-ios-xe-oper:path-echo-stats-entry;
      uses ip-sla-ios-xe-oper:path-echo-stats-key;
    }
    list sla-path-jitter-stats {
      key "oper-id hop-id";
      description
        "The list of IP SLA path jitter operations with latest
         statistics information";
      uses ip-sla-ios-xe-oper:path-jitter-stats-entry;
      uses ip-sla-ios-xe-oper:path-jitter-stats-key;
    }
    list sla-agg-stats {
      key "oper-id hour-id";
      description
        "The list of IPSLA aggregated statistics";
      uses ip-sla-ios-xe-oper:sla-agg-stats;
      uses ip-sla-ios-xe-oper:sla-agg-stats-key;
    }
    list sla-hist-stats {
      key "oper-id intvl-id";
      description
        "The list of IPSLA Y1731 delay and loss
         operation history interval statistics";
      uses ip-sla-ios-xe-oper:sla-y1731-hist-intvl-stats;
      uses ip-sla-ios-xe-oper:sla-y1731-hist-intvl-stats-key;
    }
    list sla-sp-stats {
      key "oper-id";
      description
        "The list of IPSLA service performance operation latest statistics";
      uses ip-sla-ios-xe-oper:sla-sp-stats;
    }
    list sla-sp-hist-stats {
      key "oper-id intvl-id";
      description
        "The list of IPSLA service performance operation history interval statistics";
      uses ip-sla-ios-xe-oper:sla-sp-hist-stats;
      uses ip-sla-ios-xe-oper:sla-sp-hist-stats-key;
    }
  }
}
