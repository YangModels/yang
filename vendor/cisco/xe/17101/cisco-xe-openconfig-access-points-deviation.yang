module cisco-xe-openconfig-access-points-deviation {
  namespace "http://openconfig.net/yang/cisco-xe-openconfig-access-points-deviation";
  prefix oc-of-wifi-devs;

  import cisco-semver {
    prefix cisco-semver;
  }
  import openconfig-access-points {
    prefix access-points;
  }
  import openconfig-ap-manager {
    prefix ap-manager;
  }

  organization
    "Cisco Systems, Inc.";
  contact
    " Cisco Systems, Inc.
     Customer Service

     Postal: 170 W Tasman Drive
     San Jose, CA 95134

     Tel: +1 1800 553-NETS

     E-mail: cs-yang@cisco.com";
  description
    "This module defines deviation statements for openconfig-access-points module.";

  revision 2020-03-01 {
    description
      "- Added deviations for dependant nodes already deviated away";
    cisco-semver:module-version "1.0.0";
  }
  revision 2019-11-01 {
    description
      "Added deviation for rx-retries, rx-retries-data and rx-retries-subframe";
  }
  revision 2018-12-04 {
    description
      "Remove deviation for 'dva' and add mapping";
  }
  revision 2018-11-25 {
    description
      "Added 'dva' under deviation as a part of up-rev changes(0.3.0)";
  }
  revision 2018-09-25 {
    description
      "Remove deviation for 'dva', 'wmm' and client capabilities 'channel-support', 'dot11v-bssidle-timeout'.
       Add deviation for 'trust-dscp'.";
  }
  revision 2018-09-06 {
    description
      "Remove deviation for client connection 'ipv6-address'";
  }
  revision 2018-08-28 {
    description
      "Remove deviation for client 'phy-rate', 'frequency', 'client-capabilities'";
  }
  revision 2018-08-09 {
    description
      "Remove deviation for 'steering-rssi', 'basic-data-rates', 'supported-data-rates'";
  }
  revision 2018-07-12 {
    description
      "Initial version";
  }

  deviation "/access-points:access-points/access-points:access-point/access-points:radios/access-points:radio/access-points:config/access-points:scanning" {
    deviate not-supported;
    description
      "Not implemented in vWLC controller";
  }

  deviation "/access-points:access-points/access-points:access-point/access-points:radios/access-points:radio/access-points:state/access-points:scanning" {
    deviate not-supported;
    description
      "Not implemented in vWLC controller";
  }

  deviation "/access-points:access-points/access-points:access-point/access-points:radios/access-points:radio/access-points:config/access-points:scanning-interval" {
    deviate not-supported;
    description
      "Not implemented in vWLC controller";
  }

  deviation "/access-points:access-points/access-points:access-point/access-points:radios/access-points:radio/access-points:state/access-points:scanning-interval" {
    deviate not-supported;
    description
      "Not implemented in vWLC controller";
  }

  deviation "/access-points:access-points/access-points:access-point/access-points:radios/access-points:radio/access-points:config/access-points:scanning-dwell-time" {
    deviate not-supported;
    description
      "Not implemented in vWLC controller";
  }

  deviation "/access-points:access-points/access-points:access-point/access-points:radios/access-points:radio/access-points:state/access-points:scanning-dwell-time" {
    deviate not-supported;
    description
      "Not implemented in vWLC controller";
  }

  deviation "/access-points:access-points/access-points:access-point/access-points:radios/access-points:radio/access-points:config/access-points:scanning-defer-clients" {
    deviate not-supported;
    description
      "Not implemented in vWLC controller";
  }

  deviation "/access-points:access-points/access-points:access-point/access-points:radios/access-points:radio/access-points:state/access-points:scanning-defer-clients" {
    deviate not-supported;
    description
      "Not implemented in vWLC controller";
  }

  deviation "/access-points:access-points/access-points:access-point/access-points:radios/access-points:radio/access-points:config/access-points:scanning-defer-traffic" {
    deviate not-supported;
    description
      "Not implemented in vWLC controller";
  }

  deviation "/access-points:access-points/access-points:access-point/access-points:radios/access-points:radio/access-points:state/access-points:scanning-defer-traffic" {
    deviate not-supported;
    description
      "Not implemented in vWLC controller";
  }

  deviation "/access-points:access-points/access-points:access-point/access-points:ssids/access-points:ssid/access-points:config/access-points:ipv6-ndp-filter" {
    deviate not-supported;
    description
      "Not implemented in vWLC controller";
  }

  deviation "/access-points:access-points/access-points:access-point/access-points:ssids/access-points:ssid/access-points:config/access-points:ipv6-ndp-filter-timer" {
    deviate not-supported;
    description
      "Not implemented in vWLC controller";
  }

  deviation "/access-points:access-points/access-points:access-point/access-points:ssids/access-points:ssid/access-points:config/access-points:mobility-domain" {
    deviate not-supported;
    description
      "Not implemented in vWLC controller";
  }

  deviation "/access-points:access-points/access-points:access-point/access-points:ssids/access-points:ssid/access-points:state/access-points:ipv6-ndp-filter" {
    deviate not-supported;
    description
      "Not implemented in vWLC controller";
  }

  deviation "/access-points:access-points/access-points:access-point/access-points:ssids/access-points:ssid/access-points:state/access-points:ipv6-ndp-filter-timer" {
    deviate not-supported;
    description
      "Not implemented in vWLC controller";
  }

  deviation "/access-points:access-points/access-points:access-point/access-points:ssids/access-points:ssid/access-points:state/access-points:bssids/access-points:bssid/access-points:state/access-points:counters/access-points:rx-bss-dot11-channel-utilization" {
    deviate not-supported;
    description
      "Not implemented in vWLC controller";
  }

  deviation "/access-points:access-points/access-points:access-point/access-points:ssids/access-points:ssid/access-points:state/access-points:bssids/access-points:bssid/access-points:state/access-points:counters/access-points:tx-bss-dot11-channel-utilization" {
    deviate not-supported;
    description
      "Not implemented in vWLC controller";
  }

  deviation "/access-points:access-points/access-points:access-point/access-points:ssids/access-points:ssid/access-points:state/access-points:bssids/access-points:bssid/access-points:state/access-points:counters/access-points:rx-retries" {
    deviate not-supported;
    description
      "Not implemented in vWLC controller";
  }

  deviation "/access-points:access-points/access-points:access-point/access-points:ssids/access-points:ssid/access-points:state/access-points:bssids/access-points:bssid/access-points:state/access-points:counters/access-points:rx-retries-data" {
    deviate not-supported;
    description
      "Not implemented in vWLC controller";
  }

  deviation "/access-points:access-points/access-points:access-point/access-points:ssids/access-points:ssid/access-points:state/access-points:bssids/access-points:bssid/access-points:state/access-points:counters/access-points:rx-retries-subframe" {
    deviate not-supported;
    description
      "Not implemented in vWLC controller";
  }

  deviation "/access-points:access-points/access-points:access-point/access-points:ssids/access-points:ssid/access-points:state/access-points:mobility-domain" {
    deviate not-supported;
    description
      "Not implemented in vWLC controller";
  }

  deviation "/access-points:access-points/access-points:access-point/access-points:ssids/access-points:ssid/access-points:wmm/access-points:config/access-points:trust-dscp" {
    deviate not-supported;
    description
      "Not implemented in vWLC controller";
  }

  deviation "/access-points:access-points/access-points:access-point/access-points:ssids/access-points:ssid/access-points:wmm/access-points:state/access-points:trust-dscp" {
    deviate not-supported;
    description
      "Not implemented in vWLC controller";
  }

  deviation "/access-points:access-points/access-points:access-point/access-points:ssids/access-points:ssid/access-points:dot11r/access-points:config/access-points:dot11r-r1key-timeout" {
    deviate not-supported;
    description
      "Not implemented in vWLC controller";
  }

  deviation "/access-points:access-points/access-points:access-point/access-points:ssids/access-points:ssid/access-points:dot11r/access-points:state/access-points:dot11r-r1key-timeout" {
    deviate not-supported;
    description
      "Not implemented in vWLC controller";
  }

  deviation "/access-points:access-points/access-points:access-point/access-points:ssids/access-points:ssid/access-points:dot11r/access-points:config/access-points:dot11r" {
    deviate add {
      default "false";
    }
    description
      "Dot11r need to be disabled by default";
  }

  deviation "/access-points:access-points/access-points:access-point/access-points:ssids/access-points:ssid/access-points:clients/access-points:client/access-points:dot11k-neighbors" {
    deviate not-supported;
    description
      "Not implemented in vWLC controller";
  }

  deviation "/access-points:access-points/access-points:access-point/access-points:ssids/access-points:ssid/access-points:clients/access-points:client/access-points:state/access-points:counters/access-points:rx-retries" {
    deviate not-supported;
    description
      "Not implemented in vWLC controller";
  }

  deviation "/access-points:access-points/access-points:access-point/access-points:ssids/access-points:ssid/access-points:clients/access-points:client/access-points:client-connection/access-points:state/access-points:operating-system" {
    deviate not-supported;
    description
      "Not implemented in vWLC controller";
  }

  deviation "/access-points:access-points/access-points:access-point/access-points:system/access-points:config/access-points:domain-name" {
    deviate not-supported;
    description
      "Not implemented in vWLC controller";
  }

  deviation "/access-points:access-points/access-points:access-point/access-points:system/access-points:config/access-points:login-banner" {
    deviate not-supported;
    description
      "Not implemented in vWLC controller";
  }

  deviation "/access-points:access-points/access-points:access-point/access-points:system/access-points:config/access-points:motd-banner" {
    deviate not-supported;
    description
      "Not implemented in vWLC controller";
  }

  deviation "/access-points:access-points/access-points:access-point/access-points:system/access-points:state/access-points:domain-name" {
    deviate not-supported;
    description
      "Not implemented in vWLC controller";
  }

  deviation "/access-points:access-points/access-points:access-point/access-points:system/access-points:state/access-points:login-banner" {
    deviate not-supported;
    description
      "Not implemented in vWLC controller";
  }

  deviation "/access-points:access-points/access-points:access-point/access-points:system/access-points:state/access-points:motd-banner" {
    deviate not-supported;
    description
      "Not implemented in vWLC controller";
  }

  deviation "/access-points:access-points/access-points:access-point/access-points:system/access-points:aaa/access-points:authentication/access-points:users/access-points:user/access-points:config/access-points:password-hashed" {
    deviate not-supported;
    description
      "Not implemented in vWLC controller";
  }

  deviation "/access-points:access-points/access-points:access-point/access-points:system/access-points:aaa/access-points:authentication/access-points:users/access-points:user/access-points:state/access-points:password-hashed" {
    deviate not-supported;
    description
      "Not implemented in vWLC controller";
  }

  deviation "/access-points:access-points/access-points:access-point/access-points:system/access-points:aaa/access-points:authentication/access-points:users/access-points:user/access-points:config/access-points:ssh-key" {
    deviate not-supported;
    description
      "Not implemented in vWLC controller";
  }

  deviation "/access-points:access-points/access-points:access-point/access-points:system/access-points:aaa/access-points:state" {
    deviate not-supported;
    description
      "Not implemented in vWLC controller";
  }

  deviation "/access-points:access-points/access-points:access-point/access-points:system/access-points:aaa/access-points:authentication/access-points:users/access-points:user/access-points:state/access-points:ssh-key" {
    deviate not-supported;
    description
      "Not implemented in vWLC controller";
  }

  deviation "/access-points:access-points/access-points:access-point/access-points:system/access-points:aaa/access-points:authentication/access-points:users/access-points:user/access-points:config/access-points:role" {
    deviate not-supported;
    description
      "Not implemented in vWLC controller";
  }

  deviation "/access-points:access-points/access-points:access-point/access-points:system/access-points:aaa/access-points:authentication/access-points:users/access-points:user/access-points:state/access-points:role" {
    deviate not-supported;
    description
      "Not implemented in vWLC controller";
  }

  deviation "/access-points:access-points/access-points:access-point/access-points:system/access-points:state/access-points:current-datetime" {
    deviate not-supported;
    description
      "Not implemented in vWLC controller";
  }

  deviation "/access-points:access-points/access-points:access-point/access-points:system/access-points:state/access-points:boot-time" {
    deviate not-supported;
    description
      "Not implemented in vWLC controller";
  }

  deviation "/access-points:access-points/access-points:access-point/access-points:system/access-points:clock" {
    deviate not-supported;
    description
      "Not implemented in vWLC controller";
  }

  deviation "/access-points:access-points/access-points:access-point/access-points:system/access-points:dns" {
    deviate not-supported;
    description
      "Not implemented in vWLC controller";
  }

  deviation "/access-points:access-points/access-points:access-point/access-points:system/access-points:telnet-server" {
    deviate not-supported;
    description
      "Not implemented in vWLC controller";
  }

  deviation "/access-points:access-points/access-points:access-point/access-points:system/access-points:ntp/access-points:config/access-points:ntp-source-address" {
    deviate not-supported;
    description
      "Not implemented in vWLC controller";
  }

  deviation "/access-points:access-points/access-points:access-point/access-points:system/access-points:ntp/access-points:config/access-points:enable-ntp-auth" {
    deviate not-supported;
    description
      "Not implemented in vWLC controller";
  }

  deviation "/access-points:access-points/access-points:access-point/access-points:system/access-points:ntp/access-points:state/access-points:ntp-source-address" {
    deviate not-supported;
    description
      "Not implemented in vWLC controller";
  }

  deviation "/access-points:access-points/access-points:access-point/access-points:system/access-points:ntp/access-points:state/access-points:enable-ntp-auth" {
    deviate not-supported;
    description
      "Not implemented in vWLC controller";
  }

  deviation "/access-points:access-points/access-points:access-point/access-points:system/access-points:ntp/access-points:state/access-points:auth-mismatch" {
    deviate not-supported;
    description
      "Not implemented in vWLC controller";
  }

  deviation "/access-points:access-points/access-points:access-point/access-points:system/access-points:ntp/access-points:ntp-keys" {
    deviate not-supported;
    description
      "Not implemented in vWLC controller";
  }

  deviation "/access-points:access-points/access-points:access-point/access-points:system/access-points:ntp/access-points:servers/access-points:server/access-points:config/access-points:port" {
    deviate not-supported;
    description
      "Not implemented in vWLC controller";
  }

  deviation "/access-points:access-points/access-points:access-point/access-points:system/access-points:ntp/access-points:servers/access-points:server/access-points:config/access-points:version" {
    deviate not-supported;
    description
      "Not implemented in vWLC controller";
  }

  deviation "/access-points:access-points/access-points:access-point/access-points:system/access-points:ntp/access-points:servers/access-points:server/access-points:config/access-points:association-type" {
    deviate not-supported;
    description
      "Not implemented in vWLC controller";
  }

  deviation "/access-points:access-points/access-points:access-point/access-points:system/access-points:ntp/access-points:servers/access-points:server/access-points:config/access-points:iburst" {
    deviate not-supported;
    description
      "Not implemented in vWLC controller";
  }

  deviation "/access-points:access-points/access-points:access-point/access-points:system/access-points:ntp/access-points:servers/access-points:server/access-points:config/access-points:prefer" {
    deviate not-supported;
    description
      "Not implemented in vWLC controller";
  }

  deviation "/access-points:access-points/access-points:access-point/access-points:system/access-points:ntp/access-points:servers/access-points:server/access-points:state/access-points:port" {
    deviate not-supported;
    description
      "Not implemented in vWLC controller";
  }

  deviation "/access-points:access-points/access-points:access-point/access-points:system/access-points:ntp/access-points:servers/access-points:server/access-points:state/access-points:version" {
    deviate not-supported;
    description
      "Not implemented in vWLC controller";
  }

  deviation "/access-points:access-points/access-points:access-point/access-points:system/access-points:ntp/access-points:servers/access-points:server/access-points:state/access-points:association-type" {
    deviate not-supported;
    description
      "Not implemented in vWLC controller";
  }

  deviation "/access-points:access-points/access-points:access-point/access-points:system/access-points:ntp/access-points:servers/access-points:server/access-points:state/access-points:iburst" {
    deviate not-supported;
    description
      "Not implemented in vWLC controller";
  }

  deviation "/access-points:access-points/access-points:access-point/access-points:system/access-points:ntp/access-points:servers/access-points:server/access-points:state/access-points:prefer" {
    deviate not-supported;
    description
      "Not implemented in vWLC controller";
  }

  deviation "/access-points:access-points/access-points:access-point/access-points:system/access-points:ntp/access-points:servers/access-points:server/access-points:state/access-points:stratum" {
    deviate not-supported;
    description
      "Not implemented in vWLC controller";
  }

  deviation "/access-points:access-points/access-points:access-point/access-points:system/access-points:ntp/access-points:servers/access-points:server/access-points:state/access-points:root-delay" {
    deviate not-supported;
    description
      "Not implemented in vWLC controller";
  }

  deviation "/access-points:access-points/access-points:access-point/access-points:system/access-points:ntp/access-points:servers/access-points:server/access-points:state/access-points:root-dispersion" {
    deviate not-supported;
    description
      "Not implemented in vWLC controller";
  }

  deviation "/access-points:access-points/access-points:access-point/access-points:system/access-points:ntp/access-points:servers/access-points:server/access-points:state/access-points:offset" {
    deviate not-supported;
    description
      "Not implemented in vWLC controller";
  }

  deviation "/access-points:access-points/access-points:access-point/access-points:system/access-points:ntp/access-points:servers/access-points:server/access-points:state/access-points:poll-interval" {
    deviate not-supported;
    description
      "Not implemented in vWLC controller";
  }

  deviation "/access-points:access-points/access-points:access-point/access-points:system/access-points:ssh-server/access-points:config/access-points:enable" {
    deviate replace {
      default "false";
    }
    description
      "Enabling ssh by default is a security risk hence making default false";
  }

  deviation "/access-points:access-points/access-points:access-point/access-points:system/access-points:ssh-server/access-points:config/access-points:timeout" {
    deviate not-supported;
    description
      "Not implemented in vWLC controller";
  }

  deviation "/access-points:access-points/access-points:access-point/access-points:system/access-points:ssh-server/access-points:config/access-points:protocol-version" {
    deviate not-supported;
    description
      "Not implemented in vWLC controller";
  }

  deviation "/access-points:access-points/access-points:access-point/access-points:system/access-points:ssh-server/access-points:config/access-points:rate-limit" {
    deviate not-supported;
    description
      "Not implemented in vWLC controller";
  }

  deviation "/access-points:access-points/access-points:access-point/access-points:system/access-points:ssh-server/access-points:config/access-points:session-limit" {
    deviate not-supported;
    description
      "Not implemented in vWLC controller";
  }

  deviation "/access-points:access-points/access-points:access-point/access-points:system/access-points:ssh-server/access-points:state/access-points:protocol-version" {
    deviate not-supported;
    description
      "Not implemented in vWLC controller";
  }

  deviation "/access-points:access-points/access-points:access-point/access-points:system/access-points:ssh-server/access-points:state/access-points:rate-limit" {
    deviate not-supported;
    description
      "Not implemented in vWLC controller";
  }

  deviation "/access-points:access-points/access-points:access-point/access-points:system/access-points:ssh-server/access-points:state/access-points:session-limit" {
    deviate not-supported;
    description
      "Not implemented in vWLC controller";
  }

  deviation "/access-points:access-points/access-points:access-point/access-points:system/access-points:ssh-server/access-points:state/access-points:timeout" {
    deviate not-supported;
    description
      "Not implemented in vWLC controller";
  }

  deviation "/access-points:access-points/access-points:access-point/access-points:system/access-points:logging" {
    deviate not-supported;
    description
      "Not implemented in vWLC controller";
  }

  deviation "/access-points:access-points/access-points:access-point/access-points:system/access-points:memory" {
    deviate not-supported;
    description
      "Not implemented in vWLC controller";
  }

  deviation "/access-points:access-points/access-points:access-point/access-points:system/access-points:aaa/access-points:authorization/access-points:events" {
    deviate not-supported;
    description
      "Not implemented in vWLC controller";
  }

  deviation "/access-points:access-points/access-points:access-point/access-points:system/access-points:cpus/access-points:cpu/access-points:state/access-points:total/access-points:min-time" {
    deviate not-supported;
    description
      "Not implemented in vWLC controller";
  }

  deviation "/access-points:access-points/access-points:access-point/access-points:system/access-points:cpus/access-points:cpu/access-points:state/access-points:total/access-points:max-time" {
    deviate not-supported;
    description
      "Not implemented in vWLC controller";
  }

  deviation "/access-points:access-points/access-points:access-point/access-points:system/access-points:cpus/access-points:cpu/access-points:state/access-points:total/access-points:avg" {
    deviate not-supported;
    description
      "Not implemented in vWLC controller";
  }

  deviation "/access-points:access-points/access-points:access-point/access-points:system/access-points:cpus/access-points:cpu/access-points:state/access-points:total/access-points:min" {
    deviate not-supported;
    description
      "Not implemented in vWLC controller";
  }

  deviation "/access-points:access-points/access-points:access-point/access-points:system/access-points:cpus/access-points:cpu/access-points:state/access-points:total/access-points:max" {
    deviate not-supported;
    description
      "Not implemented in vWLC controller";
  }

  deviation "/access-points:access-points/access-points:access-point/access-points:system/access-points:cpus/access-points:cpu/access-points:state/access-points:total/access-points:interval" {
    deviate not-supported;
    description
      "Not implemented in vWLC controller";
  }

  deviation "/access-points:access-points/access-points:access-point/access-points:system/access-points:cpus/access-points:cpu/access-points:state/access-points:user" {
    deviate not-supported;
    description
      "Not implemented in vWLC controller";
  }

  deviation "/access-points:access-points/access-points:access-point/access-points:system/access-points:cpus/access-points:cpu/access-points:state/access-points:kernel" {
    deviate not-supported;
    description
      "Not implemented in vWLC controller";
  }

  deviation "/access-points:access-points/access-points:access-point/access-points:system/access-points:cpus/access-points:cpu/access-points:state/access-points:nice" {
    deviate not-supported;
    description
      "Not implemented in vWLC controller";
  }

  deviation "/access-points:access-points/access-points:access-point/access-points:system/access-points:cpus/access-points:cpu/access-points:state/access-points:idle" {
    deviate not-supported;
    description
      "Not implemented in vWLC controller";
  }

  deviation "/access-points:access-points/access-points:access-point/access-points:system/access-points:cpus/access-points:cpu/access-points:state/access-points:wait" {
    deviate not-supported;
    description
      "Not implemented in vWLC controller";
  }

  deviation "/access-points:access-points/access-points:access-point/access-points:system/access-points:cpus/access-points:cpu/access-points:state/access-points:hardware-interrupt" {
    deviate not-supported;
    description
      "Not implemented in vWLC controller";
  }

  deviation "/access-points:access-points/access-points:access-point/access-points:system/access-points:cpus/access-points:cpu/access-points:state/access-points:software-interrupt" {
    deviate not-supported;
    description
      "Not implemented in vWLC controller";
  }

  deviation "/access-points:access-points/access-points:access-point/access-points:system/access-points:processes" {
    deviate not-supported;
    description
      "Not implemented in vWLC controller";
  }

  deviation "/access-points:access-points/access-points:access-point/access-points:system/access-points:alarms" {
    deviate not-supported;
    description
      "Not implemented in vWLC controller";
  }
}
