module Cisco-IOS-XE-wireless-rf-cfg {
  yang-version 1.1;
  namespace "http://cisco.com/ns/yang/Cisco-IOS-XE-wireless-rf-cfg";
  prefix wireless-rf-cfg;

  import Cisco-IOS-XE-wireless-enum-types {
    prefix wireless-enum-types;
  }
  import Cisco-IOS-XE-wireless-types {
    prefix wireless-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing RF(Radio-Frequency) profile configurations
     Copyright (c) 2016-2022 by Cisco Systems, Inc.
     All rights reserved.";

  revision 2022-11-01 {
    description
      "Update yang-version to 1.1";
    reference
      "9.3.0";
    cisco-semver:module-version "9.3.0";
  }
  revision 2022-07-01 {
    description
      "- Added Zero wait DFS configuration for RF profile
       - Updated the range for maximum number of clients per radio
       - Added guard interval configuration for RF profile
       - Added 6GHz specific client aware FRA thresholds";
    reference
      "9.2.0";
    cisco-semver:module-version "9.2.0";
  }
  revision 2022-03-01 {
    description
      "- Modified all 6GHz must constraints";
    reference
      "9.1.0";
    cisco-semver:module-version "9.1.0";
  }
  revision 2021-11-01 {
    description
      "- Added Spatial Reuse Group (SRG) Overlapping Basic Service Set Packet Detect (OBSS-PD) configurations
       - Updated the range for maximum number of clients per radio
       - Deprecated FILS and Unsolicited Broadcast Probe Response and added as a part of 802.11ax 6GHz specific feature
       - Updated the range for Unsolicited Broadcast Probe Response Interval
       - Added must constraint to prevent High Speed Roam (HSR) mode and client aware FRA configuration for 6 GHz RF profile
       - Modified the default value for Target Wake-up Time and Target Wake-up Time broadcast";
    reference
      "9.0.0";
    cisco-semver:module-version "9.0.0";
  }
  revision 2021-07-01 {
    description
      "- Added Multi BSSID profile and 802.11ax parameters for RF profile
       - Added radio profile configuration
       - Added preferred scanning channel bias for 6 GHz DCA
       - Added must constraint to prevent 802.11n MCS data rate configuration for 6 GHz RF profile";
    reference
      "8.1.0";
    cisco-semver:module-version "8.1.0";
  }
  revision 2021-03-01 {
    description
      "- Add ASCII 32-126 and leading/trailing spaces restriction for RF tag and profile name and ATF-policy name
       - Added Neighbor Discovery mode for AP
       - Added a default value for Rx-SOP custom threshold";
    reference
      "8.0.0";
    cisco-semver:module-version "8.0.0";
  }
  revision 2020-11-01 {
    description
      "- Added 802.11ax OBSS PD configurations
       - Added must constraints for tx-power-min, tx-power-max, client-select-threshold, client-reset-threshold";
    reference
      "7.0.0";
    cisco-semver:module-version "7.0.0";
  }
  revision 2020-07-01 {
    description
      "- Adding must constraints for data rate to mandate one rate as basic";
    reference
      "6.1.0";
    cisco-semver:module-version "6.1.0";
  }
  revision 2019-06-26 {
    description
      "- Creation of RF Profile will not need 32 mcs entries are created.
       - Added semantic version
       - Update the default values as per WLC configuration best practice.
       - Changed default value of client-network-preference to 'default'.";
    reference
      "6.0.0";
    cisco-semver:module-version "6.0.0";
  }
  revision 2019-02-19 {
    description
      "- Renaming radio type to band and removing the band variable in st_rfprofile_default
       - Cleaned up spelling errors in descriptions
       - fixed the name for load_balancing and trap_threshhold attributes
       - Removed leaf node radioType from L2 roam RF Parameters
       - Removed leaf node dot11n from RF Profile
       - Add client-aware-fra, client-select-threshold, client-reset-threshold
       - Removal of layer 2 roaming RF parameter leaves.";
    reference
      "5.0.0";
    cisco-semver:module-version "5.0.0";
  }
  revision 2018-05-03 {
    description
      "Receiver Start of Packet (RX-SOP) configuration to support custom values (-60 to -85 dbm)";
    reference
      "4.0.0";
    cisco-semver:module-version "4.0.0";
  }
  revision 2018-02-11 {
    description
      "Process Air Time Fairness(ATF) mesh stats from Access-Point(AP)";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping rf-80211-nmcs {
    description
      "This container has all the configuration related to Modulation and Coding Scheme (MCS) data rates";
    leaf rf-index {
      type uint8 {
        range "0 .. 31";
      }
      must "../../../band != 'dot11-6-ghz-band'" {
        error-message "802.11n MCS data rate configuration is not applicable for 6 GHz band";
        error-app-tag "must-violation";
      }
      description
        "Identifies the Modulation and Coding Scheme (MCS) data rate for a particular RF(Radio-Frequency) profile.";
    }
    leaf rf-80211n-mcs-enable {
      type boolean;
      must "../../../band != 'dot11-6-ghz-band'" {
        error-message "802.11n MCS data rate configuration is not applicable for 6 GHz band";
        error-app-tag "must-violation";
      }
      default "true";
      description
        "Enable or disable the data rate. When this object is set to 'true' the Modulation and Coding Scheme (MCS) support is enabled.
         When this object is set to 'false' the MCS support is disabled";
    }
  }

  grouping rf-dca-allowed-chans {
    description
      " Configure list of all the allowed channels for the parent Radio-Frequency(rf)-profile";
    leaf channel {
      type uint32;
      description
        "Configure the channel number in allowed channel list";
    }
  }

  grouping st-rf-dca-removed-chans {
    description
      "Configure the list of removed channels for the parent Radio-Frequency(rf)-profile";
    leaf channel {
      type uint32;
      description
        "Configure the channel number in removed channel list";
    }
  }

  grouping rfprofile {
    description
      "This object indicates all the configurations related to Radio-Frequency(rf)-profile";
    leaf name {
      type string {
        pattern '[!-~]([ -~]*[!-~])?';
      }
      description
        "Configure the name of the Radio-Frequency(rf)-profile";
    }
    leaf description {
      type string;
      description
        "Configure the brief description of each Radio-Frequency(rf)-profile";
    }
    leaf tx-power-min {
      type int8 {
        range "-10 .. 30";
      }
      units "dBm";
      must '../tx-power-min <= ../tx-power-max' {
        error-message "tx-power-min must be less than or equal to tx-power-max";
        error-app-tag "must-violation";
      }
      default "-10";
      description
        "Lower limit of transmit power in dBm. For an 802.11 network,
         the system will only accept this configuration if the Transmit Power Control(TPC) is in Auto or Run Once mode";
    }
    leaf tx-power-max {
      type int8 {
        range "-10 .. 30";
      }
      units "dBm";
      must '../tx-power-min <= ../tx-power-max' {
        error-message "tx-power-max must be greater than or equal to tx-power-min";
        error-app-tag "must-violation";
      }
      default "30";
      description
        "Upper limit of transmit power in dBm. For an 802.11 network,
         the system will only accept this configuration if the Transmit Power Control(TPC) is in Auto or Run Once mode";
    }
    leaf tx-power-v1-threshold {
      type int16 {
        range "-80 .. -50";
      }
      units "dBm";
      default "-70";
      description
        "Configure the transmit power control version 1 threshold for the radio resource management algorithm in dBm.";
    }
    leaf tx-power-v2-threshold {
      type int16 {
        range "-80 .. -50";
      }
      units "dBm";
      default "-67";
      description
        "Configure the transmit power control version 2 threshold for the radio resource management algorithm in dBm.";
    }
    leaf status {
      type boolean;
      default "false";
      description
        "Configure the Radio-Frequency(rf)-profile operational state.
         The value false indicates that the Radio-Frequency(rf)-profile is inactive, the value of true indicate the Radio-Frequency(rf)-profile is active";
    }
    leaf band {
      type wireless-types:enm-ewlc-dot11-radio-band;
      description
        "Configure the radio type for this profile.";
    }
    leaf data-rate-1m {
      type wireless-enum-types:rate-state;
      default "apf-tx-rate-basic";
      description
        "Configuration for 1 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-2m {
      type wireless-enum-types:rate-state;
      default "apf-tx-rate-basic";
      description
        "Configuration for 2 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-5-5m {
      type wireless-enum-types:rate-state;
      default "apf-tx-rate-basic";
      description
        "Configuration for 5.5 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-11m {
      type wireless-enum-types:rate-state;
      default "apf-tx-rate-basic";
      description
        "Configuration for 11 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-6m {
      type wireless-enum-types:rate-state;
      default "apf-tx-rate-not-applicable";
      description
        "Configuration for 6 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-9m {
      type wireless-enum-types:rate-state;
      default "apf-tx-rate-supported";
      description
        "Configuration for 9 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-12m {
      type wireless-enum-types:rate-state;
      default "apf-tx-rate-not-applicable";
      description
        "Configuration for 12 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-18m {
      type wireless-enum-types:rate-state;
      default "apf-tx-rate-supported";
      description
        "Configuration for 18 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-24m {
      type wireless-enum-types:rate-state;
      default "apf-tx-rate-not-applicable";
      description
        "Configuration for 24 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-36m {
      type wireless-enum-types:rate-state;
      default "apf-tx-rate-supported";
      description
        "Configuration for 36 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-48m {
      type wireless-enum-types:rate-state;
      default "apf-tx-rate-supported";
      description
        "Configuration for 48 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-54m {
      type wireless-enum-types:rate-state;
      default "apf-tx-rate-supported";
      description
        "Configuration for 54 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf coverage-data-packet-rssi-threshold {
      type int16 {
        range "-90 .. -60";
      }
      units "dBm";
      default "-80";
      description
        "Configure Received Signal Strength Indicator(RSSI) threshold value for data packets in dBm.";
    }
    leaf min-num-clients {
      type int32 {
        range "1 .. 200";
      }
      default "3";
      description
        "Configure client minimum exception level.";
    }
    leaf coverage-voice-packet-rssi-threshold {
      type int16 {
        range "-90 .. -60";
      }
      units "dBm";
      default "-80";
      description
        "Configure Received Signal Strength Indicator(RSSI) threshold value for voice packets in dBm.";
    }
    leaf exception-level {
      type uint16 {
        range "0 .. 100";
      }
      units "percentage";
      default "25";
      description
        "Configure the coverage exception level in percentage of total clients to actual failed clients.";
    }
    leaf band-select-client-rssi {
      type int16 {
        range "-90 .. -20";
      }
      units "dBm";
      default "-80";
      description
        "Configure minimum mobile station Received Signal Strength Indicator(RSSI) threshold in dBm.
         Mobile stations having RSSI below this value will not be recorded in the suppressed table.
         This configuration filters out far away mobile stations with weaker signal strength. This will limit the number of mobile stations on the table to a reasonable amount.";
    }
    leaf band-select-client-mid-rssi {
      type int16 {
        range "-90 .. -20";
      }
      units "dBm";
      default "-80";
      description
        "Configure medium mobile station Received Signal Strength Indicator(RSSI) threshold in dBm. Mobile station between this value and cldband_select_client_rssi will be recorded in suppressed table but will not be denied. The mobile station having RSSI stronger this value will be recorded and denied.";
    }
    leaf band-select-cycle-count {
      type uint16 {
        range "1 .. 10";
      }
      default "2";
      description
        "Configure maximum number of cycles not responding.";
    }
    leaf band-select-cycle-threshold {
      type uint16 {
        range "1 .. 1000";
      }
      units "milliseconds";
      default "200";
      description
        "Configure cycle threshold for band select in milliseconds.";
    }
    leaf band-select-age-out-dual-band {
      type uint16 {
        range "10 .. 300";
      }
      units "seconds";
      default "60";
      description
        "Configure expire of dual band in secs.";
    }
    leaf band-select-age-out-suppression {
      type uint16 {
        range "10 .. 200";
      }
      units "seconds";
      default "20";
      description
        "Configure expire of suppression in secs.";
    }
    leaf band-select-probe-response {
      type boolean;
      default "false";
      description
        "Configure Access-Point(AP)'s probe response with clients to verify whether client can associate on both 2.4 GHz and 5 Ghz spectrum.
         When set to true, AP suppresses probe response to new clients for all Service Set Identifier(SSID)'s that are not being Band Select disabled.";
    }
    leaf dca-contribution-interference {
      type boolean;
      default "true";
      description
        "Configure Dynamic Channel Assignment (DCA) for Radio-Frequency(RF)-Profiles.";
    }
    leaf rf-dca-chan-width {
      type wireless-enum-types:rf-dca-chan-width;
      default "rf-dca-chan-width-best";
      description
        "Specify the system Dynamic Channel Assignment (DCA) channel width selection for the Radio-Frequency(RF)-Profile
         Possible values:
         rf-dca-chan-width-20-mhz  =  Channel width will be set to 20 Mhz
         rf-dca-chan-width-40-mhz  =  Channel width will be set to 40 Mhz
         rf-dca-chan-width-80-mhz  =  Channel width will be set to 80 Mhz
         rf-dca-chan-width-best    =  Best channel width will be selected by Dynamic Channel Assignment (DCA) algorithm
         rf-dca-chan-width-160-mhz =  Channel width will be set to 160 Mhz";
    }
    leaf load-balancing-window {
      type uint32 {
        range "0 .. 20";
      }
      default "5";
      description
        "Configure number of clients associated between Access-Point(AP)'s.";
    }
    leaf load-balancing-denial-count {
      type uint32 {
        range "1 .. 10";
      }
      default "3";
      description
        "Configure number of clients denial with respect to Access-Point(AP).";
    }
    leaf trap-threshold-clients {
      type uint32 {
        range "1 .. 200";
      }
      default "12";
      description
        "Configure threshold number of clients per Access-Point(AP) radio to trigger a trap.
         The trap ciscoLwappApClientThresholdNotify will be triggered once the count of clients on the AP radio reaches this limit.
         A value of zero indicates that the trap is disabled.";
    }
    leaf trap-threshold-interference {
      type uint16 {
        range "0 .. 100";
      }
      units "percentage";
      default "10";
      description
        "Configure interference threshold in (%) traps are generated when interference exceeds this value .";
    }
    leaf trap-threshold-noise {
      type int32 {
        range "-127 .. 0";
      }
      units "dBm";
      default "-70";
      description
        "Configure threshold number of noise threshold between -127 and 0 dBm.";
    }
    leaf trap-threshold-utilization {
      type uint16 {
        range "0 .. 100";
      }
      units "percentage";
      default "80";
      description
        "Configure threshold of bandwidth (%) being utilized by an access-point. Traps are sent when this value is exceeded";
    }
    leaf max-radio-clients {
      type uint16 {
        range "0 .. 500";
      }
      default "200";
      description
        "Configure maximum number of radio clients per Access-Point(AP) in high density environment.";
    }
    leaf multicast-data-rate {
      type wireless-enum-types:enm-multicast-data-rate;
      default "mcast-data-rate-default";
      description
        "Configure minimum data rate at which multicast clients can associate to Access-Point(AP). A value 0 indicates that AP will automatically adjust data rates.";
    }
    leaf rx-sen-sop-threshold {
      type wireless-types:rx-sen-sop-threshold-level;
      units "dBm";
      default "rrm-ewlc-rxsensop-threshold-auto";
      description
        "Configure the Receiver Start of Packet(RX-SOP) sensitivity threshold";
    }
    leaf rx-sen-sop-custom {
      type int16 {
        range "-85 .. -60";
      }
      units "dBm";
      default "-85";
      description
        "Rx SOP custom values configured between -85 dBm (default) and -60 dBm. This configured value takes effect only when rx sop threshold is set to custom";
    }
    leaf client-network-preference {
      type wireless-types:enm-client-network-preference;
      default "default";
      description
        "Configure the client network preference. Possible values are:
         1. connectivity - Radio-Resource-Management(RRM) Algorithm has a preference on connectivity of the clients.
         2. throughput   - Radio-Resource-Management(RRM) Algorithm has a preference on high throughput of the clients.
         3. default      - Radio-Resource-Management(RRM) Algorithm has no preference on the clients.";
    }
    leaf hsr-mode {
      type boolean;
      must "((current() = 'false') or (../band != 'dot11-6-ghz-band'))" {
        error-message "High-speed roam(HSR) configuration is not applicable for 6 GHz band";
        error-app-tag "must-violation";
      }
      default "false";
      description
        "Configure High-speed roam(HSR) mode for Radio-Frequency(RF) profile.";
    }
    leaf hsr-neighbor-timeout {
      type uint16 {
        range "5 .. 60";
      }
      units "seconds";
      must "((current() = 5) or (../band != 'dot11-6-ghz-band'))" {
        error-message "hsr-neighbor-timeout configuration is not applicable for 6 GHz band";
        error-app-tag "must-violation";
      }
      default "5";
      description
        "Configure timeout interval of neighbors that will be configured for Radio-Frequency(RF) profile. Neighbor timeout factor will be five times the neighbor interval";
    }
    leaf opt-roam-rssi-treshold {
      type int16 {
        range "-127 .. 0";
      }
      units "dBm";
      default "-127";
      description
        "Configure the minimum Received Signal Strength Indicator(RSSI) threshold for optimized roaming to occur. Possible values are in the range -127 dbm to 0 dbm";
    }
    leaf opt-roam-rssi-check-enable {
      type boolean;
      default "false";
      description
        "Indicates if Received Signal Strength Indicator(RSSI) threshold is enabled before optimized roaming is enabled";
    }
    leaf atf-oper-mode {
      type wireless-enum-types:apf-ate-mode;
      default "apf-atf-mode-disable";
      description
        "Configure air time fairness operating mode.
         Possible values:
         apf-atf-mode-disable = Disable the Air Time Fairness.
         apf-atf-mode-ssid    = Configure airtime-fairness in enforce-policy mode.
         apf-atf-mode-monitor = Monitor Mode represented by cLApDot11IfType of ATF supported APs joined in the controller";
    }
    leaf atf-optimization {
      type wireless-enum-types:apf-ate-stealing-policy;
      default "apf-atf-stealing-policy-disable";
      description
        "Configure air time fairness Optimization Policy represented by cLApDot11IfType of ATF supported APs.
         Possible values:
         apf-atf-stealing-policy-disable = Disable airtime-fairness optimization
         apf-atf-stealing-policy-enable  = Enable airtime-fairness optimization";
    }
    leaf bridge-client-access {
      type boolean;
      default "false";
      description
        "Airtime Allocation Mode under Radio-Frequency(rf)-profile. Value = True, indicates Airtime Allocation feature is enabled and Value = False, indicates Airtime Allocation feature is disabled.";
    }
    leaf airtime-allocation {
      type uint8 {
        range "5 .. 90";
      }
      units "percentage";
      default "5";
      description
        "Configure airtime allocation weight percentage";
    }
    leaf client-aware-fra {
      type boolean;
      must "((current() = 'false') or (../band != 'dot11-6-ghz-band'))" {
        error-message "client aware FRA configuration is not applicable for 6 GHz band";
        error-app-tag "must-violation";
      }
      default "false";
      description
        "Client aware FRA allows the Dual band to operate on 5 Ghz or monitor mode depending on the load on the dedicated 5 Ghz radio";
    }
    leaf client-select-threshold {
      type uint8 {
        range "0 .. 100";
      }
      must "((current() = 50) or (../band != 'dot11-6-ghz-band'))" {
        error-message "client-select-threshold configuration is not applicable for 6 GHz band";
        error-app-tag "must-violation";
      }
      must '../client-reset-threshold < ../client-select-threshold' {
        error-message "client-select-threshold must be greater than client-reset-threshold";
        error-app-tag "must-violation";
      }
      default "50";
      description
        "Client aware FRA utilization threshold value for moving Dual band radio from monitor mode to to Client Serving";
    }
    leaf client-reset-threshold {
      type uint8 {
        range "0 .. 100";
      }
      must "((current() = 5) or (../band != 'dot11-6-ghz-band'))" {
        error-message "client-reset-threshold configuration is not applicable for 6 GHz band";
        error-app-tag "must-violation";
      }
      must '../client-reset-threshold < ../client-select-threshold' {
        error-message "client-reset-threshold must be less than client-select-threshold";
        error-app-tag "must-violation";
      }
      default "5";
      description
        "Client aware FRA utilization threshold value for moving Dual band radio from Client Serving mode to Monitor mode";
    }
    container rf-mcs-entries {
      description
        "Configurations related to named Radio-Frequency(rf)-profile";
      list rf-mcs-entry {
        key "rf-index";
        description
          "A list of configurations related to named Radio-Frequency(rf)-profile";
        uses wireless-rf-cfg:rf-80211-nmcs;
      }
    }
    container rf-dca-allowed-channels {
      description
        "Configurations related to allowed Dynamic Channel Assignment (DCA) channels in a named Radio-Frequency(rf)-profile";
      list rf-dca-allowed-channel {
        key "channel";
        description
          "List of configurations related to allowed Dynamic Channel Assignment (DCA) channels in a named Radio-Frequency(rf)-profile";
        uses wireless-rf-cfg:rf-dca-allowed-chans;
      }
    }
    container rfdca-removed-channels {
      description
        "Configurations related to removed Dynamic Channel Assignment (DCA) channels in a named Radio-Frequency(rf)-profile";
      list rfdca-removed-channel {
        key "channel";
        description
          "A list of configurations related to removed Dynamic Channel Assignment (DCA) channels in a named Radio-Frequency(rf)-profile";
        uses wireless-rf-cfg:st-rf-dca-removed-chans;
      }
    }
    leaf he-obss-pd-enable {
      type boolean;
      default "false";
      description
        "Enable/Disable 802.11ax OBSS PD spatial reuse";
    }
    leaf he-non-srg-obss-pd-max {
      type int8 {
        range "-82 .. -62";
      }
      units "dBm";
      default "-62";
      description
        "Non-SRG OBSS PD maximum threshold in dBm";
    }
    leaf ndp-mode {
      type wireless-enum-types:enm-ndp-mode;
      default "ndp-mode-auto";
      description
        "Neighbor discovery protocol operating mode  configuration.
         Possible values are:
         auto        - AP does neighbor discovery either on serving channel or
                       off channel based on its NDP capability
         off-channel - AP does neighbor discovery on off channel";
    }
    leaf he-bcast-probe-resp {
      type boolean;
      default "false";
      status deprecated;
      description
        "802.11ax broadcast probe response";
    }
    leaf he-bcast-probe-resp-intvl {
      type uint16 {
        range "5 .. 25";
      }
      units "seconds";
      default "20";
      description
        "802.11ax broadcast probe response interval";
    }
    leaf he-fils-disc {
      type boolean;
      default "false";
      status deprecated;
      description
        "802.11ax FILS discovery";
    }
    leaf mbssid-prof-name {
      type string;
      default "default-multi-bssid-profile";
      description
        "802.11ax Multi BSSID profile name";
    }
    leaf psc-bias {
      type boolean;
      default "false";
      description
        "Enable or disable preferred scanning channel bias for 6 GHz DCA";
    }
    leaf he-srg-obss-pd-enable {
      type boolean;
      default "false";
      description
        "Enable/Disable 802.11ax SRG OBSS PD spatial reuse";
    }
    leaf he-srg-obss-pd-min {
      type int8 {
        range "-82 .. -62";
      }
      units "dBm";
      must '../he-srg-obss-pd-min <= ../he-srg-obss-pd-max' {
        error-message "SRG OBSS PD minimum must be less than or equal to SRG OBSS PD maximum";
        error-app-tag "must-violation";
      }
      default "-82";
      description
        "SRG OBSS PD minimum threshold in dBm";
    }
    leaf he-srg-obss-pd-max {
      type int8 {
        range "-82 .. -62";
      }
      units "dBm";
      must '../he-srg-obss-pd-min <= ../he-srg-obss-pd-max' {
        error-message "SRG OBSS PD maximum must be greater than or equal to SRG OBSS PD minimum";
        error-app-tag "must-violation";
      }
      default "-62";
      description
        "SRG OBSS PD maximum threshold in dBm";
    }
    leaf dot11ax-6ghz-feature {
      type wireless-enum-types:dot11ax-6ghz-feature;
      default "he-6ghz-none";
      description
        "802.11ax 6GHz specific feature";
    }
    leaf zerowt-dfs {
      type boolean;
      must "(../band = 'dot11-5-ghz-band' or
             ../zerowt-dfs = 'false')" {
        error-message "Zero wait DFS feature is applicable only for 5 GHz band";
        error-app-tag "must-violation";
      }
      default "false";
      description
        "Enable/Disable 802.11a Zero wait DFS feature";
    }
    leaf guard-interval-ext {
      type wireless-enum-types:enm-guard-interval-ext;
      default "guard-interval-none";
      description
        "Set guard interval for rf profile";
    }
    leaf client-reset-thresh-6ghz {
      type uint8 {
        range "0 .. 100";
      }
      units "percentage";
      default "5";
      description
        "Client aware FRA utilization threshold value for moving dual band radio from 6GHz to 5GHz";
    }
    leaf client-count-reset-6ghz {
      type uint8 {
        range "1 .. 10";
      }
      default "1";
      description
        "Client aware FRA client count value for moving dual band radio from 6GHz to 5GHz";
    }
  }

  grouping rf-80211-nmcs-default {
    description
      "This object contains all the configuration related to nmcs data rates for default Radio-Frequency(rf)-profile.";
    leaf rf-index {
      type uint8 {
        range "0 .. 31";
      }
      description
        "uniquely identifies the Modulation and Coding Scheme(MCS) data rate for a particular Radio-Frequency(rf)-profile.";
    }
    leaf mcs-data-rate {
      type uint16;
      units "Mbps";
      description
        "Modulation and Coding Scheme(MCS) Data rate in Mbps.";
    }
    leaf rf-80211n-mcs-enable {
      type boolean;
      default "true";
      description
        "Enable or disable the data rate. When this object is set to 'true' the Modulation and Coding Scheme(MCS) support is enabled. When this object is set to 'false' the MCS support is disabled..";
    }
  }

  grouping rf-dca-allowed-chans-default {
    description
      "Configure list of all the allowed channels for the default Radio-Frequency(rf)-profile";
    leaf channel {
      type uint32;
      description
        "Configure the channel number in allowed channel list";
    }
  }

  grouping rf-dca-removed-chans-default {
    description
      "Configure list of all the removed channels for the default Radio-Frequency(rf)-profile";
    leaf channel {
      type uint32;
      description
        "Configure the channel number in allowed channel list";
    }
  }

  grouping rfprofile-default {
    description
      "This object indicates all the configurations related to default Radio-Frequency(rf)-profile";
    leaf band {
      type wireless-types:enm-ewlc-dot11-radio-band;
      description
        "Configure the type of the radio. Possible values are either 802.11b or 802.11a.";
    }
    leaf name {
      type string;
      description
        "Configure the name of the default Radio-Frequency(rf)-profile";
    }
    leaf description {
      type string;
      description
        "Configure the brief description of default Radio-Frequency(rf)-profile";
    }
    leaf tx-power-min {
      type int8 {
        range "-10 .. 30";
      }
      units "dBm";
      must '../tx-power-min <= ../tx-power-max' {
        error-message "tx-power-min must be less than or equal to tx-power-max";
        error-app-tag "must-violation";
      }
      default "-10";
      description
        "Lower limit of transmit power in dBm. For an 802.11 network, the system will only accept this configuration if the TPC is in Auto or Run Once mode";
    }
    leaf tx-power-max {
      type int8 {
        range "-10 .. 30";
      }
      units "dBm";
      must '../tx-power-min <= ../tx-power-max' {
        error-message "tx-power-max must be greater than or equal to tx-power-min";
        error-app-tag "must-violation";
      }
      default "30";
      description
        "Upper limit of transmit power in dBm. For an 802.11 network, the system will only accept this configuration if the TPC is in Auto or Run Once mode";
    }
    leaf tx-power-v1-threshold {
      type int16 {
        range "-80 .. -50";
      }
      units "dBm";
      default "-70";
      description
        "Configure transmit power control version 1 threshold for the radio resource management algorithm.";
    }
    leaf tx-power-v2-threshold {
      type int16 {
        range "-80 .. -50";
      }
      units "dBm";
      default "-67";
      description
        "Configure transmit power control version 2 threshold for the radio resource management algorithm.";
    }
    leaf status {
      type boolean;
      default "true";
      description
        "Configure the Radio-Frequency(rf)-profile operational state. The value false indicates that the Radio-Frequency(rf)-profile is inactive, the value of true indicate the Radio-Frequency(rf)-profile is active";
    }
    leaf data-rate-1m {
      type wireless-enum-types:rate-state;
      must "(../band != 'dot11-2-dot-4-ghz-band' or
             ../data-rate-1m = 'apf-tx-rate-basic' or
             ../data-rate-2m = 'apf-tx-rate-basic' or
             ../data-rate-5-5m = 'apf-tx-rate-basic' or
             ../data-rate-11m = 'apf-tx-rate-basic' or
             ../data-rate-6m = 'apf-tx-rate-basic' or
             ../data-rate-9m = 'apf-tx-rate-basic' or
             ../data-rate-12m = 'apf-tx-rate-basic' or
             ../data-rate-18m = 'apf-tx-rate-basic' or
             ../data-rate-24m = 'apf-tx-rate-basic' or
             ../data-rate-36m = 'apf-tx-rate-basic' or
             ../data-rate-48m = 'apf-tx-rate-basic' or
             ../data-rate-54m = 'apf-tx-rate-basic')" {
        error-message "Atleast one data rate should be configured as basic for 2.4GHz rf profile";
        error-app-tag "must-violation";
      }
      must "(../band != 'dot11-5-ghz-band' or
             ../data-rate-6m = 'apf-tx-rate-basic' or
             ../data-rate-9m = 'apf-tx-rate-basic' or
             ../data-rate-12m = 'apf-tx-rate-basic' or
             ../data-rate-18m = 'apf-tx-rate-basic' or
             ../data-rate-24m = 'apf-tx-rate-basic' or
             ../data-rate-36m = 'apf-tx-rate-basic' or
             ../data-rate-48m = 'apf-tx-rate-basic' or
             ../data-rate-54m = 'apf-tx-rate-basic')" {
        error-message "Atleast one data rate should be configured as basic for 5GHz rf profile";
        error-app-tag "must-violation";
      }
      default "apf-tx-rate-basic";
      description
        "Configure the 1 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-2m {
      type wireless-enum-types:rate-state;
      default "apf-tx-rate-basic";
      description
        "Configure the 2 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-5-5m {
      type wireless-enum-types:rate-state;
      default "apf-tx-rate-basic";
      description
        "Configure the 5.5 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-11m {
      type wireless-enum-types:rate-state;
      default "apf-tx-rate-basic";
      description
        "Configure the 11 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-6m {
      type wireless-enum-types:rate-state;
      default "apf-tx-rate-not-applicable";
      description
        "Configure the 6 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-9m {
      type wireless-enum-types:rate-state;
      default "apf-tx-rate-supported";
      description
        "Configure the 9 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-12m {
      type wireless-enum-types:rate-state;
      default "apf-tx-rate-not-applicable";
      description
        "Configure the 12 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-18m {
      type wireless-enum-types:rate-state;
      default "apf-tx-rate-supported";
      description
        "Configure the 18 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-24m {
      type wireless-enum-types:rate-state;
      default "apf-tx-rate-not-applicable";
      description
        "Configure the 24 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-36m {
      type wireless-enum-types:rate-state;
      default "apf-tx-rate-supported";
      description
        "Configure the 36 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-48m {
      type wireless-enum-types:rate-state;
      default "apf-tx-rate-supported";
      description
        "Configure the 48 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf data-rate-54m {
      type wireless-enum-types:rate-state;
      default "apf-tx-rate-supported";
      description
        "Configure the 54 Mbps data rate.
         Possible values:
         apf-tx-rate-unsupported    ->  Mark this rate as unsupported
         apf-tx-rate-supported      ->  Mark this rate as supported
         apf-tx-rate-basic          ->  Mark this rate as basic
         apf-tx-rate-not-applicable ->  Mark this rate as not applicable";
    }
    leaf coverage-data-packet-rssi-threshold {
      type int16 {
        range "-90 .. -60";
      }
      units "dBm";
      default "-80";
      description
        "Configure Received Signal Strength Indicator(RSSI) threshold value for data packets.";
    }
    leaf min-num-clients {
      type int32 {
        range "1 .. 200";
      }
      default "3";
      description
        "Configure client minimum exception level.";
    }
    leaf coverage-voice-packet-rssi-threshold {
      type int16 {
        range "-90 .. -60";
      }
      units "dBm";
      default "-80";
      description
        "Configure the Received Signal Strength Indicator(RSSI) threshold value for voice packets.";
    }
    leaf exception-level {
      type uint16 {
        range "0 .. 100";
      }
      units "dBm";
      default "25";
      description
        "Configure coverage exception level.";
    }
    leaf band-select-client-rssi {
      type int16 {
        range "-90 .. -20";
      }
      units "dBm";
      default "-80";
      description
        "Configure the minimum mobile station Received Signal Strength Indicator(RSSI) threshold. Mobile stations having RSSI below this value will not be recorded in the suppressed table. This configuration filters out far away mobile stations with weaker signal strength. This will limit the number of mobile stations on the table to a reasonable amount.";
    }
    leaf band-select-client-mid-rssi {
      type int16 {
        range "-90 .. -20";
      }
      units "dBm";
      default "-80";
      description
        "Configure the medium mobile station Received Signal Strength Indicator(RSSI) threshold. Mobile station between this value and cldband_select_client_rssi will be recorded in suppressed table but will not be denied. The mobile station having RSSI stronger this value will be recorded and denied.";
    }
    leaf band-select-cycle-count {
      type uint16 {
        range "1 .. 10";
      }
      default "2";
      description
        "Configure maximum number of cycles not responding.";
    }
    leaf band-select-cycle-threshold {
      type uint16 {
        range "1 .. 1000";
      }
      units "milliseconds";
      default "200";
      description
        "Configure cycle threshold for band select.";
    }
    leaf band-select-age-out-dual-band {
      type uint16 {
        range "10 .. 300";
      }
      units "seconds";
      default "60";
      description
        "Configure expiry time of dual band.";
    }
    leaf band-select-age-out-suppression {
      type uint16 {
        range "10 .. 200";
      }
      units "seconds";
      default "20";
      description
        "Configure expiry time of suppression.";
    }
    leaf band-select-probe-response {
      type boolean;
      default "false";
      description
        "Configure Access-Point(AP)'s probe response with clients to verify whether client can associate on both 2.4 GHz and 5 Ghz spectrum. When set to true, AP suppresses probe response to new clients for all Service Set Identifier(SSID)'s that are not being Band Select disabled.";
    }
    leaf dca-contribution-interference {
      type boolean;
      default "true";
      description
        "Configure the Dynamic Channel Assignment (DCA) for RF Profiles.";
    }
    leaf rf-dca-chan-width {
      type wireless-enum-types:rf-dca-chan-width;
      default "rf-dca-chan-width-best";
      description
        "Configure the system performs Dynamic Channel Assignment (DCA) channel width selection for the Radio-Frequency(RF) profile
         Possible values:
         rf-dca-chan-width-20-mhz  =  Channel width will be set to 20 Mhz
         rf-dca-chan-width-40-mhz  =  Channel width will be set to 40 Mhz
         rf-dca-chan-width-80-mhz  =  Channel width will be set to 80 Mhz
         rf-dca-chan-width-best    =  Best channel width will be selected by Dynamic Channel Assignment (DCA) algorithm
         rf-dca-chan-width-160-mhz =  Channel width will be set to 160 Mhz";
    }
    leaf load-balancing-window {
      type uint32 {
        range "0 .. 20";
      }
      default "5";
      description
        "Configure number of clients associated between Access-Point(AP)s.";
    }
    leaf load-balancing-denial-count {
      type uint32 {
        range "1 .. 10";
      }
      default "3";
      description
        "Configure number of clients denial with respect to Access-Point(AP).";
    }
    leaf trap-threshold-clients {
      type uint32 {
        range "1 .. 200";
      }
      default "12";
      description
        "Configure threshold number of clients per Access-Point(AP) radio to trigger a trap. The trap ciscoLwappApClientThresholdNotify will be triggered once the count of clients on the AP radio reaches this limit. A value of zero indicates that the trap is disabled.";
    }
    leaf trap-threshold-interference {
      type uint16 {
        range "0 .. 100";
      }
      units "percentage";
      default "10";
      description
        "Configure the interference threshold in (%) traps are generated when interference exceeds this value .";
    }
    leaf trap-threshold-noise {
      type int32 {
        range "-127 .. 0";
      }
      units "dBm";
      default "-70";
      description
        "Configure threshold number of noise threshold between -127 and 0 dBm.";
    }
    leaf trap-threshold-utilization {
      type uint16 {
        range "0 .. 100";
      }
      units "percentage";
      default "80";
      description
        "Configure threshold of bandwidth (%) being utilized by an access-point. Traps are sent when this value is exceeded";
    }
    leaf max-radio-clients {
      type uint16 {
        range "0 .. 500";
      }
      default "200";
      description
        "Configure maximum number of radio clients per Access-Point(AP) in high density environment.";
    }
    leaf multicast-data-rate {
      type wireless-enum-types:enm-multicast-data-rate;
      default "mcast-data-rate-default";
      description
        "Configure minimum data rate at which multicast clients can associate to Access-Point(AP). A value 0 indicates that AP will automatically adjust data rates.";
    }
    leaf rx-sen-sop-threshold {
      type wireless-types:rx-sen-sop-threshold-level;
      units "dBm";
      default "rrm-ewlc-rxsensop-threshold-auto";
      description
        "Configure the Receiver Start of Packet (RX-SOP) sensitivity threshold";
    }
    leaf rx-sen-sop-custom {
      type int16 {
        range "-85 .. -60";
      }
      units "dBm";
      default "-85";
      description
        "Rx SOP custom values configured between -85 dBm (default) and -60 dBm. This configured value takes effect only when rx sop threshold is set to custom";
    }
    leaf client-network-preference {
      type wireless-types:enm-client-network-preference;
      default "default";
      description
        "Configure the client network preference. Possible values are:
         1. connectivity - Radio-Resource-Management(RRM) Algorithm has a preference on connectivity of the clients.
         2. throughput   - Radio-Resource-Management(RRM) Algorithm has a preference on high throughput of the clients.
         3. default      - Radio-Resource-Management(RRM) Algorithm has no preference on the clients.";
    }
    leaf hsr-mode {
      type boolean;
      default "false";
      description
        "Configure High-speed roam(HSR) mode for Radio-Frequency(RF) is enabled or not.";
    }
    leaf hsr-neighbor-timeout {
      type uint16 {
        range "5 .. 60";
      }
      default "5";
      description
        "Configure the timeout interval of neighbors that will be configured for Radio-Frequency(RF) profile. Neighbor timeout factor will be five times the neighbor interval";
    }
    leaf opt-roam-rssi-treshold {
      type int16 {
        range "-127 .. 0";
      }
      units "dBm";
      default "-127";
      description
        "Configure the minimum Received Signal Strength Indicator(RSSI) threshold for optimized roaming to occur. Possible values are in the range -127 dbm to 0 dbm";
    }
    leaf opt-roam-rssi-check-enable {
      type boolean;
      default "false";
      description
        "Configure if Received Signal Strength Indicator(RSSI) threshold is enabled before optimized roaming is enabled";
    }
    leaf atf-oper-mode {
      type wireless-enum-types:apf-ate-mode;
      description
        "Configure air time fairness operating mode
         Possible values:
         apf-atf-mode-disable = Disable the Air Time Fairness.
         apf-atf-mode-ssid    = Configure airtime-fairness in enforce-policy mode.
         apf-atf-mode-monitor = Monitor Mode represented by cLApDot11IfType of ATF supported APs joined in the controller";
    }
    leaf atf-optimization {
      type wireless-enum-types:apf-ate-stealing-policy;
      description
        "Configure air time fairness optimization Policy represented by cLApDot11IfType of ATF supported APs.
         Possible values:
         apf-atf-stealing-policy-disable = Disable airtime-fairness optimization
         apf-atf-stealing-policy-enable  = Enable airtime-fairness optimization";
    }
    leaf bridge-client-access {
      type boolean;
      default "false";
      description
        "Airtime Allocation mode under default Radio-Frequency(rf)-profile. Value = True,
         indicates Airtime Allocation feature is enabled and Value = False , indicates Airtime Allocation feature is disabled.";
    }
    leaf airtime-allocation {
      type uint8 {
        range "5 .. 90";
      }
      units "percentage";
      default "5";
      description
        "Configure airtime allocation weight percentage";
    }
    leaf client-aware-fra {
      type boolean;
      default "false";
      description
        "Client Aware FRA allows the Dual band to operate on 5 Ghz or monitor mode depending on the load on the dedicated 5 Ghz radio";
    }
    leaf client-select-threshold {
      type uint8 {
        range "0 .. 100";
      }
      must '../client-reset-threshold < ../client-select-threshold' {
        error-message "client-select-threshold must be greater than client-reset-threshold";
        error-app-tag "must-violation";
      }
      default "50";
      description
        "Client aware FRA utilization threshold value for moving Dual band radio from monitor mode to to Client Serving";
    }
    leaf client-reset-threshold {
      type uint8 {
        range "0 .. 100";
      }
      must '../client-reset-threshold < ../client-select-threshold' {
        error-message "client-reset-threshold must be less than client-select-threshold";
        error-app-tag "must-violation";
      }
      default "5";
      description
        "Client aware FRA utilization threshold value for moving Dual band radio from Client Serving mode to Monitor mode";
    }
    container rf-mcs-default-entries {
      description
        "Configurations related to default Radio-Frequency(rf)-profile";
      list rf-mcs-default-entry {
        key "rf-index";
        description
          "A list of configurations related to default Radio-Frequency(rf)-profile";
        uses wireless-rf-cfg:rf-80211-nmcs-default;
      }
    }
    container rf-dca-allowed-channels-default-entries {
      description
        "Configurations related to allowed Dynamic Channel Assignment (DCA) channels in default Radio-Frequency(rf)-profile";
      list rf-dca-allowed-channel-default-entry {
        key "channel";
        description
          "A list of configurations related to allowed Dynamic Channel Assignment (DCA) channels in default Radio-Frequency(rf)-profile";
        uses wireless-rf-cfg:rf-dca-allowed-chans-default;
      }
    }
    container rf-dca-removed-channels-default-entries {
      description
        "Configurations related to removed Dynamic Channel Assignment (DCA) channels in default Radio-Frequency(rf)-profile";
      list rf-dca-removed-channels-default-entry {
        key "channel";
        description
          "A list of configurations related to removed Dynamic Channel Assignment (DCA) channels in default Radio-Frequency(rf)-profile";
        uses wireless-rf-cfg:rf-dca-removed-chans-default;
      }
    }
    leaf he-obss-pd-enable {
      type boolean;
      default "false";
      description
        "Enable/Disable 802.11ax OBSS PD spatial reuse";
    }
    leaf he-non-srg-obss-pd-max {
      type int8 {
        range "-82 .. -62";
      }
      units "dBm";
      default "-62";
      description
        "Non-SRG OBSS PD maximum threshold in dBm";
    }
    leaf ndp-mode {
      type wireless-enum-types:enm-ndp-mode;
      default "ndp-mode-auto";
      description
        "Neighbor discovery protocol operating mode configuration.
         Possible values are:
         auto        - AP does neighbor discovery either on serving channel or
                       off channel based on its NDP capability
         off-channel - AP does neighbor discovery on off channel";
    }
    leaf he-srg-obss-pd-enable {
      type boolean;
      default "false";
      description
        "Enable/Disable 802.11ax SRG OBSS PD spatial reuse";
    }
    leaf he-srg-obss-pd-min {
      type int8 {
        range "-82 .. -62";
      }
      units "dBm";
      must '../he-srg-obss-pd-min <= ../he-srg-obss-pd-max' {
        error-message "SRG OBSS PD minimum must be less than or equal to SRG OBSS PD maximum";
        error-app-tag "must-violation";
      }
      default "-82";
      description
        "SRG OBSS PD minimum threshold in dBm";
    }
    leaf he-srg-obss-pd-max {
      type int8 {
        range "-82 .. -62";
      }
      units "dBm";
      must '../he-srg-obss-pd-min <= ../he-srg-obss-pd-max' {
        error-message "SRG OBSS PD maximum must be greater than or equal to SRG OBSS PD minimum";
        error-app-tag "must-violation";
      }
      default "-62";
      description
        "SRG OBSS PD maximum threshold in dBm";
    }
    leaf dot11ax-6ghz-feature {
      type wireless-enum-types:dot11ax-6ghz-feature;
      default "he-6ghz-none";
      description
        "802.11ax 6GHz specific feature";
    }
    leaf zerowt-dfs {
      type boolean;
      must "(../band = 'dot11-5-ghz-band' or
             ../zerowt-dfs = 'false')" {
        error-message "Zero wait DFS feature is applicable only for 5 GHz band";
        error-app-tag "must-violation";
      }
      default "false";
      description
        "Enable/Disable 802.11a Zero wait DFS feature";
    }
    leaf guard-interval-ext {
      type wireless-enum-types:enm-guard-interval-ext;
      default "guard-interval-none";
      description
        "Set guard interval for rf profile";
    }
    leaf client-reset-thresh-6ghz {
      type uint8 {
        range "0 .. 100";
      }
      units "percentage";
      default "5";
      description
        "Client aware FRA utilization threshold value for moving dual band radio from 6GHz to 5GHz";
    }
    leaf client-count-reset-6ghz {
      type uint8 {
        range "1 .. 10";
      }
      default "1";
      description
        "Client aware FRA client count value for moving dual band radio from 6GHz to 5GHz";
    }
  }

  grouping st-atf-policy {
    description
      "Configurations of Air Time Fairness policy.";
    leaf atfpolicy-name {
      type string {
        length "0..32";
        pattern '[!-~]([ -~]*[!-~])?';
      }
      description
        "Configure profile name assigned to the Air Time Fairness policy. The name assigned to an ATF policy has to be unique across all the ATF policies on the controller";
    }
    leaf policy-id {
      type uint32 {
        range "0 .. 511";
      }
      description
        "uniquely configure the one instance of an ATF policy id on the controller";
    }
    leaf policy-weight {
      type uint8 {
        range "5 .. 100";
      }
      default "10";
      description
        "Configure policy weight assigned to the ATF policy";
    }
    leaf client-sharing {
      type boolean;
      default "false";
      description
        "Configure the client fair sharing is enabled or disabled for an ATF policy present";
    }
  }

  grouping st-rf-tag-radio-profile {
    description
      "Configure the slot specific radio profiles mapped in the (RF) Radio-Frequency tag";
    leaf radio-profile-name {
      type string;
      description
        "Name of the radio profile";
    }
  }

  grouping rf-tag {
    description
      "Contains configurations related to rf tag.";
    leaf tag-name {
      type string {
        pattern '[!-~]([ -~]*[!-~])?';
      }
      description
        "Configure the rf tag name";
    }
    leaf description {
      type string;
      default "";
      description
        "Configure the brief description about the rf tag.";
    }
    leaf dot11a-rf-profile-name {
      type string;
      default "default_rf_5gh";
      description
        "Configure the 802.11a Radio-Frequency(rf)-profile that is associated with this rf tag";
    }
    leaf dot11b-rf-profile-name {
      type string;
      default "default_rf_24gh";
      description
        "Configure the 802.11b Radio-Frequency(rf)-profile that is associated with this rf tag";
    }
    leaf dot11-6ghz-rf-prof-name {
      type string;
      default "default-rf-profile-6ghz";
      description
        "802.11 6GHz Radio-Frequency(rf)-profile that is associated with this RF tag";
    }
    container rf-tag-radio-profiles {
      description
        "Radio profile configuration related to the RF tag";
      list rf-tag-radio-profile {
        key "slot-id band-id";
        description
          "Slot specific radio profile configuration related to the RF tag";
        uses wireless-types:st-slot-band-key;
        uses wireless-rf-cfg:st-rf-tag-radio-profile;
      }
    }
  }

  grouping multi-bssid-profile {
    description
      "802.11ax Multi BSSID profile configuration";
    leaf profile-name {
      type string {
        pattern '[!-~]([ -~]*[!-~])?';
      }
      description
        "Name of the 802.11ax Multi BSSID profile";
    }
    leaf description {
      type string;
      default "";
      description
        "Brief description of 802.11ax Multi BSSID profile";
    }
    leaf he-ofdma-downlink {
      type boolean;
      default "true";
      description
        "802.11ax OFDMA downlink";
    }
    leaf he-ofdma-uplink {
      type boolean;
      default "true";
      description
        "802.11ax OFDMA uplink";
    }
    leaf he-mumimo-downlink {
      type boolean;
      default "true";
      description
        "802.11ax MU-MIMO downlink";
    }
    leaf he-mumimo-uplink {
      type boolean;
      default "true";
      description
        "802.11ax MU-MIMO uplink";
    }
    leaf he-twt {
      type boolean;
      default "false";
      description
        "802.11ax Target Wake-up time";
    }
    leaf he-twt-broadcast {
      type boolean;
      default "false";
      description
        "802.11ax Target Wake-up time broadcast";
    }
  }

  container rf-cfg-data {
    description
      "This Model contains all the Radio-Frequency(rf)-profile related configurations";
    container multi-bssid-profiles {
      description
        "Multi BSSID profile configuration";
      list multi-bssid-profile {
        key "profile-name";
        description
          "Multi BSSID profile";
        uses wireless-rf-cfg:multi-bssid-profile;
      }
    }
    container atf-policies {
      description
        "Air Time Fairness Policies";
      list atf-policy {
        key "policy-id";
        unique "atfpolicy-name";
        description
          "A list of Air Time Fairness Policy objects";
        uses wireless-rf-cfg:st-atf-policy {
          refine "atfpolicy-name" {
            mandatory true;
          }
        }
      }
    }
    container rf-tags {
      description
        "Configuration related to named rf-tag";
      list rf-tag {
        key "tag-name";
        description
          "A list of configurations related to named rf-tag";
        uses wireless-rf-cfg:rf-tag;
      }
    }
    container rf-profiles {
      description
        "Configurations related to named Radio-Frequency(rf)-profile";
      list rf-profile {
        key "name";
        description
          "A list of configurations related to named Radio-Frequency(rf)-profile";
        uses wireless-rf-cfg:rfprofile;
      }
    }
    container rf-profile-default-entries {
      description
        "Configurations related to default Radio-Frequency(rf)-profile";
      list rf-profile-default-entry {
        key "band";
        unique "name";
        description
          "Configurations of default Radio-Frequency(rf)-profile";
        uses wireless-rf-cfg:rfprofile-default {
          refine "name" {
            mandatory true;
          }
        }
      }
    }
  }
}
