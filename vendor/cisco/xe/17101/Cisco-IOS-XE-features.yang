module Cisco-IOS-XE-features {
  yang-version 1.1;
  namespace "http://cisco.com/ns/yang/Cisco-IOS-XE-features";
  prefix ios-features;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE feature Definitions
     Copyright (c) 2016-2022 by Cisco Systems, Inc.
     All rights reserved.";

  revision 2022-11-01 {
    description
      "- Update yang-version to 1.1
       - Added feature LORAWAN
       - Added feature ptp
       - Added feature pae";
    cisco-semver:module-version "1.1.0";
  }
  revision 2022-07-01 {
    description
      "- Add feature NHRP
       - Added feature prp
       - Added feature ntp-ptp
       - Added feature mrp
       - Added if-feature switching-guard to selectively enable/disable switching features";
    cisco-semver:module-version "1.0.0";
  }
  revision 2022-03-01 {
    description
      "- Added features cellular-serviceability-enhancement";
  }
  revision 2021-11-01 {
    description
      "- Added features vrrp-tloc";
  }
  revision 2021-07-01 {
    description
      "- Added port channel load balance feature";
  }
  revision 2021-03-01 {
    description
      "- Added features enforcement-routing-platform and fhrp-sso.
       - Added features cts-switching";
  }
  revision 2020-11-01 {
    description
      "- Added ip prefix-list feature for controller and autonomous
       - Added macsec-common feature";
  }
  revision 2020-07-01 {
    description
      "- Added down-monitoring feature
       - Added IPSLA Service performance feature";
  }
  revision 2020-03-01 {
    description
      "Added rawsocket feature
       Added sg-epg-ignore-vrf feature for Security-Group and Endpoint-Group
       translation";
  }
  revision 2019-10-01 {
    description
      "Added new features";
  }
  revision 2019-02-25 {
    description
      "Added iso-igrp feature";
  }
  revision 2018-11-20 {
    description
      "Added license-suite-command feature for license boot suite command";
  }
  revision 2017-02-07 {
    description
      "Initial revision";
  }

  feature switching-platform {
    description
      "switching platform specific features";
  }

  feature macsec-common {
    description
      "common macsec support";
  }

  feature crypto {
    description
      "crypto feature";
  }

  feature device-tracking {
    description
      "device-tracking feature";
  }

  feature dhcp-border-relay {
    description
      "dhcp-border-relay feature";
  }

  feature dhcp-guard {
    description
      "ipv6 dhcp guard feature";
  }

  feature dot1x {
    description
      "dot1x feature";
  }

  feature ecfm-llb {
    description
      "Ethernet CFM latching-loopback feature";
  }

  feature efp {
    description
      "Ethernet Flow Point (efp) feature";
  }

  feature esmc {
    description
      "Ethernet Synchronization Messaging Channel (esmc) feature";
  }

  feature eth-evc {
    description
      "Ethernet Virtual Circuit (EVC) feature";
  }

  feature ezpm {
    description
      "Easy Performance Monitor feature";
  }

  feature ignition {
    description
      "Ignition power management";
  }

  feature inspection {
    description
      "nd inspection feature";
  }

  feature iso-igrp {
    description
      "ISO IGRP feature";
  }

  feature l2 {
    description
      "Layer2 VPN feature";
  }

  feature l2vpn {
    description
      "Layer2 VPN feature";
  }

  feature lorawan {
    description
      "LORAWAN feature";
  }

  feature macsec {
    description
      "macsec";
  }

  feature mem-size {
    description
      "Memory size commands";
  }

  feature module {
    description
      "Device module feature";
  }

  feature multilink {
    description
      "PPP multilink global configuration";
  }

  feature mls {
    description
      "Multilayer Switching feature";
  }

  feature nhrp {
    description
      "Next Hop Resolution Protocol";
  }

  feature ntp-ptp {
    description
      "PTP as NTP refclock";
  }

  feature mrp {
    description
      "mrp (media redundancy protocol) feature";
  }

  feature omp {
    description
      "Overlay Management Protocol (OMP) feature";
  }

  feature pae {
    description
      "Product Analytics feature (PAE)";
  }

  feature parameter-map {
    description
      "Parameter Map feature";
  }

  feature private-vlan {
    description
      "Private-vlan feature";
  }

  feature prp {
    description
      "prp (parallel redundancy protocol) feature";
  }

  feature ptp {
    description
      "PTP new config feature";
  }

  feature punt-num {
    description
      "Police punt feature";
  }

  feature qos-qsm {
    description
      "QoS queue softmax multiplier";
  }

  feature raguard {
    description
      "nd guard feature";
  }

  feature rawsocket {
    description
      "Rawsocket";
  }

  feature scada-gw {
    description
      "SCADA Gateway";
  }

  feature sdwan {
    description
      "sdwan feature";
  }

  feature sr-policy {
    description
      "BGP SR-TE Policy feature";
  }

  feature suppress {
    description
      "ipv6 nd suppress feature";
  }

  feature license-suite-command {
    description
      "license boot suite feature";
  }

  feature setup {
    description
      "Express setup feature";
  }

  feature switch-virtual {
    description
      "Switch-virtual feature";
  }

  feature table-map {
    description
      "table-map feature";
  }

  feature tod-clock {
    description
      "Time of Day clock feature";
  }

  feature transceiver {
    description
      "Transceiver commands";
  }

  feature virtual-template {
    description
      "Virtual-template commands";
  }

  feature vlan {
    description
      "Vlan feature";
  }

  feature med {
    description
      "Media End-point Discovery";
  }

  feature routing-platform {
    description
      "routing platform specific features";
  }

  feature mdns-switch {
    description
      "mDNS under interface vlan for switching platforms";
  }

  feature mdns-ewlc {
    description
      "mDNS under interface vlan for eWLC platforms";
  }

  feature l2pt-more-protocols {
    description
      "L2 protocol tunneling support new protocols:
       MVRP,DTP,PTP Peer Delay Protocol,
       Multiple MAC Registration Protocol,ELMI,LINK-OAM,ESMC";
  }

  feature l2cp-fwd {
    description
      "Switchport support forwarding L2 PDUs:
       CDP,STP,VTP,LLDP,PAGP,LACP,UDLD,MVRP,DTP,PTP Peer Delay Protocol,
       Multiple MAC Registration Protocol,ELMI,LINK-OAM,ESMC,R4,R5,R6,R8,R9,
       RA,RB,RC,RD,RF";
  }

  feature sg-epg-ignore-vrf {
    description
      "Cisco TrustSec Security-Group and Endpoint-Group translation supports
       new functionality to disable VRF awareness";
  }

  feature bfd-dm {
    description
      "dampening with down-monitoring support";
  }

  feature service-performance {
    description
      "IPSLA Service Performance platform specific feature";
  }

  feature prefixlist-controller {
    description
      "prefix-list version for controller";
  }

  feature prefixlist-autonomous {
    description
      "prefix-list version for autonomous";
  }

  feature enforcement-routing-platform {
    description
      "Cisco Trustsec Role-based Access Control support for routing platform";
  }

  feature fhrp-sso {
    description
      "FHRP Stateful switchover.";
  }

  feature fqdn-acl {
    description
      "FQDN ACL feature support";
  }

  feature reflexive-acl {
    description
      "Reflexive ACL feature support";
  }

  feature cts-switching {
    description
      "Cisco Trustsec Role-based Access Control support for switching platform";
  }

  feature router-poch-lb {
    description
      "Port-channel load-balance hash algorithms on Router";
  }

  feature vrrp-tloc {
    description
      "TLOC preference increase for VRRP primary on sdwan platforms";
  }

  feature cts-intf-enable {
    description
      "Cisco Trustsec config support for Loopback";
  }

  feature cts-controller {
    description
      "CTS CLIs for controller mode only";
  }

  feature cts-autonomous {
    description
      "CTS CLIs for autonomous mode only";
  }

  feature canbus {
    description
      "CAN bus configuration";
  }

  feature cellular-serviceability-enhancement {
    description
      "cellular serviceability enhancement";
  }

  feature switching-guard {
    description
      "switching platform specific features that should not be present on router";
  }

  feature ctc-http-app {
    description
      "ctc-app UEA platform specific feature";
  }
}
