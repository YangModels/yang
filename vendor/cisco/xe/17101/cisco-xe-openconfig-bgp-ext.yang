module cisco-xe-openconfig-bgp-ext {

  yang-version "1";

  // namespace
  namespace "http://cisco.com/ns/yang/cisco-xe-openconfig-bgp-ext";

  prefix "cisco-bgp";

  import openconfig-network-instance {
    prefix "oc-ni";
  }


 organization
    "Cisco Systems, Inc.";

  contact
    "Cisco Systems, Inc. Customer Service Postal: 170 W Tasman Drive
     San Jose, CA 95134 Tel: +1 1800 553-NETS E-mail: cs-yang@cisco.com";

  description
    "Cisco augmentation  to support BFD to OC-BGP model."+
    "Copyright (c) 2021 by Cisco Systems, Inc."+
    "All rights reserved.";

  revision 2021-11-01 {
    description
      "Initial version";
    reference "openconfig-bgp.yang";
  }

grouping enable-bfd-config {
  description
    "Configuration parameters related to enabling BFD.";

  leaf enabled {
    type boolean;
    description
      "When this leaf is set to true, BFD is used to detect the
       liveliness of the remote peer or next-hop.";
  }
}

grouping bfd-enable {
  description
    "Grouping which can be included in a protocol wishing to enable BFD.";

  container enable-bfd {
    description
      "Enable BFD for liveliness detection to the next-hop or neighbor.";

    container config {
      description
        "Configuration parameters relating to enabling BFD.";

      uses enable-bfd-config;
    }
  }
}

augment "/oc-ni:network-instances/oc-ni:network-instance/oc-ni:protocols/oc-ni:protocol/oc-ni:bgp/oc-ni:neighbors/oc-ni:neighbor" {
    uses bfd-enable;
  }

augment "/oc-ni:network-instances/oc-ni:network-instance/oc-ni:protocols/oc-ni:protocol/oc-ni:bgp/oc-ni:peer-groups/oc-ni:peer-group" {
    uses bfd-enable;
  }
}
