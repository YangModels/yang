module Cisco-IOS-XE-l2vpn-oper {
  yang-version 1.1;
  namespace "http://cisco.com/ns/yang/Cisco-IOS-XE-l2vpn-oper";
  prefix l2vpn-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for L2VPN services operational data.
     Copyright (c) 2022 by Cisco Systems, Inc.
     All rights reserved.";

  revision 2022-11-01 {
    description
      "Initial revision";
    reference
      "1.0.0";
    cisco-semver:module-version "1.0.0";
  }

  typedef l2vpn-service-type {
    type enumeration {
      enum l2vpn-service-invalid {
        value 0;
        description
          "Invalid service type";
      }
      enum l2vpn-service-vpws {
        value 1;
        description
          "L2VPN service type xconnect";
      }
      enum l2vpn-service-vpls {
        value 2;
        description
          "L2VPN service type VPLS";
      }
      enum l2vpn-service-transport {
        value 3;
        description
          "L2VPN service type Transport";
      }
      enum l2vpn-service-bd {
        value 4;
        description
          "L2VPN service type bridge-domain";
      }
      enum l2vpn-service-evpn {
        value 5;
        description
          "L2VPN service type evpn";
      }
    }
    description
      "L2VPN service type";
  }

  typedef l2vpn-ac-circuit-type {
    type enumeration {
      enum ac-circuit-invalid {
        value 0;
        description
          "Invalid attachment circuit type";
      }
      enum ac-circuit-fr-dlci {
        value 1;
        description
          "Attachment circuit type fr dlci";
      }
      enum ac-circuit-fr-dlci-local {
        value 2;
        description
          "Attachment circuit type fr dlci local";
      }
      enum ac-circuit-atm-aal5 {
        value 3;
        description
          "Attachment circuit type atm aal5";
      }
      enum ac-circuit-atm-cell {
        value 4;
        description
          "Attachment circuit type atm cell";
      }
      enum ac-circuit-ether-vlan {
        value 5;
        description
          "Attachment circuit type ether vlan";
      }
      enum ac-circuit-ether {
        value 6;
        description
          "Attachment circuit type ether";
      }
      enum ac-circuit-hdlc {
        value 7;
        description
          "Attachment circuit type hdlc";
      }
      enum ac-circuit-ppp {
        value 8;
        description
          "Attachment circuit type ppp";
      }
      enum ac-circuit-cem {
        value 9;
        description
          "Attachment circuit type cem";
      }
      enum ac-circuit-atm-vcc-cell {
        value 10;
        description
          "Attachment circuit type atm vcc cell";
      }
      enum ac-circuit-atm-vpc-cell {
        value 11;
        description
          "Attachment circuit type atm vpc cell";
      }
      enum ac-circuit-ip {
        value 12;
        description
          "Attachment circuit type ip";
      }
      enum ac-circuit-vfi {
        value 13;
        description
          "Attachment circuit type vfi";
      }
      enum ac-circuit-satop-e1 {
        value 15;
        description
          "Attachment circuit type satop e1";
      }
      enum ac-circuit-satop-t1 {
        value 16;
        description
          "Attachment circuit type satop t1";
      }
      enum ac-circuit-satop-e3 {
        value 17;
        description
          "Attachment circuit type satop e3";
      }
      enum ac-circuit-satop-t3 {
        value 18;
        description
          "Attachment circuit type satop t3";
      }
      enum ac-circuit-ces-psn-basic {
        value 19;
        description
          "Attachment circuit type ces psn basic";
      }
      enum ac-circuit-ces-psn-cas {
        value 20;
        description
          "Attachment circuit type ces psn cas";
      }
      enum ac-circuit-atm-vc-unknown {
        value 21;
        description
          "Attachment circuit type atm vc unknown";
      }
      enum ac-circuit-atm-vp-unknown {
        value 22;
        description
          "Attachment circuit type atm vp unknown";
      }
      enum ac-circuit-atom {
        value 23;
        description
          "Attachment circuit type atom";
      }
      enum ac-circuit-l2tpv2 {
        value 24;
        description
          "Attachment circuit type l2tpv2";
      }
      enum ac-circuit-l2tpv3 {
        value 25;
        description
          "Attachment circuit type l2tpv3";
      }
      enum ac-circuit-pw-udp {
        value 26;
        description
          "Attachment circuit type pw udp";
      }
      enum ac-circuit-dossis {
        value 27;
        description
          "Attachment circuit type docsis";
      }
      enum ac-circuit-dossis-vlan {
        value 28;
        description
          "Attachment circuit type docsis vlan";
      }
    }
    description
      "L2VPN attachment circuit type";
  }

  typedef l2vpn-pw-encap-type {
    type enumeration {
      enum l2vpn-pw-encap-invalid {
        value 0;
        description
          "Invalid pw encap type";
      }
      enum l2vpn-pw-encap-l2tpv3 {
        value 1;
        description
          "PW encap type l2tpv3";
      }
      enum l2vpn-pw-encap-l2tpv2 {
        value 2;
        description
          "PW encap type l2tpv2";
      }
      enum l2vpn-pw-encap-mpls {
        value 3;
        description
          "PW encap type mpls";
      }
      enum l2vpn-pw-encap-udp {
        value 4;
        description
          "PW encap type udp";
      }
    }
    description
      "L2VPN PW encap type";
  }

  typedef l2vpn-xconnect-segment-state {
    type enumeration {
      enum xconnect-segment-state-undefined {
        value 0;
        description
          "Xconnect segment state is undefined";
      }
      enum xconnect-segment-state-up {
        value 1;
        description
          "Xconnect segment is up";
      }
      enum xconnect-segment-state-down {
        value 2;
        description
          "Xconnect segment is down";
      }
      enum xconnect-segment-state-admin-down {
        value 3;
        description
          "Xconnect segment is admin down";
      }
      enum xconnect-segment-state-recovering {
        value 4;
        description
          "Xconnect segment is recovering";
      }
      enum xconnect-segment-state-standby {
        value 5;
        description
          "Xconnect segment is standby";
      }
      enum xconnect-segment-state-hot-standby {
        value 6;
        description
          "Xconnect segment is hot standby";
      }
      enum xconnect-segment-state-inactive {
        value 7;
        description
          "Xconnect segment is inactive";
      }
    }
    description
      "L2VPN xconnect segment state";
  }

  typedef l2vpn-xconnect-state {
    type enumeration {
      enum xconnect-state-undefined {
        value 0;
        description
          "Xconnect state is undefined";
      }
      enum xconnect-state-up {
        value 1;
        description
          "Xconnect state is up";
      }
      enum xconnect-state-down {
        value 2;
        description
          "Xconnect state is down";
      }
      enum xconnect-state-admin-down {
        value 3;
        description
          "Xconnect state is admin down";
      }
      enum xconnect-state-recovering {
        value 4;
        description
          "Xconnect state is recovering";
      }
      enum xconnect-state-standby {
        value 5;
        description
          "Xconnect state is standby";
      }
      enum xconnect-state-hot-standby {
        value 6;
        description
          "Xconnect state is hot standby";
      }
      enum xconnect-state-incomplete {
        value 7;
        description
          "Xconnect state is incomplete";
      }
      enum xconnect-state-no-hardware {
        value 8;
        description
          "Xconnect state is no hardware";
      }
    }
    description
      "L2VPN xconnect state";
  }

  typedef l2vpn-fwd-type {
    type enumeration {
      enum l2vpn-fwd-type-invalid {
        value 0;
        description
          "L2VPN forwarder type invalid";
      }
      enum l2vpn-fwd-type-ac {
        value 1;
        description
          "L2VPN forwarder type attachment circuit";
      }
      enum l2vpn-fwd-type-pw {
        value 2;
        description
          "L2VPN forwarder type pseudo-wire";
      }
      enum l2vpn-fwd-type-vfi {
        value 3;
        description
          "L2VPN forwarder type virtual forwarding interface";
      }
      enum l2vpn-fwd-type-bd {
        value 4;
        description
          "L2VPN forwarder type bridge domain";
      }
    }
    description
      "L2VPN forwarder type";
  }

  typedef l2vpn-vc-status {
    type enumeration {
      enum l2vpn-vc-undefined {
        value 0;
        description
          "L2VPN VC status Undefined";
      }
      enum l2vpn-vc-up {
        value 1;
        description
          "L2VPN VC status Up";
      }
      enum l2vpn-vc-down {
        value 2;
        description
          "L2VPN VC status Down";
      }
      enum l2vpn-vc-admin-down {
        value 3;
        description
          "L2VPN VC status Admin Down";
      }
      enum l2vpn-vc-recovering {
        value 4;
        description
          "L2VPN VC status Recovering";
      }
      enum l2vpn-vc-standby {
        value 5;
        description
          "L2VPN VC status StandBy";
      }
      enum l2vpn-vc-hot-standby {
        value 6;
        description
          "L2VPN VC status Hot StandBy";
      }
      enum l2vpn-vc-state-max {
        value 7;
        description
          "L2VPN VC status State Max";
      }
    }
    description
      "VC status change";
  }

  typedef l2vpn-atom-service-type {
    type enumeration {
      enum l2vpn-atom-invalid {
        value 0;
        description
          "Invalid service type";
      }
      enum l2vpn-atom-p2p {
        value 1;
        description
          "L2VPN atom service type p2p";
      }
      enum l2vpn-atom-vfi {
        value 2;
        description
          "L2VPN atom service type VFI";
      }
      enum l2vpn-atom-transport {
        value 3;
        description
          "L2VPN atom service type Transport";
      }
      enum l2vpn-atom-bd {
        value 4;
        description
          "L2VPN atom service type bridge-domain";
      }
      enum l2vpn-atom-evpn {
        value 5;
        description
          "L2VPN atom service type evpn";
      }
    }
    description
      "L2VPN atom service type";
  }

  grouping fwd-info-ac {
    description
      "L2VPN forwarder info for attachment circuit";
    leaf if-name {
      type string;
      description
        "Attachment circuit interface ";
    }
    leaf group-name {
      type string;
      description
        "Attachment circuit group name";
    }
    leaf encap {
      type l2vpn-ios-xe-oper:l2vpn-ac-circuit-type;
      description
        "Attachment circuit encapsulation";
    }
    leaf state {
      type l2vpn-ios-xe-oper:l2vpn-xconnect-segment-state;
      description
        "Attachment circuit state";
    }
    leaf state-in-l2vpn-service {
      type l2vpn-ios-xe-oper:l2vpn-xconnect-state;
      description
        "Attachment circuit state in L2VPN service";
    }
    leaf priority {
      type uint32;
      description
        "Attachment circuit priority";
    }
  }

  grouping fwd-info-pw {
    description
      "L2VPN forwarder info for pseudo-wire";
    leaf if-name {
      type string;
      description
        "Pseudo-wire interface ";
    }
    leaf group-name {
      type string;
      description
        "Pseudo-wire group name";
    }
    leaf encap {
      type l2vpn-ios-xe-oper:l2vpn-pw-encap-type;
      description
        "Pseudo-wire encapsulation";
    }
    leaf peer-address {
      type inet:ipv4-address;
      description
        "Pseudo-wire peer ipv4 address";
    }
    leaf vcid {
      type uint32;
      description
        "Pseudo-wire virtual circuit id";
    }
    leaf state {
      type l2vpn-ios-xe-oper:l2vpn-xconnect-segment-state;
      description
        "Pseudo-wire state";
    }
    leaf state-in-l2vpn-service {
      type l2vpn-ios-xe-oper:l2vpn-xconnect-state;
      description
        "Pseudo-wire state in L2VPN service";
    }
    leaf priority {
      type uint32;
      description
        "Pseudo-wire priority";
    }
  }

  grouping fwd-info-vfi {
    description
      "L2VPN forwarder info for ";
    leaf if-name {
      type string;
      description
        " VPLS interface ";
    }
    leaf group-name {
      type string;
      description
        " VPLS group name";
    }
    leaf encap {
      type l2vpn-ios-xe-oper:l2vpn-pw-encap-type;
      description
        " VPLS encapsulation";
    }
    leaf state {
      type l2vpn-ios-xe-oper:l2vpn-xconnect-segment-state;
      description
        " VPLS state";
    }
    leaf state-in-l2vpn-service {
      type l2vpn-ios-xe-oper:l2vpn-xconnect-state;
      description
        " State in L2VPN service";
    }
    leaf priority {
      type uint32;
      description
        " VPLS priority";
    }
  }

  grouping fwd-info-bd {
    description
      "L2VPN forwarder info for bd";
    leaf if-name {
      type string;
      description
        "Bridge domain interface ";
    }
    leaf group-name {
      type string;
      description
        "Bridge domain group name";
    }
    leaf encap {
      type l2vpn-ios-xe-oper:l2vpn-pw-encap-type;
      description
        "Bridge domain encapsulation";
    }
    leaf state {
      type l2vpn-ios-xe-oper:l2vpn-xconnect-segment-state;
      description
        "Bridge domain state";
    }
    leaf state-in-l2vpn-service {
      type l2vpn-ios-xe-oper:l2vpn-xconnect-state;
      description
        "Bridge domain state in L2VPN service";
    }
    leaf priority {
      type uint32;
      description
        "Bridge domain priority";
    }
  }

  grouping forwarder {
    description
      "L2VPN forwarder info";
    choice fwd-type-choice {
      description
        "Type of the L2VPN forwarder";
      case l2vpn-fwd-type-ac {
        container attachment-circuit {
          description
            "L2VPN attachment-circuit information";
          uses l2vpn-ios-xe-oper:fwd-info-ac;
        }
      }
      case l2vpn-fwd-type-pw {
        container pseudowire {
          description
            "L2VPN pseudo-wire information";
          uses l2vpn-ios-xe-oper:fwd-info-pw;
        }
      }
      case l2vpn-fwd-type-vfi {
        container vfi {
          description
            "L2VPN VPLS information";
          uses l2vpn-ios-xe-oper:fwd-info-vfi;
        }
      }
      case l2vpn-fwd-type-bd {
        container bridge-domain {
          description
            "L2VPN bridge domain information";
          uses l2vpn-ios-xe-oper:fwd-info-bd;
        }
      }
    }
  }

  grouping l2vpn-xconnect-key {
    description
      "L2VPN xconnect key";
    leaf peer-address {
      type inet:ipv4-address;
      description
        "L2VPN xconnect peer ipv4 address";
    }
    leaf vcid {
      type uint32;
      description
        "L2VPN xconnect virtual circuit id";
    }
  }

  grouping standby-segments {
    description
      "L2VPN xconnect standby segments";
    container segment1 {
      description
        "L2VPN xconnect standby segment 1";
      uses l2vpn-ios-xe-oper:forwarder;
    }
    container segment2 {
      description
        "L2VPN xconnect standby segment 2";
      uses l2vpn-ios-xe-oper:forwarder;
    }
  }

  grouping l2vpn-xconnect-data {
    description
      "L2VPN xconnect data";
    leaf xconnect-name {
      type string;
      description
        "L2VPN xconnect service name";
    }
    leaf service-type {
      type l2vpn-ios-xe-oper:l2vpn-service-type;
      description
        "L2VPN xconnect service type";
    }
    leaf xconnect-state {
      type l2vpn-ios-xe-oper:l2vpn-xconnect-state;
      description
        "L2VPN xconnect state";
    }
    leaf description {
      type string;
      description
        "L2VPN xconnect description";
    }
    container segment1 {
      description
        "L2VPN xconnect segment 1";
      uses l2vpn-ios-xe-oper:forwarder;
    }
    container segment2 {
      description
        "L2VPN xconnect segment 2";
      uses l2vpn-ios-xe-oper:forwarder;
    }
    list standby {
      description
        "A List of L2VPN xconnect standby segments if present";
      uses l2vpn-ios-xe-oper:standby-segments;
    }
  }

  grouping l2vpn-services {
    description
      "L2VPN services";
    list l2vpn-xconnect {
      key "peer-address vcid";
      description
        "L2VPN xconnect";
      uses l2vpn-ios-xe-oper:l2vpn-xconnect-key;
      uses l2vpn-ios-xe-oper:l2vpn-xconnect-data;
    }
  }

  grouping l2vpn-atom-vc-data {
    description
      "L2vpn L2 atom VC data";
    leaf local-if-name {
      type string;
      description
        "Local Interface name";
    }
    leaf circuit-type {
      type l2vpn-ios-xe-oper:l2vpn-ac-circuit-type;
      description
        "Circuit Interface name";
    }
    leaf if-name {
      type string;
      description
        "Interface name";
    }
    leaf service-type {
      type l2vpn-ios-xe-oper:l2vpn-atom-service-type;
      description
        "Service Type";
    }
    leaf service-name {
      type string;
      description
        "Service name";
    }
    leaf vc-status {
      type l2vpn-ios-xe-oper:l2vpn-vc-status;
      description
        "VC status";
    }
  }

  grouping l2vpn-atom-key {
    description
      "L2VPN atom vc table key";
    leaf peer-address {
      type inet:ipv4-address;
      description
        "L2VPN vc peer ipv4 address";
    }
    leaf vcid {
      type uint32;
      description
        "L2VPN virtual circuit id";
    }
  }

  container l2vpn-oper-data {
    config false;
    description
      "L2VPN operational data";
    container l2vpn-services {
      presence "l2vpn-services";
      description
        "L2VPN services";
      uses l2vpn-ios-xe-oper:l2vpn-services;
    }
    list l2vpn-atom-vc-info {
      key "peer-address vcid";
      description
        "L2VPN atom VC Info";
      uses l2vpn-ios-xe-oper:l2vpn-atom-key;
      uses l2vpn-ios-xe-oper:l2vpn-atom-vc-data;
    }
  }
}
