module Cisco-IOS-XE-wireless-rfid-global-oper {
  yang-version 1.1;
  namespace "http://cisco.com/ns/yang/Cisco-IOS-XE-wireless-rfid-global-oper";
  prefix wireless-rfid-global-oper;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains RFID operational data.
     Copyright (c) 2021-2022 by Cisco Systems, Inc.
     All rights reserved.";

  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  grouping st-rfid-count-data {
    description
      "This object contains RFID count data";
    leaf total-rfid-count {
      type uint32;
      description
        "This is the total number of unique RFID found in the RFID radio entry data";
    }
  }

  grouping rfid-radio-key {
    description
      "RFID radio entry";
    leaf rfid-mac-addr {
      type yang:mac-address;
      description
        "RFID MAC address";
    }
    leaf ap-mac-addr {
      type yang:mac-address;
      description
        "AP MAC address";
    }
    leaf slot {
      type uint8 {
        range "0..3";
      }
      description
        "Slot ID";
    }
  }

  grouping st-rfid-radio-entries {
    description
      "RFID radio entry data";
    leaf ap-name {
      type string;
      description
        "AP Name";
    }
    leaf rssi-last-heard {
      type yang:date-and-time;
      description
        "Time at which RFID was last heard by controller";
    }
    leaf rssi-value {
      type int8;
      units "dBm";
      description
        "RSSI value of the RFID tag when last heard by controller";
    }
    leaf snr-value {
      type int8;
      units "dBm";
      description
        "SNR signal to noise ratio value of RFID tag";
    }
    leaf radio-int-type {
      type wireless-enum-types:enm-radio-type;
      description
        "Radio type of the detecting AP that detected RFID";
    }
  }

  container rfid-global-oper-data {
    config false;
    description
      "RFID operational data";
    container rfid-total-count {
      presence "rfid-total-count";
      description
        "Total number of unique RFID entries";
      uses wireless-rfid-global-oper:st-rfid-count-data;
    }
    list rfid-radio-data {
      key "rfid-mac-addr ap-mac-addr slot";
      description
        "Operational data of known RFID tags";
      uses wireless-rfid-global-oper:rfid-radio-key;
      uses wireless-rfid-global-oper:st-rfid-radio-entries;
    }
  }
}
