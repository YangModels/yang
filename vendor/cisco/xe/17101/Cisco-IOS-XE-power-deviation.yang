module Cisco-IOS-XE-power-deviation {
  yang-version 1.1;
  namespace "http://cisco.com/ns/yang/Cisco-IOS-XE-power-deviation";
  prefix ios-power-d;

  import cisco-semver {
    prefix cisco-semver;
  }
  import Cisco-IOS-XE-native {
    prefix ios;
  }
  import Cisco-IOS-XE-power {
    prefix ios-power;
  }

  organization
    "Cisco Systems";
  description
    "Cisco XE Native Deviation YANG module for IOS
     Copyright (c) 2019 by Cisco Systems, Inc.
     All rights reserved.";

  revision 2022-11-01 {
    description
      "- Update yang-version to 1.1";
  }
  revision 2019-04-17 {
    description
      "Added LLDP deviation";
  }

  deviation "/ios:native/ios-power:power/ios-power:supply/ios-power:autoLC" {
    deviate not-supported;
  }

  deviation "/ios:native/ios-power:power/ios-power:redundancy-mode-config/ios-power:combined" {
    deviate not-supported;
  }

  deviation "/ios:native/ios-power:power/ios-power:redundancy-mode-config/ios-power:redundant" {
    deviate not-supported;
  }
}
