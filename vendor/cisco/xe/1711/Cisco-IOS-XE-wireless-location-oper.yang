module Cisco-IOS-XE-wireless-location-oper {
  yang-version 1;
  namespace "http://cisco.com/ns/yang/Cisco-IOS-XE-wireless-location-oper";
  prefix wireless-location-oper;

  import Cisco-IOS-XE-wireless-rrm-types {
    prefix wireless-rrm-types;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for accessing location data for clients. This module produces a large amount
     of data. The update rate will be high for this data.
     Copyright (c) 2018-2019 by Cisco Systems, Inc.
     All rights reserved.";

  revision 2019-05-01 {
    description
      "Added semantic version";
    reference "1.1.0";
    cisco-semver:module-version "1.1.0";
  }
  revision 2018-07-25 {
    description
      "Initial revision";
    reference "1.0.0";
    cisco-semver:module-version "1.0.0";
  }

  typedef source-type {
    type enumeration {
      enum "location-rssi-source-none" {
        value 0;
        description
          "RSSI information source unset. This means that the 
           data for this slot is unset";
      }
      enum "location-rssi-source-probe" {
        value 1;
        description
          "RSSI information coming from client probe request frames";
      }
      enum "location-rssi-source-plm" {
        value 2;
        description
          "RSSI information coming through CCX";
      }
    }
    description
      "Enumeration for probe RSSI source type.";
  }

  grouping rssi-sample {
    description
      "RSSI values per antenna and the timestamp of the last update";
    leaf rssi-value-a {
      type int8;
      description
        "RSSI value of antenna A";
    }
    leaf rssi-value-b {
      type int8;
      description
        "RSSI value of antenna B";
    }
    leaf rssi-timestamp {
      type yang:date-and-time;
      description
        "Last updated time for the RSSI";
    }
  }

  grouping client-lrad-key {
    description
      "Indicates which AP has heard from a specific client";
    leaf client-mac-addr {
      type yang:mac-address;
      description
        "Wireless client MAC address";
    }
    leaf lrad-addr {
      type yang:mac-address;
      description
        "AP MAC address which heard the client";
    }
  }

  grouping radio-measurement {
    description
      "RSSI measurements and information for an AP radio slot";
    leaf band {
      type wireless-rrm-types:enm-rrm-phy-type;
      description
        "Radio band type";
    }
    leaf type {
      type wireless-location-oper:source-type;
      description
        "Source of the radio measurement";
    }
    container sample {
      description
        "RSSI samples for antennas A and B";
      uses wireless-location-oper:rssi-sample;
    }
    leaf snr {
      type int8;
      description
        "Signal over noise ratio";
    }
  }

  grouping ap-radio-measurement {
    description
      "RSSI measurements and information for a specific AP for all radio slots";
    list radio-measurements {
      max-elements "3";
      description
        "List of radio measurement per AP slot";
      uses wireless-location-oper:radio-measurement;
    }
  }

  container location-oper-data {
    config false;
    description
      "yang model for location operational";
    list location-rssi-measurements {
      key "client-mac-addr lrad-addr";
      description
        "Radio measurements for a specific AP hearing from a specific client";
      uses wireless-location-oper:client-lrad-key;
      uses wireless-location-oper:ap-radio-measurement;
    }
  }
}
