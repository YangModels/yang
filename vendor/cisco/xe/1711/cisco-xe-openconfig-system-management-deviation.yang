module cisco-xe-openconfig-system-management-deviation {
  namespace "http://cisco.com/ns/cisco-xe-openconfig-system-management-deviation";
  prefix oc-system-management-devs;

  import openconfig-system {
    prefix oc-sys;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module defines deviation statements for openconfig-system-management module.";

  revision 2019-07-01 {
    description
      "Initial Revision";
  }

  deviation "/oc-sys:system/oc-sys:grpc-server/oc-sys:config/oc-sys:transport-security" {
    deviate not-supported;
    description
      "Currently not supported";
  }
  deviation "/oc-sys:system/oc-sys:grpc-server/oc-sys:config/oc-sys:listen-addresses" {
    deviate not-supported;
    description
      "Currently not supported";
  }
  deviation "/oc-sys:system/oc-sys:grpc-server/oc-sys:state/oc-sys:transport-security" {
    deviate not-supported;
    description
      "Currently not supported";
  }
  deviation "/oc-sys:system/oc-sys:grpc-server/oc-sys:state/oc-sys:listen-addresses" {
    deviate not-supported;
    description
      "Currently not supported";
  }
}
