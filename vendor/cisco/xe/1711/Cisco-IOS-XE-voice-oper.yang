module Cisco-IOS-XE-voice-oper {
  yang-version 1;
  namespace "http://cisco.com/ns/yang/Cisco-IOS-XE-voice-oper";
  prefix voice-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for voice operational data.
     Copyright (c) 2018-2019 by Cisco Systems, Inc.
     All rights reserved.";

  revision 2019-05-27 {
    description
      "- Added show DSPFarm Profiles.
       - Added DSPfarm and SCCP connections.
       - Added voice register phone details for SRST mode.
       - Added VOIP calls summary and per-call-leg details";
    reference "1.3.0";
    cisco-semver:module-version "1.3.0";
  }
  revision 2019-05-01 {
    description
      "- Added show sccp ccm group details.
       - Added active calls summary and per-call details.
       - Added semantic version";
    reference "1.2.0";
    cisco-semver:module-version "1.2.0";
  }
  revision 2018-10-29 {
    description
      "- display SIP line voice port, device name, registration state, device type and directory number
       - Cleaned up spelling errors in descriptions.
       - Display SIP line feature access codes";
    reference "1.1.0";
    cisco-semver:module-version "1.1.0";
  }
  revision 2018-07-17 {
    description
      "Initial revision";
    reference "1.0.0";
    cisco-semver:module-version "1.0.0";
  }

  typedef dsp-port-type {
    type enumeration {
      enum "dsp-port-type-digital" {
        value 0;
        description
          "Digital port";
      }
      enum "dsp-port-type-analog" {
        value 1;
        description
          "Analog port";
      }
    }
    description
      "Type of the voice recording source port";
  }

  typedef reg-state-type {
    type enumeration {
      enum "reg-state-unregistered" {
        value 0;
        description
          "Unregistered registration state";
      }
      enum "reg-state-registered" {
        value 1;
        description
          "Registered registration state";
      }
    }
    description
      "Line device registration state type";
  }

  typedef device-type {
    type enumeration {
      enum "alg-encrypted" {
        value 0;
        description
          "Encrypted analog device";
      }
      enum "alg-authenticated" {
        value 1;
        description
          "Authenticated analog device";
      }
      enum "alg-regular" {
        value 2;
        description
          "Regular analog device";
      }
    }
    description
      "Line device device type";
  }

  typedef vad-configuration {
    type enumeration {
      enum "vad-none" {
        value 0;
        description
          "Voice Activity Detection is not used";
      }
      enum "vad-enable" {
        value 1;
        description
          "Voice Activity Detection enabled";
      }
      enum "vad-disable" {
        value 2;
        description
          "Voice Activity Detection disabled";
      }
    }
    description
      "Enumeration for Voice Activity Detection configuration";
  }

  typedef voip-codec-type {
    type enumeration {
      enum "voip-codec-none" {
        value 0;
        description
          "No VOIP codec is used";
      }
      enum "voip-codec-g729r8" {
        value 1;
        description
          "VOIP codec type g729r8";
      }
      enum "voip-codec-g729ar8" {
        value 2;
        description
          "VOIP codec type g729ar8";
      }
      enum "voip-codec-g726r16" {
        value 3;
        description
          "VOIP codec type g726r16";
      }
      enum "voip-codec-g726r24" {
        value 4;
        description
          "VOIP codec type g726r24";
      }
      enum "voip-codec-g726r32" {
        value 5;
        description
          "VOIP codec type g726r32";
      }
      enum "voip-codec-g711ulaw" {
        value 6;
        description
          "VOIP codec type g711ulaw";
      }
      enum "voip-codec-g711alaw" {
        value 7;
        description
          "VOIP codec type g711alaw";
      }
      enum "voip-codec-g728" {
        value 8;
        description
          "VOIP codec type g728";
      }
      enum "voip-codec-g723r63" {
        value 9;
        description
          "VOIP codec type g723r63";
      }
      enum "voip-codec-g723r53" {
        value 10;
        description
          "VOIP codec type g723r53";
      }
      enum "voip-codec-gsm" {
        value 11;
        description
          "VOIP codec type gsm";
      }
      enum "voip-codec-gsmefr" {
        value 12;
        description
          "VOIP codec type gsmefr";
      }
      enum "voip-codec-g729br8" {
        value 13;
        description
          "VOIP codec type g729br8";
      }
      enum "voip-codec-g729abr8" {
        value 14;
        description
          "VOIP codec type g729abr8";
      }
      enum "voip-codec-g729ar63" {
        value 15;
        description
          "VOIP codec type g723ar63";
      }
      enum "voip-codec-g729ar53" {
        value 16;
        description
          "VOIP codec type g723ar53";
      }
      enum "voip-codec-g729ietf" {
        value 17;
        description
          "VOIP codec type g729r8";
      }
      enum "voip-codec-t38" {
        value 18;
        description
          "VOIP codec type t38";
      }
      enum "voip-codec-clearchannel" {
        value 19;
        description
          "VOIP codec type clear channel";
      }
      enum "voip-codec-vofr-telogy-fax" {
        value 20;
        description
          "VOIP codec type vofr Cisco Fax";
      }
      enum "voip-codec-llcc" {
        value 21;
        description
          "VOIP codec type llcc";
      }
      enum "voip-codec-g726r40" {
        value 22;
        description
          "VOIP codec type g726r40";
      }
      enum "voip-codec-transparent" {
        value 23;
        description
          "VOIP codec type transparent";
      }
      enum "voip-codec-modem-relay" {
        value 24;
        description
          "VOIP codec type modem relay";
      }
      enum "voip-codec-cisco-fax" {
        value 25;
        description
          "VOIP codec type Cisco FAX";
      }
      enum "voip-codec-t120" {
        value 26;
        description
          "VOIP codec type t120";
      }
      enum "voip-codec-video" {
        value 27;
        description
          "VOIP codec type Video";
      }
      enum "voip-codec-video-h261" {
        value 28;
        description
          "VOIP codec type Video h261";
      }
      enum "voip-codec-video-h263" {
        value 29;
        description
          "VOIP codec type Video h263";
      }
      enum "voip-codec-video-h263-plus" {
        value 30;
        description
          "VOIP codec type Video h263+";
      }
      enum "voip-codec-video-h264" {
        value 31;
        description
          "VOIP codec type Video h264";
      }
      enum "voip-codec-pass-through" {
        value 32;
        description
          "VOIP codec type pass through";
      }
      enum "voip-codec-gsmamr-nb" {
        value 33;
        description
          "VOIP codec type gsmamrnb";
      }
      enum "voip-codec-ilbc" {
        value 34;
        description
          "VOIP codec type ilbc";
      }
      enum "voip-codec-g722-124" {
        value 35;
        description
          "VOIP codec type g722124";
      }
      enum "voip-codec-g722-132" {
        value 36;
        description
          "VOIP codec type g722132";
      }
      enum "voip-codec-video-vieo" {
        value 37;
        description
          "VOIP codec type video wide band";
      }
      enum "voip-codec-g722-64" {
        value 38;
        description
          "VOIP codec type g72264";
      }
      enum "voip-codec-g722-56" {
        value 39;
        description
          "VOIP codec type g72256";
      }
      enum "voip-codec-g722-48" {
        value 40;
        description
          "VOIP codec type g72248";
      }
      enum "voip-codec-video-mpeg4" {
        value 41;
        description
          "VOIP codec type Video mpeg4";
      }
      enum "voip-codec-g7231r" {
        value 42;
        description
          "VOIP codec type g723";
      }
      enum "voip-codec-g7231ar" {
        value 43;
        description
          "VOIP codec type g723ar";
      }
      enum "voip-codec-aacld" {
        value 44;
        description
          "VOIP codec type aacld";
      }
      enum "voip-codec-isac" {
        value 45;
        description
          "VOIP codec type isac";
      }
      enum "voip-codec-no-audio" {
        value 46;
        description
          "VOIP codec type no audio";
      }
      enum "voip-codec-syn-video-1mbps" {
        value 47;
        description
          "VOIP codec type Video 1 MBPS";
      }
      enum "voip-codec-syn-video-2mbps" {
        value 48;
        description
          "VOIP codec type Video 2 MBPS";
      }
      enum "voip-codec-syn-video-4mbps" {
        value 49;
        description
          "VOIP codec type Video 4 MBPS";
      }
      enum "voip-codec-amr-wb" {
        value 50;
        description
          "VOIP codec type amrwb";
      }
      enum "voip-codec-h224" {
        value 51;
        description
          "VOIP codec type h224";
      }
      enum "voip-codec-mp4-alatm" {
        value 52;
        description
          "VOIP codec type mp4alatm";
      }
      enum "voip-codec-max" {
        value 53;
        description
          "It is not used, it is end of non fax codec";
      }
      enum "voip-codec-fax-voice" {
        value 54;
        description
          "VOIP codec type Fax Voice";
      }
      enum "voip-codec-fax-rate-2400" {
        value 55;
        description
          "VOIP codec type Fax rate 2400";
      }
      enum "voip-codec-fax-rate-4800" {
        value 56;
        description
          "VOIP codec type Fax rate 4800";
      }
      enum "voip-codec-fax-rate-7200" {
        value 57;
        description
          "VOIP codec type Fax rate 7200";
      }
      enum "voip-codec-fax-rate-9600" {
        value 58;
        description
          "VOIP codec type Fax rate 9600";
      }
      enum "voip-codec-fax-rate-12000" {
        value 59;
        description
          "VOIP codec type Fax rate 12000";
      }
      enum "voip-codec-fax-rate-14400" {
        value 60;
        description
          "VOIP codec type Fax rate 14400";
      }
      enum "voip-codec-fax-rate-33600" {
        value 61;
        description
          "VOIP codec type Fax rate 33600";
      }
      enum "voip-codec-fax-rate-none" {
        value 62;
        description
          "VOIP codec type Fax rate none";
      }
      enum "voip-codec-fax-rate-system" {
        value 63;
        description
          "VOIP codec type Fax rate system";
      }
    }
    description
      "Enumeration for VOIP codec type";
  }

  typedef dsp-type-enum {
    type enumeration {
      enum "dsp-type-none" {
        value 0;
        description
          "DSP type none";
      }
      enum "dsp-type-dm8147" {
        value 1;
        description
          "DSP type dm8147";
      }
      enum "dsp-type-sp2700" {
        value 2;
        description
          "DSP type sp2700";
      }
      enum "dsp-type-tilegx" {
        value 3;
        description
          "DSP type tilegx";
      }
      enum "dsp-type-sp2600" {
        value 4;
        description
          "DSP type sp2600";
      }
    }
    description
      "Enumeration for DSP types";
  }

  typedef swo-method {
    type enumeration {
      enum "switchover-invalid" {
        value 0;
        description
          "Invalid method";
      }
      enum "switchover-immediate" {
        value 1;
        description
          "Immediately switch over";
      }
      enum "switchover-graceful" {
        value 2;
        description
          "Gracefully switch over";
      }
    }
    description
      "Call Manager group switch over methods";
  }

  typedef swb-method {
    type enumeration {
      enum "switchback-invalid" {
        value 0;
        description
          "Invalid method";
      }
      enum "switchback-immediate" {
        value 1;
        description
          "Immediately switch back";
      }
      enum "switchback-graceful" {
        value 2;
        description
          "Gracefully switch back";
      }
      enum "switchback-scheduled" {
        value 3;
        description
          "Scheduled switch back";
      }
      enum "switchback-uptime-delay" {
        value 4;
        description
          "Up-time delayed switch back";
      }
      enum "switchback-graceful-guard" {
        value 5;
        description
          "Graceful with guard switch back";
      }
    }
    description
      "Call Manager group switch back methods";
  }

  typedef sccp-conn-mode {
    type enumeration {
      enum "invalid" {
        value 0;
        description
          "Invalid Mode";
      }
      enum "inactive" {
        value 1;
        description
          "Inactive Mode";
      }
      enum "recvonly" {
        value 2;
        description
          "Receive Only Mode";
      }
      enum "sendonly" {
        value 3;
        description
          "Send Only Mode";
      }
      enum "sendrecv" {
        value 4;
        description
          "Send and Receive Mode";
      }
    }
    description
      "SCCP Connection Mode";
  }

  typedef sccp-sess-type {
    type enumeration {
      enum "none" {
        value 0;
        description
          "No SCCP Session";
      }
      enum "mtp-service" {
        value 1;
        description
          "MTP Session";
      }
      enum "transcoding" {
        value 2;
        description
          "Transcoding Session";
      }
      enum "conferencing" {
        value 3;
        description
          "Conferencing Session";
      }
      enum "alg-phone" {
        value 4;
        description
          "ALG Phone";
      }
      enum "bri-phone" {
        value 5;
        description
          "BRI Phone";
      }
      enum "virtual-phone" {
        value 6;
        description
          "Virtual Phone";
      }
      enum "dp-mtp-service" {
        value 7;
        description
          "DP MTP Session";
      }
      enum "video-conferencing" {
        value 8;
        description
          "Video Conferencing Session";
      }
      enum "video-transcoding" {
        value 9;
        description
          "Video Transcoding Session";
      }
    }
    description
      "SCCP session type";
  }

  typedef dtmf-method-type {
    type enumeration {
      enum "dtmf-relay-none" {
        value 0;
        description
          "No DTMF Relay";
      }
      enum "dtmf-passthru" {
        value 1;
        description
          "DTMF Passthrough";
      }
      enum "dtmf-report" {
        value 2;
        description
          "DTMF Report";
      }
      enum "dtmf-passthru-report" {
        value 3;
        description
          "DTMF Passthrough and Report";
      }
      enum "dtmf-rfc-2833" {
        value 4;
        description
          "DTMF RFC 2833";
      }
      enum "dtmf-inband" {
        value 5;
        description
          "DTMF Inband";
      }
      enum "dtmf-unknown" {
        value 6;
        description
          "DTMF Unknown";
      }
    }
    description
      "DTMF Method Configuration";
  }

  typedef dsp-status-type {
    type enumeration {
      enum "dsp-down" {
        value 0;
        description
          "DSP Down";
      }
      enum "dsp-up" {
        value 1;
        description
          "DSP Up";
      }
    }
    description
      "DSP Status";
  }

  typedef chnl-status-type {
    type enumeration {
      enum "chnl-free" {
        value 0;
        description
          "DSP channel is free";
      }
      enum "chnl-used" {
        value 1;
        description
          "DSP channel is in use";
      }
    }
    description
      "DSP Channel Status";
  }

  typedef dsp-service-type {
    type enumeration {
      enum "xcode" {
        value 0;
        description
          "DSP Transcoding Service";
      }
      enum "conf" {
        value 1;
        description
          "DSP Conferencing Service";
      }
      enum "hw-mtp" {
        value 2;
        description
          "Hardware MTP Service";
      }
      enum "secure-xcode" {
        value 3;
        description
          "Secure Transcoding Service";
      }
      enum "secure-conf" {
        value 4;
        description
          "Secure Conferencing Service";
      }
      enum "secure-hw-mtp" {
        value 5;
        description
          "Secure Hardware MTP Service";
      }
      enum "dspfarm-unknown" {
        value 6;
        description
          "Unknown DSP Service";
      }
    }
    description
      "DSP Service Type";
  }

  typedef srvc-id {
    type enumeration {
      enum "profile-none" {
        value 0;
        description
          "Service None";
      }
      enum "profile-invalid" {
        value 1;
        description
          "Invalid Service";
      }
      enum "profile-mtp" {
        value 2;
        description
          "MTP Service";
      }
      enum "profile-transcode" {
        value 3;
        description
          "Xcode Service";
      }
      enum "profile-conference" {
        value 4;
        description
          "Conference Service ";
      }
    }
    description
      "DSPFarm Service ID";
  }

  typedef app-id {
    type enumeration {
      enum "app-id-none" {
        value 0;
        description
          "Application None";
      }
      enum "app-id-sccp" {
        value 1;
        description
          "SCCP Application";
      }
      enum "app-id-cube" {
        value 2;
        description
          "CUBE Application";
      }
    }
    description
      "DSPFarm Application";
  }

  typedef app-assoc {
    type enumeration {
      enum "app-assoc-none" {
        value 0;
        description
          "Status None";
      }
      enum "app-assoc-unknown" {
        value 1;
        description
          "Status - Invalid";
      }
      enum "app-assoc-done" {
        value 2;
        description
          "Status - Associated";
      }
      enum "app-assoc-active-in-prog" {
        value 3;
        description
          "Status - Association in Progress";
      }
      enum "app-assoc-down-in-prog" {
        value 4;
        description
          "Status - DisAssociation in Progress";
      }
      enum "app-assoc-not-down" {
        value 5;
        description
          "Status - Not Associated";
      }
    }
    description
      "DSPFarm Profile Registration Status";
  }

  typedef secure-mode {
    type enumeration {
      enum "srvc-mode-non-secure" {
        value 0;
        description
          "DSPFarm Non Secure Mode";
      }
      enum "srvc-mode-secure" {
        value 1;
        description
          "DSPFarm Secure Mode";
      }
    }
    description
      "DSPFarm Profile Service Mode";
  }

  typedef prof-oper-state {
    type enumeration {
      enum "prof-oper-state-none" {
        value 0;
        description
          "Profile Operation Status None";
      }
      enum "prof-oper-state-unknown" {
        value 1;
        description
          "Profile Operation Status Invalid ";
      }
      enum "prof-oper-state-down" {
        value 2;
        description
          "Profile Operation Status Down";
      }
      enum "prof-oper-state-down-in-progress" {
        value 3;
        description
          "Down in Progress";
      }
      enum "prof-oper-state-active" {
        value 4;
        description
          "Active";
      }
      enum "prof-oper-state-active-in-prog" {
        value 5;
        description
          "Active in Progress";
      }
      enum "prof-oper-state-rsc-alloc" {
        value 6;
        description
          "Resource Allocated";
      }
    }
    description
      "DSPFarm Profile Operational State";
  }

  typedef rscprv-id {
    type enumeration {
      enum "rsc-prov-none" {
        value 0;
        description
          "Resource Provider None";
      }
      enum "rsc-prov-flex-dsprm" {
        value 1;
        description
          "Flex DSPRM";
      }
    }
    description
      "DSPFarm Resource Provider";
  }

  typedef prof-admin-state {
    type enumeration {
      enum "prof-admin-state-down" {
        value 0;
        description
          "DSPFarm Profile Admin State Down";
      }
      enum "prof-admin-state-up" {
        value 1;
        description
          "DSPFarm Profile Admin State UP";
      }
    }
    description
      "DSPFarm Profile Admin State";
  }

  typedef rscprv-state {
    type enumeration {
      enum "rsc-group-state-none" {
        value 0;
        description
          "Resource Status None";
      }
      enum "rsc-group-state-down-pend" {
        value 1;
        description
          "Resource Status Down Pending";
      }
      enum "rsc-group-state-down" {
        value 2;
        description
          "Resource Status Down";
      }
      enum "rsc-group-state-up-pend" {
        value 3;
        description
          "Resource Status Up Pending";
      }
      enum "rsc-group-state-up" {
        value 4;
        description
          "Resource Status Up";
      }
      enum "rsc-group-state-new-rsc" {
        value 5;
        description
          "Resource Status New";
      }
    }
    description
      "DSPFarm Resource Provider Status";
  }

  typedef voice-call-type-enum {
    type enumeration {
      enum "unknown-call-leg-type" {
        value 0;
        description
          "Call leg type unknown";
      }
      enum "voip-call-leg" {
        value 1;
        description
          "VOIP call leg";
      }
      enum "telephony-call-leg" {
        value 2;
        description
          "Telephony call leg";
      }
    }
    description
      "Enumeration for voice call leg type";
  }

  typedef voice-call-direction-enum {
    type enumeration {
      enum "unknown-leg" {
        value 0;
        description
          "Call leg direction unknown";
      }
      enum "outgoing-leg" {
        value 1;
        description
          "Originating or the outgoing leg";
      }
      enum "incoming-leg" {
        value 2;
        description
          "Answering or the incoming leg";
      }
    }
    description
      "Enumeration for incoming or outgoing leg indication";
  }

  typedef voice-call-state-enum {
    type enumeration {
      enum "unknown-state" {
        value 0;
        description
          "Call leg state unknown";
      }
      enum "connecting-state" {
        value 1;
        description
          "Call leg in connecting state";
      }
      enum "connected-state" {
        value 2;
        description
          "Call leg in connected state";
      }
      enum "active-state" {
        value 3;
        description
          "Call leg in active state";
      }
    }
    description
      "Enumeration for the call state";
  }

  grouping voice-recording-port {
    description
      "Voice recording port status";
    leaf port-dptag {
      type uint32;
      description
        "Dial peer tag of the voice recording source port";
    }
    leaf pa-bay {
      type uint32;
      description
        "Bay number of the voice recording source port";
    }
    leaf port-type {
      type voice-ios-xe-oper:dsp-port-type;
      description
        "Type of the voice recording source port";
    }
    leaf port-id {
      type string;
      description
        "The name of the voice recording source port";
    }
    leaf server-dptag {
      type uint32;
      description
        "Dial peer tag of the voice recording destination server";
    }
  }

  grouping voice-recording-license {
    description
      "Voice recording license status";
    leaf configured {
      type uint32;
      description
        "Configured number of voice recording licenses";
    }
    leaf allocated {
      type uint32;
      description
        "Number of licenses allocated by license server";
    }
    leaf max-support-call {
      type uint32;
      description
        "Maximum number of calls licensed for recording";
    }
    leaf call-use-license {
      type uint32;
      description
        "Number of current calls licensed for recording";
    }
  }

  grouping profile-pvdm-entry {
    description
      "Entry of each PVDM utilization";
    leaf pvdm-id {
      type string;
      description
        "PVDM ID in format slot/bay";
    }
    leaf pvdm-utlz {
      type uint32;
      description
        "PVDM credit usage percentage for this profile";
    }
  }

  grouping dspfarm-utlz-profile {
    description
      "DSP Farm profile credit utilization status";
    leaf profile-id {
      type uint32;
      description
        "ID number of the profile";
    }
    leaf type {
      type string;
      description
        "Type of the profile";
    }
    leaf profile-utlz {
      type uint32;
      description
        "Profile credit usage percentage";
    }
    list profile-pvdm-entry {
      key "pvdm-id";
      description
        "A list of PVDM credit utilization of this profile";
      uses voice-ios-xe-oper:profile-pvdm-entry;
    }
  }

  grouping dsp-utlz-detail-entry {
    description
      "Entry of detailed dsp utilization status";
    leaf dsp-id {
      type string;
      description
        "DSP ID in format slot/bay/dsp ID";
    }
    leaf dsp-alloc-ratio {
      type uint32;
      description
        "Profile credit allocation percentage with regards to the DSP";
    }
    leaf dsp-channel-utlz {
      type uint32;
      description
        "Channel utilization for transcoding";
    }
    leaf dsp-credit-utlz {
      type uint32;
      description
        "Credit utilization for transcoding";
    }
    leaf dsp-session-utlz {
      type uint32;
      description
        "Session utilization for conferencing";
    }
  }

  grouping dspfarm-utlz-detail {
    description
      "DSP Farm profile utilization detail status";
    leaf profile-id {
      type uint32;
      description
        "ID number of the profile";
    }
    leaf type {
      type string;
      description
        "Type of the profile";
    }
    leaf profile-utlz {
      type uint32;
      description
        "Profile credit usage percentage";
    }
    list dsp-utlz-detail-entry {
      key "dsp-id";
      description
        "A list of dsp utilization detail entries";
      uses voice-ios-xe-oper:dsp-utlz-detail-entry;
    }
  }

  grouping voice-port-num {
    description
      "voice port number";
    leaf slot {
      type uint32;
      description
        "slot number";
    }
    leaf subslot {
      type uint32;
      description
        "sub slot number";
    }
    leaf port {
      type uint32;
      description
        "port number";
    }
  }

  grouping dsapp-line-dev-entry {
    description
      "DSAPP line device entry";
    leaf key-id {
      type string;
      description
        "Key to the entry";
    }
    container port-id {
      description
        "DSAPP line device voice port ID";
      uses voice-ios-xe-oper:voice-port-num;
    }
    leaf dev-name {
      type string;
      description
        "DSAPP line device name";
    }
    leaf reg-state {
      type voice-ios-xe-oper:reg-state-type;
      description
        "DSAPP line device registration state";
    }
    leaf dev-type {
      type voice-ios-xe-oper:device-type;
      description
        "DSAPP line device type";
    }
    leaf dir-num {
      type string;
      description
        "DSAPP line device directory number";
    }
  }

  grouping dsapp-line-dev-sum {
    description
      "DSAPP line device summary";
    leaf total-dev {
      type uint32;
      description
        "DSAPP line device total entries";
    }
    list dsapp-line-dev-entry {
      key "key-id";
      description
        "A list of DSAPP line device entries";
      uses voice-ios-xe-oper:dsapp-line-dev-entry;
    }
  }

  grouping dsapp-line-fac {
    description
      "DSAPP line feature access codes";
    leaf prefix {
      type string;
      description
        "DSAPP line feature access code prefix";
    }
    leaf call-forward-all {
      type string;
      description
        "DSAPP line call forward all feature access code";
    }
    leaf call-forward-cancel {
      type string;
      description
        "DSAPP line cancel call forward feature access code";
    }
    leaf pickup-local {
      type string;
      description
        "DSAPP line call pickup local feature access code";
    }
    leaf pickup-group {
      type string;
      description
        "DSAPP line call pickup group feature access code";
    }
    leaf pickup-direct {
      type string;
      description
        "DSAPP line call pickup direct feature access code";
    }
    leaf cancel-call-waiting {
      type string;
      description
        "DSAPP line cancel call waiting feature access code";
    }
    leaf last-redial {
      type string;
      description
        "DSAPP line last number redial feature access code";
    }
  }

  grouping active-voice-call-entry {
    description
      "Active voice Call entry";
    leaf key-id {
      type string;
      description
        "Key to the entry";
    }
    leaf call-id {
      type uint64;
      description
        "Active call ID";
    }
    leaf voice-port-id {
      type string;
      description
        "Voice port ID";
    }
    leaf codec-type {
      type voice-ios-xe-oper:voip-codec-type;
      description
        "VOIP codec type in use";
    }
    leaf vad {
      type voice-ios-xe-oper:vad-configuration;
      description
        "Voice Activity detection configuration";
    }
    leaf dsp-id {
      type string;
      description
        "DSP ID";
    }
    leaf dsp-type {
      type voice-ios-xe-oper:dsp-type-enum;
      description
        "DSP type";
    }
    leaf dsp-version {
      type string;
      description
        "DSP version";
    }
    leaf dsp-abort-packet-cnt {
      type uint32;
      description
        "DSP aborted packet count";
    }
    leaf dsp-tx-packet-cnt {
      type uint32;
      description
        "DSP transmit packet count";
    }
    leaf dsp-rx-packet-cnt {
      type uint32;
      description
        "DSP receive packet count";
    }
  }

  grouping active-voice-call-sum {
    description
      "Active Voice Call Summary";
    leaf total-entry {
      type uint32;
      description
        "Total active voice call entries";
    }
    list active-voice-call-entry {
      key "key-id";
      description
        "A list of active voice call entries";
      uses voice-ios-xe-oper:active-voice-call-entry;
    }
  }

  grouping asso-ccm-entry {
    description
      " Details of this associated Cisco Call Manager";
    leaf ccm-id {
      type uint32;
      description
        "Identifier of this associated Cisco Call Manager";
    }
    leaf ccm-priority {
      type uint32;
      description
        "Priority of this associated Cisco Call Manager";
    }
  }

  grouping asso-profile-entry {
    description
      "Details of this associated profile";
    leaf profile-id {
      type uint32;
      description
        "Identifier of this associated profile";
    }
    leaf reg-name {
      type string;
      description
        "Registration name of this associated profile";
    }
  }

  grouping sccp-ccm-group {
    description
      "Skinny Call Control Protocol Call Manager group detail settings";
    leaf ccm-group-id {
      type uint32;
      description
        "Skinny Call Control Protocol Call Manager group identifier";
    }
    leaf description {
      type string;
      description
        "Description of this Cisco Call Manager group";
    }
    leaf bound-intf {
      type string;
      description
        "Interface which is bound to this Call Manager group";
    }
    leaf ipv6-address {
      type inet:ip-address;
      description
        "IPv6 address of the bound interface";
    }
    leaf ipv4-address {
      type inet:ip-address;
      description
        "IPv4 address of the bound interface";
    }
    leaf registration-retries {
      type uint32;
      description
        "Number of attempts to register onto a Cisco Call Manager";
    }
    leaf registration-timeout {
      type uint32;
      units "seconds";
      description
        "Time it takes to timeout a registration attempt";
    }
    leaf keepalive-retries {
      type uint32;
      description
        "Number of attempts for keepalive to receive ACK";
    }
    leaf keepalive-timeout {
      type uint32;
      units "seconds";
      description
        "Time it takes for keepalive to timeout";
    }
    leaf connect-retries {
      type uint32;
      description
        "Number of retries to connect to a Cisco Call Manager";
    }
    leaf connect-interval {
      type uint32;
      units "seconds";
      description
        "Time interval between Call Manager connect attempts";
    }
    leaf switchover-method {
      type voice-ios-xe-oper:swo-method;
      description
        "Method used when switching over to secondary Cisco Call Manager";
    }
    leaf switchback-method {
      type voice-ios-xe-oper:swb-method;
      description
        "Method used when switching back to primary Cisco Call Manager";
    }
    leaf switchback-interval {
      type uint32;
      description
        "Time interval for Call Manager switchback polling";
    }
    leaf switchback-timeout {
      type uint32;
      units "seconds";
      description
        "Timeout value when switching back to primary Cisco Call Manager";
    }
    leaf signaling-dscp {
      type uint8;
      description
        "Value of the signaling DSCP";
    }
    leaf audio-dscp {
      type uint8;
      description
        "Value of the audio DSCP";
    }
    list asso-ccm-entry {
      key "ccm-id";
      description
        "List of associated Cisco Call Managers";
      uses voice-ios-xe-oper:asso-ccm-entry;
    }
    list asso-profile-entry {
      key "profile-id";
      description
        "List of associated profiles";
      uses voice-ios-xe-oper:asso-profile-entry;
    }
  }

  grouping sccp-connection {
    description
      "SCCP Connection";
    leaf conn-id {
      type uint32;
      description
        "SCCP connection ID";
    }
    leaf sess-id {
      type uint32;
      description
        "SCCP session ID";
    }
    leaf stype {
      type voice-ios-xe-oper:sccp-sess-type;
      description
        "SCCP session type";
    }
    leaf mode {
      type voice-ios-xe-oper:sccp-conn-mode;
      description
        "SCCP connection mode";
    }
    leaf codec {
      type voice-ios-xe-oper:voip-codec-type;
      description
        "SCCP connection codec";
    }
    leaf rmt-ipaddr {
      type inet:ip-address;
      description
        "SCCP connection remote IP address";
    }
    leaf rmt-port {
      type uint16;
      description
        "SCCP connection remote port";
    }
    leaf src-port {
      type uint16;
      description
        "SCCP connection source port";
    }
    leaf dtmf-method {
      type voice-ios-xe-oper:dtmf-method-type;
      description
        "SCCP connection DTMF method";
    }
  }

  grouping dspfarm-dsp {
    description
      "DSPFARM DSP resource information";
    leaf bridge-id {
      type uint32;
      description
        "Bridge ID";
    }
    leaf dsp-slot {
      type string;
      description
        "DSP slot";
    }
    leaf dsp-num {
      type uint32;
      description
        "DSP number";
    }
    leaf dsp-version {
      type string;
      description
        "DSP Version";
    }
    leaf dsp-status {
      type voice-ios-xe-oper:dsp-status-type;
      description
        "DSP status";
    }
    leaf chnl-id {
      type uint32;
      description
        "DSP channel ID";
    }
    leaf chnl-status {
      type voice-ios-xe-oper:chnl-status-type;
      description
        "DSP channel status";
    }
    leaf service-type {
      type voice-ios-xe-oper:dsp-service-type;
      description
        "DSP service type";
    }
    leaf rsc-id {
      type uint32;
      description
        "DSP resource ID";
    }
    leaf pkts-txed {
      type uint32;
      description
        "DSP transmitted packets";
    }
    leaf pkts-rxed {
      type uint32;
      description
        "DSP received packets";
    }
  }

  grouping dspfp-codec-entry {
    description
      " Details of DSPFarm Profile Codecs";
    leaf codec-idx {
      type uint32;
      description
        "Index to the codec entry list";
    }
    leaf codec-type {
      type voice-ios-xe-oper:voip-codec-type;
      description
        "VOIP codec type entry";
    }
    leaf max-pkt-period {
      type uint32;
      description
        "Max. packetization period for the codec";
    }
  }

  grouping dspfp {
    description
      "DSPFarm Profile Information ";
    leaf profile-id {
      type uint32;
      description
        "DSPFarm Profile ID";
    }
    leaf service-id {
      type voice-ios-xe-oper:srvc-id;
      description
        "DSPFarm Service ID";
    }
    leaf resource-id {
      type uint32;
      description
        "DSPFarm Resource ID";
    }
    leaf secure-mode {
      type voice-ios-xe-oper:secure-mode;
      description
        "DSPFarm Profile Service Mode";
    }
    leaf prof-admin-state {
      type voice-ios-xe-oper:prof-admin-state;
      description
        "DSPFarm Profile Admin State";
    }
    leaf prof-oper-state {
      type voice-ios-xe-oper:prof-oper-state;
      description
        "DSPFarm Profile Operation State";
    }
    leaf app-id {
      type voice-ios-xe-oper:app-id;
      description
        "DSPFarm Profile Application ID";
    }
    leaf app-assoc-status {
      type voice-ios-xe-oper:app-assoc;
      description
        "DSPFarm Application Registration Status";
    }
    leaf rsc-provider {
      type voice-ios-xe-oper:rscprv-id;
      description
        "DSPFarm Profile Resource Provider";
    }
    leaf rsc-status {
      type voice-ios-xe-oper:rscprv-state;
      description
        "DSPFarm Profile Resource Status";
    }
    leaf total-rsc-cfg-count {
      type uint32;
      description
        "DSPFarm Profile Resource Configured Count";
    }
    leaf total-rsc-avail-count {
      type uint32;
      description
        "DSPFarm Profile Resource Available Count";
    }
    leaf total-rsc-oos-count {
      type uint32;
      description
        "DSPFarm Profile Resource Out of Service Count";
    }
    leaf total-rsc-active-count {
      type uint32;
      description
        "DSPFarm Profile Resource Active Count";
    }
    leaf total-codec-count {
      type uint32;
      description
        "DSPFarm Profile Total Codec Count";
    }
    list dspfp-codec-entry {
      key "codec-idx";
      description
        "List of associated codecs for the profile";
      uses voice-ios-xe-oper:dspfp-codec-entry;
    }
  }

  grouping voice-reg-line-info {
    description
      "Voice register line information";
    leaf dialpeer-tag {
      type uint32;
      description
        "Dial-peer tag";
    }
    leaf address {
      type inet:ip-address;
      description
        "IP address of phone";
    }
    leaf dir-number {
      type string;
      description
        "Directory number";
    }
  }

  grouping voice-reg-phone-info {
    description
      "Status of phones fallen back to SRST";
    leaf pool-tag {
      type uint32;
      description
        "Pool tag";
    }
    leaf id-network {
      type inet:ip-address;
      description
        "ID network";
    }
    leaf reg-state {
      type voice-ios-xe-oper:reg-state-type;
      description
        "State of phone registration";
    }
    list voice-reg-line-info {
      key "dialpeer-tag";
      description
        "Phone line information";
      uses voice-ios-xe-oper:voice-reg-line-info;
    }
  }

  grouping active-voip-call-key {
    description
      "Active VOIP call leg key parameters";
    leaf call-index {
      type uint32;
      description
        "Index of the call leg";
    }
    leaf call-setuptime {
      type yang:date-and-time;
      description
        "Call leg setup time";
    }
  }

  grouping active-voip-call-details {
    description
      "Active VOIP call leg details";
    leaf call-id {
      type uint32;
      description
        "Unique ID of the call leg";
    }
    leaf call-type {
      type voice-ios-xe-oper:voice-call-type-enum;
      description
        "Call leg type";
    }
    leaf bridge-id {
      type uint32;
      description
        "Unique ID for call";
    }
    leaf peer-id {
      type int32;
      description
        "Dial-peer ID";
    }
    leaf direction {
      type voice-ios-xe-oper:voice-call-direction-enum;
      description
        "Incoming leg or Outgoing leg";
    }
    leaf directory-number {
      type string;
      description
        "Directory Number (DN) of this call leg";
    }
    leaf call-state {
      type voice-ios-xe-oper:voice-call-state-enum;
      description
        "State of this call leg";
    }
    leaf call-duration {
      type uint32;
      units "milliseconds";
      description
        "Call duration";
    }
    leaf transmit-packets {
      type uint32;
      description
        "Number of packets transmitted";
    }
    leaf transmit-bytes {
      type uint32;
      description
        "Number of bytes transmitted";
    }
    leaf receive-packets {
      type uint32;
      description
        "Number of packets received";
    }
    leaf receive-bytes {
      type uint32;
      description
        "Number of bytes received";
    }
    leaf remote-ip-address {
      type inet:ip-address;
      description
        "Call leg remote IP address";
    }
    leaf remote-media-port {
      type uint16;
      description
        "Call leg remote media port";
    }
    leaf codec {
      type voice-ios-xe-oper:voip-codec-type;
      description
        "VOIP codec negotiated on the leg";
    }
  }

  grouping active-voip-call-summary {
    description
      "Total active VOIP call summary";
    leaf telephony-call-legs {
      type uint32;
      description
        "Total number of telephony call legs";
    }
    leaf sip-call-legs {
      type uint32;
      description
        "Total number of SIP call legs";
    }
    leaf total-call-legs {
      type uint32;
      description
        "Total number of SIP and telephony legs";
    }
    list active-voip-call-details {
      key "call-index call-setuptime";
      description
        "A list of active VOIP call leg details";
      uses voice-ios-xe-oper:active-voip-call-key;
      uses voice-ios-xe-oper:active-voip-call-details;
    }
  }

  container voice-oper-data {
    config false;
    description
      "Voice operational data";
    list dspfarm-dsp {
      key "bridge-id";
      description
        "DSPFARM DSP details";
      uses voice-ios-xe-oper:dspfarm-dsp;
    }
    list sccp-connection {
      key "conn-id";
      description
        "SCCP Connection details";
      uses voice-ios-xe-oper:sccp-connection;
    }
    list voice-recording-port {
      key "port-dptag";
      description
        "Voice recording port status";
      uses voice-ios-xe-oper:voice-recording-port;
    }
    container voice-recording-license {
      presence "voice-recording-license";
      description
        "Voice recording license status";
      uses voice-ios-xe-oper:voice-recording-license;
    }
    list dspfarm-utlz-profile {
      key "profile-id";
      description
        "DSP Farm profile utilization status";
      uses voice-ios-xe-oper:dspfarm-utlz-profile;
    }
    list dspfarm-utlz-detail {
      key "profile-id";
      description
        "DSP Farm detailed utilization status";
      uses voice-ios-xe-oper:dspfarm-utlz-detail;
    }
    container dsapp-line-dev-sum {
      presence "dsapp-line-dev-sum";
      description
        "DSAPP line device summary";
      uses voice-ios-xe-oper:dsapp-line-dev-sum;
    }
    container dsapp-line-fac {
      presence "dsapp-line-fac";
      description
        "DSAPP line feature access codes";
      uses voice-ios-xe-oper:dsapp-line-fac;
    }
    container active-voice-call-sum {
      presence "active-voice-call-sum";
      description
        "Active voice call summary";
      uses voice-ios-xe-oper:active-voice-call-sum;
    }
    container active-voip-call-summary {
      presence "active-voip-call-summary";
      description
        "Active VOIP call details";
      uses voice-ios-xe-oper:active-voip-call-summary;
    }
    list sccp-ccm-group {
      key "ccm-group-id";
      description
        "Skinny Call Control Protocol Call Manager group detail settings";
      uses voice-ios-xe-oper:sccp-ccm-group;
    }
    list dspfp {
      key "profile-id";
      description
        "DSPFarm Profile Details";
      uses voice-ios-xe-oper:dspfp;
    }
    list voice-reg-phone-info {
      key "pool-tag";
      description
        "Status of phones fallen back to SRST";
      uses voice-ios-xe-oper:voice-reg-phone-info;
    }
  }
}
