module Cisco-IOS-XE-vxlan {
  namespace "http://cisco.com/ns/yang/Cisco-IOS-XE-vxlan";
  prefix ios-vxlan;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Virtual Extensible Local Area Network (VXLAN) Yang Model.
     Copyright (c) 2018 by Cisco Systems, Inc.
     All rights reserved.";

  revision 2019-07-01 {
    description
      "Establish semantic version baseline";
    cisco-semver:module-version "1.0.0";
  }
  revision 2019-02-25 {
    description
      "Initial revision";
  }

  grouping config-vxlan-grouping {
    container udp {
      leaf port {
        description
          "VxLAN dataplane UDP destination port for global";
        type uint16 {
          range "1024..65535";
        }
      }
    }
  }

  augment "/ios:native/ios:vxlan" {
    uses config-vxlan-grouping;
  }
}
