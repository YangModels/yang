submodule Cisco-IOS-XE-license {
  belongs-to Cisco-IOS-XE-native {
    prefix ios;
  }

  import cisco-semver {
    prefix cisco-semver;
  }
  import Cisco-IOS-XE-features {
    prefix ios-features;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native License Yang model.
     Copyright (c) 2016 by Cisco Systems, Inc.
     All rights reserved.";

  revision 2019-07-01 {
    description
      "Establish semantic version baseline";
    cisco-semver:module-version "1.0.0";
  }
  revision 2018-11-07 {
    description
      "Cleanup spelling errors in description statements";
  }
  revision 2018-10-23 {
    description
      "Added license boot suite command. Command not applicable to CSR";
  }
  revision 2017-12-01 {
    description
      "Add licenses boot level addon for cat3k";
  }
  revision 2017-10-18 {
    description
      "Add licenses boot level on switch and smart licensing";
  }
  revision 2017-05-25 {
    description
      "Add licenses ax and security";
  }
  revision 2017-02-07 {
    description
      "Initial revision";
  }

  grouping config-license-grouping {
    container license {
      description
        "Configure license features";
      container udi {
        leaf pid {
          type string;
        }
        leaf sn {
          type string;
        }
      }
      container feature {
        description
          "License features";
        leaf name {
          type string;
        }
        container port {
          description
            "Enable Ports for IM";
          leaf bulk {
            description
              "Enable Bulk port licenses";
            type empty;
          }
          leaf onegig {
            description
              "Enable 1G port bundles";
            type uint8 {
              range "1..2";
            }
          }
          leaf b-6xonegig {
            description
              "Enable 6x1G port bundles";
            type uint8 {
              range "1..2";
            }
          }
          leaf tengig {
            description
              "Enable 10G port bundles";
            type uint8 {
              range "1..2";
            }
          }
        }
      }
      container accept {
        leaf end {
          type empty;
        }
        leaf user {
          type empty;
        }
        leaf agreement {
          type empty;
        }
      }
      container boot {
        description
          "license boot config commands";
        container level {
          description
            "which level to boot";
          choice license-choice {
            case ipbase-case {
              container ipbase {
                description
                  "ipbase level";
                presence "true";
                leaf switch {
                  description
                    "Switch license information";
                  type uint8;
                }
              }
            }
            case ipbasek9-case {
              container ipbasek9 {
                description
                  "License Level IPBASEK9";
                presence "true";
                leaf addon {
                  description
                    "select add-on to include";
                  type enumeration {
                    enum "dna-advantage";
                    enum "dna-essentials";
                  }
                }
              }
            }
            case ipservices-case {
              container ipservices {
                description
                  "ipservices level";
                presence "true";
                leaf switch {
                  description
                    "Switch license information";
                  type empty;
                }
              }
            }
            case ipservicesk9-case {
              container ipservicesk9 {
                description
                  "ipservicesk9 level";
                presence "true";
                leaf addon {
                  description
                    "select add-on to include";
                  type enumeration {
                    enum "dna-advantage";
                    enum "dna-essentials";
                  }
                }
              }
            }
            case lanbase-case {
              container lanbase {
                description
                  "lanbase level";
                presence "true";
                leaf switch {
                  description
                    "Switch license information";
                  type empty;
                }
              }
            }
            case lanbasek9-case {
              container lanbasek9 {
                description
                  "License Level LANBASEK9";
                presence "true";
                leaf addon {
                  description
                    "select add-on to include";
                  type enumeration {
                    enum "dna-essentials";
                  }
                }
              }
            }
            case lite-case {
              container lite {
                description
                  "lite level";
                presence "true";
                leaf switch {
                  description
                    "Switch license information";
                  type empty;
                }
              }
            }
            case metroaggrservices-case {
              container metroaggrservices {
                description
                  "metroaggrservices level";
                presence "true";
                leaf switch {
                  description
                    "Switch license information";
                  type empty;
                }
              }
            }
            case metroipservices-case {
              leaf metroipservices {
                description
                  "Metroipservices License Level";
                type empty;
              }
            }
            case metroservices-case {
              leaf metroservices {
                description
                  "Metroservices License Level";
                type empty;
              }
            }
            case advancedmetroipaccess-case {
              leaf advancedmetroipaccess {
                description
                  "Advanced Metro IP Access License Level";
                type empty;
              }
            }
            case metroaccess-case {
              leaf metroaccess {
                description
                  "Metro Access License Level";
                type empty;
              }
            }
            case metroipaccess-case {
              leaf metroipaccess {
                description
                  "Metro IP Access License Level";
                type empty;
              }
            }
            case entservices-case {
              leaf entservices {
                description
                  "Entservices License Level";
                type empty;
              }
            }
            case adventerprise-case {
              leaf adventerprise {
                description
                  "Adventerprise License Level";
                type empty;
              }
            }
            case appx-case {
              leaf appx {
                description
                  "Appx License Level";
                type empty;
              }
            }
            case appxk9-case {
              leaf appxk9 {
                description
                  "Appxk9 License Level";
                type empty;
              }
            }
            case ax-case {
              leaf ax {
                description
                  "ax(ipb+sec+appx) License Level";
                type empty;
              }
            }
            case security-case {
              leaf security {
                description
                  "Security License Level";
                type empty;
              }
            }
            case securityk9-case {
              leaf securityk9 {
                description
                  "Securityk9 License Level";
                type empty;
              }
            }
            case uck9-case {
              container uck9 {
                description
                  "Uck9 License Level";
                presence "true";
                leaf disable {
                  type empty;
                }
              }
            }
            case network-advantage-case {
              container network-advantage {
                description
                  "License Level Network-Advantage";
                presence "true";
                leaf addon {
                  description
                    "select add-on to include";
                  type enumeration {
                    enum "dna-advantage";
                    enum "dna-essentials";
                  }
                }
              }
            }
            case network-essentials-case {
              container network-essentials {
                description
                  "License Level Network-Essentials";
                presence "true";
                leaf addon {
                  description
                    "select add-on to include";
                  type enumeration {
                    enum "dna-essentials";
                  }
                }
              }
            }
            case AdvUCSuiteK9-case {
              leaf AdvUCSuiteK9 {
                description
                  "AdvUCSuiteK9 License Level";
                type empty;
              }
            }
            case FoundationSuiteK9-case {
              leaf FoundationSuiteK9 {
                description
                  "FoundationSuiteK9 License Level";
                type empty;
              }
            }
          }
        }
        container suite {
          description
            "License suite to boot";
          if-feature "ios-features:license-suite-command";
          leaf suite-name {
            description
              "License Suite name";
            type enumeration {
              enum "AdvUCSuiteK9";
              enum "FoundationSuiteK9";
            }
          }
        }
        container boot-module {
          leaf module {
            type enumeration {
              enum "c2900";
            }
          }
          container technology-package {
            leaf securityk9 {
              type empty;
            }
            leaf uck9 {
              type empty;
            }
            leaf datak9 {
              type empty;
            }
          }
        }
      }
      container smart {
        description
          "Smart licensing";
        leaf customer-id {
          description
            "Customer defined id";
          type string;
        }
        leaf enable {
          description
            "Enable Smart licensing";
          type empty;
        }
        leaf transport-type {
          type enumeration {
            enum "callhome";
            enum "smart";
          }
          description
            "The transport type. If transport-type is set to 
                    callhome then any additional transport settings must 
                    be done from the callhome CLI.
                    If the transport-type is set to smart, additional 
                    settings are available below.";
        }
        container privacy {
          leaf hostname {
            type empty;
          }
          leaf version {
            type empty;
          }
        }
        container utility {
          description
            "Enable or disable usage reporting on the device";
          leaf enable {
            description
              "Enable or disable usage reporting";
            type empty;
          }
          container customer-info {
            leaf city {
              description
                "Customer defined city";
              type string;
            }
            leaf country {
              description
                "Customer defined country";
              type string;
            }
            leaf id {
              description
                "Customer defined id";
              type string;
            }
            leaf name {
              description
                "Customer defined name";
              type string;
            }
            leaf postalcode {
              description
                "Customer defined postal code";
              type string;
            }
            leaf state {
              description
                "Customer defined state";
              type string;
            }
            leaf street {
              description
                "Customer defined street";
              type string;
            }
          }
        }
        container url {
          description
            "Specify the Smart Transport primary and the Utility URL";
          choice url-setting {
            description
              "Specify the URL(s) used for communications to the SSM,
               satellite or Third Party Billing Platform.";
            case set-default {
              leaf default {
                type empty;
                description
                  "Enable the default URLs for both
                   url-registration and url-utility that point to 
                   the Cisco SSM.";
              }
            }
            case set-urls {
              leaf name {
                type string;
                description
                  "Specify the URL used for registration, authorization and
                   anything else not related to utility usage reporting.";
              }
              leaf utility {
                type string;
                description
                  "Specify the URL to be used for sending utility usage 
                   reports. This should be the same as url-registration 
                   if you are using a satellite.";
              }
            }
          }
        }
      }
    }
  }
}
