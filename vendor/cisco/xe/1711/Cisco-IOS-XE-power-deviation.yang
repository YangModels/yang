module Cisco-IOS-XE-power-deviation {
  namespace "http://cisco.com/ns/yang/Cisco-IOS-XE-power-deviation";
  prefix ios-power-d;

  import Cisco-IOS-XE-native {
    prefix ios;
  }
  import Cisco-IOS-XE-power {
    prefix ios-power;
  }

  organization
    "Cisco Systems";
  description
    "Cisco XE Native Deviation YANG module for IOS
     Copyright (c) 2019 by Cisco Systems, Inc.
     All rights reserved.";

  revision 2019-04-17 {
    description
      "Added LLDP deviation";
  }

  deviation "/ios:native/ios-power:power/ios-power:supply/ios-power:autoLC" {
    deviate not-supported;
  }
  deviation "/ios:native/ios-power:power/ios-power:redundancy-mode-config/ios-power:combined" {
    deviate not-supported;
  }
  deviation "/ios:native/ios-power:power/ios-power:redundancy-mode-config/ios-power:redundant" {
    deviate not-supported;
  }
}
