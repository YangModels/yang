module Cisco-IOS-XE-stackwise-virtual {
  namespace "http://cisco.com/ns/yang/Cisco-IOS-XE-stackwise-virtual";
  prefix ios-stackwise-virtual;

  import cisco-semver {
    prefix cisco-semver;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "StackWise Virtual Interface for the NetConf protocol: Client side
     Cisco XE StackWise Virtual Yang Model.
     Copyright (c) 2017 by Cisco Systems, Inc.
     All rights reserved.";

  revision 2019-07-01 {
    description
      "Establish semantic version baseline";
    cisco-semver:module-version "1.0.0";
  }
  revision 2017-06-05 {
    description
      "Initial revision";
  }

  grouping config-stackwise-virtual-grouping {
    container domain {
      description
        "Set the Stackwise Virtual switch domain number";
      leaf domain {
        type uint16 {
          range "1..255";
        }
      }
    }
    container dual-active {
      description
        "Stackwise Virtual dual active detection";
      container detection {
        description
          "Stackwise Virtual dual active detection configuration";
        container pagp {
          description
            "Dual-active detection using PAgP";
          presence "true";
          container trust {
            description
              "Trusted channels for PAgP dual-active detection";
            container channel-group {
              description
                "Etherchannel/port bundle to be used for pagp dual-active detection";
              leaf channel-group-number {
                description
                  "Percent range from 1 to 128.";
                type uint16 {
                  range "1..128";
                }
              }
            }
          }
        }
      }
    }
  }

  augment "/ios:native/ios:stackwise-virtual" {
    uses config-stackwise-virtual-grouping;
  }
}
