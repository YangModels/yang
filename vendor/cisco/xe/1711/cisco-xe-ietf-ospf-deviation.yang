module cisco-xe-ietf-ospf-deviation {
  namespace "http://cisco.com/ns/cisco-xe-ietf-ospf-deviation";
  prefix ospf-devs;

  import ietf-routing {
    prefix rt;
  }
  import ietf-ospf {
    prefix ospf;
  }

  organization
    "Cisco Systems, Inc.";
  contact
    " Cisco Systems, Inc.
     Customer Service
     
     Postal: 170 W Tasman Drive
     San Jose, CA 95134
     
     Tel: +1 1800 553-NETS
     
     E-mail: cs-yang@cisco.com";
  description
    "This module defines deviation statements for ietf-ospf
     module.";

  revision 2018-02-09 {
    description
      "Added deviations for operational data";
    reference
      "RFC 6020: YANG - A Data Modeling Language for the
       Network Configuration Protocol (NETCONF)";
  }
  revision 2015-09-11 {
    description
      "Initial Revision";
    reference
      "RFC 6020: YANG - A Data Modeling Language for the
       Network Configuration Protocol (NETCONF)";
  }

  deviation "/ospf:if-state-change" {
    deviate not-supported;
    description
      "Not supported in IOS-XE 3.17 release.";
  }
  deviation "/ospf:if-config-error" {
    deviate not-supported;
    description
      "Not supported in IOS-XE 3.17 release.";
  }
  deviation "/ospf:nbr-state-change" {
    deviate not-supported;
    description
      "Not supported in IOS-XE 3.17 release.";
  }
  deviation "/ospf:nbr-restart-helper-status-change" {
    deviate not-supported;
    description
      "Not supported in IOS-XE 3.17 release.";
  }
  deviation "/ospf:lsdb-approaching-overflow" {
    deviate not-supported;
    description
      "Not supported in IOS-XE 3.17 release.";
  }
  deviation "/ospf:lsdb-overflow" {
    deviate not-supported;
    description
      "Not supported in IOS-XE 3.17 release.";
  }
  deviation "/ospf:nssa-translator-status-change" {
    deviate not-supported;
    description
      "Not supported in IOS-XE 3.17 release.";
  }
  deviation "/ospf:restart-status-change" {
    deviate not-supported;
    description
      "Not supported in IOS-XE 3.17 release.";
  }
  deviation "/ospf:rx-bad-packet" {
    deviate not-supported;
    description
      "Not supported in IOS-XE 3.17 release.";
  }
  deviation "/rt:routing/rt:routing-instance/rt:routing-protocols/rt:routing-protocol/ospf:ospf/ospf:operation-mode" {
    deviate not-supported;
    description
      "Not supported in IOS-XE 3.17 release.";
  }
  deviation "/rt:routing/rt:routing-instance/rt:routing-protocols/rt:routing-protocol/ospf:ospf/ospf:all-instances-inherit" {
    deviate not-supported;
    description
      "Not supported in IOS-XE 3.17 release.";
  }
  deviation "/rt:routing/rt:routing-instance/rt:routing-protocols/rt:routing-protocol/ospf:ospf/ospf:instance/ospf:admin-distance/ospf:granularity/ospf:coarse" {
    deviate not-supported;
    description
      "Not supported in IOS-XE 3.17 release.";
  }
  deviation "/rt:routing/rt:routing-instance/rt:routing-protocols/rt:routing-protocol/ospf:ospf/ospf:instance/ospf:graceful-restart" {
    deviate not-supported;
    description
      "Not supported in IOS-XE 3.17 release.";
  }
  deviation "/rt:routing/rt:routing-instance/rt:routing-protocols/rt:routing-protocol/ospf:ospf/ospf:instance/ospf:enable" {
    deviate not-supported;
    description
      "Not supported in IOS-XE 3.17 release.";
  }
  deviation "/rt:routing/rt:routing-instance/rt:routing-protocols/rt:routing-protocol/ospf:ospf/ospf:instance/ospf:mpls/ospf:te-rid/ospf:source/ospf:explicit" {
    deviate not-supported;
    description
      "Not supported in IOS-XE 3.17 release.";
  }
  deviation "/rt:routing/rt:routing-instance/rt:routing-protocols/rt:routing-protocol/ospf:ospf/ospf:instance/ospf:mpls/ospf:ldp" {
    deviate not-supported;
    description
      "Not supported in IOS-XE 3.17 release.";
  }
  deviation "/rt:routing/rt:routing-instance/rt:routing-protocols/rt:routing-protocol/ospf:ospf/ospf:instance/ospf:fast-reroute" {
    deviate not-supported;
    description
      "Not supported in IOS-XE 3.17 release.";
  }
  deviation "/rt:routing/rt:routing-instance/rt:routing-protocols/rt:routing-protocol/ospf:ospf/ospf:instance/ospf:all-areas-inherit" {
    deviate not-supported;
    description
      "Not supported in IOS-XE 3.17 release.";
  }
  deviation "/rt:routing/rt:routing-instance/rt:routing-protocols/rt:routing-protocol/ospf:ospf/ospf:instance/ospf:area/ospf:area-type" {
    deviate not-supported;
    description
      "Not supported in IOS-XE 3.17 release.";
  }
  deviation "/rt:routing/rt:routing-instance/rt:routing-protocols/rt:routing-protocol/ospf:ospf/ospf:instance/ospf:area/ospf:summary" {
    deviate not-supported;
    description
      "Not supported in IOS-XE 3.17 release.";
  }
  deviation "/rt:routing/rt:routing-instance/rt:routing-protocols/rt:routing-protocol/ospf:ospf/ospf:instance/ospf:area/ospf:range" {
    deviate not-supported;
    description
      "Not supported in IOS-XE 3.17 release.";
  }
  deviation "/rt:routing/rt:routing-instance/rt:routing-protocols/rt:routing-protocol/ospf:ospf/ospf:instance/ospf:area/ospf:all-interfaces-inherit" {
    deviate not-supported;
    description
      "Not supported in IOS-XE 3.17 release.";
  }
  deviation "/rt:routing/rt:routing-instance/rt:routing-protocols/rt:routing-protocol/ospf:ospf/ospf:instance/ospf:area/ospf:virtual-link/ospf:mtu-ignore" {
    deviate not-supported;
    description
      "Not supported in IOS-XE 3.17 release.";
  }
  deviation "/rt:routing/rt:routing-instance/rt:routing-protocols/rt:routing-protocol/ospf:ospf/ospf:instance/ospf:area/ospf:virtual-link/ospf:cost" {
    deviate not-supported;
    description
      "Not supported in IOS-XE 3.17 release.";
  }
  deviation "/rt:routing/rt:routing-instance/rt:routing-protocols/rt:routing-protocol/ospf:ospf/ospf:instance/ospf:area/ospf:virtual-link/ospf:lls" {
    deviate not-supported;
    description
      "Not supported in IOS-XE 3.17 release.";
  }
  deviation "/rt:routing/rt:routing-instance/rt:routing-protocols/rt:routing-protocol/ospf:ospf/ospf:instance/ospf:area/ospf:virtual-link/ospf:prefix-suppression" {
    deviate not-supported;
    description
      "Not supported in IOS-XE 3.17 release.";
  }
  deviation "/rt:routing/rt:routing-instance/rt:routing-protocols/rt:routing-protocol/ospf:ospf/ospf:instance/ospf:area/ospf:virtual-link/ospf:bfd" {
    deviate not-supported;
    description
      "Not supported in IOS-XE 3.17 release.";
  }
  deviation "/rt:routing/rt:routing-instance/rt:routing-protocols/rt:routing-protocol/ospf:ospf/ospf:instance/ospf:area/ospf:virtual-link/ospf:ttl-security/ospf:enable" {
    deviate not-supported;
    description
      "Not supported in IOS-XE 3.17 release.";
  }
  deviation "/rt:routing/rt:routing-instance/rt:routing-protocols/rt:routing-protocol/ospf:ospf/ospf:instance/ospf:area/ospf:virtual-link/ospf:enable" {
    deviate not-supported;
    description
      "Not supported in IOS-XE 3.17 release.";
  }
  deviation "/rt:routing/rt:routing-instance/rt:routing-protocols/rt:routing-protocol/ospf:ospf/ospf:instance/ospf:area/ospf:virtual-link/ospf:authentication" {
    deviate not-supported;
    description
      "Not supported in IOS-XE 3.17 release.";
  }
  deviation "/rt:routing/rt:routing-instance/rt:routing-protocols/rt:routing-protocol/ospf:ospf/ospf:instance/ospf:area/ospf:sham-link/ospf:hello-interval" {
    deviate not-supported;
    description
      "Not supported in IOS-XE 3.17 release.";
  }
  deviation "/rt:routing/rt:routing-instance/rt:routing-protocols/rt:routing-protocol/ospf:ospf/ospf:instance/ospf:area/ospf:sham-link/ospf:dead-interval" {
    deviate not-supported;
    description
      "Not supported in IOS-XE 3.17 release.";
  }
  deviation "/rt:routing/rt:routing-instance/rt:routing-protocols/rt:routing-protocol/ospf:ospf/ospf:instance/ospf:area/ospf:sham-link/ospf:retransmit-interval" {
    deviate not-supported;
    description
      "Not supported in IOS-XE 3.17 release.";
  }
  deviation "/rt:routing/rt:routing-instance/rt:routing-protocols/rt:routing-protocol/ospf:ospf/ospf:instance/ospf:area/ospf:sham-link/ospf:transmit-delay" {
    deviate not-supported;
    description
      "Not supported in IOS-XE 3.17 release.";
  }
  deviation "/rt:routing/rt:routing-instance/rt:routing-protocols/rt:routing-protocol/ospf:ospf/ospf:instance/ospf:area/ospf:sham-link/ospf:mtu-ignore" {
    deviate not-supported;
    description
      "Not supported in IOS-XE 3.17 release.";
  }
  deviation "/rt:routing/rt:routing-instance/rt:routing-protocols/rt:routing-protocol/ospf:ospf/ospf:instance/ospf:area/ospf:sham-link/ospf:lls" {
    deviate not-supported;
    description
      "Not supported in IOS-XE 3.17 release.";
  }
  deviation "/rt:routing/rt:routing-instance/rt:routing-protocols/rt:routing-protocol/ospf:ospf/ospf:instance/ospf:area/ospf:sham-link/ospf:prefix-suppression" {
    deviate not-supported;
    description
      "Not supported in IOS-XE 3.17 release.";
  }
  deviation "/rt:routing/rt:routing-instance/rt:routing-protocols/rt:routing-protocol/ospf:ospf/ospf:instance/ospf:area/ospf:sham-link/ospf:bfd" {
    deviate not-supported;
    description
      "Not supported in IOS-XE 3.17 release.";
  }
  deviation "/rt:routing/rt:routing-instance/rt:routing-protocols/rt:routing-protocol/ospf:ospf/ospf:instance/ospf:area/ospf:sham-link/ospf:ttl-security/ospf:enable" {
    deviate not-supported;
    description
      "Not supported in IOS-XE 3.17 release.";
  }
  deviation "/rt:routing/rt:routing-instance/rt:routing-protocols/rt:routing-protocol/ospf:ospf/ospf:instance/ospf:area/ospf:sham-link/ospf:enable" {
    deviate not-supported;
    description
      "Not supported in IOS-XE 3.17 release.";
  }
  deviation "/rt:routing/rt:routing-instance/rt:routing-protocols/rt:routing-protocol/ospf:ospf/ospf:instance/ospf:area/ospf:sham-link/ospf:authentication" {
    deviate not-supported;
    description
      "Not supported in IOS-XE 3.17 release.";
  }
  deviation "/rt:routing/rt:routing-instance/rt:routing-protocols/rt:routing-protocol/ospf:ospf/ospf:instance/ospf:area/ospf:interface/ospf:network-type" {
    deviate not-supported;
    description
      "Not supported in IOS-XE 3.17 release.";
  }
  deviation "/rt:routing/rt:routing-instance/rt:routing-protocols/rt:routing-protocol/ospf:ospf/ospf:instance/ospf:area/ospf:interface/ospf:passive" {
    deviate not-supported;
    description
      "Not supported in IOS-XE 3.17 release.";
  }
  deviation "/rt:routing/rt:routing-instance/rt:routing-protocols/rt:routing-protocol/ospf:ospf/ospf:instance/ospf:area/ospf:interface/ospf:demand-circuit" {
    deviate not-supported;
    description
      "Not supported in IOS-XE 3.17 release.";
  }
  deviation "/rt:routing/rt:routing-instance/rt:routing-protocols/rt:routing-protocol/ospf:ospf/ospf:instance/ospf:area/ospf:interface/ospf:static-neighbors" {
    deviate not-supported;
    description
      "Not supported in IOS-XE 3.17 release.";
  }
  deviation "/rt:routing/rt:routing-instance/rt:routing-protocols/rt:routing-protocol/ospf:ospf/ospf:instance/ospf:area/ospf:interface/ospf:node-flag" {
    deviate not-supported;
    description
      "Not supported in IOS-XE 3.17 release.";
  }
  deviation "/rt:routing/rt:routing-instance/rt:routing-protocols/rt:routing-protocol/ospf:ospf/ospf:instance/ospf:area/ospf:interface/ospf:fast-reroute" {
    deviate not-supported;
    description
      "Not supported in IOS-XE 3.17 release.";
  }
  deviation "/rt:routing/rt:routing-instance/rt:routing-protocols/rt:routing-protocol/ospf:ospf/ospf:instance/ospf:area/ospf:interface/ospf:mtu-ignore" {
    deviate not-supported;
    description
      "Not supported in IOS-XE 3.17 release.";
  }
  deviation "/rt:routing/rt:routing-instance/rt:routing-protocols/rt:routing-protocol/ospf:ospf/ospf:instance/ospf:area/ospf:interface/ospf:lls" {
    deviate not-supported;
    description
      "Not supported in IOS-XE 3.17 release.";
  }
  deviation "/rt:routing/rt:routing-instance/rt:routing-protocols/rt:routing-protocol/ospf:ospf/ospf:instance/ospf:area/ospf:interface/ospf:prefix-suppression" {
    deviate not-supported;
    description
      "Not supported in IOS-XE 3.17 release.";
  }
  deviation "/rt:routing/rt:routing-instance/rt:routing-protocols/rt:routing-protocol/ospf:ospf/ospf:instance/ospf:area/ospf:interface/ospf:bfd" {
    deviate not-supported;
    description
      "Not supported in IOS-XE 3.17 release.";
  }
  deviation "/rt:routing/rt:routing-instance/rt:routing-protocols/rt:routing-protocol/ospf:ospf/ospf:instance/ospf:area/ospf:interface/ospf:ttl-security" {
    deviate not-supported;
    description
      "Not supported in IOS-XE 3.17 release.";
  }
  deviation "/rt:routing/rt:routing-instance/rt:routing-protocols/rt:routing-protocol/ospf:ospf/ospf:instance/ospf:area/ospf:interface/ospf:enable" {
    deviate not-supported;
    description
      "Not supported in IOS-XE 3.17 release.";
  }
  deviation "/rt:routing/rt:routing-instance/rt:routing-protocols/rt:routing-protocol/ospf:ospf/ospf:instance/ospf:area/ospf:interface/ospf:authentication" {
    deviate not-supported;
    description
      "Not supported in IOS-XE 3.17 release.";
  }
  deviation "/rt:routing/rt:routing-instance/rt:routing-protocols/rt:routing-protocol/ospf:ospf/ospf:instance/ospf:area/ospf:interface/ospf:topology" {
    deviate not-supported;
    description
      "Not supported in IOS-XE 3.17 release.";
  }
  deviation "/rt:routing/rt:routing-instance/rt:routing-protocols/rt:routing-protocol/ospf:ospf/ospf:instance/ospf:topology" {
    deviate not-supported;
    description
      "Not supported in IOS-XE 3.17 release.";
  }
  deviation "/rt:routing-state/rt:routing-instance/rt:routing-protocols/rt:routing-protocol/ospf:ospf/ospf:instance/ospf:topology" {
    deviate not-supported;
    description
      "Not supported in Polaris 16.8.1 release.";
  }
  deviation "/rt:routing-state/rt:routing-instance/rt:routing-protocols/rt:routing-protocol/ospf:ospf/ospf:instance/ospf:as-scope-lsas" {
    deviate not-supported;
    description
      "Not supported in Polaris 16.8.1 release.";
  }
  deviation "/rt:routing-state/rt:routing-instance/rt:routing-protocols/rt:routing-protocol/ospf:ospf/ospf:instance/ospf:area/ospf:interfaces/ospf:link-scope-lsas" {
    deviate not-supported;
    description
      "Not supported in Polaris 16.8.1 release.";
  }
  deviation "/rt:routing-state/rt:routing-instance/rt:routing-protocols/rt:routing-protocol/ospf:ospf/ospf:instance/ospf:area/ospf:interfaces/ospf:enable" {
    deviate not-supported;
    description
      "Not supported in Polaris 16.8.1 release.";
  }
  deviation "/rt:routing-state/rt:routing-instance/rt:routing-protocols/rt:routing-protocol/ospf:ospf/ospf:operation-mode" {
    deviate not-supported;
    description
      "Not supported in Polaris 16.8.1 release.";
  }
  deviation "/rt:routing-state/rt:routing-instance/rt:routing-protocols/rt:routing-protocol/ospf:ospf/ospf:instance/ospf:area/ospf:interfaces/ospf:passive" {
    deviate not-supported;
    description
      "Not supported in Polaris 16.8.1 release.";
  }
  deviation "/rt:routing-state/rt:routing-instance/rt:routing-protocols/rt:routing-protocol/ospf:ospf/ospf:instance/ospf:area/ospf:interfaces/ospf:node-flag" {
    deviate not-supported;
    description
      "Not supported in Polaris 16.8.1 release.";
  }
  deviation "/rt:routing-state/rt:routing-instance/rt:routing-protocols/rt:routing-protocol/ospf:ospf/ospf:instance/ospf:area/ospf:interfaces/ospf:fast-reroute" {
    deviate not-supported;
    description
      "Not supported in Polaris 16.8.1 release.";
  }
  deviation "/rt:routing-state/rt:routing-instance/rt:routing-protocols/rt:routing-protocol/ospf:ospf/ospf:instance/ospf:area/ospf:interfaces/ospf:mtu-ignore" {
    deviate not-supported;
    description
      "Not supported in Polaris 16.8.1 release.";
  }
  deviation "/rt:routing-state/rt:routing-instance/rt:routing-protocols/rt:routing-protocol/ospf:ospf/ospf:instance/ospf:area/ospf:interfaces/ospf:topology" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:decoded-completed" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:raw-data" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:version/ospf:v2/ospf:ospfv2/ospf:header/ospf:opaque-type" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:version/ospf:v2/ospf:ospfv2/ospf:header/ospf:opaque-id" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:version/ospf:v2/ospf:ospfv2/ospf:header/ospf:type" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:version/ospf:v2/ospf:ospfv2/ospf:body/ospf:external" {
    deviate not-supported;
    description
      "Not supported in Polaris 16.8.1 release.";
  }
  deviation "/rt:routing-state/rt:routing-instance/rt:routing-protocols/rt:routing-protocol/ospf:ospf/ospf:instance/ospf:area/ospf:area-scope-lsas/ospf:area-scope-lsa/ospf:version/ospf:v3/ospf:ospfv3/ospf:body/ospf:as-external" {
    deviate not-supported;
    description
      "Not supported in Polaris 16.8.1 release.";
  }
}
