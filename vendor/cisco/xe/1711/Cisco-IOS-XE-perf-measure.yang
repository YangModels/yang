module Cisco-IOS-XE-perf-measure {
  namespace "http://cisco.com/ns/yang/Cisco-IOS-XE-perf-measure";
  prefix ios-performance-measurement;

  import cisco-semver {
    prefix cisco-semver;
  }
  import ietf-inet-types {
    prefix inet;
  }
  import Cisco-IOS-XE-native {
    prefix ios;
  }
  import Cisco-IOS-XE-types {
    prefix ios-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Performance-Measurement Yang model.
     Copyright (c) 2016, 2018-2019 by Cisco Systems, Inc.
     All rights reserved.";

  revision 2019-11-01 {
    description
      "Initial revision";
    cisco-semver:module-version "1.0.0";
  }

  grouping config-perf-measure-advertisement-grouping {
    description
      "Common node for delay profile advertisment";
    container advertisement {
      description
        "Advertisement Profile";
      container accelerated {
        description
          "Accelerated Advertisement Profile";
        leaf threshold {
          type ios-types:percentage;
          units "percentage";
          default "20";
          description
            "Accelerated advertisement threshold percentage";
        }
        leaf minimum-change {
          type uint32 {
            range "0..100000";
          }
          units "microseconds";
          default "500";
          description
            "Accelerated advertisement minimum value in
             microseconds (uSec)";
        }
      }
      container periodic {
        description
          "Periodic Advertisement Profile";
        leaf interval {
          type uint32 {
            range "30..3600";
          }
          units "second";
          default "120";
          description
            "Periodic advertisement interval in seconds";
        }
        leaf threshold {
          type ios-types:percentage;
          units "percentage";
          default "10";
          description
            "Periodic advertisement threshold percentage";
        }
        leaf minimum-change {
          type uint32 {
            range "0..100000";
          }
          units "microsecond";
          description
            "Periodic advertisement minimum value in microseconds (uSec)";
        }
        leaf disable {
          type empty;
          description
            "Disable Performance Measurement Periodic Advertisement";
        }
      }
    }
  }

  grouping config-perf-measure-probe-grouping {
    container probe {
      description
        "PM Delay Profile Probe";
      leaf interval {
        type uint32 {
          range "30..3600";
        }
        units "second";
        default "30";
        description
          "The value for delay profile probe interval in
           seconds";
      }
      leaf one-way {
        type empty;
        description
          "Enable one-way measurement";
      }
      container burst {
        description
          "PM Delay Profile Probe Burst";
        leaf count {
          type uint8 {
            range "1..30";
          }
          default "10";
          description
            "The value for delay profile probe burst count";
        }
        leaf interval {
          type uint32 {
            range "30..15000";
          }
          units "millisecond";
          default "3000";
          description
            "The value for delay profile probe burst 
                   interval in milliseconds";
        }
      }
      container protocol {
        description
          "Protocol used to send probes";
        choice protocol-choice {
          default "pm-mpls";
          case pm-mpls {
            leaf pm-mpls {
              type empty;
              description
                "SR Policy delay measurement using RFC 6374 with MPLS encap";
            }
          }
          case twamp-light {
            leaf twamp-light {
              type empty;
              description
                "SR Policy delay measurement using RFC 5357";
            }
          }
        }
      }
    }
  }

  grouping config-perf-measure-grouping {
    list interface {
      description
        "Configure a performance-measurement interface";
      key "interface-name";
      leaf interface-name {
        type string;
      }
      container delay-measurement {
        presence "true";
        description
          "Interface delay measurement";
        leaf advertise-delay {
          type uint32 {
            range "0..16777215";
          }
          units "microsecond";
          description
            "The value for interface delay measurement
             advertisement delay in uSec";
        }
      }
      container next-hop {
        description
          "next-hop address";
        choice nexthop-address-choice {
          case nexthop-ipv4-address {
            leaf ipv4 {
              description
                "IPv4 address";
              type inet:ipv4-address;
            }
          }
          case nexthop-ipv6-address {
            leaf ipv6 {
              description
                "IPv6 address";
              type inet:ipv6-address;
            }
          }
        }
      }
    }
    container delay-profile {
      description
        "Performance-measurement delay profile";
      container interfaces {
        description
          "Performance-measurement interface delay profile";
        uses config-perf-measure-advertisement-grouping;
        uses config-perf-measure-probe-grouping;
      }
    }
    container protocol {
      description
        "Supported Protocol";
      container twamp-light {
        description
          "Enter twamp-light protocol submode";
        container measurement {
          description
            "Supported measurement types";
          container delay {
            description
              "Enter delay measurement submode";
            container unauthenticated {
              description
                "Enter unauthenticated mode";
              leaf querier-dst-port {
                description
                  "<11000-14999>  Port number";
                type uint16 {
                  range "11000..14999";
                }
              }
              leaf querier-src-port {
                must "not (. = ../querier-dst-port)" {
                  error-message "querier-dst-port and querier-src-port cannot be configured equal";
                }
                description
                  "<11000-14999>  Port number";
                type uint16 {
                  range "11000..14999";
                }
              }
            }
          }
        }
      }
    }
  }

  augment "/ios:native/ios:performance-measurement" {
    uses config-perf-measure-grouping;
  }
}
