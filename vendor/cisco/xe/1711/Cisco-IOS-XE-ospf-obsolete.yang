submodule Cisco-IOS-XE-ospf-obsolete {
  belongs-to Cisco-IOS-XE-ospf {
    prefix ios-ospf;
  }

  import ietf-inet-types {
    prefix inet;
  }
  import Cisco-IOS-XE-types {
    prefix ios-types;
  }
  import Cisco-IOS-XE-interface-common {
    prefix ios-ifc;
  }
  import Cisco-IOS-XE-native {
    prefix ios;
  }
  import Cisco-IOS-XE-features {
    prefix ios-features;
  }

  revision 2019-10-01 {
    description
      "Initial revision";
  }

  typedef redist-ospf-external-type {
    type enumeration {
      enum "1";
      enum "2";
    }
  }

  grouping authentication-ipsec-grouping {
    container ipsec {
      status obsolete;
      description
        "Use IPsec authentication";
      leaf spi {
        status obsolete;
        description
          "Set the SPI (Security Parameters Index)";
        type uint64 {
          range "256..4294967295";
        }
      }
      container md5 {
        status obsolete;
        description
          "Use MD5 authentication";
        container key-string {
          status obsolete;
          leaf encrypt {
            status obsolete;
            type enumeration {
              enum "0";
              enum "7";
            }
          }
          leaf string {
            status obsolete;
            type string;
          }
        }
      }
      container sha1 {
        status obsolete;
        description
          "Use SHA-1 authentication";
        container key-string {
          status obsolete;
          leaf encrypt {
            status obsolete;
            type enumeration {
              enum "0";
              enum "7";
            }
          }
          leaf string {
            status obsolete;
            type string;
          }
        }
      }
    }
  }

  grouping interface-ospf-neighbor-grouping {
    list neighbor {
      status obsolete;
      description
        "OSPF neighbor";
      ordered-by user;
      must "count(*) > 1";
      key "id";
      leaf id {
        status obsolete;
        type inet:ipv6-address;
      }
      leaf cost {
        status obsolete;
        description
          "OSPF cost for point-to-multipoint neighbor";
        type uint16 {
          range "1..65535";
        }
      }
      container database-filter {
        status obsolete;
        description
          "Filter OSPF LSA during synchronization and flooding for point-to-multipoint neighbor";
        choice database {
          status obsolete;
          leaf all {
            status obsolete;
            description
              "Filter all LSA";
            type enumeration {
              enum "out";
            }
          }
        }
      }
      leaf poll-interval {
        status obsolete;
        description
          "OSPF dead-router polling interval";
        type uint32 {
          range "0..65535";
        }
      }
      leaf priority {
        status obsolete;
        description
          "OSPF priority of non-broadcast neighbor";
        type uint8 {
          range "0..255";
        }
      }
    }
  }

  grouping interface-ospf-encryption-grouping {
    container encryption {
      status obsolete;
      description
        "Enable encryption";
      leaf null {
        status obsolete;
        description
          "No IPsec encryption on this interface";
        type empty;
      }
      container ipsec {
        status obsolete;
        description
          "Use IPsec encryption";
        leaf spi {
          status obsolete;
          description
            "Set the SPI (Security Parameters Index)";
          type uint64;
        }
        leaf esp {
          status obsolete;
          description
            "Use ESP encapsulation";
          type empty;
        }
        container ipsec_3des {
          status obsolete;
          description
            "Use 3DES encryption";
          container key-string {
            status obsolete;
            leaf encrypt {
              status obsolete;
              type enumeration {
                enum "0";
                enum "7";
              }
            }
            leaf string {
              status obsolete;
              type string;
            }
          }
        }
        container aes-cbc {
          status obsolete;
          description
            "Use AES-CBC encryption";
          container aes-cbc-128 {
            status obsolete;
            description
              "Use 128 bit key";
            container key-string {
              status obsolete;
              leaf encrypt {
                status obsolete;
                type enumeration {
                  enum "0";
                  enum "7";
                }
              }
              leaf string {
                status obsolete;
                type string;
              }
            }
          }
          container aes-192 {
            status obsolete;
            description
              "Use 192 bit key";
            container key-string {
              status obsolete;
              leaf encrypt {
                status obsolete;
                type enumeration {
                  enum "0";
                  enum "7";
                }
              }
              leaf string {
                status obsolete;
                type string;
              }
            }
          }
          container aes-256 {
            status obsolete;
            description
              "Use 256 bit key";
            container key-string {
              status obsolete;
              leaf encrypt {
                status obsolete;
                type enumeration {
                  enum "0";
                  enum "7";
                }
              }
              leaf string {
                status obsolete;
                type string;
              }
            }
          }
        }
      }
    }
  }

  grouping interface-ospf-dead-interval-grouping {
    leaf dead-interval {
      status obsolete;
      description
        "Interval after which a neighbor is declared dead";
      type uint16 {
        range "1..65535";
      }
    }
  }

  grouping interface-ospf-hello-interval-grouping {
    leaf hello-interval {
      status obsolete;
      description
        "Time between HELLO packets";
      type uint32 {
        range "1..65535";
      }
    }
  }

  grouping interface-ospf-prefix-suppression-grouping {
    container prefix-suppression {
      status obsolete;
      description
        "OSPF prefix suppression";
      presence "true";
      leaf disable {
        status obsolete;
        description
          "Disable prefix suppression";
        type empty;
      }
    }
  }

  grouping interface-ospf-priority-grouping {
    leaf priority {
      status obsolete;
      description
        "Router priority";
      type uint8 {
        range "0..255";
      }
    }
  }

  grouping interface-ospf-retransmit-interval-grouping {
    leaf retransmit-interval {
      status obsolete;
      description
        "Time between retransmitting lost link state advertisements";
      type uint32 {
        range "1..65535";
      }
    }
  }

  grouping interface-ospf-transmit-delay-grouping {
    leaf transmit-delay {
      status obsolete;
      description
        "Link state transmit delay";
      type uint32 {
        range "1..65535";
      }
    }
  }

  grouping interface-ospf-bfd-grouping {
    container bfd {
      status obsolete;
      description
        "Enable BFD on this interface";
      presence "true";
      leaf disable {
        status obsolete;
        description
          "Disable BFD on this interface";
        type empty;
      }
    }
  }

  grouping interface-ospf-network-grouping {
    container network {
      status obsolete;
      description
        "Network type";
      leaf broadcast {
        status obsolete;
        description
          "Specify OSPF broadcast multi-access network";
        type empty;
      }
      leaf manet {
        status obsolete;
        description
          "Specify MANET OSPF interface type";
        type empty;
      }
      leaf non-broadcast {
        status obsolete;
        description
          "Specify OSPF NBMA network";
        type empty;
      }
      container point-to-multipoint {
        status obsolete;
        description
          "Specify OSPF point-to-multipoint network";
        presence "true";
        leaf non-broadcast {
          description
            "Specify non-broadcast point-to-mpoint network";
          type empty;
        }
      }
      leaf point-to-point {
        status obsolete;
        description
          "Specify OSPF point-to-point network";
        type empty;
      }
    }
  }

  grouping config-interface-ip-ospf-grouping {
    status obsolete;
    container ospf {
      status obsolete;
      description
        "OSPF interface commands";
      list process-id {
        status obsolete;
        must "not (../../../ios:switchport-conf/ios:switchport) or (../../../ios:switchport-conf/ios:switchport = 'false')" {
          error-message "To configure ip ospf, set switchport to false 1st; To change switchport from false to true, delete ip ospf 1st ";
        }
        key "id";
        leaf id {
          status obsolete;
          type leafref {
            path "/ios:native/ios:router/ios-ospf:ospf/ios-ospf:id";
          }
        }
        leaf area {
          status obsolete;
          type ios-types:ospf-area-type;
        }
        leaf secondaries {
          status obsolete;
          description
            "Include or exclude secondary IP addresses";
          type empty;
        }
        leaf none {
          status obsolete;
          description
            "Do not include secondary IP addresses";
          type empty;
        }
      }
      container authentication {
        status obsolete;
        description
          "Enable authentication";
        presence "Enable authentication";
        container key-chain {
          status obsolete;
          description
            "Use a key-chain for cryptographic authentication keys";
          leaf name {
            status obsolete;
            type string;
          }
        }
        leaf message-digest {
          status obsolete;
          description
            "Use message-digest authentication";
          type empty;
        }
        leaf null {
          status obsolete;
          description
            "Use no authentication";
          type empty;
        }
      }
      uses ospf-authentication-key-grouping;
      leaf network {
        status obsolete;
        description
          "Network type";
        type enumeration {
          enum "broadcast";
          enum "non-broadcast";
          enum "point-to-multipoint";
          enum "point-to-point";
        }
      }
      uses interface-ospf-bfd-grouping;
      leaf cost {
        status obsolete;
        description
          "Interface cost";
        type uint16 {
          range "1..65535";
        }
      }
      container database-filter {
        status obsolete;
        description
          "Filter OSPF LSA during synchronization and flooding";
        leaf all {
          status obsolete;
          description
            "Filter all LSA";
          type empty;
        }
        leaf out {
          status obsolete;
          description
            "Outgoing LSA";
          type empty;
        }
      }
      container dead-interval {
        status obsolete;
        description
          "Interval after which a neighbor is declared dead";
        leaf value {
          status obsolete;
          type uint32 {
            range "1..65535";
          }
        }
        container minimal {
          status obsolete;
          description
            "Set to 1 second";
          leaf hello-multiplier {
            status obsolete;
            description
              "Set multiplier for Hellos";
            type uint8;
          }
        }
      }
      container demand-circuit {
        status obsolete;
        description
          "OSPF Demand Circuit";
        presence "true";
        leaf ignore {
          status obsolete;
          description
            "Ignore demand circuit auto-negotiation requests";
          type empty;
        }
      }
      container fast-reroute {
        status obsolete;
        description
          "LFA FastReroute parameters";
        container per-prefix {
          status obsolete;
          description
            "Per-prefix LFA FRR parameters";
          container candidate {
            status obsolete;
            description
              "If interface can be protecting";
            presence "true";
            leaf disable {
              status obsolete;
              description
                "Disable LFA FRR interface protection";
              type empty;
            }
          }
          container protection {
            status obsolete;
            description
              "If interface can be protected";
            presence "true";
            leaf disable {
              status obsolete;
              description
                "Disable LFA FRR interface protection";
              type empty;
            }
          }
        }
      }
      leaf flood-reduction {
        status obsolete;
        description
          "OSPF Flood Reduction";
        type empty;
      }
      uses interface-ospf-hello-interval-grouping;
      container lls {
        status obsolete;
        description
          "Link-local Signaling (LLS) support";
        presence "true";
        leaf disable {
          status obsolete;
          description
            "disable LLS";
          type empty;
        }
      }
      list message-digest-key {
        status obsolete;
        description
          "Set message digest key";
        key "id";
        leaf id {
          status obsolete;
          type uint8 {
            range "1 .. 255";
          }
        }
        container md5 {
          status obsolete;
          description
            "Use MD5 algorithm";
          leaf auth-type {
            status obsolete;
            type uint8 {
              range "0 .. 7";
            }
          }
          leaf auth-key {
            status obsolete;
            type string {
              pattern ".*";
            }
          }
        }
      }
      leaf mtu-ignore {
        status obsolete;
        description
          "Ignores the MTU in DBD packets";
        type empty;
      }
      container multi-area {
        status obsolete;
        description
          "Set the OSPF multi-area ID";
        leaf id {
          status obsolete;
          type union {
            type uint32 {
              range "0..4294967295";
            }
            type inet:ipv4-address;
          }
        }
        leaf cost {
          status obsolete;
          description
            "Interface cost";
          type uint32 {
            range "1..65535";
          }
        }
      }
      uses interface-ospf-prefix-suppression-grouping;
      uses interface-ospf-priority-grouping;
      leaf resync-timeout {
        status obsolete;
        description
          "Interval after which adjacency is reset if oob-resync is not started";
        type uint32 {
          range "1..65535";
        }
      }
      uses interface-ospf-retransmit-interval-grouping;
      leaf shutdown {
        status obsolete;
        description
          "Set OSPF protocol's state to disable under current interface";
        type empty;
      }
      uses interface-ospf-transmit-delay-grouping;
      container ttl-security {
        status obsolete;
        description
          "TTL security check";
        presence "true";
        leaf diable {
          status obsolete;
          description
            "disable TTL security check";
          type empty;
        }
        leaf hops {
          status obsolete;
          description
            "IP hops";
          type uint8 {
            range "1..254";
          }
        }
      }
    }
  }

  grouping config-interface-ipv6-ospf-grouping {
    status obsolete;
    container ospf {
      status obsolete;
      description
        "OSPF interface commands";
      list process {
        status obsolete;
        key "id";
        leaf id {
          status obsolete;
          type uint16 {
            range "1..65535";
          }
        }
        leaf area {
          status obsolete;
          description
            "Set the OSPF area ID";
          type union {
            type uint32 {
              range "0..4294967295";
            }
            type inet:ipv4-address;
          }
        }
        leaf instance {
          status obsolete;
          description
            "Set the OSPF instance";
          type union {
            type uint8 {
              range "0..31";
            }
            type uint8 {
              range "32..255";
            }
          }
        }
      }
      container authentication {
        status obsolete;
        description
          "Enable authentication";
        leaf null {
          status obsolete;
          description
            "Use no authentication";
          type empty;
        }
        uses authentication-ipsec-grouping;
      }
      uses interface-ospf-bfd-grouping;
      leaf cost {
        status obsolete;
        description
          "Route cost of this interface";
        type uint16 {
          range "1..65535";
        }
      }
      container database-filter {
        status obsolete;
        description
          "Filter OSPF LSA during synchronization and flooding";
        choice database {
          status obsolete;
          leaf all {
            status obsolete;
            description
              "Filter all LSA";
            type enumeration {
              enum "out";
            }
          }
          leaf disable {
            status obsolete;
            description
              "Disable LSA Filter on this interface";
            type empty;
          }
        }
      }
      uses interface-ospf-dead-interval-grouping;
      container demand-circuit {
        status obsolete;
        description
          "OSPF demand circuit";
        presence "true";
        leaf disable {
          status obsolete;
          description
            "Disable demand circuit on this interface";
          type empty;
        }
        leaf ignore {
          status obsolete;
          description
            "Ignore demand circuit auto-negotiation requests";
          type empty;
        }
      }
      uses interface-ospf-encryption-grouping;
      container flood-reduction {
        status obsolete;
        description
          "OSPF Flood Reduction";
        presence "true";
        leaf disable {
          status obsolete;
          description
            "Disable Flood Reduction on this interface";
          type empty;
        }
      }
      uses interface-ospf-hello-interval-grouping;
      container mtu-ignore {
        status obsolete;
        description
          "Ignores the MTU in DBD packets";
        presence "true";
        leaf disable {
          status obsolete;
          description
            "Disable Ignore MTU on this interface";
          type empty;
        }
      }
      uses interface-ospf-neighbor-grouping;
      uses interface-ospf-network-grouping;
      uses interface-ospf-priority-grouping;
      uses interface-ospf-retransmit-interval-grouping;
      container shutdown {
        status obsolete;
        description
          "Shut down the interface in OSPFv3";
        presence "true";
        leaf disable {
          status obsolete;
          description
            "Disable inherited shutdown";
          type empty;
        }
      }
      uses interface-ospf-transmit-delay-grouping;
    }
  }

  grouping ospf-ospfv3-common-address-family-grouping {
    container capability {
      status obsolete;
      description
        "Enable specific OSPF feature";
      leaf capability-type {
        status obsolete;
        type enumeration {
          enum "lls";
          enum "opaque";
          enum "transit";
          enum "vrf-lite";
        }
      }
    }
    container compatible {
      status deprecated;
      description
        "OSPF compatibility list";
      leaf rfc1583 {
        status deprecated;
        description
          "Compatible with RFC 1583";
        type empty;
      }
      leaf rfc1587 {
        status obsolete;
        description
          "Compatible with RFC 1587";
        type empty;
      }
      leaf rfc5243 {
        status obsolete;
        description
          "Compatible with RFC 5243";
        type empty;
      }
    }
    container default-information {
      status deprecated;
      description
        "Control distribution of default information";
      container originate {
        status deprecated;
        description
          "Distribute a default route";
        presence "Distribute a default route";
        leaf always {
          status deprecated;
          description
            "Always advertise default route";
          type empty;
        }
        leaf metric {
          status deprecated;
          description
            "OSPF default metric";
          type uint32 {
            range "0 .. 16777214";
          }
        }
        leaf metric-type {
          status deprecated;
          description
            "OSPF metric type for default routes";
          type ios-types:ospf-metric-type;
        }
        leaf route-map {
          status deprecated;
          description
            "Route map reference";
          type string;
        }
      }
    }
    leaf default-metric {
      status obsolete;
      description
        "Set metric of redistributed routes";
      type uint32 {
        range "1 .. 16777214";
      }
    }
    container discard-route {
      status obsolete;
      description
        "Enable or disable discard-route installation";
      presence "Enable or disable discard-route installation";
      leaf external {
        status obsolete;
        description
          "Discard route for redistributed summarised routes";
        type empty;
      }
      leaf internal {
        status obsolete;
        description
          "Discard route for summarised internal routes";
        type empty;
      }
      leaf metric {
        status obsolete;
        type uint32 {
          range "1 .. 255";
        }
      }
    }
    container distance {
      status deprecated;
      description
        "Define an administrative distance";
      container ospf-distance {
        status obsolete;
        leaf distance {
          status obsolete;
          type uint32 {
            range "1 .. 255";
          }
        }
        leaf ip {
          status obsolete;
          type inet:ipv4-address;
        }
        leaf wildcard {
          status obsolete;
          type inet:ipv4-address;
        }
        leaf acl-name {
          status obsolete;
          type ios-types:access-list-standard-id-type;
        }
      }
      container ospf {
        status deprecated;
        description
          "OSPF routes Administrative distance";
        leaf external {
          status deprecated;
          description
            "External routes";
          type uint32 {
            range "1 .. 255";
          }
        }
        leaf inter-area {
          status deprecated;
          description
            "Inter-area routes";
          type uint32 {
            range "1 .. 255";
          }
        }
        leaf intra-area {
          status deprecated;
          description
            "Intra-area routes";
          type uint32 {
            range "1 .. 255";
          }
        }
      }
    }
    leaf maximum-paths {
      status obsolete;
      description
        "Forward packets over multiple paths";
      type uint32 {
        range "1 .. 32";
      }
    }
    container redistribute {
      status deprecated;
      description
        "Redistribute information from another routing protocol";
      uses ospf-redistribute-top-grouping;
      container maximum-prefix {
        status obsolete;
        description
          "Maximum number of prefixes redistributed to protocol";
        leaf number {
          status obsolete;
          type uint32 {
            range "1 .. 4294967295";
          }
        }
        container threshold-warning-only-container {
          status obsolete;
          leaf threshold {
            status obsolete;
            type uint32 {
              range "1 .. 100";
            }
          }
          leaf warning-only {
            status obsolete;
            description
              "Only give warning message when limit is exceeded";
            type empty;
          }
        }
      }
      container vrf {
        status obsolete;
        description
          "Specify a source VRF";
        list non-global-vrf {
          status obsolete;
          key "name";
          leaf name {
            status obsolete;
            must "/ios:native/ios:vrf/ios:definition[ios:name=current()] or /ios:native/ios:ip/ios:vrf[ios:name=current()]" {
              error-message "VRF must be created 1st, deleted last";
            }
            type string;
          }
          uses ospf-redistribute-top-grouping;
        }
        container global {
          status obsolete;
          description
            "global VRF";
          uses ospf-redistribute-top-grouping;
        }
      }
    }
  }

  grouping ospf-ospfv3-common-grouping {
    list area {
      status deprecated;
      description
        "OSPF area parameters";
      key "id";
      leaf id {
        status deprecated;
        type ios-types:ospf-area-type;
      }
      container authentication {
        status deprecated;
        description
          "Enable authentication";
        presence "true";
        leaf message-digest {
          status deprecated;
          description
            "Use message-digest authentication";
          type empty;
        }
      }
      container capability {
        status obsolete;
        description
          "Enable area specific capability";
        leaf default-exclusion {
          status obsolete;
          description
            "Enable exclusion of links from base topology";
          type empty;
        }
      }
      leaf default-cost {
        status obsolete;
        description
          "Set the summary default-cost of a NSSA/stub area";
        type uint32 {
          range "0 .. 16777215";
        }
      }
      list filter-list {
        status obsolete;
        description
          "Filter networks between OSPF areas";
        key "in-out";
        leaf in-out {
          status obsolete;
          type enumeration {
            enum "in";
            enum "out";
          }
        }
        leaf prefix {
          status obsolete;
          mandatory true;
          description
            "Filter prefixes between OSPF areas";
          type string;
        }
      }
      container nssa {
        status obsolete;
        description
          "Specify a NSSA area";
        presence "Specify a NSSA area";
        container default-information-originate {
          status obsolete;
          description
            "Originate Type 7 default into NSSA area";
          presence "Originate Type 7 default into NSSA area";
          leaf metric {
            status obsolete;
            description
              "OSPF default metric";
            type int32 {
              range "0 .. 16777214";
            }
          }
          leaf metric-type {
            status obsolete;
            description
              "OSPF metric type for default routes";
            type ios-types:ospf-metric-type;
          }
          leaf no-ext-capability {
            status obsolete;
            description
              "Do not send domain specific capabilities into NSSA";
            type empty;
          }
          leaf no-redistribution {
            status obsolete;
            description
              "No redistribution into this NSSA area";
            type empty;
          }
          leaf no-summary {
            status obsolete;
            description
              "Do not send summary LSA into NSSA";
            type empty;
          }
          leaf nssa-only {
            status obsolete;
            description
              "Limit default advertisement to this NSSA area";
            type empty;
          }
          container translate {
            status obsolete;
            description
              "Translate LSA";
            container type7 {
              status obsolete;
              description
                "From Type 7 to Type 5";
              leaf always {
                status obsolete;
                description
                  "Always translate LSAs on this ABR";
                type empty;
              }
              leaf suppress-fa {
                status obsolete;
                description
                  "Suppress forwarding address in translated LSAs";
                type empty;
              }
            }
          }
        }
        leaf no-ext-capability {
          status obsolete;
          description
            "Do not send domain specific capabilities into NSSA";
          type empty;
        }
        leaf no-redistribution {
          status obsolete;
          description
            "No redistribution into this NSSA area";
          type empty;
        }
        leaf no-summary {
          status obsolete;
          description
            "Do not send summary LSA into NSSA";
          type empty;
        }
        leaf nssa-only {
          status obsolete;
          description
            "Limit default advertisement to this NSSA area";
          type empty;
        }
        container translate {
          status obsolete;
          description
            "Translate LSA";
          container type7 {
            status obsolete;
            description
              "From Type 7 to Type 5";
            leaf always {
              status obsolete;
              description
                "Always translate LSAs on this ABR";
              type empty;
            }
            leaf suppress-fa {
              status obsolete;
              description
                "Suppress forwarding address in translated LSAs";
              type empty;
            }
          }
        }
      }
      container ipv4-range {
        status obsolete;
        list range {
          status obsolete;
          description
            "Summarize routes matching address/mask (border routers only)";
          key "ip mask";
          leaf ip {
            status obsolete;
            type inet:ipv4-address;
          }
          leaf mask {
            status obsolete;
            type inet:ipv4-address;
          }
          choice advertise-choice {
            status obsolete;
            leaf advertise {
              status obsolete;
              description
                "Advertise this range (default)";
              type empty;
            }
            leaf not-advertise {
              status obsolete;
              description
                "DoNotAdvertise this range";
              type empty;
            }
          }
          leaf cost {
            status obsolete;
            description
              "User specified metric for this range";
            type uint32 {
              range "0 .. 16777215";
            }
          }
        }
      }
      container ipv6-range {
        status obsolete;
        list range {
          status obsolete;
          description
            "Summarize routes matching address/mask (border routers only)";
          key "ip";
          leaf ip {
            status obsolete;
            type ios-types:ipv6-prefix;
          }
          choice advertise-choice {
            status obsolete;
            leaf advertise {
              status obsolete;
              description
                "Advertise this range (default)";
              type empty;
            }
            leaf not-advertise {
              status obsolete;
              description
                "DoNotAdvertise this range";
              type empty;
            }
          }
          leaf cost {
            status obsolete;
            description
              "User specified metric for this range";
            type uint32 {
              range "0 .. 16777215";
            }
          }
        }
      }
      list sham-link {
        status obsolete;
        description
          "Define a sham link and its parameters";
        key "source dest";
        leaf source {
          status obsolete;
          type inet:ip-address;
        }
        leaf dest {
          status obsolete;
          type inet:ip-address;
        }
        leaf cost {
          status obsolete;
          description
            "Associate a cost with the sham-link";
          type uint16 {
            range "0 .. 65535";
          }
        }
        container ttl-security {
          status obsolete;
          description
            "TTL security check";
          leaf hops {
            status obsolete;
            description
              "IP hops";
            type uint8;
          }
        }
      }
      container stub {
        status obsolete;
        description
          "Specify a stub area";
        presence "Specify a stub area";
        leaf no-ext-capability {
          status obsolete;
          description
            "Do not send domain specific capabilities into stub area";
          type empty;
        }
        leaf no-summary {
          status obsolete;
          description
            "Do not send summary LSA into stub area";
          type empty;
        }
      }
      list virtual-link {
        status obsolete;
        description
          "Define a virtual link and its parameters";
        key "id";
        leaf id {
          status obsolete;
          type inet:ip-address;
        }
        container authentication {
          status obsolete;
          description
            "Set authentication type";
          uses ospf-area-virtual-link-grouping;
          container key-chain {
            status obsolete;
            description
              "Use a key-chain for cryptographic authentication keys";
            leaf name {
              status obsolete;
              type string;
            }
            uses ospf-area-virtual-link-grouping;
          }
          container message-digest {
            status obsolete;
            description
              "Message-digest authentication";
            uses ospf-area-virtual-link-grouping;
          }
          leaf null {
            status obsolete;
            description
              "No authentication";
            type empty;
          }
        }
        container hello-interval {
          status obsolete;
          description
            "Hello packet interval";
          leaf hello-interval-value {
            status obsolete;
            type int32 {
              range "1 .. 8192";
            }
          }
        }
        container dead-interval {
          status obsolete;
          description
            "Dead router detection time";
          leaf dead-interval-value {
            status obsolete;
            type uint16 {
              range "1 .. 8192";
            }
          }
        }
        container retransmit-interval {
          status obsolete;
          description
            "LSA retransmit interval";
          leaf retransmit-interval-value {
            status obsolete;
            type uint16 {
              range "1 .. 8192";
            }
          }
        }
        container transmit-delay {
          status obsolete;
          description
            "LSA transmission delay";
          leaf transmit-delay-value {
            status obsolete;
            type uint16 {
              range "1 .. 8192";
            }
          }
        }
        container topology {
          status obsolete;
          description
            "Disable virtual link on topology";
          leaf disable {
            status obsolete;
            description
              "Disable virtual link";
            type empty;
          }
        }
        container ttl-security {
          status obsolete;
          description
            "TTL security check";
          leaf hops {
            status obsolete;
            description
              "IP hops";
            type uint8 {
              range "1..254";
            }
          }
        }
        uses ospf-area-virtual-link-grouping;
      }
    }
    container auto-cost {
      status deprecated;
      description
        "Calculate OSPF interface cost according to bandwidth";
      presence "Calculate OSPF interface cost according to bandwidth";
      leaf reference-bandwidth {
        status deprecated;
        description
          "Use reference bandwidth method to assign OSPF cost";
        type uint32 {
          range "1 .. 4294967";
        }
      }
    }
    container event-log {
      status obsolete;
      description
        "OSPF Event Logging";
      presence "true";
      leaf one-shot {
        status obsolete;
        description
          "Disable Logging When Log Buffer Becomes Full";
        type empty;
      }
      leaf pause {
        status obsolete;
        description
          "Pause Event Logging";
        type empty;
      }
      leaf size {
        status obsolete;
        description
          "Maximum Number of Events Stored in the Event Log";
        type uint32 {
          range "1..65534";
        }
      }
    }
    container bfd {
      status obsolete;
      description
        "BFD configuration commands";
      leaf all-interfaces {
        status obsolete;
        description
          "Enable BFD on all interfaces";
        type empty;
      }
    }
    container interface-id {
      status obsolete;
      description
        "Source of the interface ID";
      leaf snmp-if-index {
        status obsolete;
        description
          "SNMP MIB ifIndex";
        type empty;
      }
    }
    container log-adjacency-changes {
      status obsolete;
      description
        "Log changes in adjacency state";
      presence "true";
      leaf detail {
        status obsolete;
        description
          "Log all state changes";
        type empty;
      }
    }
    container max-lsa {
      status obsolete;
      description
        "maximum number of LSAs OSPF process will receive";
      leaf number {
        status obsolete;
        type uint32 {
          range "1 .. 4294967294";
        }
      }
      leaf threshold-value {
        status obsolete;
        type uint32 {
          range "1 .. 100";
        }
      }
      leaf ignore-count {
        status obsolete;
        description
          "maximum number of times adjacencies can be suppressed";
        type uint32 {
          range "1 .. 65534";
        }
      }
      leaf ignore-time {
        status obsolete;
        description
          "time during which all adjacencies are suppressed";
        type uint32 {
          range "1 .. 17895";
        }
      }
      leaf reset-time {
        status obsolete;
        description
          "time after which ignore-count is reset to zero";
        type uint32 {
          range "2 .. 35791";
        }
      }
      leaf warning-only {
        status obsolete;
        description
          "Only give warning message when limit is exceeded";
        type empty;
      }
    }
    container max-metric {
      status deprecated;
      description
        "Set maximum metric";
      container router-lsa {
        status deprecated;
        description
          "Maximum metric in self-originated router-LSAs";
        presence "Maximum metric in self-originated router-LSAs";
        container external-lsa {
          status deprecated;
          presence "Override external-lsa metric with max-metric value";
          description
            "Override external-lsa metric with max-metric value";
          leaf metric {
            status deprecated;
            type uint32 {
              range "1 .. 16777215";
            }
          }
        }
        leaf include-stub {
          status deprecated;
          description
            "Set maximum metric for stub links in router-LSAs";
          type empty;
        }
        container on-startup {
          status deprecated;
          description
            "Set maximum metric temporarily after reboot";
          presence "Set maximum metric temporarily after reboot";
          choice time-wait-for-bgp-choice {
            status deprecated;
            leaf time {
              status deprecated;
              type uint32 {
                range "5 .. 86400";
              }
            }
            leaf wait-for-bgp {
              status deprecated;
              description
                "Let BGP decide when to originate router-LSA with normal metric";
              type empty;
            }
          }
        }
        container summary-lsa {
          status obsolete;
          description
            "Override summary-lsa metric with max-metric value";
          presence "Override summary-lsa metric with max-metric value";
          leaf metric {
            status obsolete;
            type uint32 {
              range "1 .. 16777215";
            }
          }
        }
      }
    }
    container passive-interface {
      status obsolete;
      description
        "Suppress routing updates on an interface";
      choice passive-interface-choice {
        status obsolete;
        leaf default {
          status obsolete;
          description
            "Suppress routing updates on all interfaces";
          type empty;
        }
        leaf-list interface {
          status obsolete;
          type string;
        }
      }
    }
    container disable {
      status obsolete;
      when "../passive-interface/default";
      list passive-interface {
        status obsolete;
        key "interface";
        leaf interface {
          status obsolete;
          type string;
        }
      }
    }
    container queue-depth {
      status obsolete;
      description
        "OSPF Hello/Router process queue depth";
      container hello {
        status obsolete;
        description
          "OSPF Hello process queue depth";
        uses queue-depth-grouping;
      }
      container update {
        status obsolete;
        description
          "OSPF Router process queue depth";
        uses queue-depth-grouping;
      }
    }
    container timers {
      status deprecated;
      description
        "Adjust routing timers";
      container lsa {
        status obsolete;
        description
          "OSPF LSA timers";
        leaf arrival {
          status obsolete;
          description
            "OSPF LSA arrival timer";
          type uint32 {
            range "0 .. 600000";
          }
        }
      }
      container pacing {
        status obsolete;
        description
          "OSPF pacing timers";
        leaf flood {
          status obsolete;
          description
            "OSPF flood pacing timer";
          type uint32 {
            range "5 .. 100";
          }
        }
        leaf lsa-group {
          status obsolete;
          description
            "OSPF LSA group pacing timer";
          type uint32 {
            range "10 .. 1800";
          }
        }
        leaf retransmission {
          status obsolete;
          description
            "OSPF retransmission pacing timer";
          type uint32 {
            range "5 .. 200";
          }
        }
      }
      container throttle {
        status deprecated;
        description
          "OSPF throttle timers";
        container lsa {
          status obsolete;
          description
            "OSPF LSA throttle timers";
          container all {
            status obsolete;
            description
              "For all type of OSPF LSAs";
            leaf delay {
              status obsolete;
              type uint32 {
                range "0 .. 600000";
              }
            }
            leaf min-delay {
              status obsolete;
              type uint32 {
                range "0 .. 600000";
              }
            }
            leaf max-delay {
              status obsolete;
              type uint32 {
                range "0 .. 600000";
              }
            }
          }
        }
        container spf {
          status deprecated;
          description
            "OSPF SPF throttle timers";
          leaf delay {
            status deprecated;
            type uint32 {
              range "0 .. 600000";
            }
          }
          leaf min-delay {
            status deprecated;
            type uint32 {
              range "0 .. 600000";
            }
          }
          leaf max-delay {
            status deprecated;
            type uint32 {
              range "0 .. 600000";
            }
          }
        }
      }
    }
    leaf router-id {
      status deprecated;
      description
        "Override configured router identifier (peers will reset)";
      type inet:ipv4-address;
    }
    leaf nsr {
      status obsolete;
      description
        "Enable non-stop routing";
      type empty;
    }
    container traffic-share {
      status obsolete;
      description
        "How to compute traffic share over alternate paths";
      leaf min {
        status obsolete;
        description
          "All traffic shared among min metric paths";
        type empty;
      }
      leaf across-interfaces {
        status obsolete;
        description
          "Use different interfaces for equal-cost paths";
        type empty;
      }
    }
    container ttl-security {
      status obsolete;
      description
        "TTL security check";
      leaf all-interfaces {
        status obsolete;
        description
          "Enable TTL Security on all interfaces";
        type empty;
      }
      leaf hops {
        status obsolete;
        description
          "IP hops";
        type uint8 {
          range "1..254";
        }
      }
    }
  }

  grouping distribute-list-grouping {
    container distribute-list {
      status obsolete;
      description
        "Filter networks in routing updates";
      list accesslist {
        status obsolete;
        key "in-out";
        leaf in-out {
          status obsolete;
          type ios-types:access-list-in-out-type;
        }
      }
      list accesslist-ifname {
        status obsolete;
        key "in-out interface";
        leaf in-out {
          status obsolete;
          type ios-types:access-list-in-out-type;
        }
        leaf interface {
          status obsolete;
          type string;
        }
        leaf interface-routing-id {
          status obsolete;
          type uint8;
        }
        leaf isis-tag {
          status obsolete;
          type string;
        }
        leaf vrf {
          status obsolete;
          description
            "VPN Routing/Forwarding Instance";
          type string;
        }
      }
      list accesslist-prefix-gateway {
        status obsolete;
        key "in-out";
        leaf in-out {
          status obsolete;
          type ios-types:access-list-in-out-type;
        }
        leaf prefix-gateway {
          status obsolete;
          mandatory true;
          type enumeration {
            enum "prefix";
            enum "gateway";
            enum "route-map";
          }
        }
        leaf name {
          status obsolete;
          mandatory true;
          type string;
        }
      }
      list accesslist-prefix-gateway-ifname {
        status obsolete;
        key "in-out interface";
        leaf in-out {
          status obsolete;
          type ios-types:access-list-in-out-type;
        }
        leaf interface {
          status obsolete;
          type string;
        }
        leaf prefix-gateway {
          status obsolete;
          mandatory true;
          type enumeration {
            enum "prefix";
            enum "gateway";
            enum "route-map";
          }
        }
        leaf name {
          status obsolete;
          mandatory true;
          type string;
        }
        leaf interface-routing-id {
          status obsolete;
          type uint8;
        }
        leaf isis-tag {
          status obsolete;
          type string;
        }
        leaf vrf {
          status obsolete;
          description
            "VPN Routing/Forwarding Instance";
          type string;
        }
      }
    }
  }

  grouping ospf-authentication-key-grouping {
    container authentication-key {
      status obsolete;
      description
        "Set authentication key";
      leaf auth-type {
        status obsolete;
        type uint8 {
          range "0 .. 7";
        }
      }
      leaf auth-key {
        status obsolete;
        type string;
      }
    }
  }

  grouping ospf-area-virtual-link-grouping {
    uses ospf-authentication-key-grouping;
    list message-digest-key {
      status obsolete;
      description
        "Set message digest key";
      key "id";
      leaf id {
        status obsolete;
        type uint8 {
          range "1 .. 255";
        }
      }
      container md5 {
        status obsolete;
        description
          "Use MD5 algorithm";
        leaf auth-type {
          status obsolete;
          type uint8 {
            range "0 .. 7";
          }
        }
        leaf auth-key {
          status obsolete;
          type string {
            length "1 .. 16";
          }
        }
      }
    }
  }

  grouping tie-break-index {
    leaf required {
      status obsolete;
      description
        "Mandatory repair path attribute";
      type empty;
    }
    leaf index {
      status obsolete;
      description
        "Tiebreak attribute priority";
      type uint8 {
        range "1..255";
      }
    }
  }

  grouping queue-depth-grouping {
    leaf options {
      status obsolete;
      type union {
        type uint32 {
          range "1 .. 2147483647";
        }
        type enumeration {
          enum "unlimited";
        }
      }
    }
  }

  grouping router-eigrp-redistribute-grouping {
    container metric {
      status obsolete;
      description
        "Metric for redistributed routes";
      leaf bandwith {
        status obsolete;
        description
          "Bandwidth metric in Kbits per second";
        type uint32 {
          range "1..4294967295";
        }
      }
      leaf delay {
        status obsolete;
        description
          "EIGRP delay metric, in 10 microsecond units";
        type uint32 {
          range "0..4294967295";
        }
      }
      leaf reliability {
        status obsolete;
        description
          "EIGRP reliability metric where 255 is 100% reliable";
        type uint8 {
          range "0..255";
        }
      }
      leaf Effective {
        status obsolete;
        description
          "EIGRP Effective bandwidth metric (Loading) where 255 is 100% loaded";
        type uint8 {
          range "1..255";
        }
      }
      leaf mtu {
        status obsolete;
        description
          "EIGRP MTU of the path";
        type uint16 {
          range "1..65535";
        }
      }
    }
    leaf route-map {
      status obsolete;
      description
        "Route map reference";
      type string;
    }
  }

  grouping ospf-redistribute-match-grouping {
    leaf metric {
      status obsolete;
      description
        "Metric for redistributed routes";
      type uint32;
    }
    leaf metric-type {
      status obsolete;
      description
        "OSPF/IS-IS exterior metric type for redistributed routes";
      type enumeration {
        enum "1";
        enum "2";
      }
    }
    leaf nssa-only {
      status obsolete;
      description
        "Limit redistributed routes to NSSA areas";
      type empty;
    }
    leaf subnets {
      status obsolete;
      description
        "Consider subnets for redistribution into OSPF";
      type empty;
    }
    leaf route-map {
      status obsolete;
      description
        "Route map reference";
      type string;
    }
    leaf tag {
      status obsolete;
      description
        "Set tag for routes redistributed into OSPF";
      type uint32 {
        range "0 .. 4294967295";
      }
    }
  }

  grouping ospf-redistribute-top-match-grouping {
    container match {
      status obsolete;
      description
        "Redistribution of OSPF routes";
      container internal {
        status obsolete;
        presence "Redistribute OSPF internal routes";
        description
          "Redistribute OSPF internal routes";
        uses ospf-redistribute-match-grouping;
      }
      container external {
        status obsolete;
        description
          "Redistribute OSPF external routes";
        presence "Redistribute OSPF external routes";
        leaf external-routes {
          status obsolete;
          type redist-ospf-external-type;
        }
        uses ospf-redistribute-match-grouping;
      }
      container nssa-external {
        status obsolete;
        description
          "Redistribute OSPF NSSA external routes";
        presence "Redistribute OSPF NSSA external routes";
        leaf nssa-external-routes {
          status obsolete;
          type redist-ospf-external-type;
        }
        uses ospf-redistribute-match-grouping;
      }
    }
  }

  grouping ospf-iso-igrp-redistribute-grouping {
    leaf metric {
      status obsolete;
      description
        "Metric for redistributed routes";
      type uint32;
    }
    leaf metric-type {
      status obsolete;
      description
        "OSPF/IS-IS exterior metric type for redistributed routes";
      type enumeration {
        enum "1";
        enum "2";
      }
    }
    leaf tag {
      status obsolete;
      description
        "Set tag for routes redistributed into OSPF";
      type uint32 {
        range "0 .. 4294967295";
      }
    }
    leaf subnets {
      status obsolete;
      description
        "Consider subnets for redistribution into OSPF";
      type empty;
    }
  }

  grouping ospf-redistribute-grouping {
    container redist-options {
      status deprecated;
      uses ospf-iso-igrp-redistribute-grouping;
      leaf route-map {
        status deprecated;
        description
          "Route map reference";
        type string;
      }
      leaf nssa-only {
        status obsolete;
        description
          "Limit redistributed routes to NSSA areas";
        type empty;
      }
    }
  }

  grouping ospf-redistribute-top-grouping {
    list application {
      status obsolete;
      description
        "Application";
      key "name";
      leaf name {
        status obsolete;
        type string;
      }
      uses ospf-redistribute-grouping;
    }
    list bgp {
      status deprecated;
      description
        "Border Gateway Protocol (BGP)";
      key "as-number";
      uses ospf-redistribute-bgp-grouping;
    }
    container connected {
      status deprecated;
      description
        "Connected";
      presence "Connected";
      uses ospf-redistribute-grouping;
    }
    list eigrp {
      status deprecated;
      description
        "Enhanced Interior Gateway Routing Protocol (EIGRP)";
      key "as-number";
      uses ospf-redistribute-bgp-grouping;
    }
    container isis {
      status obsolete;
      presence "ISO IS-IS";
      description
        "ISO IS-IS";
      choice isis-level-routes-isis-area-choice {
        status obsolete;
        leaf isis-level-routes {
          status obsolete;
          type enumeration {
            enum "level-1";
            enum "level-2";
            enum "level-1-2";
          }
        }
        list isis-area {
          status obsolete;
          key "name";
          leaf name {
            status obsolete;
            type string;
          }
          leaf isis-level-routes {
            status obsolete;
            type enumeration {
              enum "level-1";
              enum "level-2";
              enum "level-1-2";
            }
          }
          uses ospf-redistribute-grouping;
        }
      }
      uses ospf-redistribute-grouping;
    }
    container iso-igrp {
      status obsolete;
      description
        "IGRP for OSI networks";
      presence "IGRP for OSI networks";
      choice area-tag-route-map-choice {
        status obsolete;
        container area-tag-route-map-container {
          status obsolete;
          leaf area-tag {
            status obsolete;
            type string;
          }
          leaf route-map {
            status obsolete;
            description
              "Route map reference";
            type string;
          }
        }
        leaf route-map {
          status obsolete;
          description
            "Route map reference";
          type string;
        }
      }
      container iso-igrp-container {
        status obsolete;
        uses ospf-iso-igrp-redistribute-grouping;
      }
    }
    container lisp {
      status obsolete;
      description
        "Locator ID Separation Protocol (LISP)";
      uses ospf-redistribute-grouping;
    }
    container mobile {
      status obsolete;
      description
        "Mobile routes";
      presence "Mobile routes";
      uses ospf-redistribute-grouping;
    }
    container odr {
      status obsolete;
      description
        "On Demand stub Routes";
      presence "On Demand stub Routes";
      uses ospf-redistribute-grouping;
    }
    container omp {
      status deprecated;
      if-feature "ios-features:omp";
      description
        "Overlay Management Protocol (OMP)";
      presence "omp";
      uses ospf-redistribute-grouping;
    }
    container nat-route {
      status deprecated;
      if-feature "ios-features:sdwan";
      description
        "NAT Route";
      leaf dia {
        status deprecated;
        description
          "Redistribute NAT Direct Internet Access routes";
        type empty;
      }
      leaf outside {
        status deprecated;
        description
          "Redistribute NAT outside routes";
        type empty;
      }
      uses ospf-redistribute-grouping;
    }
    list ospf {
      status obsolete;
      description
        "Open Shortest Path First (OSPF)";
      key "id";
      leaf id {
        status obsolete;
        type uint32 {
          range "1 .. 65535";
        }
      }
      uses ospf-redistribute-top-match-grouping;
      uses ospf-redistribute-match-grouping;
      leaf vrf {
        status obsolete;
        description
          "VPN Routing/Forwarding Instance";
        must "/ios:native/ios:vrf/ios:definition[ios:name=current()] or /ios:native/ios:ip/ios:vrf[ios:name=current()]" {
          error-message "VRF must be created 1st, deleted last";
        }
        type string;
      }
    }
    list ospfv3 {
      status obsolete;
      description
        "OSPFv3";
      key "id";
      leaf id {
        status obsolete;
        type uint32 {
          range "1 .. 65535";
        }
      }
      uses ospf-redistribute-top-match-grouping;
      uses ospf-redistribute-match-grouping;
    }
    list rip {
      status obsolete;
      description
        "Routing Information Protocol (RIP)";
      key "id";
      leaf id {
        status obsolete;
        description
          "User selected string identifying this rip process";
        type string;
      }
      uses ospf-redistribute-grouping;
    }
    container static {
      status deprecated;
      description
        "Static routes";
      presence "Static routes";
      uses ospf-redistribute-grouping;
    }
  }

  grouping ospf-redistribute-bgp-grouping {
    leaf as-number {
      status obsolete;
      type ios-types:bgp-as-number-type;
    }
    uses ospf-redistribute-grouping;
  }

  grouping router-snmp-grouping {
    container snmp {
      status obsolete;
      description
        "Modify snmp parameters";
      list context {
        status obsolete;
        description
          "Configure a SNMP context";
        key "name";
        leaf name {
          status obsolete;
          description
            "Context Name";
          type string;
        }
        container community {
          status obsolete;
          description
            "Configure a SNMP v2c Community string and access privs";
          leaf community-string {
            status obsolete;
            type string;
          }
          container access {
            status obsolete;
            leaf standard-acl {
              status obsolete;
              type uint32 {
                range "1..99";
              }
            }
            leaf expanded-acl {
              status obsolete;
              type uint32 {
                range "1300..1999";
              }
            }
            leaf acl-name {
              status obsolete;
              type string;
            }
            leaf ipv6 {
              status obsolete;
              description
                "Specify IPv6 Named Access-List";
              type string;
            }
            leaf ro {
              status obsolete;
              description
                "Read-only access with this community string";
              type empty;
            }
            leaf rw {
              status obsolete;
              description
                "Read-write access with this community string";
              type empty;
            }
          }
        }
        container user {
          status obsolete;
          description
            "Configure a SNMP v3 user";
          leaf name {
            status obsolete;
            type string;
          }
          container permisssion {
            status obsolete;
            container access {
              status obsolete;
              description
                "specify an access-list associated with this group";
              leaf standard-acl {
                status obsolete;
                type uint32;
              }
              leaf acl-name {
                status obsolete;
                type string;
              }
              leaf ipv6 {
                status obsolete;
                type string;
              }
            }
            container auth {
              status obsolete;
              description
                "authentication parameters for the user";
              leaf md5 {
                status obsolete;
                description
                  "Use HMAC MD5 algorithm for authentication";
                type string;
              }
              leaf sha {
                status obsolete;
                description
                  "Use HMAC SHA algorithm for authentication";
                type string;
              }
            }
            leaf credential {
              status obsolete;
              description
                "If the user password is already configured and saved";
              type empty;
            }
            leaf encrypted {
              status obsolete;
              description
                "specifying passwords as MD5 or SHA digests";
              type empty;
            }
          }
        }
      }
    }
  }

  grouping router-table-map-grouping {
    container table-map {
      status deprecated;
      description
        "Map external entry attributes into routing table";
      leaf name {
        status deprecated;
        description
          "WORD;;route-map name";
        type string;
      }
      leaf filter {
        status deprecated;
        description
          "Selective route download";
        type empty;
      }
    }
  }

  grouping ospf-address-family-grouping {
    uses router-snmp-grouping;
    container topology {
      status obsolete;
      description
        "Associate the routing protocol to a topology instance";
      leaf name {
        status obsolete;
        type string;
      }
      leaf tid {
        status obsolete;
        description
          "Configuring the routing protocol topology tid";
        type uint32 {
          range "32..127";
        }
      }
    }
  }

  grouping config-router-ospf-grouping {
    status deprecated;
    list ospf {
      status deprecated;
      description
        "Open Shortest Path First (OSPF) (DEPRECATED, use router-ospf)";
      key "id";
      leaf id {
        status deprecated;
        type uint16 {
          range "1..65535";
        }
      }
      leaf vrf {
        status deprecated;
        description
          "VPN Routing/Forwarding Instance";
        must "(/ios:native/ios:vrf/ios:definition[ios:name=current()] and /ios:native/ios:vrf/ios:definition[ios:name=current()]/ios:address-family/ios:ipv4) or /ios:native/ios:ip/ios:vrf[ios:name=current()]" {
          error-message "ipv4 VRF must be created 1st, deleted last";
        }
        type string;
      }
      container address-family {
        status obsolete;
        description
          "Enter Address Family command mode";
        container ipv4_1 {
          status obsolete;
          container ipv4 {
            status obsolete;
            description
              "Address family";
            uses ospf-address-family-grouping;
          }
        }
        container ipv4 {
          status obsolete;
          description
            "Address family";
          container unicast {
            status obsolete;
            description
              "Address Family Modifier";
            uses ospf-address-family-grouping;
          }
          container multicast {
            status obsolete;
            description
              "Address Family Modifier";
            uses ospf-address-family-grouping;
          }
        }
      }
      uses ospf-ospfv3-common-grouping;
      uses ospf-ospfv3-common-address-family-grouping;
      uses distribute-list-grouping;
      container domain-id {
        status obsolete;
        description
          "OSPF domain-id";
        choice domain-id-choice {
          status obsolete;
          leaf ip-format {
            status obsolete;
            type inet:ipv4-address;
          }
          container ip-format-secondary {
            status obsolete;
            leaf ip {
              status obsolete;
              type inet:ipv4-address;
            }
            leaf secondary {
              status obsolete;
              description
                "Secondary Domain-ID";
              type empty;
            }
          }
          leaf Null {
            status obsolete;
            description
              "Null Domain-ID";
            type empty;
          }
          container type {
            status obsolete;
            description
              "OSPF domain ID type in Hex format";
            leaf type-leaf {
              status obsolete;
              type enumeration {
                enum "0005";
                enum "0105";
                enum "0205";
                enum "8005";
              }
            }
            leaf value {
              status obsolete;
              description
                "OSPF domain ID value in Hex format";
              type string {
                pattern "[0-9a-fA-F]{12}";
              }
            }
          }
        }
      }
      leaf domain-tag {
        status obsolete;
        description
          "OSPF domain-tag";
        type uint32 {
          range "1 .. 4294967295";
        }
      }
      container fast-reroute {
        status obsolete;
        description
          "LFA FastReroute parameters";
        leaf keep-all-paths {
          status obsolete;
          description
            "Keep LFA FRR audit trail";
          type empty;
        }
        container per-prefix {
          status obsolete;
          description
            "Per-prefix LFA FRR parameters";
          container enable {
            status obsolete;
            description
              "Enable LFA Fast Reroute";
            leaf area {
              status obsolete;
              description
                "Area to enable LFA FRR in";
              type ios-types:ospf-area-type;
            }
            leaf prefix-priority {
              status obsolete;
              description
                "Priority of prefixes to be protected";
              type enumeration {
                enum "high";
                enum "low";
              }
            }
          }
          container remote-lfa {
            status obsolete;
            description
              "Remote LFA FastReroute parameters";
            container area-cost {
              status obsolete;
              leaf area {
                status obsolete;
                description
                  "Area for remote LFA command";
                type ios-types:ospf-area-type;
              }
              leaf maximum-cost {
                status obsolete;
                description
                  "Maximum distance to tunnel endpoint";
                type uint32 {
                  range "1..16777214";
                }
              }
            }
            container area-tunnel {
              status obsolete;
              leaf area {
                status obsolete;
                description
                  "Area for remote LFA command";
                type ios-types:ospf-area-type;
              }
              leaf tunnel {
                status obsolete;
                description
                  "Remote LFA tunnel type";
                type enumeration {
                  enum "mpls-ldp";
                }
              }
            }
            leaf maximum-cost {
              status obsolete;
              description
                "Maximum distance to tunnel endpoint";
              type uint32 {
                range "1..16777214";
              }
            }
            leaf tunnel {
              status obsolete;
              description
                "Remote LFA tunnel type";
              type enumeration {
                enum "mpls-ldp";
              }
            }
          }
          container tie-break {
            status obsolete;
            description
              "LFA FRR repair path selection policy tiebreaks";
            container broadcast-interface-disjoint {
              status obsolete;
              description
                "Interface protection attribute";
              uses tie-break-index;
            }
            container downstream {
              status obsolete;
              description
                "Downstream repair path attribute";
              uses tie-break-index;
            }
            container linecard-disjoint {
              status obsolete;
              description
                "Line card protection attribute";
              uses tie-break-index;
            }
            container lowest-metric {
              status obsolete;
              description
                "Lowest metric repair path attribute";
              uses tie-break-index;
            }
            container node-protecting {
              status obsolete;
              description
                "Node protecting repair path attribute";
              uses tie-break-index;
            }
            container primary-path {
              status obsolete;
              description
                "Equal cost multipath attribute";
              uses tie-break-index;
            }
            container secondary-path {
              status obsolete;
              description
                "Not-equal cost multipath attribute";
              uses tie-break-index;
            }
            container srlg {
              status obsolete;
              description
                "Shared risk link group attribute";
              uses tie-break-index;
            }
          }
        }
      }
      container graceful-restart {
        status obsolete;
        presence "true";
        description
          "Graceful-restart options";
        leaf disable {
          status obsolete;
          description
            "Graceful restart disable";
          type empty;
        }
        container helper {
          status obsolete;
          description
            "helper support";
          presence "true";
          leaf disable {
            status obsolete;
            description
              "disable helper support";
            type empty;
          }
          leaf strict-lsa-checking {
            status obsolete;
            description
              "enable helper strict LSA checking";
            type empty;
          }
        }
        leaf restart-interval {
          status obsolete;
          description
            "Graceful restart interval";
          type uint16;
        }
      }
      container ignore {
        status obsolete;
        description
          "Do not complain about specific event";
        container lsa {
          status obsolete;
          description
            "Do not complain upon receiving LSA of the specified type";
          leaf mospf {
            status obsolete;
            description
              "MOSPF Type 6 LSA";
            type empty;
          }
        }
      }
      leaf ispf {
        status obsolete;
        description
          "Enable incremental SPF computation";
        type empty;
      }
      container limit {
        status obsolete;
        description
          "Limit a specific OSPF feature";
        container retransmissions {
          status obsolete;
          description
            "LS update, DBD, and LS request retransmissions";
          leaf non-dc {
            status obsolete;
            description
              "Non-demand-circuit retransmissions";
            type ios-types:limit-dc-non-dc-type;
          }
          leaf dc {
            status obsolete;
            description
              "Demand circuit retransmissions";
            type ios-types:limit-dc-non-dc-type;
          }
        }
      }
      container local-rib-criteria {
        status obsolete;
        description
          "Enable or disable usage of local RIB as route criteria";
        leaf forwarding-address {
          status obsolete;
          description
            "Local RIB used to validate external/NSSA forwarding addresses";
          type empty;
        }
        leaf inter-area-summary {
          status obsolete;
          description
            "Local RIB used as criteria for inter-area summaries";
          type empty;
        }
        leaf nssa-translation {
          status obsolete;
          description
            "Local RIB used as criteria for NSSA translation";
          type empty;
        }
      }
      container microloop {
        status obsolete;
        description
          "Traffic microloop control parameters";
        container avoidance {
          status obsolete;
          description
            "Traffic microloop avoidance parameters";
          presence "true";
          leaf disable {
            status obsolete;
            description
              "Microloop avoidance auto-enable prohibited";
            type empty;
          }
          leaf protected {
            status obsolete;
            description
              "Microloop avoidance for protected prefixes only";
            type empty;
          }
          leaf rib-update-delay {
            status obsolete;
            description
              "Delay before updating the RIB";
            type uint32 {
              range "1..600000";
            }
          }
        }
      }
      container mpls {
        status obsolete;
        description
          "Configure MPLS routing protocol parameters";
        container ldp {
          status obsolete;
          description
            "routing protocol commands for MPLS LDP";
          container autoconfig {
            status obsolete;
            description
              "Configure LDP automatic configuration";
            presence "Configure LDP automatic configuration";
            leaf area {
              status obsolete;
              description
                "Configure an OSPF area to run MPLS LDP";
              type ios-types:ospf-area-type;
            }
          }
          container sync {
            status obsolete;
            description
              "Configure LDP-IGP Synchronization";
            presence "Configure LDP-IGP Synchronization";
          }
        }
        container traffic-eng {
          status obsolete;
          description
            "routing protocol commands for MPLS Traffic Engineering";
          leaf multicast-intact {
            status obsolete;
            description
              "MPLS TE and PIM interaction";
            type empty;
          }
          list area {
            status obsolete;
            description
              "configure an ospf area to run MPLS Traffic Engineering";
            key "id";
            leaf id {
              status obsolete;
              description
                "OSPF area ID";
              type ios-types:ospf-area-type;
            }
          }
          container autoroute-exclude {
            status obsolete;
            description
              "MPLS TE autoroute exclude";
            leaf prefix-list {
              status obsolete;
              description
                "Filter prefixes";
              type string;
            }
          }
          list interface {
            status obsolete;
            description
              "MPLS TE interface configuration for this OSPF process";
            key "name-id";
            leaf name-id {
              status obsolete;
              description
                "Interface name and ID";
              type string;
            }
            leaf area {
              status obsolete;
              description
                "Advertise MPLS TE information for this interface into area";
              type uint32;
            }
          }
          list mesh-group {
            status obsolete;
            description
              "Traffic Engineering Mesh-Group advertisement";
            key "id area";
            leaf id {
              status obsolete;
              description
                "Mesh Group ID: <0..4294967295>";
              type uint32;
            }
            leaf area {
              status obsolete;
              description
                "configure flooding scope as area";
              type ios-types:ospf-area-type;
            }
            leaf interface {
              status obsolete;
              description
                "Interface name and ID";
              type string;
            }
          }
          container router-id {
            status obsolete;
            description
              "Traffic Engineering stable IP address for system";
            uses ios-ifc:interface-grouping;
          }
        }
      }
      list neighbor {
        status obsolete;
        description
          "Specify a neighbor router";
        key "ip";
        leaf ip {
          status obsolete;
          type inet:ipv4-address;
        }
        leaf cost {
          status obsolete;
          description
            "OSPF cost for point-to-multipoint neighbor";
          type uint32 {
            range "1 .. 65535";
          }
        }
        container database-filter {
          status obsolete;
          description
            "Filter OSPF LSA during synchronization and flooding for point-to-multipoint neighbor";
          container all {
            status obsolete;
            description
              "Filter all LSA";
            leaf out {
              status obsolete;
              description
                "Outgoing LSA";
              type empty;
            }
          }
        }
        leaf poll-interval {
          status obsolete;
          description
            "OSPF dead-router polling interval";
          type uint32 {
            range "0 .. 65535";
          }
        }
        leaf priority {
          status obsolete;
          description
            "OSPF priority of non-broadcast neighbor";
          type uint32 {
            range "0 .. 255";
          }
        }
      }
      list network {
        status obsolete;
        description
          "Enable routing on an IP network";
        key "ip mask";
        leaf ip {
          status obsolete;
          type inet:ipv4-address;
        }
        leaf mask {
          status obsolete;
          type inet:ipv4-address;
        }
        leaf area {
          status obsolete;
          description
            "Set the OSPF area ID";
          type ios-types:ospf-area-type;
        }
      }
      container nsf {
        status obsolete;
        description
          "Non-stop forwarding";
        presence "true";
        container cisco {
          status obsolete;
          description
            "Cisco Non-stop forwarding";
          presence "true";
          container enforce {
            status obsolete;
            description
              "Cancel NSF restart when non-NSF-aware neighbors detected";
            leaf global {
              status obsolete;
              description
                "For the whole OSPF process";
              type empty;
            }
          }
          container helper {
            status obsolete;
            description
              "helper support";
            presence "helper support";
            leaf disable {
              status obsolete;
              description
                "disable helper support";
              type empty;
            }
          }
        }
        container ietf {
          status obsolete;
          description
            "IETF graceful restart";
          presence "true";
          container helper {
            status obsolete;
            description
              "helper support";
            presence "helper support";
            leaf disable {
              status obsolete;
              description
                "disable helper support";
              type empty;
            }
            leaf strict-lsa-checking {
              status obsolete;
              description
                "enable helper strict LSA checking";
              type empty;
            }
          }
          leaf restart-interval {
            status obsolete;
            description
              "Graceful restart interval";
            type uint16 {
              range "1..1800";
            }
          }
        }
      }
      container prefix-priority {
        status obsolete;
        description
          "OSPF prefix priority";
        leaf high {
          status obsolete;
          description
            "High prefix priority";
          type empty;
        }
        leaf route-map {
          status obsolete;
          description
            "Prefix priority selection by route-map";
          type string;
        }
      }
      leaf prefix-suppression {
        status obsolete;
        description
          "OSPF prefix suppression";
        type empty;
      }
      leaf priority {
        status obsolete;
        description
          "OSPF topology priority";
        type uint8 {
          range "0..127";
        }
      }
      container process-min-time {
        status obsolete;
        description
          "Percentage of quantum to be used before releasing CPU";
        leaf percent {
          status obsolete;
          description
            "percent";
          type uint32 {
            range "1 .. 100";
          }
        }
      }
      leaf shutdown {
        status obsolete;
        description
          "Shutdown the OSPF protocol under the current instance";
        type boolean;
      }
      uses router-snmp-grouping;
      list summary-address {
        status obsolete;
        description
          "Configure IP address summaries";
        key "ip wildcard";
        leaf ip {
          status obsolete;
          type inet:ipv4-address;
        }
        leaf wildcard {
          status obsolete;
          type inet:ipv4-address;
        }
        choice tag-no-advertise-choice {
          status obsolete;
          leaf nssa-only {
            status obsolete;
            description
              "Limit summary to NSSA areas";
            type empty;
          }
          leaf tag {
            status obsolete;
            description
              "Set tag";
            type uint32 {
              range "0 .. 4294967295";
            }
          }
          leaf not-advertise {
            status obsolete;
            description
              "Do not advertise when translating OSPF type-7 LSA";
            type empty;
          }
        }
      }
      uses router-table-map-grouping;
    }
  }
}
