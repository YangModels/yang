module Cisco-IOS-XE-call-home {
  namespace "http://cisco.com/ns/yang/Cisco-IOS-XE-call-home";
  prefix ios-ch;

  import cisco-semver {
    prefix cisco-semver;
  }
  import Cisco-IOS-XE-native {
    prefix ios;
  }
  import Cisco-IOS-XE-types {
    prefix ios-types;
  }
  import Cisco-IOS-XE-interface-common {
    prefix ios-ifc;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Call Home Yang Model.
     Copyright (c) 2016, 2018-2019 by Cisco Systems, Inc.
     All rights reserved.";

  revision 2019-07-01 {
    description
      "- Establish semantic version baseline
       - Add contract-id, customer-id, mail-server, phone-number,
         rate-limit, site-id, street-address
       - Add support for reporting smart-call-home-data and smart-licensing-data
       - Add support for data-privacy";
    cisco-semver:module-version "1.0.0";
  }
  revision 2018-10-11 {
    description
      "add anonymous-reporting-only and server-identity-check";
  }
  revision 2017-02-07 {
    description
      "Initial revision";
  }

  typedef ipv4-address-with-auth {
    description
      "It consists of SMTP authentication parameters and ipv4-address";
    type string {
      length "1..64";
      pattern "(([^@]*)?@)?((25[0-5]|2[0-4][0-9]|[01]?[0-9]?[0-9])\\.){3}(25[0-5]|2[0-4][0-9]|[01]?[0-9]?[0-9])(%[\\p{N}\\p{L}]+)?";
    }
  }

  typedef ipv6-address-with-auth {
    description
      "It consists of SMTP authentication parameters and ipv6-address";
    type string {
      length "1..64";
      pattern "(([^@]*)?@)?((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(%[\\p{N}\\p{L}]+)?";
      pattern "(([^@]*)?@)?(([^:]+:){6}(([^:]+:[^:]+)|(.*\\..*)))|((([^:]+:)*[^:]+)?::(([^:]+:)*[^:]+)?)(%.+)?";
    }
  }

  typedef host-with-auth {
    description
      "It consists of SMTP authentication parameters and hostname.";
    type string {
      length "1..64";
      pattern "(([^@]*)?@)?(([a-zA-Z0-9]([a-zA-Z0-9-]){0,61})?[a-zA-Z0-9]\\.)*([a-zA-Z0-9]([a-zA-Z0-9-]){0,61})?[a-zA-Z0-9]\\.?";
    }
  }

  grouping call-home-profile-periodic-grouping {
    container periodic {
      choice periodic-choice {
        description
          "Periodic call-home message";
        container daily {
          description
            "Daily call-home message";
          leaf begin-time {
            description
              "Begin time";
            type ios-types:hhmm-type;
          }
        }
        container monthly {
          description
            "Monthly call-home message";
          leaf date {
            description
              "Day of month";
            type uint8 {
              range "1..31";
            }
          }
          leaf begin-time {
            description
              "Begin time";
            type ios-types:hhmm-type;
          }
        }
        container weekly {
          description
            "Weekly call-home message";
          leaf day {
            description
              "Day of the week";
            type ios-types:weekday-type;
          }
          leaf begin-time {
            description
              "Begin time";
            type ios-types:hhmm-type;
          }
        }
      }
    }
  }

  grouping cfg-call-home-profile-grouping {
    leaf active {
      description
        "Activate the current profile";
      type boolean;
    }
    leaf anonymous-reporting-only {
      description
        "Enable call-home anonymous reporting only";
      type empty;
    }
    container reporting {
      description
        "Choose what data to report";
      leaf smart-call-home-data {
        description
          "Report Smart Call Home data";
        type boolean;
        default "true";
      }
      leaf tac-sl-data {
        description
          "Report Smart Licensing data for TAC profile";
        when "translate(current()/../../profile-name,\"CISOTA\",\"cisota\") = \"ciscotac-1\"";
        type boolean;
        default "true";
      }
      leaf user-sl-data {
        description
          "Report Smart Licensing data for user defined profile";
        when "translate(current()/../../profile-name,\"CISOTA\",\"cisota\") != \"ciscotac-1\"";
        type boolean;
        default "false";
      }
    }
    container destination {
      description
        "Message destination related configuration";
      leaf transport-method {
        description
          "To specify transport method for this profile";
        type enumeration {
          enum "http";
          enum "email";
        }
      }
      container address {
        description
          "To add destination address to this profile";
        leaf email {
          description
            "Use email address";
          type string;
        }
        leaf http {
          description
            "To add http address to this profile";
          type string;
        }
      }
    }
    container subscribe-to-alert-group {
      description
        "Subscribe to alert-group";
      container diagnostic {
        description
          "diagnostic info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container environment {
        description
          "environmental info";
        presence "true";
        leaf severity {
          description
            "Severity";
          type enumeration {
            enum "catastrophic";
            enum "critical";
            enum "debugging";
            enum "disaster";
            enum "fatal";
            enum "major";
            enum "minor";
            enum "normal";
            enum "notification";
            enum "warning";
          }
        }
      }
      container inventory {
        description
          "inventory info";
        presence "true";
        uses call-home-profile-periodic-grouping;
      }
      container syslog {
        description
          "syslog info";
        presence "true";
        list severity {
          description
            "severity";
          key "value";
          leaf value {
            type enumeration {
              enum "catastrophic";
              enum "critical";
              enum "debugging";
              enum "disaster";
              enum "fatal";
              enum "major";
              enum "minor";
              enum "normal";
              enum "notification";
              enum "warning";
            }
          }
          leaf pattern {
            description
              "Syslog message pattern";
            type string;
          }
        }
      }
      container configuration {
        description
          "configuration info";
        presence "true";
        uses call-home-profile-periodic-grouping;
      }
    }
  }

  grouping config-call-home-grouping {
    leaf contact-email-addr {
      description
        "Use email address";
      type string;
    }
    leaf contract-id {
      description
        "Contract identification for Cisco Smart Call Home.
         It cannot contain quote or special characters or only spaces.";
      type string {
        length "1..64";
        pattern "[^\"]*[^ \"]+[^\"]*";
        pattern "[ -~]+";
      }
    }
    leaf customer-id {
      description
        "customer identification for Cisco Smart Call Home.
         It cannot contain quote or special characters or only spaces.";
      type string {
        length "1..64";
        pattern "[^\"]*[^ \"]+[^\"]*";
        pattern "[ -~]+";
      }
    }
    container mail-server {
      description
        "call-home mail server";
      list server {
        description
          "used as a structure to contain other data";
        max-elements "5";
        key "server-name";
        leaf server-name {
          description
            "the server-name has the following format
             
               user:password@host
               host
             
             the user and password is used for SMTP authentication.
             They can be any valid printable ascii code except '@'.
             They also can be empty -- depending on mail servers.
             
             host is the hostname or ip address. hostname consists of labels.
             Each label: 
               contains letters, digits, hyphen; cannot start/end with hyphen;
               separated by dot; Refer to RFC 1123, RFC 1034 for detail.";
          type union {
            type ipv4-address-with-auth;
            type ipv6-address-with-auth;
            type host-with-auth;
          }
        }
        leaf priority {
          description
            "Mail server priority order";
          mandatory true;
          type uint8 {
            range "1..100";
          }
        }
      }
    }
    leaf phone-number {
      description
        "Phone number of the contact person. The phone number must 
         start with '+', and only space, - and numbers are allowed. 
         Total length is between 12 to 17 characters.";
      type string {
        length "12..17";
        pattern "\\+[0123456789 -]*";
      }
    }
    leaf rate-limit {
      description
        "call-home message rate-limit threshold per minute";
      type uint8 {
        range "1..60";
      }
      default "20";
    }
    leaf site-id {
      description
        "Site identification for Cisco Smart Call Home.
         It cannot contain quote or special characters or only spaces.";
      type string {
        length "1..200";
        pattern "[^\"]*[^ \"]+[^\"]*";
        pattern "[ -~]+";
      }
    }
    leaf street-address {
      description
        "Customer's address for equipment shipments:
           street address, city, state, and zip code.
         It cannot contain quote or special characters or only spaces.";
      type string {
        length "1..200";
        pattern "[^\"]*[^ \"]+[^\"]*";
        pattern "[ -~]+";
      }
    }
    container source-interface {
      description
        "Source interface name to send call-home messages using email";
      uses ios-ifc:interface-grouping;
    }
    container data-privacy {
      description
        "Set call-home data-privacy";
      leaf hostname {
        description
          "Level hostname";
        type empty;
      }
      leaf level {
        description
          "Set call-home data-privacy level";
        type enumeration {
          enum "high";
          enum "normal";
        }
        default "normal";
      }
    }
    container http {
      description
        "Set parameters for http transport method";
      container secure {
        description
          "Specify secure settings for http transport method";
        leaf server-identity-check {
          description
            "check server identity";
          type boolean;
          default "true";
        }
      }
    }
    container http-proxy {
      description
        "Specify proxy server for http request";
      list proxy-servers {
        key "proxy-server";
        leaf proxy-server {
          description
            "Http proxy server";
          type string;
        }
        leaf port {
          description
            "http proxy server port number";
          type uint16 {
            range "1..65535";
          }
        }
      }
    }
    list profile {
      description
        "Enter call-home profile configuration mode";
      key "profile-name";
      leaf profile-name {
        type string;
      }
      uses cfg-call-home-profile-grouping;
    }
  }

  augment "/ios:native/ios:call-home" {
    uses config-call-home-grouping;
  }
}
