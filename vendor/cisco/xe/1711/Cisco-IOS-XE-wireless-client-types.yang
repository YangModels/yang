module Cisco-IOS-XE-wireless-client-types {
  yang-version 1;
  namespace "http://cisco.com/ns/yang/Cisco-IOS-XE-wireless-client-types";
  prefix wireless-client-types;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless client data types.
     Copyright (c) 2016-2019 by Cisco Systems, Inc.
     All rights reserved.";

  revision 2019-05-01 {
    description
      "- Added enum value SAE for authentication algorithm.
       - Added semantic version";
    reference "4.1.0";
    cisco-semver:module-version "4.1.0";
  }
  revision 2018-12-17 {
    description
      "- Insertion of an enumeration for wired guest
       - Cleaned up spelling errors in descriptions
       - Removed explicit MAX from CO state enum";
    reference "4.0.0";
    cisco-semver:module-version "4.0.0";
  }
  revision 2018-08-08 {
    description
      "- Add 11ax client physical type enumeration
       - Add WPA3 support";
    reference "3.1.0";
    cisco-semver:module-version "3.1.0";
  }
  revision 2018-03-22 {
    description
      "Insertion of an enumeration";
    reference "3.0.0";
    cisco-semver:module-version "3.0.0";
  }
  revision 2018-01-24 {
    description
      "The first generally available version";
    reference "2.0.0";
    cisco-semver:module-version "2.0.0";
  }
  revision 2017-05-05 {
    description
      "Initial revision";
    reference "1.0.0";
    cisco-semver:module-version "1.0.0";
  }

  typedef client-co-state {
    type enumeration {
      enum "client-status-idle" {
        value 0;
        description
          "Represents the client in idle state";
      }
      enum "client-status-associating" {
        value 1;
        description
          "Used to indicate that the client is trying to associate";
      }
      enum "client-status-associated" {
        value 2;
        description
          "Used to indicate that the client has associated to the Access point";
      }
      enum "client-status-authenticating" {
        value 3;
        description
          "Used to indicate that the client is in the the process of authenticating";
      }
      enum "client-status-authenticated" {
        value 4;
        description
          "Used to indicate that the client has been Authenticated";
      }
      enum "client-status-mobility-discovery" {
        value 5;
        description
          "Used to indicate that the client is in mobility discovery state";
      }
      enum "client-status-mobility-complete" {
        value 6;
        description
          "Used to indicate that the client is in mobility complete state";
      }
      enum "client-status-ip-learning" {
        value 7;
        description
          "Used to indicate that the client is in the state of learning the IP";
      }
      enum "client-status-ip-learn-complete" {
        value 8;
        description
          "Used to indicate that the client has completed the IP learn process";
      }
      enum "client-status-webauth-required" {
        value 9;
        description
          "Used to indicate that the client web authentication is pending";
      }
      enum "client-status-static-ip-anchor-discovery" {
        value 10;
        description
          "Used to indicate that the client is in static ip anchor discovery state";
      }
      enum "client-status-run" {
        value 11;
        description
          "Used to indicate that the client has moved to run state";
      }
      enum "client-status-delete-in-progress" {
        value 12;
        description
          "Used to indicate that the client delete is in progress";
      }
      enum "client-status-deleted" {
        value 13;
        description
          "Used to indicate that the client has been deleted";
      }
    }
    description
      "represents the client orchestrator state";
  }

  typedef ms-radio-type {
    type enumeration {
      enum "dot11-radio-type-none" {
        value 0;
        description
          "Used to indicate that the radio is not of type BG or A";
      }
      enum "dot11-radio-type-bg" {
        value 1;
        description
          "Used to indicate that the radio is of type BG";
      }
      enum "dot11-radio-type-a" {
        value 2;
        description
          "Used to indicate that the radio is of type A";
      }
    }
    description
      "Used to indicate whether the radio type is BG or A";
  }

  typedef ms-phy-radio-type {
    type enumeration {
      enum "client-unknown-prot" {
        value 0;
        description
          "The client protocol is unknown";
      }
      enum "client-dot11b" {
        value 1;
        description
          "The client is using 802.11b standard to connect to the access point (AP)";
      }
      enum "client-dot11g" {
        value 2;
        description
          "The client is using 802.11g standard to connect to the access point (AP)";
      }
      enum "client-dot11a" {
        value 3;
        description
          "The client is using 802.11a standard to connect to the access point (AP)";
      }
      enum "client-dot11n-24-ghz-prot" {
        value 4;
        description
          "The client is using 802.11n standard with 2.4 GHz frequency to connect to the access point (AP)";
      }
      enum "client-dot11n-5-ghz-prot" {
        value 5;
        description
          "The client is using 802.11n standard with 5 GHz frequency to connect to the access point (AP)";
      }
      enum "client-dot11ac" {
        value 6;
        description
          "The client is using dot11ac standard to connect to the access point (AP).";
      }
      enum "client-phy-type-notappl" {
        value 7;
        description
          "Radio type is not applicable to WGB wired client";
      }
      enum "client-ethernet" {
        value 8;
        description
          "Radio type is not applicable to rlan client";
      }
      enum "client-dot11ax-5ghz-prot" {
        value 9;
        description
          "The client is using dot11ax standard on 5 GHz radio to connect to the access point (AP)";
      }
      enum "client-dot11ax-24ghz-prot" {
        value 10;
        description
          "The client is using dot11ax standard on 2.4 GHz radio to connect to the access point (AP)";
      }
      enum "client-802-3" {
        value 11;
        description
          "The client is a wired guest client, protocol 802.3";
      }
    }
    description
      "The 802.11 protocol type of the client";
  }

  typedef ms-type {
    type enumeration {
      enum "ms-type-local" {
        value 0;
        description
          "Mobile station type is local";
      }
      enum "ms-type-anchor" {
        value 1;
        description
          "Mobile station type is Anchor";
      }
      enum "ms-type-flex-central-auth" {
        value 2;
        description
          "Mobile station is centrally authenticated in flex mode";
      }
      enum "ms-type-flex-local-auth" {
        value 3;
        description
          "Mobile station is locally authenticated in flex mode";
      }
      enum "ms-type-guest" {
        value 4;
        description
          "Mobile station type is guest";
      }
    }
    description
      "Mobile station entry type";
  }

  typedef ms-client-type {
    type enumeration {
      enum "dot11-client-normal" {
        value 0;
        description
          "wireless client";
      }
      enum "dot11-client-wgb" {
        value 1;
        description
          "workgroup bridge";
      }
      enum "dot11-client-wired" {
        value 2;
        description
          "wired client";
      }
      enum "dot11-client-rlan" {
        value 3;
        description
          "rlan client";
      }
      enum "client-802-3-guest-lan" {
        value 4;
        description
          "Wired Guest client connected through 802.3 protocol";
      }
    }
    description
      "client type";
  }

  typedef dot11-eap-wpa-version {
    type enumeration {
      enum "dot1x-wpa-version" {
        value 0;
        description
          "The WPA version of the client is 802.1x";
      }
      enum "wpa1" {
        value 1;
        description
          "The WPA version of the client is WPA1";
      }
      enum "wpa2" {
        value 2;
        description
          "The WPA version of the client is WPA2";
      }
      enum "wpa-version-wpa2-v3" {
        value 3;
        description
          "The WPA version of the client is WPA wVFF";
      }
      enum "wpa-version-not-def" {
        value 4;
        description
          "The WPA version of the client is Not Defined";
      }
      enum "wpa-version-wpa3" {
        value 5;
        description
          "The WPA version of the client is WPA3";
      }
    }
    description
      "Enumeration for the WPA versions that can be used in a client connection";
  }

  typedef client-wep-policy-type {
    type enumeration {
      enum "client-policy-type-none" {
        value 0;
        description
          "The client's WEP State is None";
      }
      enum "client-policy-type-static-wep" {
        value 1;
        description
          "The client's WEP State is Static WEP";
      }
      enum "client-policy-type-dynamic-wep" {
        value 2;
        description
          "The client's WEP State is Dynamic WEP";
      }
    }
    description
      "This data type tells us about the WEP state of the client";
  }

  typedef dot11-state {
    type enumeration {
      enum "idle" {
        value 0;
        description
          "The current client state is Idle";
      }
      enum "associating" {
        value 1;
        description
          "The current client state is Associating";
      }
      enum "associated" {
        value 2;
        description
          "The current client state is Associated";
      }
      enum "deleting" {
        value 3;
        description
          "The current client state is Deleting";
      }
      enum "deleted" {
        value 4;
        description
          "The current client state is Deleted";
      }
    }
    description
      "Enumeration for the client current status";
  }

  typedef auth-algo {
    type enumeration {
      enum "open-system" {
        value 0;
        description
          "The client joined through Open Authentication";
      }
      enum "shared-key" {
        value 1;
        description
          "The client joined through Shared WEP Authentication";
      }
      enum "open-and-eap" {
        value 128;
        description
          "The client joined through Open and EAP Authentication";
      }
      enum "auth-algo-none" {
        value 129;
        description
          "The authentication algorithm is NA";
      }
      enum "simultaneous-authentication-of-equals" {
        value 130;
        description
          "The client joined through Simultaneous Authentication Of Equals";
      }
    }
    description
      "Enumeration for the authentication algorithms used by the client";
  }

  typedef dot11i-cipher-suite {
    type enumeration {
      enum "rsn-cipher-suite-use-group" {
        value 0;
        description
          "The Cipher suite used by the client is the same as group cipher";
      }
      enum "wep-40-bits" {
        value 1;
        description
          "The Cipher suite used by the client is WEP (40 bits)";
      }
      enum "tkip-mic" {
        value 2;
        description
          "The Cipher Suite used by the client is TKIP";
      }
      enum "reserved" {
        value 3;
        description
          "The Cipher suite used by the client is Reserved";
      }
      enum "ccmp-aes" {
        value 4;
        description
          "The Cipher suite used by the client is CCMP";
      }
      enum "wep-104-bits" {
        value 5;
        description
          "The Cipher suite used by the client is WEP (104 bits)";
      }
      enum "bip" {
        value 6;
        description
          "The Cipher suite used by the client is BIP";
      }
      enum "traffic-not-allowed" {
        value 7;
        description
          "Traffic not allowed on cipher suite used by client";
      }
      enum "gcmp128" {
        value 8;
        description
          "The Cipher suite used by the client is GCMP128";
      }
      enum "gcmp256" {
        value 9;
        description
          "The Cipher suite used by the client is GCMP256";
      }
      enum "ccmp256" {
        value 10;
        description
          "The Cipher suite used by the client is CCMP256";
      }
      enum "wep-128-bits" {
        value 127;
        description
          "The Cipher suite used by the client is WEP (128 bits)";
      }
      enum "rsn-cipher-suite-invalid" {
        value 255;
        description
          "The Cipher suite used by the client is Invalid";
      }
    }
    description
      "Enumeration for the 802.11i encryption protocols that can be employed by the client";
  }

  typedef reason-code {
    type enumeration {
      enum "reason-none" {
        value 0;
        description
          "The reason for disassocdeauth is None";
      }
      enum "reason-unspecified" {
        value 1;
        description
          "The reason for disassocdeauth is Unspecified";
      }
      enum "reason-prev-auth-not-valid" {
        value 2;
        description
          "The reason for disassocdeauth was invalid previous authentication";
      }
      enum "reason-deauth-leaving" {
        value 3;
        description
          "The reason for disassocdeauth was a deauthentication received";
      }
      enum "reason-disassoc-due-to-inactivity" {
        value 4;
        description
          "The reason for disassocdeauth was disassociation due to inactivity";
      }
      enum "reason-disassoc-ap-busy" {
        value 5;
        description
          "The reason for disassocdeauth was disassociation because AP is busy";
      }
      enum "reason-class2-frame-from-nonauth-sta" {
        value 6;
        description
          "The reason for disassocdeauth was a Class 2 Frame received from Non Authenticated AP";
      }
      enum "reason-class2-frame-from-nonassoc-sta" {
        value 7;
        description
          "The reason for disassocdeauth was a Class 2 Frame received from Non Associated AP";
      }
      enum "reason-disassoc-sta-has-left" {
        value 8;
        description
          "The reason for disassocdeauth was the AP left the controller";
      }
      enum "reason-sta-req-assoc-without-auth" {
        value 9;
        description
          "The reason for disassocdeauth was the AP requested association without authentication";
      }
      enum "reason-invalid-ie" {
        value 13;
        description
          "The reason for disassocdeauth was invalid Information Element";
      }
      enum "reason-micheal-failure" {
        value 14;
        description
          "The reason for disassocdeauth was a Micheal failure";
      }
      enum "reason-4-way-handshake-timeout" {
        value 15;
        description
          "The reason for disassocdeauth was a 4 way Handshake Timeout";
      }
      enum "reason-group-key-update-timeout" {
        value 16;
        description
          "The reason for disassocdeauth was a Group key update Timeout";
      }
      enum "reason-invalid-rsn-ie" {
        value 17;
        description
          "The reason for disassocdeauth was invalid RSN Information Element";
      }
      enum "reason-group-cipher-invalid" {
        value 18;
        description
          "The reason for disassocdeauth was invalid Group cipher";
      }
      enum "reason-unicast-cipher-invalid" {
        value 19;
        description
          "The reason for disassocdeauth was invalid Unicast Cipher";
      }
      enum "reason-akmp-invalid" {
        value 20;
        description
          "The reason for disassocdeauth was invalid AKMP";
      }
      enum "reason-unsupported-rsn-version" {
        value 21;
        description
          "The reason for disassocdeauth was unsupported RSN version";
      }
      enum "reason-invalid-rsn-ie-capabilities" {
        value 22;
        description
          "The reason for disassocdeauth was invalid RSN information element capabilities";
      }
      enum "reason-8021-x-auth-failed" {
        value 23;
        description
          "The reason for disassocdeauth was a 802.1x authentication failure";
      }
      enum "reason-cipher-suite-rejected" {
        value 24;
        description
          "The reason for disassocdeauth was the Cipher suite was rejected";
      }
      enum "reason-unspec-qos-related-reason" {
        value 32;
        description
          "The reason for disassocdeauth was an unspecified QOS related failure";
      }
      enum "reason-insufficient-bandwidth" {
        value 33;
        description
          "The reason for disassocdeauth was insufficient bandwidth";
      }
      enum "reason-poor-channel-conditions" {
        value 34;
        description
          "The reason for disassocdeauth was the channel conditions were poor";
      }
      enum "reason-sta-violating-txop" {
        value 35;
        description
          "The reason for disassocdeauth was the AP violated TXOP (Transmission Opportunity)";
      }
      enum "reason-voice-sta-reanchoring" {
        value 36;
        description
          "The reason for disassocdeauth was voice AP reanchoring";
      }
      enum "reason-probing-sta-in-loc-calib" {
        value 37;
        description
          "The reason for disassocdeauth was a Probing AP in LOC Calibration";
      }
      enum "reason-guest-anchor-down" {
        value 98;
        description
          "The reason for disassocdeauth was Guest Anchor being down";
      }
      enum "reason-missing-reason-code" {
        value 99;
        description
          "The reason for disassocdeauth is NA";
      }
      enum "reason-client-access-to-quarantine" {
        value 100;
        description
          "The reason for disassocdeauth was the client accessed Quarantine";
      }
      enum "reason-max-associated-clients-reached" {
        value 101;
        description
          "The reason for disassocdeauth was exceeding the limit of maximum associated clients";
      }
      enum "reason-max-clients-reached-on-ap" {
        value 102;
        description
          "The reason for disassocdeauth was exceeding the limit of maximum clients on the AP";
      }
      enum "reason-webauth-reqd-timeout" {
        value 103;
        description
          "The reason for disassocdeauth was a Webauth required timeout";
      }
      enum "reason-webauth-async-timeout" {
        value 104;
        description
          "The reason for disassocdeauth was a Webauth asynchronous timeout";
      }
      enum "reason-max-clients-reached-on-ap-radio" {
        value 105;
        description
          "The reason for disassocdeauth was exceeding the limit of maximum clients on the AP radio";
      }
      enum "reason-max-clients-reached-on-ap-wlan" {
        value 106;
        description
          "The reason for disassocdeauth was exceeding the limit of maximum clients on the AP WLAN";
      }
      enum "reason-max-clients-reached-on-ap-radio-wlan" {
        value 107;
        description
          "The reason for disassocdeauth was exceeding the limit of maximum clients on the AP Radio WLAN";
      }
      enum "reason-sta-no-ip" {
        value 108;
        description
          "The reason for disassocdeauth was that the AP had no IP";
      }
      enum "reason-ccx-qos-unspecified-failure" {
        value 200;
        description
          "The reason for disassocdeauth was a CCX QOS unspecified failure";
      }
      enum "reason-ccx-qos-policy" {
        value 201;
        description
          "The reason for disassocdeauth was CCX QOS policy failure";
      }
      enum "reason-ccx-insufficient-bandwidth" {
        value 202;
        description
          "The reason for disassocdeauth was CCX insufficient bandwidth";
      }
      enum "reason-ccx-invalid-qos-parameter" {
        value 203;
        description
          "The reason for disassocdeauth was CCX QOS parameters being invalid";
      }
      enum "reason-tunnel-eogre-roam-fail" {
        value 204;
        description
          "The reason for disassocdeauth was a Tunnel EOGRE roam failure";
      }
      enum "reason-sta-roam-without-auth" {
        value 205;
        description
          "The reason for disassocdeauth was the AP roamed without authentication";
      }
      enum "reason-authz-fail" {
        value 250;
        description
          "The reason for disassocdeauth was the authorization failed";
      }
      enum "reason-logout" {
        value 251;
        description
          "The reason for disassocdeauth was the user has logged out";
      }
      enum "reason-admin-reset" {
        value 252;
        description
          "The reason for disassocdeauth was an Admin reset";
      }
      enum "reason-anchor-close" {
        value 253;
        description
          "The reason for disassocdeauth was an Anchor close";
      }
      enum "reason-common-enum-end" {
        value 300;
        description
          "The reason for disassocdeauth was a Common Enumeration end";
      }
    }
    description
      "Enumeration for the Reason Codes for disassociation deauthentication as defined by 802.11 standards";
  }

  typedef ip-binding-learn-type {
    type enumeration {
      enum "ip-learn-type-unknown" {
        value 0;
        description
          "The method used to learn the IP Address is unknown";
      }
      enum "ip-learn-type-dhcp" {
        value 1;
        description
          "The method used to learn the IP Address is DHCP";
      }
      enum "ip-learn-type-arp" {
        value 2;
        description
          "The method used to learn the IP Address is ARP";
      }
      enum "ip-learn-type-ip-snooping" {
        value 3;
        description
          "The method used to learn the IP Address is IP Snooping";
      }
      enum "ip-learn-type-roaming" {
        value 4;
        description
          "The method used to learn the IP Address is Roaming";
      }
      enum "ip-learn-type-ip-theft" {
        value 5;
        description
          "The method used to learn the IP Address is IP Theft";
      }
      enum "ip-learn-type-static" {
        value 6;
        description
          "The method used to learn the IP Address is Static";
      }
      enum "ipv6-learn-type-unknown" {
        value 7;
        description
          "The method used to learn the IPv6 Address is Unknown";
      }
      enum "ipv6-learn-type-ndp" {
        value 8;
        description
          "The method used to learn the IPv6 Address is NDP";
      }
      enum "ipv6-learn-type-dhcp" {
        value 9;
        description
          "The method used to learn the IPv6 Address is DHCP";
      }
      enum "ipv6-learn-type-packet" {
        value 10;
        description
          "The method used to learn the IPv6 Address is Packet";
      }
      enum "ipv6-learn-type-local" {
        value 11;
        description
          "The method used to learn the IPv6 Address is Local";
      }
      enum "ipv6-learn-type-static" {
        value 12;
        description
          "The method used to learn the IPv6 Address is Static";
      }
    }
    description
      "This data type enumerates the various methods used for learning the IP of the client";
  }
}
