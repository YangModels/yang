module Cisco-IOS-XE-breakout-port-oper {
  yang-version 1;
  namespace "http://cisco.com/ns/yang/Cisco-IOS-XE-breakout-port-oper";
  prefix bc-port-ios-xe-oper;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring breakout ports in a Network Element.
     Copyright (c) 2018-2019 by Cisco Systems, Inc.
     All rights reserved.";

  revision 2019-05-01 {
    description
      "Added semantic version";
    reference "1.2.0";
    cisco-semver:module-version "1.2.0";
  }
  revision 2018-10-29 {
    description
      "Cleaned up spelling errors in descriptions.";
    reference "1.1.0";
    cisco-semver:module-version "1.1.0";
  }
  revision 2018-01-02 {
    description
      "Initial revision";
    reference "1.0.0";
    cisco-semver:module-version "1.0.0";
  }

  typedef bc-channel-speed {
    type enumeration {
      enum "10gb" {
        value 0;
      }
      enum "unknown" {
        value 1;
      }
    }
    description
      "Speed of each channel";
  }

  grouping port-breakout {
    description
      "List of breakout ports, keyed by name";
    leaf name {
      type string;
      description
        "Name of the breakout port";
    }
    leaf number {
      type int16;
      description
        "Number of channels to 'breakout' on a port capable of channelization";
    }
    leaf speed {
      type bc-port-ios-xe-oper:bc-channel-speed;
      description
        "Channel speed on each channel";
    }
  }

  container breakout-port-oper-data {
    config false;
    description
      "Information about breakout ports";
    list port-breakout {
      key "name";
      description
        "List of breakout ports, keyed by name";
      uses bc-port-ios-xe-oper:port-breakout;
    }
  }
}
