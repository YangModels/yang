module Cisco-IOS-XE-wireless-flex-cfg {
  yang-version 1;
  namespace "http://cisco.com/ns/yang/Cisco-IOS-XE-wireless-flex-cfg";
  prefix wireless-flex-cfg;

  import Cisco-IOS-XE-wireless-enum-types {
    prefix wireless-enum-types;
  }
  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing flex configurations
     Copyright (c) 2016-2019 by Cisco Systems, Inc.
     All rights reserved.";

  revision 2019-11-01 {
    description
      "- Added Radius server group name for accounting
       - Added umbrella-profile under flex profile
       - Marked VLAN-ACLs obsolete";
    reference "6.0.0";
    cisco-semver:module-version "6.0.0";
  }
  revision 2019-05-01 {
    description
      "Added semantic version";
    reference "5.1.0";
    cisco-semver:module-version "5.1.0";
  }
  revision 2019-02-12 {
    description
      "Removed Unsupported multicast overridden-interface from flex profile";
    reference "5.0.0";
    cisco-semver:module-version "5.0.0";
  }
  revision 2019-02-11 {
    description
      "- Removed unused RLAN related leaves
       - Changed range constraint and default value of native-vlan-id
       - Restrict password type options available for local user under FLEX profile
       - Semantical and default value cleanup and
         moved RLAN configuration related entries to new config model
       - Change type of boolean leafs of security parameters to empty
       - Leaf rename: is-punt to is-cwa.";
    reference "4.0.0";
    cisco-semver:module-version "4.0.0";
  }
  revision 2018-06-05 {
    description
      "- Add constraints
       - Password encryption type configuration";
    reference "3.0.0";
    cisco-semver:module-version "3.0.0";
  }
  revision 2018-03-08 {
    description
      "Add remote LAN configuration";
    reference "2.1.0";
    cisco-semver:module-version "2.1.0";
  }
  revision 2018-01-24 {
    description
      "The first generally available version";
    reference "2.0.0";
    cisco-semver:module-version "2.0.0";
  }
  revision 2017-05-05 {
    description
      "Initial revision";
    reference "1.0.0";
    cisco-semver:module-version "1.0.0";
  }

  grouping vlan-acl-list {
    description
      "Configuration of vlan-acl mappings for REAPs";
    leaf vlan-id {
      type uint32;
      description
        "VLAN ID to be mapped to the ACL for the REAP group";
    }
    leaf ingress-acl-name {
      type string;
      default "";
      description
        "Name of the ingress Access Control List for the vlan-acl mapping";
    }
    leaf egress-acl-name {
      type string;
      default "";
      description
        "Name of the egress Access Control List for the vlan-acl mapping";
    }
  }

  grouping local-auth-user-list {
    description
      "Local authenticated user list";
    leaf user-name {
      type string;
      description
        "User name for this group, used for authenticating a client associated to an AP within the group";
    }
    leaf password {
      type string;
      default "";
      description
        "Password for this conceptual row.";
    }
    leaf password-type {
      type wireless-enum-types:crypt-type;
      must "((current() = 'clear') or (current() = 'aes'))" {
        error-message "Password type should be either clear text or AES encryption";
        error-app-tag "must-violation";
      }
      default "clear";
      description
        "Password encryption type for authentication by AP";
    }
  }

  grouping policy-acl-list {
    description
      "Configuration of webpolicy Access Control List(ACL) mappings for REAP groups";
    leaf acl-name {
      type string;
      description
        "Name of the webpolicy Access Control List(ACL) to be mapped to the REAP group";
    }
    leaf is-cwa {
      type boolean;
      default "false";
      description
        "Enable or Disable central webauth for this ACL.";
    }
    leaf urlfilterlist-name {
      type string;
      description
        "Mapping of IPv4/IPv6 ACL name to url filter list this ACL.";
    }
  }

  grouping if-name-vlan-id-list {
    description
      "VLAN Name- ACL mappings to be configured for the REAP";
    leaf interface-name {
      type string;
      description
        "VLAN name for the vlan-acl mapping.";
    }
    leaf vlan-id {
      type uint32 {
        range "1 .. 4096";
      }
      default "1";
      description
        "VLAN ID to be mapped to the ACL for the Access Point identified by VLAN name.";
    }
    leaf acl-name {
      type string;
      default "";
      description
        "Name of the Access Control List(ACL) for the vlan-acl mapping";
    }
  }

  grouping st-security-params {
    description
      "Flex policy security parameters";
    leaf is-peap {
      type empty;
      description
        "Enable or Disable Protected Extensible Authentication Protocol(PEAP)";
    }
    leaf is-leap {
      type empty;
      description
        "Enable or Disable Lightweight Extensible Authentication Protocol(LEAP)";
    }
    leaf is-eap {
      type empty;
      description
        "Enable or Disable Extensible Authentication Protocol(EAP)";
    }
    leaf is-tls {
      type empty;
      description
        "Enable or Disable Transport Layer Security(TLS)";
    }
  }

  grouping st-umbrella-profile-list {
    description
      "Configuration of umbrella profile under flex mode";
    leaf umbrella-name {
      type string;
      description
        "Umbrella profile name";
    }
  }

  grouping flex-policy-config {
    description
      "Encompasses the flex profile attributes";
    leaf policy-name {
      type string;
      description
        "Name of the flex profile";
    }
    leaf description {
      type string;
      description
        "Description for the flex profile";
    }
    leaf eap-fast-profile-name {
      type string;
      description
        "EAP fast profile used for local auth";
    }
    leaf radius-server-group-name {
      type string;
      description
        "Radius server group name for authentication";
    }
    leaf fallback-radio-shut {
      type boolean;
      default "false";
      description
        "Whether Fallback Radio Shut feature is enabled for the flexconnect Access Points connected to the Wireless LAN Controller";
    }
    leaf arp-caching {
      type boolean;
      default "true";
      description
        "Whether ARP cache feature is enabled for the flexconnect Access Points connected to the Wireless LAN Controller";
    }
    leaf cts-inline-tagging {
      type boolean;
      default "false";
      description
        "Whether CTS inline tagging feature is enabled for the flexconnect Access Points connected to the Wireless LAN Controller";
    }
    leaf cts-rolebased-enforce {
      type boolean;
      default "false";
      description
        "Whether CTS rolebased enforcement feature is enabled for flexconnect Access Points connected to the Wireless LAN Controller";
    }
    leaf cts-profile-name {
      type string;
      default "default-sxp-profile";
      description
        "CTS SXP profile name";
    }
    leaf join-min-latency {
      type boolean;
      default "false";
      description
        "REAP AP should join controller with smallest latency";
    }
    leaf radius-enable {
      type boolean;
      default "true";
      description
        "Enable or Disable RADIUS";
    }
    leaf vlan-enable {
      type boolean;
      default "true";
      description
        "Availability of Native VLAN configured on this REAP";
    }
    leaf is-home-ap-enable {
      type boolean;
      default "false";
      description
        "APs connected to this profile/group are used as Home APs";
    }
    leaf is-radio-backhaul {
      type boolean;
      default "false";
      description
        "Enable or Disable WLAN on backhaul radio";
    }
    leaf is-resilient-mode {
      type boolean;
      default "false";
      description
        "Enable or Disable Standalone mode support on a REAP AP.";
    }
    leaf efficient-ap-upgrade-enable {
      type boolean;
      default "true";
      description
        "Efficient AP image upgrade is enabled";
    }
    leaf http-proxy-ip {
      type inet:ip-address;
      default "0.0.0.0";
      description
        "HTTP proxy Ip address";
    }
    container security {
      description
        "Flex policy security parameters";
      uses wireless-flex-cfg:st-security-params;
    }
    leaf native-vlan-id {
      type uint32 {
        range "1 .. 4094";
      }
      default "1";
      description
        "Native VLAN ID for the particular AP";
    }
    leaf slave-max-retry-count {
      type uint32;
      default "0";
      description
        "Maximum retries the slave has to undertake to start the download from the master in the HREAP group";
    }
    leaf http-proxy-port {
      type uint16 {
        range "0 .. 65535";
      }
      default "0";
      description
        "HTTP proxy port";
    }
    container vlan-acls {
      status obsolete;
      description
        "VLAN ACLs";
      list vlan-acl {
        key "vlan-id";
        description
          "List of VLAN ACLs";
        uses wireless-flex-cfg:vlan-acl-list;
      }
    }
    container policy-acls {
      description
        "Policy ACLs";
      list policy-acl {
        key "acl-name";
        description
          "List of Policy ACLs";
        uses wireless-flex-cfg:policy-acl-list;
      }
    }
    container local-auth-users {
      description
        "Local auth users";
      list local-auth-user {
        key "user-name";
        description
          "List of Local auth users";
        uses wireless-flex-cfg:local-auth-user-list;
      }
    }
    container if-name-vlan-ids {
      description
        "Interface name VLAN IDs";
      list if-name-vlan-id {
        key "interface-name";
        description
          "Interface name VLAN ID list";
        uses wireless-flex-cfg:if-name-vlan-id-list;
      }
    }
    leaf acct-radius-server-group-name {
      type string {
        length "1..32";
        pattern "[\\]A-Za-z0-9!\"#%&()*+,\\-./:;<=>^?@\\\\$_`{|}\\[']+";
      }
      description
        "Radius server group name for accounting";
    }
    leaf is-local-roaming-enable {
      type boolean;
      default "false";
      description
        "Enable or Disable distributed client data caching on AP for local roaming.";
    }
    container umbrella-profiles {
      description
        "Umbrella Profiles";
      list umbrella-profile {
        key "umbrella-name";
        description
          "List of umbrella profiles";
        uses wireless-flex-cfg:st-umbrella-profile-list;
      }
    }
  }

  container flex-cfg-data {
    description
      "Yang model for configuring site";
    container flex-policy-entries {
      description
        "Flex policy profile configuration";
      list flex-policy-entry {
        key "policy-name";
        description
          "Flex profile name mapped to the site tag";
        uses wireless-flex-cfg:flex-policy-config;
      }
    }
  }
}
