module cisco-xe-openconfig-openflow-deviation {
  namespace "http://openconfig.net/yang/cisco-xe-openconfig-openflow-deviation";
  prefix oc-of-devs;

  import openconfig-system {
    prefix oc-sys;
  }
  import openconfig-openflow {
    prefix oc-of;
  }
  import ietf-yang-types {
    prefix yang;
  }

  organization
    "Cisco Systems, Inc.";
  contact
    " Cisco Systems, Inc.
     Customer Service
     
     Postal: 170 W Tasman Drive
     San Jose, CA 95134
     
     Tel: +1 1800 553-NETS
     
     E-mail: cs-yang@cisco.com";
  description
    "This module defines deviation statements for openconfig-openflow module.";

  revision 2017-10-12 {
    description
      "Remove deviation for connected state leaf";
  }
  revision 2017-09-26 {
    description
      "Remove deviation for failure-mode";
  }
  revision 2017-08-03 {
    description
      "Add deviations to openconfig-openflow model";
  }

  deviation "/oc-sys:system/oc-of:openflow/oc-of:controllers/oc-of:controller/oc-of:connections/oc-of:connection/oc-of:state/oc-of:priority" {
    deviate not-supported;
    description
      "Connection priority not implemented in IOS-XE";
  }
  deviation "/oc-sys:system/oc-of:openflow/oc-of:agent/oc-of:config/oc-of:backoff-interval" {
    deviate not-supported;
    description
      "Agent backoff-interval leaf not supported";
  }
  deviation "/oc-sys:system/oc-of:openflow/oc-of:agent/oc-of:state/oc-of:backoff-interval" {
    deviate not-supported;
    description
      "Agent backoff-interval leaf not supported";
  }
}
