module Cisco-IOS-XE-controller {
  namespace "http://cisco.com/ns/yang/Cisco-IOS-XE-controller";
  prefix ios-ctrl;

  import cisco-semver {
    prefix cisco-semver;
  }
  import ietf-inet-types {
    prefix inet;
  }
  import Cisco-IOS-XE-native {
    prefix ios;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Controller Yang Model.
     Copyright (c) 2016-2019 by Cisco Systems, Inc.
     All rights reserved.";

  revision 2019-11-01 {
    description
      "
       - Added new framing config";
    cisco-semver:module-version "1.1.0";
  }
  revision 2019-07-01 {
    description
      "Establish semantic version baseline";
    cisco-semver:module-version "1.0.0";
  }
  revision 2018-11-07 {
    description
      "Cleanup spelling errors in description statements";
  }
  revision 2018-07-24 {
    description
      "Add dependency to data-profile on profile id";
  }
  revision 2018-05-19 {
    description
      "Add options under vdsl operating mode auto";
  }
  revision 2018-05-02 {
    description
      "Remove cli-full-command for profile id authentication";
  }
  revision 2018-04-19 {
    description
      "Add firmware filename CLI to VDSL controller";
  }
  revision 2018-04-18 {
    description
      "Make linecode specific to controller type, and add profile for controller Cellular";
  }
  revision 2018-04-02 {
    description
      "Add tailf:cli-remove-before-change for channel group timeslots";
  }
  revision 2018-03-28 {
    description
      "Add configuration for VDSL controller";
  }
  revision 2018-03-06 {
    description
      "Add model for VDSL controller";
  }
  revision 2018-02-21 {
    description
      "Add options for lte modem and lte event";
  }
  revision 2018-02-14 {
    description
      "Add lte sms to controller Cellular";
  }
  revision 2018-02-10 {
    description
      "Add lte dying gasp";
  }
  revision 2018-02-03 {
    description
      "Remove lower case t1/e1/t3 controller name";
  }
  revision 2017-12-16 {
    description
      "Add data model for Controller Cellular lte options";
  }
  revision 2017-12-15 {
    description
      "Support lte failovertimer/firmware auto-sim/radio off";
  }
  revision 2017-11-28 {
    description
      "Add description node for tx-ex controllers";
  }
  revision 2017-02-07 {
    description
      "Initial revision";
  }

  grouping sonet-grouping {
    leaf framing {
      description
        "SONET framing";
      type enumeration {
        enum "sonet";
        enum "sdh";
      }
    }
    leaf shutdown {
      type empty;
    }
    container clock {
      description
        "SONET clock";
      leaf source {
        description
          "SONET clock source";
        type enumeration {
          enum "internal";
          enum "line";
        }
      }
    }
    container aug {
      description
        "AUG";
      leaf mapping {
        type enumeration {
          enum "au-3";
          enum "au-4";
        }
      }
    }
    list au-3 {
      description
        "AU-3";
      key "number";
      leaf number {
        description
          "AU-3 number";
        type int8 {
          range "1..3";
        }
      }
      container overhead {
        description
          "overhead";
        leaf byte {
          type enumeration {
            enum "j1";
          }
        }
        leaf length {
          type uint8;
        }
      }
      container mode {
        description
          "mode";
        leaf mapping {
          type enumeration {
            enum "c-11";
            enum "c-12";
            enum "c-2";
          }
        }
      }
    }
    container au-4-atm {
      container au-4 {
        description
          "AU-4";
        leaf number {
          description
            "AU-4 number";
          type int8 {
            range "1..3";
          }
        }
        leaf atm {
          type empty;
        }
      }
    }
    list au-4 {
      description
        "AU-4";
      key "number tug-3";
      leaf number {
        description
          "AU-4 number";
        type int8 {
          range "1..3";
        }
      }
      leaf tug-3 {
        description
          "TUG-3";
        type int8 {
          range "1..3";
        }
      }
      leaf mode {
        description
          "mode";
        type enumeration {
          enum "c-11";
          enum "c-12";
          enum "c-2";
          enum "c-3";
          enum "c-4";
          enum "e3";
        }
      }
      leaf cem-group {
        description
          "CEM group";
        type int32;
      }
      choice framing-choice {
        case unframed-case {
          leaf unframed {
            description
              "Unframed";
            type empty;
          }
        }
        case framing-case {
          leaf framing {
            type enumeration {
              enum "unframed";
            }
          }
        }
      }
      container cem-group-timeslots {
        list tug-2 {
          description
            "TUG-2";
          key "number e1 cem-group";
          leaf number {
            description
              "TUG-2 number";
            type int8 {
              range "1..7";
            }
          }
          leaf e1 {
            description
              "E1";
            type int8 {
              range "1..3";
            }
          }
          leaf cem-group {
            description
              "CEM group";
            type int32;
          }
          leaf timeslots {
            description
              "Time slots";
            type string;
          }
        }
      }
      container channel-group-timeslots {
        list tug-2 {
          description
            "TUG-2";
          key "number e1 channel-group";
          leaf number {
            description
              "TUG-2 number";
            type int8 {
              range "1..7";
            }
          }
          leaf e1 {
            description
              "E1";
            type int8 {
              range "1..3";
            }
          }
          leaf channel-group {
            description
              "Channel group";
            type int32;
          }
          leaf timeslots {
            description
              "Time slots";
            type string;
          }
        }
      }
      container cem-group-unframed {
        list tug-2 {
          description
            "TUG-2";
          key "number e1 cem-group";
          leaf number {
            description
              "TUG-2 number";
            type int8 {
              range "1..7";
            }
          }
          leaf e1 {
            description
              "E1";
            type int8 {
              range "1..3";
            }
          }
          leaf cem-group {
            description
              "CEM group";
            type int32;
          }
          leaf unframed {
            description
              "Unframed";
            type empty;
          }
        }
      }
      container framing-unframed {
        list tug-2 {
          description
            "TUG-2";
          key "number e1";
          leaf number {
            description
              "TUG-2 number";
            type int8 {
              range "1..7";
            }
          }
          leaf e1 {
            description
              "E1";
            type int8 {
              range "1..3";
            }
          }
          leaf framing {
            type enumeration {
              enum "unframed";
            }
          }
        }
      }
      container cem-group-atm {
        list tug-2 {
          description
            "TUG-2";
          key "number e1";
          leaf number {
            description
              "TUG-2 number";
            type int8 {
              range "1..7";
            }
          }
          leaf e1 {
            description
              "E1";
            type int8 {
              range "1..3";
            }
          }
          leaf atm {
            type empty;
          }
        }
      }
      container ima-group {
        list tug-2 {
          description
            "TUG-2";
          key "number e1 ima-group";
          leaf number {
            description
              "TUG-2 number";
            type int8 {
              range "1..7";
            }
          }
          leaf e1 {
            description
              "E1";
            type int8 {
              range "1..3";
            }
          }
          leaf ima-group {
            description
              "IMA group";
            type int32;
          }
        }
      }
    }
    container aps {
      description
        "SONET APS";
      container group {
        description
          "SONET APS group";
        leaf group-number {
          type uint8;
        }
        leaf acr {
          description
            "ACR";
          type int8;
        }
      }
      leaf working {
        description
          "Working line";
        type int8;
      }
      container protect {
        description
          "Protect line";
        leaf number {
          type int8;
        }
        leaf ip-addr {
          type inet:ipv4-address;
        }
      }
      leaf hspw-icrm-grp {
        type uint8;
      }
      container interchassis {
        leaf group {
          type uint8;
        }
      }
    }
  }

  grouping threshold-grouping {
    leaf threshold {
      type int16 {
        range "-150..0";
      }
    }
  }

  grouping high-threshold-grouping {
    leaf threshold {
      type int8 {
        range "-20..0";
      }
    }
  }

  grouping mib-trap-grouping {
    leaf mib-trap {
      description
        "mibtrap";
      type empty;
    }
  }

  grouping ecio-option-grouping {
    leaf-list mib-trap {
      description
        "mibtrap";
      type enumeration {
        enum "1xrtt";
        enum "All-lte";
        enum "edge";
        enum "evdoRel0";
        enum "evdoRelA";
        enum "evdoRelB";
        enum "gprs";
        enum "umts/wcdma";
        enum "hsdpa";
        enum "hsupa";
        enum "hspa";
        enum "hspa-plus";
        enum "lte-tdd";
        enum "lte-fdd";
      }
    }
    uses threshold-grouping;
  }

  grouping mib-trap-lte-grouping {
    leaf-list mib-trap {
      description
        "mibtrap";
      type enumeration {
        enum "All-lte";
        enum "lte-tdd";
        enum "lte-fdd";
      }
    }
  }

  grouping threshold-mib-trap-lte-grouping {
    container abate {
      uses mib-trap-lte-grouping;
      uses threshold-grouping;
    }
    container onset {
      uses mib-trap-lte-grouping;
      uses threshold-grouping;
    }
  }

  grouping high-threshold-mib-trap-lte-grouping {
    container abate {
      uses mib-trap-lte-grouping;
      uses high-threshold-grouping;
    }
    container onset {
      uses mib-trap-lte-grouping;
      uses high-threshold-grouping;
    }
  }

  grouping config-controller-grouping {
    list controller-tx-ex-list {
      key "name number";
      leaf name {
        type enumeration {
          enum "T1";
          enum "E1";
          enum "T3";
        }
      }
      leaf number {
        type string;
      }
      leaf atm {
        description
          "Specify atm";
        type empty;
      }
      container framing-config {
        description
          "Specify the type of Framing";
        leaf tx-framing {
          when "../../name = 'T1' or ../../name = 'T3'";
          type enumeration {
            enum "esf";
            enum "sf";
          }
        }
        leaf e1-framing {
          when "../../name = 'E1'";
          type enumeration {
            enum "crc4";
            enum "no-crc4";
          }
        }
        leaf australia {
          when "../e1-framing";
          description
            "Australian Layer 1 homologation";
          type empty;
        }
      }
      leaf framing {
        status deprecated;
        type string;
      }
      container clock {
        container source {
          choice source-choice {
            container line {
              presence "true";
              leaf line-mode {
                type enumeration {
                  enum "primary";
                  enum "secondary";
                }
              }
            }
            leaf internal {
              type empty;
            }
            leaf loop-timed {
              type empty;
            }
            leaf network {
              description
                "Internal TDM Switch Source";
              type empty;
            }
          }
        }
      }
      leaf description {
        description
          "Controller specific description";
        type string {
          length "1..240";
        }
      }
      leaf linecode-t1 {
        when "../name = 'T1'";
        type enumeration {
          enum "ami";
          enum "b8zs";
        }
        default "b8zs";
      }
      leaf linecode-e1 {
        when "../name = 'E1'";
        type enumeration {
          enum "ami";
          enum "hdb3";
        }
        default "hdb3";
      }
      leaf linecode-t3 {
        when "../name = 'T3'";
        type enumeration {
          enum "b3zs";
        }
      }
      container cablelength {
        choice cablelength-choice {
          leaf long {
            type string;
          }
          leaf short {
            type string;
          }
        }
      }
      leaf line-termination {
        when "../name = 'E1'";
        description
          "Specify the line termination for E1";
        type enumeration {
          enum "75-ohm";
          enum "120-ohm";
        }
        default "75-ohm";
      }
      list channel-group {
        key "number";
        leaf number {
          type uint8 {
            range "0..30";
          }
        }
        leaf-list timeslots {
          type union {
            type uint16;
            type string;
          }
        }
      }
      leaf shutdown {
        description
          "Shut down this link (send Blue Alarm)";
        type boolean;
        default "false";
      }
    }
    list Cellular {
      key "id";
      leaf id {
        type string;
      }
      container lte {
        description
          "LTE type carrier";
        container sim {
          description
            "Subscriber Identity Module";
          container authenticate {
            description
              "CHV1 authentication";
            leaf pin-type {
              description
                "0 Specifies an UNENCRYPTED (cleartext) PIN will follow 7 Specifies a HIDDEN PIN will follow";
              type enumeration {
                enum "0";
                enum "7";
              }
            }
            leaf pin {
              description
                "Unecrypted PIN (Length 4 to 8 characters)Encrypted PIN";
              type string;
            }
            leaf slot {
              description
                "Slot number";
              type uint8;
            }
          }
          list data-profile-list {
            description
              "Data Profile number";
            key "slot";
            leaf slot {
              description
                "Slot number";
              type uint8;
            }
            leaf data-profile {
              description
                "Profile Number corresponding to the data bearer APN";
              type leafref {
                path "../../../../profile/id";
              }
            }
            leaf attach-profile {
              description
                "Profile Number corresponding to initial attach APN";
              type leafref {
                path "../../../../profile/id";
              }
            }
          }
          leaf max-retry {
            description
              "Maximum number of SIM switchover retries";
            type uint16;
          }
          container primary {
            description
              "Controller's primary SIM";
            leaf slot {
              description
                "Slot number";
              type uint8;
            }
          }
        }
        container sms {
          description
            "SMS configuration";
          container archive {
            description
              "SMS archive configuration";
            leaf path {
              description
                "path in URL to archive SMS";
              type enumeration {
                enum "ftp:";
                enum "http:";
                enum "https:";
                enum "pram:";
                enum "rcp:";
                enum "scp:";
                enum "tftp:";
              }
            }
          }
        }
        container gps {
          description
            "GPS configuration";
          container nmea-conf {
            leaf nmea {
              description
                "enable NMEA data";
              type empty;
            }
          }
          container nmea {
            container ip {
              description
                "enable NMEA stream over IP UDP interface";
              container udp {
                description
                  "UDP Transport";
                leaf source-address {
                  description
                    "Source address";
                  type inet:ipv4-address;
                }
                leaf destination-address {
                  description
                    "Destination address";
                  type inet:ipv4-address;
                }
                leaf destination-port {
                  description
                    "Destination port";
                  type uint16;
                }
              }
            }
          }
          leaf enable {
            description
              "enable GPS feature";
            type empty;
          }
          leaf mode {
            description
              "select GPS mode";
            type enumeration {
              enum "ms-based";
              enum "standalone";
            }
          }
        }
        leaf failovertimer {
          description
            "Failover timeout value in mins";
          type uint8 {
            range "3..7";
          }
        }
        container firmware {
          description
            "Select firmware option";
          presence "true";
          leaf auto-sim {
            description
              "Select firmware auto-sim";
            type empty;
          }
        }
        container radio {
          description
            "Controller's radio";
          leaf off {
            description
              "Power down radio";
            type empty;
          }
        }
        container modem {
          container dm-log {
            description
              "Modem DM logging configuration";
            container output {
              description
                "DM logging output files";
              choice output-choice {
                leaf local-uf {
                  description
                    "Use Module Utility flash to store DM logs";
                  type empty;
                }
                leaf path {
                  description
                    "URL to store DM log files";
                  type enumeration {
                    enum "bootflash:";
                    enum "flash:";
                    enum "ftp:";
                    enum "http:";
                    enum "https:";
                    enum "pram:";
                    enum "rcp:";
                    enum "scp:";
                    enum "tftp:";
                  }
                }
              }
            }
            leaf filter {
              description
                "DM log filter file. Specify DM log filter location (in .sqf format)";
              type enumeration {
                enum "bootflash:";
                enum "flash:";
                enum "webui:";
              }
            }
            leaf size {
              description
                "Specify maximum log size. Maximum log size in MB (default is 64MB, 0 means no upper limit)";
              type uint16 {
                range "0..1024";
              }
            }
            leaf filesize {
              description
                "Specify maximum log file size. Maximum file size in MB (default is 20MB)";
              type int8 {
                range "1..64";
              }
            }
            leaf rotation {
              description
                "DM log rotation (only supported on flash:)";
              type empty;
            }
            leaf enable {
              description
                "Enable DM logging";
              type empty;
            }
            container autostop {
              description
                "Auto stop trigger event";
              choice autostop-choice {
                leaf link-down {
                  description
                    "Cellular interface link down event";
                  type empty;
                }
                leaf timer {
                  description
                    "Timer interval in minutes";
                  type int8 {
                    range "12..120";
                  }
                }
              }
            }
          }
          container fota {
            description
              "Firmware upgrade over the air";
            leaf enable {
              description
                "Enable FOTA";
              type empty;
            }
            leaf poll-timer {
              description
                "Set poll timer for AVMS, Interval(in minutes) at which modem polls server for firmware.";
              type uint32 {
                range "15..525600";
              }
            }
          }
          container link-recovery {
            container rssi {
              leaf onset-threshold {
                type int32;
              }
            }
            leaf monitor-timer {
              type uint32;
            }
            leaf wait-timer {
              type uint32;
            }
            leaf debounce-count {
              type uint32;
            }
            leaf disable {
              type empty;
            }
          }
          container nas-log {
            description
              "Modem NAS logging configuration";
            container output {
              description
                "DM logging output files";
              leaf path {
                description
                  "URL to store DM log files";
                type enumeration {
                  enum "bootflash:";
                  enum "flash:";
                }
              }
            }
            leaf size {
              description
                "Specify maximum log size. Maximum log size in MB (default is 64MB, 0 means no upper limit)";
              type uint16 {
                range "0..1024";
              }
            }
            leaf filesize {
              description
                "Specify maximum log file size. Maximum file size in MB (default is 20MB)";
              type int8 {
                range "1..64";
              }
            }
            leaf enable {
              description
                "Enable NAS logging";
              type empty;
            }
          }
        }
        container event {
          description
            "cellular snmp event persistence";
          container connection-status {
            description
              "connection status";
            leaf-list mib-trap {
              description
                "mibtrap";
              type enumeration {
                enum "All-lte";
                enum "active";
                enum "inactive";
              }
            }
          }
          container ecio {
            description
              "ecio";
            container abate {
              uses ecio-option-grouping;
            }
            container onset {
              uses ecio-option-grouping;
            }
          }
          container modem-state {
            description
              "modem state";
            leaf-list mib-trap {
              description
                "mibtrap";
              type enumeration {
                enum "all";
                enum "down";
                enum "up";
              }
            }
          }
          container network {
            description
              "enable trap for network";
            uses mib-trap-grouping;
          }
          container rsrp {
            description
              "Reference Signal Received Power";
            uses threshold-mib-trap-lte-grouping;
          }
          container rsrq {
            description
              "Reference Signal Received Quality";
            uses high-threshold-mib-trap-lte-grouping;
          }
          container rssi {
            description
              "rssi";
            uses threshold-mib-trap-lte-grouping;
          }
          container service {
            description
              "enable trap for service";
            uses mib-trap-grouping;
          }
          container temperature {
            description
              "modem temperature";
            container abate {
              uses mib-trap-grouping;
              uses threshold-grouping;
            }
            container onset {
              uses mib-trap-grouping;
              uses threshold-grouping;
            }
          }
        }
        container dyinggasp {
          description
            "Dying Gasp Configuration";
          container detach {
            description
              "Send Detach Request";
            leaf enable {
              description
                "Enable Dying Gasp Detach Request";
              type empty;
            }
          }
          container sms {
            description
              "SMS Commands";
            leaf send {
              description
                "Send SMS";
              type string;
            }
            leaf sms-text {
              description
                "SMS text until the end of line (EOL) up to 160 characters";
              type string {
                length "1..160";
              }
            }
          }
        }
      }
      list profile {
        description
          "LTE Profile management commands";
        key "id";
        leaf id {
          description
            "Profile identification number configuration";
          type int8 {
            range "1..16";
          }
        }
        leaf apn {
          description
            "Access point name configuration";
          type string;
        }
        leaf authentication {
          description
            "Select authentication type";
          type enumeration {
            enum "chap";
            enum "none";
            enum "pap";
            enum "pap_chap";
          }
        }
        leaf username {
          description
            "Username";
          when "../authentication and not(../authentication = 'none')";
          type string;
        }
        leaf password {
          description
            "Password";
          when "../authentication and not(../authentication = 'none')";
          type string;
        }
        leaf pdn-type {
          description
            "Select pdn type";
          type enumeration {
            enum "ipv4";
            enum "ipv4v6";
            enum "ipv6";
          }
        }
        leaf no-overwrite {
          description
            "Don't replace, if profile exists";
          type empty;
        }
      }
    }
    list SONET {
      description
        "SONET";
      key "name";
      leaf name {
        type string;
      }
      uses sonet-grouping;
    }
    list SONET-ACR {
      description
        "SONET-ACR";
      key "name";
      leaf name {
        type string {
          pattern "([0-9\\.])+";
        }
      }
      uses sonet-grouping;
    }
    list wanphy {
      description
        "wanphy";
      key "name";
      leaf name {
        type string;
      }
    }
    list VDSL {
      description
        "VDSL2 controller";
      key "name";
      leaf name {
        type string;
      }
      leaf shutdown {
        type empty;
      }
      leaf sra {
        description
          "Seamless rate adaption";
        type empty;
      }
      leaf bitswap {
        description
          "Bit swap";
        type empty;
      }
      leaf diagnostics {
        type enumeration {
          enum "DELT";
        }
      }
      leaf description {
        description
          " Controller specific description";
        type string {
          length "1..240";
        }
      }
      container line-mode {
        description
          "Line Mode configuration to select Bonding/Single-wire";
        choice line-mode-choice {
          leaf bonding {
            type empty;
          }
          container single-wire {
            container line {
              leaf zero {
                type empty;
              }
              container one {
                presence "true";
                leaf profile {
                  type enumeration {
                    enum "30a";
                  }
                }
              }
            }
          }
        }
      }
      container operating {
        description
          "Configure auto or specific VDSL operating mode";
        container mode {
          choice operating-mode-choice {
            leaf adsl1 {
              type empty;
            }
            container adsl2 {
              presence "true";
              leaf annex {
                type enumeration {
                  enum "A";
                  enum "M";
                  enum "B";
                  enum "J";
                }
              }
            }
            container auto {
              presence "true";
              leaf adsl1 {
                type empty;
              }
              leaf adsl2 {
                type empty;
              }
              leaf adsl2plus {
                type empty;
              }
              leaf vdsl2 {
                type empty;
              }
              leaf ansi {
                type empty;
              }
            }
            leaf vdsl2 {
              type empty;
            }
            leaf ansi {
              type empty;
            }
            container adsl2plus {
              presence "true";
              leaf annex {
                type enumeration {
                  enum "A";
                  enum "M";
                  enum "B";
                  enum "J";
                }
              }
            }
          }
        }
      }
      container training {
        description
          "Dsl firmware training log";
        container log {
          leaf filename {
            description
              "file name to store dsl training log";
            type string;
          }
        }
      }
      container firmware {
        description
          "xDSL PHY FW update";
        container phy {
          description
            "Component name";
          leaf filename {
            description
              "file name to read firmware";
            type string;
          }
        }
      }
      container sync {
        description
          "xDSL sync preferences";
        container interval {
          description
            "seconds between ITU and ANSI sync";
          leaf seconds {
            type uint32;
          }
        }
        container mode {
          description
            "Choose preferred sync mode";
          container itu {
            presence "true";
            leaf previous {
              type empty;
            }
          }
          leaf none {
            type empty;
          }
          container ansi {
            presence "true";
            leaf previous {
              type empty;
            }
          }
        }
      }
      leaf modem {
        description
          "vdsl modem configuration";
        type string {
          length "1..48";
        }
      }
    }
  }

  augment "/ios:native/ios:controller" {
    uses config-controller-grouping;
  }
}
