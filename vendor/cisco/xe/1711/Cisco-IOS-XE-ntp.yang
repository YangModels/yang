module Cisco-IOS-XE-ntp {
  namespace "http://cisco.com/ns/yang/Cisco-IOS-XE-ntp";
  prefix ios-ntp;

  import cisco-semver {
    prefix cisco-semver;
  }
  import ietf-inet-types {
    prefix inet;
  }
  import Cisco-IOS-XE-types {
    prefix ios-types;
  }
  import Cisco-IOS-XE-native {
    prefix ios;
  }
  import Cisco-IOS-XE-interface-common {
    prefix ios-ifc;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Network Time Protocol (NTP) Yang model.
     Copyright (c) 2016-2019 by Cisco Systems, Inc.
     All rights reserved.";

  revision 2019-11-01 {
    description
      "- Added new leaf periodic to ntp-peer-server-attr-grouping
       - Added choice node for 'auth type' in ntp authentication-key
       - deprecated acl and kod leafs from ntp access-group peer, query-only, serve, 
         serve-only container. Preserved only single xPath with ipv4 option
       - Added new grouping ntp-access-group-grouping-revised to met above requirements
       - Incorporated backward compatible changes for NTP auth md5 leaf";
    cisco-semver:module-version "1.1.0";
  }
  revision 2019-07-01 {
    description
      "- Establish semantic version baseline
       - Corrected encryption-type in ntp authentication-key
       - Corrected ntp trusted-key
       - Corrected ntp server source command to accept interfaces
       - Change the ntp server source to leaf
       - Added new grouping ntp-peer-server-grouping-vrf";
    cisco-semver:module-version "1.0.0";
  }
  revision 2019-01-22 {
    description
      "Added leaf for App-hosting Gigabit Ethernet interface";
  }
  revision 2018-10-25 {
    description
      "Update types for ipv6 acl to only support string";
  }
  revision 2018-10-22 {
    description
      "Add defaults for server and peer list grouping";
  }
  revision 2018-06-28 {
    description
      "Added must constraints for deleting vrf";
  }
  revision 2018-01-05 {
    description
      "ntp server-list union order changed to make string type last";
  }
  revision 2017-11-27 {
    description
      "Added Change 25GE name";
  }
  revision 2017-11-14 {
    description
      "Added Two and 40 GE support";
  }
  revision 2017-09-21 {
    description
      "Added interface ntp broadcast";
  }
  revision 2017-09-20 {
    description
      "Added interface ntp broadcast client";
  }
  revision 2017-02-07 {
    description
      "Initial revision";
  }

  grouping ntp-access-group-kod-grouping {
    leaf acl {
      type ios-types:std-acl-type;
    }
    leaf kod {
      description
        "Send a Kiss-o-Death packet for failing peers";
      type empty;
      must "../acl";
    }
  }

  grouping ntp-access-group-kod-grouping-deprecated {
    leaf acl {
      type ios-types:std-acl-type;
      status deprecated;
    }
    leaf kod {
      description
        "Send a Kiss-o-Death packet for failing peers";
      type empty;
      must "../acl";
      status deprecated;
    }
  }

  grouping ntp-ipv6-access-group-kod-grouping {
    leaf acl {
      type string;
    }
    leaf kod {
      description
        "Send a Kiss-o-Death packet for failing peers";
      type empty;
      must "../acl";
    }
  }

  grouping ntp-access-group-grouping-revised {
    container peer {
      description
        "Provide full access";
      uses ntp-access-group-kod-grouping;
    }
    container query-only {
      description
        "Provide server and query access";
      uses ntp-access-group-kod-grouping;
    }
    container serve {
      description
        "Provide server and query access";
      uses ntp-access-group-kod-grouping;
    }
    container serve-only {
      description
        "Provide only server access";
      uses ntp-access-group-kod-grouping;
    }
  }

  grouping ntp-access-group-grouping {
    container peer {
      description
        "Provide full access";
      uses ntp-access-group-kod-grouping-deprecated;
    }
    container query-only {
      description
        "Provide server and query access";
      uses ntp-access-group-kod-grouping-deprecated;
    }
    container serve {
      description
        "Provide server and query access";
      uses ntp-access-group-kod-grouping-deprecated;
    }
    container serve-only {
      description
        "Provide only server access";
      uses ntp-access-group-kod-grouping-deprecated;
    }
  }

  grouping ntp-ipv6-access-group-grouping {
    container peer {
      description
        "Provide full access";
      uses ntp-ipv6-access-group-kod-grouping;
    }
    container query-only {
      description
        "Provide server and query access";
      uses ntp-ipv6-access-group-kod-grouping;
    }
    container serve {
      description
        "Provide server and query access";
      uses ntp-ipv6-access-group-kod-grouping;
    }
    container serve-only {
      description
        "Provide only server access";
      uses ntp-ipv6-access-group-kod-grouping;
    }
  }

  grouping ntp-peer-server-attr-grouping {
    leaf burst {
      description
        "Send a burst when peer is reachable (Default)";
      type boolean;
      default "true";
    }
    leaf iburst {
      description
        "Send a burst when peer is unreachable (Default)";
      type boolean;
      default "true";
    }
    leaf key {
      description
        "Configure peer authentication key";
      type uint32 {
        range "1..4294967295";
      }
    }
    leaf maxpoll {
      description
        "Maximum poll interval";
      type uint8 {
        range "4..17";
      }
      default "10";
    }
    leaf minpoll {
      description
        "Minimum poll interval";
      type uint8 {
        range "4..17";
      }
      default "6";
    }
    leaf prefer {
      description
        "Prefer this peer when possible";
      type empty;
    }
    leaf version {
      description
        "    Configure NTP version";
      type uint8 {
        range "1..4";
      }
      default "4";
    }
    leaf periodic {
      description
        "Check server availability periodically and switch to a new server\\
         if required";
      type empty;
    }
  }

  grouping ntp-peer-server-grouping {
    list server-list {
      key "ip-address";
      leaf ip-address {
        type union {
          type inet:ipv4-address;
          type inet:ipv6-address;
          type string;
        }
      }
      leaf source {
        description
          "Interface for source address";
        type string;
      }
      uses ntp-peer-server-attr-grouping;
    }
    list ip {
      description
        "Use IP for DNS resolution";
      key "host-name";
      leaf host-name {
        type string;
      }
      leaf source {
        description
          "Interface for source address";
        type string;
      }
      uses ntp-peer-server-attr-grouping;
    }
    list ipv6 {
      description
        "Use IPv6 for DNS resolution";
      key "host-name";
      leaf host-name {
        type string;
      }
      leaf source {
        description
          "Interface for source address";
        type string;
      }
      uses ntp-peer-server-attr-grouping;
    }
  }

  grouping ntp-peer-server-grouping-vrf {
    list server-list {
      key "ip-address";
      leaf ip-address {
        type union {
          type inet:ipv4-address;
          type inet:ipv6-address;
          type string;
        }
      }
      leaf source {
        description
          "Interface for source address";
        status obsolete;
        type string;
      }
      uses ntp-peer-server-attr-grouping;
    }
    list ip {
      description
        "Use IP for DNS resolution";
      key "host-name";
      leaf host-name {
        type string;
      }
      leaf source {
        description
          "Interface for source address";
        status obsolete;
        type string;
      }
      uses ntp-peer-server-attr-grouping;
    }
    list ipv6 {
      description
        "Use IPv6 for DNS resolution";
      key "host-name";
      leaf host-name {
        type string;
      }
      leaf source {
        description
          "Interface for source address";
        status obsolete;
        type string;
      }
      uses ntp-peer-server-attr-grouping;
    }
  }

  grouping config-ntp-grouping {
    container access-group {
      description
        "Control NTP access";
      container ipv4 {
        description
          "ipv4 access lists";
        uses ntp-access-group-grouping-revised;
      }
      container ipv6 {
        description
          "ipv6 access lists";
        uses ntp-ipv6-access-group-grouping;
      }
      uses ntp-access-group-grouping;
    }
    container allow {
      description
        "Allow processing of packets";
      container mode {
        description
          "Allow processing of particular mode packets";
        container control {
          description
            "Allow processing control mode packets";
          presence "true";
          leaf delay {
            description
              "Rate limiting delay (s)";
            type uint8 {
              range "0..15";
            }
          }
        }
        leaf private {
          description
            "Allow processing private mode packets";
          type empty;
        }
      }
    }
    leaf authenticate {
      description
        "Authenticate time sources";
      type empty;
    }
    list authentication-key {
      description
        "Authentication key for trusted time sources";
      key "number";
      leaf number {
        type uint32 {
          range "1..4294967295";
        }
      }
      choice authtype {
        leaf md5-cfg {
          description
            "MD5 authentication";
          type string;
        }
        leaf cmac-aes-128 {
          description
            "CMAC-AES-128 (digest length = 128 bits,\\
              key length = [16 or 32] bytes)";
          type string;
        }
        leaf hmac-sha1 {
          description
            "HMAC-SHA1 (digest length = 160 bits,\\
              key length = [1-32] bytes)";
          type string;
        }
        leaf hmac-sha2-256 {
          description
            "HMAC-SHA2-256 (digest length = 256 bits,\\
              key length = [1-32] bytes)";
          type string;
        }
      }
      leaf md5 {
        description
          "MD5 authentication";
        type string;
        status deprecated;
      }
      leaf encryption-type {
        description
          "Authentication key encryption type";
        type uint32;
      }
    }
    leaf broadcastdelay {
      description
        "Estimated round-trip delay in microseconds";
      type uint32 {
        range "1..999999";
      }
    }
    leaf clock-period {
      description
        "Length of hardware clock tick";
      type uint32;
    }
    leaf logging {
      description
        "Enable NTP message logging";
      type empty;
    }
    container master {
      description
        "Act as NTP master clock";
      presence "true";
      leaf stratum-number {
        type uint8 {
          range "1..15";
        }
      }
    }
    leaf max-associations {
      description
        "Set maximum number of associations";
      type uint32;
    }
    leaf maxdistance {
      description
        "Maximum Distance for synchronization";
      type uint8 {
        range "1..16";
      }
    }
    leaf mindistance {
      description
        "Minimum distance to consider for clockhop";
      type uint16 {
        range "1..500";
      }
    }
    leaf orphan {
      description
        "Threshold Stratum for orphan mode";
      type uint8 {
        range "1..16";
      }
    }
    container panic {
      description
        "Reject time updates > panic threshold (default 1000Sec)";
      leaf update {
        description
          "Reject time updates > panic threshold (default 1000Sec)";
        type empty;
      }
    }
    leaf passive {
      description
        "NTP passive mode";
      type empty;
    }
    container peer {
      description
        "Configure NTP peer";
      uses ntp-peer-server-grouping;
      list vrf {
        description
          "VPN Routing/Forwarding Information";
        key "name";
        leaf name {
          must "/ios:native/ios:vrf/ios:definition[ios:name=current()] or /ios:native/ios:ip/ios:vrf[ios:name=current()]" {
            error-message "VRF must be created 1st, deleted last";
          }
          type string;
        }
        uses ntp-peer-server-grouping-vrf;
      }
    }
    container server {
      description
        "Configure NTP server";
      uses ntp-peer-server-grouping;
      list vrf {
        description
          "VPN Routing/Forwarding Information";
        key "name";
        leaf name {
          must "/ios:native/ios:vrf/ios:definition[ios:name=current()] or /ios:native/ios:ip/ios:vrf[ios:name=current()]" {
            error-message "VRF must be created 1st, deleted last";
          }
          type string;
        }
        uses ntp-peer-server-grouping-vrf;
      }
    }
    container source {
      description
        "Configure interface for source address";
      uses ios-ifc:interface-grouping;
    }
    list trusted-key {
      description
        "Key numbers for trusted time sources";
      key "number";
      leaf number {
        type uint16 {
          range "1..65535";
        }
      }
      leaf hyphen {
        type empty;
      }
      leaf end-key {
        description
          "End Key range";
        type uint16 {
          range "1..65535";
        }
      }
    }
    leaf update-calendar {
      description
        "Periodically update calendar with NTP time";
      type empty;
    }
  }

  grouping config-interface-ntp-grouping {
    container ntp {
      description
        "Configure NTP";
      leaf broadcast {
        description
          "Configure NTP broadcast service";
        type boolean;
        default "false";
      }
      container broadcast-option {
        description
          "Configure NTP broadcast service";
        container broadcast {
          leaf client {
            description
              "Listen to NTP broadcasts";
            type boolean;
            default "false";
          }
        }
      }
      container disable {
        description
          "Disable NTP traffic (both IP and IPv6)";
        presence "true";
        must
          "not (../broadcast = 'true'
                or ../broadcast-option/broadcast/client = 'true')" {
          error-message
            "%NTP: Unconfigure other NTP commands on this
             interface before executing 'ntp disable'";
        }
        leaf ip-ipv6 {
          type enumeration {
            enum "ip" {
              description
                "Disable IP based NTP traffic";
            }
            enum "ipv6" {
              description
                "Disable IPv6 based NTP traffic";
            }
          }
        }
      }
    }
  }

  augment "/ios:native/ios:ntp" {
    uses config-ntp-grouping;
  }
  augment "/ios:native/ios:interface/ios:FastEthernet" {
    uses config-interface-ntp-grouping;
  }
  augment "/ios:native/ios:interface/ios:GigabitEthernet" {
    uses config-interface-ntp-grouping;
  }
  augment "/ios:native/ios:interface/ios:TenGigabitEthernet" {
    uses config-interface-ntp-grouping;
  }
  augment "/ios:native/ios:interface/ios:FiveGigabitEthernet" {
    uses config-interface-ntp-grouping;
  }
  augment "/ios:native/ios:interface/ios:AppGigabitEthernet" {
    uses config-interface-ntp-grouping;
  }
  augment "/ios:native/ios:interface/ios:TwentyFiveGigE" {
    uses config-interface-ntp-grouping;
  }
  augment "/ios:native/ios:interface/ios:HundredGigE" {
    uses config-interface-ntp-grouping;
  }
  augment "/ios:native/ios:interface/ios:TwoGigabitEthernet" {
    uses config-interface-ntp-grouping;
  }
  augment "/ios:native/ios:interface/ios:FortyGigabitEthernet" {
    uses config-interface-ntp-grouping;
  }
  augment "/ios:native/ios:interface/ios:Loopback" {
    uses config-interface-ntp-grouping;
  }
  augment "/ios:native/ios:interface/ios:Tunnel" {
    uses config-interface-ntp-grouping;
  }
  augment "/ios:native/ios:interface/ios:Virtual-Template" {
    uses config-interface-ntp-grouping;
  }
  augment "/ios:native/ios:interface/ios:Vlan" {
    uses config-interface-ntp-grouping;
  }
}
