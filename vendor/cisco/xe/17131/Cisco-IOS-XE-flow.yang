module Cisco-IOS-XE-flow {
  yang-version 1.1;
  namespace "http://cisco.com/ns/yang/Cisco-IOS-XE-flow";
  prefix ios-flow;

  import cisco-semver {
    prefix cisco-semver;
  }
  import ietf-inet-types {
    prefix inet;
  }
  import Cisco-IOS-XE-native {
    prefix ios;
  }
  import Cisco-IOS-XE-types {
    prefix ios-types;
  }
  import Cisco-IOS-XE-interface-common {
    prefix ios-ifc;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native NetFlow Yang model.
     Copyright (c) 2016-2023 by Cisco Systems, Inc.
     All rights reserved.";

  revision 2023-11-01 {
    description
      "- Predefined flow records: added assurance-dns and assurance-dhcp
       - Add flow-name type to replace string type for monitor record exporter and sampler names
       - Fix file exporter defaults
       - Flow monitor attach/detach to/from interface: add dependency on monitor existence";
    cisco-semver:module-version "3.7.0";
  }
  revision 2023-07-01 {
    description
      "- File-export: add HTTPS transport
       - File-export: change destination from ipv4 to string";
    cisco-semver:module-version "3.6.0";
  }
  revision 2023-03-01 {
    description
      "- Added more file-export parameters
       - Added Remote Access fields";
    cisco-semver:module-version "3.5.0";
  }
  revision 2022-11-01 {
    description
      "- Update yang-version to 1.1
       - Added BFD metrics for flow exporter
       - Added new collect for Cloud Region ID";
    cisco-semver:module-version "3.4.0";
  }
  revision 2022-07-01 {
    description
      "- Added new collect for Cloud SaaS path type
       - Added export-spread for flow exporter
       - Added firewall user name field";
    cisco-semver:module-version "3.3.0";
  }
  revision 2021-11-01 {
    description
      "- Added new multi tenant opt table";
    cisco-semver:module-version "3.2.0";
  }
  revision 2021-07-01 {
    description
      "- Modify dscp-input for flow record
       - Added must condition for flow monitor
       - Added new collect for unified logging utd";
    cisco-semver:module-version "3.1.0";
  }
  revision 2021-03-01 {
    description
      "- Added new collect for service area";
    cisco-semver:module-version "3.0.0";
  }
  revision 2020-11-01 {
    description
      "- Added new collect for Appqoe Multi-SN
       - Added new collects for unified logging
       - Added new optional tables for unified logging";
    cisco-semver:module-version "2.3.0";
  }
  revision 2020-07-01 {
    description
      "- Added new collect for traffic category on Cloud Express";
    cisco-semver:module-version "2.2.0";
  }
  revision 2020-03-01 {
    description
      "- Added new counters for AppQoe SSL";
    cisco-semver:module-version "2.1.0";
  }
  revision 2019-11-01 {
    description
      "- Added new appqoe config
       - removed output-feature config under exporter configuration
       - Added new when statement under flow-vendor-version-grouping";
    cisco-semver:module-version "2.0.0";
  }
  revision 2019-07-01 {
    description
      "- Establish semantic version baseline
       - Add support for predefined assurance and assurance-rtp flow records
         Added new predefined records under flow monitor
          - record netflow ipv4 assurance-rtp
          - record netflow ipv6 assurance-rtp
          - record wireless avc ipv4 assurance-rtp
          - record wireless avc ipv6 assurance-rtp";
    cisco-semver:module-version "1.0.0";
  }
  revision 2019-01-22 {
    description
      "Added leaf for App-hosting Gigabit Ethernet interface";
  }
  revision 2018-11-22 {
    description
      "Adding below missing CLI's as part of CSCvm07845:
       - Add new fields under flow record
           - application cisco-collaboration
           - application citrix citrix-ica-tag
           - application first-in-flow <>
           - application sip <>
           - application ssh <>
           - application ssl session-idh
           - application tftp source-file
           - vxlan <>
           - wireless <>
           - flow id
           - pfr br ipv4 address
           - interface output physical
           - ipv4/ipv6 dscp output
       - Add mtu field under flow exporter";
  }
  revision 2018-10-22 {
    description
      "This revision has changes for ATM, Multilink and Vlan interfaces addition";
  }
  revision 2018-10-01 {
    description
      "Add leafref to flow monitor to cause deletion of flow references first";
  }
  revision 2018-09-22 {
    description
      "This revison has changes for serial,dialer,service,cellular interface addition";
  }
  revision 2018-07-31 {
    description
      "Add dependency for ip visibility global flow monitor sdwan_flow_monitor";
  }
  revision 2018-05-18 {
    description
      "Changes for cedge platforms:
       - Add dependency to ip flow and add dependency to flow exporter
       - Add local sdwan destination option for exporter, as well as exporter match command for filtering
       - Add tunnel-to-tloc option table
       - Add FNF global config 'ip visibility ...'
       - Add new fields under flow record
           - overlay session id input/output
           - routing vrf service
           - connection id long";
  }
  revision 2018-01-04 {
    description
      "Added destination local wlc and options for record wireless avc";
  }
  revision 2017-11-27 {
    description
      "Added Change 25GE name";
  }
  revision 2017-11-14 {
    description
      "This revison has changes for new 40 and 100GE interface addition";
  }
  revision 2017-09-14 {
    description
      "This revison has changes for new 2gig interface addition";
  }
  revision 2017-08-16 {
    description
      "This revision has changes for new 5gig and 25gig interfaces addition";
  }
  revision 2017-06-28 {
    description
      "add match datalink vlan input/output under flow record";
  }
  revision 2017-06-18 {
    description
      "add flow record collect connection delay response to-server histogram late support";
  }
  revision 2017-04-19 {
    description
      "flow exporter source interface dependency on loopbacks";
  }
  revision 2017-02-07 {
    description
      "Initial revision";
  }

  typedef flow-name {
    type string {
      pattern '[a-zA-Z0-9\-_@\[\]{}()\.]*';
    }
  }

  grouping flow-name-grouping {
    container name {
      description
        "Application name";
      presence "true";
      leaf account-on-resolution {
        description
          "Account on resolution";
        type empty;
      }
    }
  }

  grouping flow-vendor-version-grouping {
    leaf vendor {
      description
        "Application vendor id";
      when "/ios:native/ios:flow/ios-flow:record/ios-flow:type = 'performance-monitor'";
      type empty;
    }
    leaf version {
      description
        "Application version id";
      when "/ios:native/ios:flow/ios-flow:record/ios-flow:type = 'performance-monitor'";
      type empty;
    }
  }

  grouping flow-client-ipv4-ipv6-transport-grouping {
    container ipv4 {
      description
        "Client side IPv4 metrics";
      leaf address {
        description
          "IPv4 address of the flow initiator";
        type empty;
      }
    }
    container ipv6 {
      description
        "Client side IPv6 metrics";
      leaf address {
        description
          "IPv6 address of the flow initiator";
        type empty;
      }
    }
    container transport {
      description
        "Client side transport metrics";
      leaf port {
        description
          "Transport port of the flow initiator";
        type empty;
      }
    }
  }

  grouping flow-server-ipv4-ipv6-transport-grouping {
    container ipv4 {
      description
        "Server side IPv4 metrics";
      leaf address {
        description
          "IPv4 address of the flow responder";
        type empty;
      }
    }
    container ipv6 {
      description
        "Server side IPv6 metrics";
      leaf address {
        description
          "IPv6 address of the flow responder";
        type empty;
      }
    }
    container transport {
      description
        "Server side transport metrics";
      leaf port {
        description
          "Transport port of the flow responder";
        type empty;
      }
    }
  }

  grouping flow-transaction-id-grouping {
    leaf transaction-id {
      description
        "An identifier for a transaction between client and server";
      type empty;
    }
  }

  grouping flow-id-initiator-grouping {
    leaf initiator {
      description
        "The direction of the flow";
      type empty;
    }
  }

  grouping flow-datalink-grouping {
    leaf destination-vlan-id {
      description
        "ID of the VLAN that the packet is going to";
      type empty;
    }
    container dot1q {
      description
        "dot1q field";
      leaf priority {
        description
          "The CoS field out of the dot1q header";
        type empty;
      }
      container vlan {
        description
          "The VLAN the packet is on";
        leaf input {
          description
            "The VLAN the packet is on at input";
          type empty;
        }
        leaf output {
          description
            "The VLAN the packet is on at output";
          type empty;
        }
      }
    }
    leaf ethertype {
      description
        "The Ethertype of the packet";
      type empty;
    }
    leaf vlan {
      description
        "The VLAN the packet is on";
      type enumeration {
        enum input;
        enum output;
      }
    }
    container mac {
      description
        "MAC fields";
      container destination {
        description
          "destination MAC fields";
        container address {
          description
            "Destination MAC address from packet";
          leaf input {
            description
              "Destination MAC address from packet at input";
            type empty;
          }
          leaf output {
            description
              "Destination MAC address from packet at output";
            type empty;
          }
        }
      }
      container source {
        description
          "source MAC fields";
        container address {
          description
            "Source MAC address from packet";
          leaf input {
            description
              "Source MAC address from packet at input";
            type empty;
          }
          leaf output {
            description
              "Source MAC address from packet at output";
            type empty;
          }
        }
      }
    }
    leaf source-vlan-id {
      description
        "ID of the VLAN that the packet came from";
      type empty;
    }
  }

  grouping flow-flow-common-grouping {
    container cts {
      description
        "Cisco Trusted Security fields";
      container destination {
        description
          "Cisco Trusted Security destination fields";
        leaf group-tag {
          description
            "destination group-tag";
          type empty;
        }
      }
      container source {
        description
          "Cisco Trusted Security source fields";
        leaf group-tag {
          description
            "source group-tag";
          type empty;
        }
      }
    }
    leaf direction {
      description
        "Direction the flow was monitored in";
      type empty;
    }
    leaf id {
      description
        "Unique ID of the flow";
      type empty;
    }
    container observation {
      description
        "Flow observation metrics";
      leaf point {
        description
          "Observation point ID";
        type empty;
      }
    }
    leaf sampler {
      description
        "ID of the sampler";
      type empty;
    }
  }

  grouping flow-interface-grouping {
    container input {
      description
        "The input interface";
      presence "true";
      leaf snmp {
        description
          "SNMP Index of the input interface";
        type empty;
      }
    }
    container output {
      description
        "The output interface";
      presence "true";
      container physical {
        description
          "The physical output interface";
        leaf snmp {
          description
            "SNMP Index of the output interface";
          type empty;
        }
      }
      leaf snmp {
        description
          "SNMP Index of the output interface";
        type empty;
      }
    }
  }

  grouping flow-ipv4-grouping {
    container destination {
      description
        "IPv4 destination address based fields";
      leaf address {
        description
          "IPv4 destination address";
        type empty;
      }
      container mask {
        description
          "IPv4 address mask for the IPv4 destination address";
        presence "true";
        leaf minimum-mask {
          description
            "Provide a minimum mask for this field";
          type uint8 {
            range "1..32";
          }
        }
      }
      container prefix {
        description
          "IPv4 address prefix for the IPv4 destination address";
        presence "true";
        leaf minimum-mask {
          description
            "Provide a minimum mask for this field";
          type uint8 {
            range "1..32";
          }
        }
      }
    }
    leaf dscp-input {
      description
        "IPv4 DSCP input (part of TOS)";
      type empty;
    }
    container dscp {
      description
        "IPv4 DSCP (part of TOS)";
      leaf output {
        description
          "IPv4 output DSCP";
        type empty;
      }
    }
    container fragmentation {
      description
        "IPv4 fragmentation fields";
      leaf flags {
        description
          "IPv4 fragmentation flags";
        type empty;
      }
      leaf offset {
        description
          "IPv4 fragmentation offset";
        type empty;
      }
    }
    leaf header-length {
      description
        "IPv4 header length (IHL in 32 bit words)";
      type empty;
    }
    leaf id {
      description
        "IPv4 ID";
      type empty;
    }
    container length {
      description
        "IPv4 length fields";
      leaf header {
        description
          "Length of the IPv4 header in bytes";
        type empty;
      }
      leaf payload {
        description
          "Length of the IPv4 payload in bytes";
        type empty;
      }
      container total {
        description
          "Total length of the IPv4 header and payload in bytes";
        presence "true";
        leaf maximum {
          description
            "Maximum total length in bytes";
          type empty;
        }
        leaf minimum {
          description
            "Minimum total length in bytes";
          type empty;
        }
      }
    }
    container option {
      description
        "IPv4 option fields";
      leaf map {
        description
          "Bitmap of IPv4 options";
        type empty;
      }
    }
    leaf precedence {
      description
        "IPv4 precedence (part of TOS)";
      type empty;
    }
    leaf protocol {
      description
        "IPv4 protocol";
      type empty;
    }
    container section {
      description
        "Part of the packet";
      container header {
        description
          "Raw data starting at the IPv4 header";
        leaf size {
          description
            "Specify the number of bytes to capture";
          type uint16 {
            range "1..1200";
          }
        }
      }
      container payload {
        description
          "Raw data starting at the IPv4 payload";
        leaf size {
          description
            "Specify the number of bytes to capture";
          type uint16 {
            range "1..1200";
          }
        }
      }
    }
    container source {
      description
        "IPv4 source address based fields";
      leaf address {
        description
          "IPv4 source address";
        type empty;
      }
      container mask {
        description
          "IPv4 address mask for the IPv4 source address";
        presence "true";
        leaf minimum-mask {
          description
            "Provide a minimum mask for this field";
          type uint8 {
            range "1..32";
          }
        }
      }
      container prefix {
        description
          "IPv4 address prefix for the IPv4 source address";
        presence "true";
        leaf minimum-mask {
          description
            "Provide a minimum mask for this field";
          type uint8 {
            range "1..32";
          }
        }
      }
    }
    leaf tos {
      description
        "IPv4 type of service";
      type empty;
    }
    container total-length {
      description
        "IPv4 total length";
      presence "true";
      leaf maximum {
        description
          "Largest value for IPv4 length seen in the flow";
        type empty;
      }
      leaf minimum {
        description
          "Smallest value for IPv4 length seen in the flow";
        type empty;
      }
    }
    container ttl {
      description
        "IPv4 TTL";
      presence "true";
      leaf maximum {
        description
          "Largest value seen for TTL in the flow";
        type empty;
      }
      leaf minimum {
        description
          "Smallest value seen for TTL in the flow";
        type empty;
      }
    }
    leaf version {
      description
        "IP version from IPv4 header";
      type empty;
    }
  }

  grouping flow-ipv6-grouping {
    container destination {
      description
        "IPv6 destination address based fields";
      leaf address {
        description
          "IPv6 destination address";
        type empty;
      }
      container mask {
        description
          "IPv6 address mask for the IPv6 destination address";
        presence "true";
        leaf minimum-mask {
          description
            "Provide a minimum mask for this field";
          type uint8 {
            range "1..128";
          }
        }
      }
      container prefix {
        description
          "IPv6 address prefix for the IPv6 destination address";
        presence "true";
        leaf minimum-mask {
          description
            "Provide a minimum mask for this field";
          type uint8 {
            range "1..128";
          }
        }
      }
    }
    container dscp {
      description
        "IPv6 DSCP (part of Traffic Class)";
      presence "true";
      leaf output {
        description
          "IPv6 output DSCP";
        type empty;
      }
    }
    container extension {
      description
        "IPv6 extension header fields";
      leaf map {
        description
          "Bitmap of IPv6 extension headers";
        type empty;
      }
    }
    leaf flow-label {
      description
        "IPv6 flow label";
      type empty;
    }
    container fragmentation {
      description
        "IPv6 fragmentation fields";
      leaf flags {
        description
          "IPv6 fragmentation flags";
        type empty;
      }
      leaf id {
        description
          "IPv6 fragmentation ID";
        type empty;
      }
      leaf offset {
        description
          "IPv6 fragmentation offset";
        type empty;
      }
    }
    container hop-limit {
      description
        "IPv6 hop limit";
      presence "true";
      leaf maximum {
        description
          "Largest value seen for hop-limit in the flow";
        type empty;
      }
      leaf minimum {
        description
          "Smallest value seen for hop-limit in the flow";
        type empty;
      }
    }
    container length {
      description
        "IPv6 length fields";
      leaf header {
        description
          "Length of the IPv6 header, not including any extension headers, in bytes";
        type empty;
      }
      leaf payload {
        description
          "Length of the IPv6 payload, including any extension headers, in bytes";
        type empty;
      }
      container total {
        description
          "Total length of the IPv6 header and payload in bytes";
        presence "true";
        leaf maximum {
          description
            "Maximum total length in bytes";
          type empty;
        }
        leaf minimum {
          description
            "Minimum total length in bytes";
          type empty;
        }
      }
    }
    leaf next-header {
      description
        "The value of the next-header field in the IPv6 header";
      type empty;
    }
    leaf payload-length {
      description
        "Length of the IPv6 payload in bytes";
      type empty;
    }
    leaf precedence {
      description
        "IPv6 precedence (part of Traffic Class)";
      type empty;
    }
    leaf protocol {
      description
        "IPv6 payload protocol";
      type empty;
    }
    container section {
      description
        "Part of the packet";
      container header {
        description
          "Raw data starting at the IPv6 header";
        leaf size {
          description
            "Specify the number of bytes to capture";
          type uint16 {
            range "1..1200";
          }
        }
      }
      container payload {
        description
          "Raw data starting at the IPv6 payload";
        leaf size {
          description
            "Specify the number of bytes to capture";
          type uint16 {
            range "1..1200";
          }
        }
      }
    }
    container source {
      description
        "IPv6 source address based fields";
      leaf address {
        description
          "IPv6 source address";
        type empty;
      }
      container mask {
        description
          "IPv6 address mask for the IPv6 source address";
        presence "true";
        leaf minimum-mask {
          description
            "Provide a minimum mask for this field";
          type uint8 {
            range "1..128";
          }
        }
      }
      container prefix {
        description
          "IPv6 address prefix for the IPv6 source address";
        presence "true";
        leaf minimum-mask {
          description
            "Provide a minimum mask for this field";
          type uint8 {
            range "1..128";
          }
        }
      }
    }
    leaf traffic-class {
      description
        "IPv6 traffic class";
      type empty;
    }
    leaf version {
      description
        "IP version from IPv6 header";
      type empty;
    }
  }

  grouping flow-mpls-grouping {
    container label {
      description
        "MPLS label details";
      container one {
        description
          "MPLS label 1 information";
        leaf details {
          description
            "MPLS label 1 details";
          type empty;
        }
        leaf exp {
          description
            "MPLS EXP field from the last label that was pushed";
          type empty;
        }
        leaf ttl {
          description
            "MPLS TTL field from the last label that was pushed";
          type empty;
        }
        leaf type {
          description
            "MPLS label type of the last label that was pushed";
          type empty;
        }
      }
      container two {
        description
          "MPLS label 2 information";
        leaf details {
          description
            "MPLS label 2 details";
          type empty;
        }
      }
      container three {
        description
          "MPLS label 3 information";
        leaf details {
          description
            "MPLS label 3 details";
          type empty;
        }
      }
      container four {
        description
          "MPLS label 4 information";
        leaf details {
          description
            "MPLS label 4 details";
          type empty;
        }
      }
      container five {
        description
          "MPLS label 5 information";
        leaf details {
          description
            "MPLS label 5 details";
          type empty;
        }
      }
      container six {
        description
          "MPLS label 6 information";
        leaf details {
          description
            "MPLS label 6 details";
          type empty;
        }
      }
    }
  }

  grouping flow-network-grouping {
    container delay {
      description
        "network delay metrics";
      leaf sample {
        description
          "The number of samples of roundtrip delay";
        type empty;
      }
      leaf sum {
        description
          "The sum of roundtrip delay";
        type empty;
      }
    }
  }

  grouping flow-overlay-grouping {
    container session {
      description
        "Overlay session";
      container id {
        description
          "Overlay session id";
        leaf input {
          description
            "Input overlay session id";
          type empty;
        }
        leaf output {
          description
            "Output overlay session id";
          type empty;
        }
      }
    }
  }

  grouping flow-pfr-grouping {
    container br {
      description
        "PfR br metrics";
      container ipv4 {
        description
          "PfR br IPv4 metrics";
        leaf address {
          description
            "IPv4 address of the PfR Border Router";
          type empty;
        }
      }
    }
    container label {
      description
        "PfR label metrics";
      leaf identifier {
        description
          "pfr label id";
        type empty;
      }
    }
    container one-way-delay {
      description
        "The packet transmission delay between specified nodes";
      leaf samples {
        description
          "Total number of one-way-delay samples";
        type empty;
      }
      leaf sum {
        description
          "The packet transmission delay sum between specified nodes";
        type empty;
      }
    }
    container service {
      description
        "PfR service metrics";
      leaf provider {
        description
          "PfR service provider metrics";
        type empty;
      }
      leaf tag {
        description
          "PfR service provider tag metrics";
        type empty;
      }
      leaf identifier {
        description
          "PfR service provider tag";
        type empty;
      }
    }
    container site {
      description
        "PfR site  metrics";
      container destination {
        description
          "PfR site destination metrics";
        container id {
          description
            "PfR site destination ID metrics";
          leaf ipv4 {
            description
              "site ID of the packet destination";
            type empty;
          }
        }
        container prefix {
          description
            "PfR site prefix of the packet destination";
          leaf ipv4 {
            description
              "site prefix of the packet destination";
            type empty;
          }
          container mask {
            description
              "PfR site prefix mask of the packet destination";
            leaf ipv4 {
              description
                "site prefix mask of the packet destination";
              type empty;
            }
          }
        }
      }
      container source {
        description
          "PfR site source metrics";
        container id {
          description
            "PfR site source ID metrics";
          leaf ipv4 {
            description
              "site ID of the packet source";
            type empty;
          }
        }
        container prefix {
          description
            "PfR site prefix of the packet source";
          leaf ipv4 {
            description
              "site prefix of the packet source";
            type empty;
          }
          container mask {
            description
              "PfR site prefix mask of the packet source";
            leaf ipv4 {
              description
                "site prefix mask of the packet source";
              type empty;
            }
          }
        }
      }
    }
  }

  grouping flow-policy-grouping {
    container performance-monitor {
      description
        "Performance-monitor policy related metrics";
      container classification {
        description
          "Classification metrics";
        leaf hierarchy {
          description
            "Performance-monitor class hierarchy";
          type empty;
        }
      }
    }
    container qos {
      description
        "QoS policy related metrics";
      container classification {
        description
          "Classification metrics";
        leaf hierarchy {
          description
            "QoS class hierarchy";
          type empty;
        }
      }
      container queue {
        description
          "Queue metrics";
        leaf drops {
          description
            "QoS queue drops";
          when '../../../../../collect';
          type empty;
        }
        leaf index {
          description
            "QoS queue index";
          type empty;
        }
      }
    }
  }

  grouping flow-routing-grouping {
    container destination {
      description
        "Destination routing attributes";
      container as {
        description
          "AS number of the destination network";
        presence "true";
        leaf as4-octet {
          description
            "4 octet AS number of the destination network";
          type empty;
        }
        container peer {
          description
            "AS number of the peer network we will forward to";
          presence "true";
          leaf peer4-octet {
            description
              "4 octet AS number of the peer network we will forward to";
            type empty;
          }
        }
      }
      leaf traffic-index {
        description
          "BGP destination traffic index";
        type empty;
      }
    }
    container forwarding-status {
      description
        "Forwarding status of the packet";
      presence "true";
      leaf reason {
        description
          "Forwarding status reason of the packet";
        type empty;
      }
    }
    leaf is-multicast {
      description
        "Indicates if this is multicast";
      type empty;
    }
    container next-hop {
      description
        "Information regarding the next hop";
      container address {
        description
          "IP address of the next hop";
        container ipv4 {
          description
            "IPv4 address of the next hop";
          presence "true";
          leaf bgp {
            description
              "IPv4 address of the BGP next hop";
            type empty;
          }
        }
        container ipv6 {
          description
            "IPv6 address of the next hop";
          presence "true";
          leaf bgp {
            description
              "IPv6 address of the BGP next hop";
            type empty;
          }
        }
      }
    }
    container pw {
      description
        "Pseudowire fields";
      container destination {
        description
          "Pseudowire destination";
        leaf address {
          description
            "Pseudowire destination address";
          type empty;
        }
      }
    }
    container source {
      description
        "Source routing attributes";
      container as {
        description
          "AS number of the original network";
        presence "true";
        leaf as4-octet {
          description
            "4 octet AS number of the original network";
          type empty;
        }
        container peer {
          description
            "AS number of the peer network where the packet came from";
          presence "true";
          leaf peer4-octet {
            description
              "4 octet AS number of the peer network where the packet came from";
            type empty;
          }
        }
      }
      leaf traffic-index {
        description
          "BGP source traffic index";
        type empty;
      }
    }
    container vrf {
      description
        "VRF routing attributes";
      leaf input {
        description
          "VRF ID for incoming packet";
        type empty;
      }
      leaf output {
        description
          "VRF ID for outgoing packet";
        type empty;
      }
      leaf service {
        description
          "VRF ID for service vpn";
        type empty;
      }
    }
  }

  grouping flow-services-grouping {
    container waas {
      description
        "WAAS (Wide Area Application Services) metrics";
      leaf passthrough-reason {
        description
          "WAAS passthrough reason";
        when '../../../../collect';
        type empty;
      }
      container segment {
        description
          "WAAS optimization segment";
        presence "true";
        leaf account-on-resolution {
          description
            "Account on resolution";
          type empty;
        }
      }
    }
  }

  grouping flow-transport-common-grouping {
    leaf destination-port {
      description
        "Transport destination port";
      type empty;
    }
    container icmp {
      description
        "ICMP fields";
      container ipv4 {
        description
          "IPv4 ICMP fields";
        leaf code {
          description
            "IPv4 ICMP code";
          type empty;
        }
        leaf type {
          description
            "IPv4 ICMP type";
          type empty;
        }
      }
      container ipv6 {
        description
          "IPv6 ICMP fields";
        leaf code {
          description
            "IPv6 ICMP code";
          type empty;
        }
        leaf type {
          description
            "IPv6 ICMP type";
          type empty;
        }
      }
    }
    container igmp {
      description
        "IGMP fields";
      leaf type {
        description
          "IGMP type";
        type empty;
      }
    }
    leaf source-port {
      description
        "Transport source port";
      type empty;
    }
    container tcp {
      description
        "TCP fields";
      leaf acknowledgement-number {
        description
          "TCP acknowledgement number";
        type empty;
      }
      leaf destination-port {
        description
          "TCP destination port";
        type empty;
      }
      container flags {
        description
          "TCP flags";
        presence "true";
        leaf ack {
          description
            "TCP acknowledgement flag";
          type empty;
        }
        leaf cwr {
          description
            "TCP congestion window reduced flag";
          type empty;
        }
        leaf ece {
          description
            "TCP ECN echo flag";
          type empty;
        }
        leaf fin {
          description
            "TCP finish flag";
          type empty;
        }
        leaf psh {
          description
            "TCP push flag";
          type empty;
        }
        leaf rst {
          description
            "TCP reset flag";
          type empty;
        }
        leaf syn {
          description
            "TCP synchronise flag";
          type empty;
        }
        leaf urg {
          description
            "TCP urgent flag";
          type empty;
        }
      }
      container flow {
        description
          "TCP flow";
        when '../../../../collect';
        leaf count {
          description
            "Number of tcp flows";
          type empty;
        }
      }
      leaf header-length {
        description
          "TCP header length (in 32 bit words)";
        type empty;
      }
      leaf maximum-segment-size {
        description
          "The maximum size of TCP segment";
        type empty;
      }
      container option {
        description
          "TCP option fields";
        container map {
          description
            "Bitmap of TCP options";
          presence "true";
          leaf long {
            description
              "Extended bitmap of TCP options";
            type empty;
          }
        }
      }
      leaf sequence-number {
        description
          "TCP sequence number";
        type empty;
      }
      leaf source-port {
        description
          "TCP source port";
        type empty;
      }
      leaf urgent-pointer {
        description
          "TCP urgent pointer";
        type empty;
      }
      container window-size {
        description
          "TCP window size";
        presence "true";
        container average {
          description
            "The average size of TCP window";
          presence "true";
          leaf sum {
            description
              "The sum of per flow TCP window average size";
            type empty;
          }
        }
        leaf maximum {
          description
            "The maximum size of TCP window";
          type empty;
        }
        leaf minimum {
          description
            "The minimum size of TCP window";
          type empty;
        }
        leaf sum {
          description
            "The sum of TCP window size";
          type empty;
        }
      }
    }
    container udp {
      description
        "UDP fields";
      leaf destination-port {
        description
          "UDP destination port";
        type empty;
      }
      leaf message-length {
        description
          "UDP message length";
        type empty;
      }
      leaf source-port {
        description
          "UDP source port";
        type empty;
      }
    }
  }

  grouping flow-wireless-grouping {
    container ap {
      description
        "Wireless access point fields";
      container mac {
        description
          "Wireless access point MAC fields";
        leaf address {
          description
            "The MAC address of the wireless access point";
          type empty;
        }
      }
    }
    container client {
      description
        "Wireless client fields";
      container mac {
        description
          "Wireless client MAC fields";
        leaf address {
          description
            "The MAC address of the client on the wireless network";
          type empty;
        }
      }
    }
    leaf ssid {
      description
        "The SSID name identifying the wireless network";
      type empty;
    }
  }

  grouping flow-record-collect-grouping {
    container collect {
      description
        "Specify a non-key field";
      container application {
        description
          "Application fields";
        container cisco-collaboration {
          description
            "Cisco Collaboration Media";
          leaf cisco-collaboration-server-name {
            description
              "Cisco collaboration server name extracted from IP phone configuration";
            type empty;
          }
        }
        container citrix {
          description
            "Citrix Systems Metaframe 3.0";
          leaf citrix-ica-tag {
            description
              "Citrix ICA tag 0-high 1-medium 2-low 3-background";
            type empty;
          }
        }
        container dns {
          description
            "Domain Name Server lookup";
          leaf domain-name {
            description
              "Domain name";
            type empty;
          }
        }
        container first-in-flow {
          description
            "The protocol extracts early first in flow classification";
          leaf fif-cls {
            description
              "First in flow early classification";
            type empty;
          }
          leaf fif-engine-winner {
            description
              "First in flow early classification engine name";
            type empty;
          }
          leaf fif-engines-cls {
            description
              "First in flow early classification per working engine name";
            type empty;
          }
        }
        container http {
          description
            "World Wide Web traffic";
          leaf connection {
            description
              "Connection type";
            type empty;
          }
          leaf host {
            description
              "Host name of Origin Server containing resource";
            type empty;
          }
          leaf referer {
            description
              "Address the resource request was obtained from";
            type empty;
          }
          container uri {
            description
              "List of URIs and associated hit counts";
            leaf statistics {
              description
                "Collect URI statistics";
              type empty;
            }
          }
          leaf url {
            description
              "Uniform Resource Locator path";
            type empty;
          }
          leaf user-agent {
            description
              "Software used by agent sending the request";
            type empty;
          }
        }
        container media {
          description
            "Media fields";
          container bytes {
            description
              "Media fields";
            container counter {
              description
                "A count of the number of bytes of media payload";
              presence "true";
              leaf long {
                description
                  "A count of the number of bytes of media payload (64 bit counter)";
                type empty;
              }
            }
            container rate {
              description
                "Byte rate for the media stream";
              presence "true";
              container per-flow {
                description
                  "Average media byte rate across flows";
                presence "true";
                leaf max {
                  description
                    "Maximum byte rate in the media stream";
                  type empty;
                }
                leaf min {
                  description
                    "Minumun byte rate in the media stream";
                  type empty;
                }
              }
            }
          }
          leaf event {
            description
              "Flags indicating media events";
            type empty;
          }
          container packets {
            description
              "Media fields";
            container counter {
              description
                "A count of the number of packets with a media payload";
              presence "true";
              leaf long {
                description
                  "A count of the number of packets with a media payload (64 bit counter)";
                type empty;
              }
            }
            container rate {
              description
                "Packet rate for the media stream";
              presence "true";
              container variation {
                description
                  "Variation in packet rate from configured expected rate";
                presence "true";
                leaf max {
                  description
                    "Max variation in packet rate from configured expected rate";
                  type empty;
                }
                leaf min {
                  description
                    "Variation in packet rate from configured expected rate";
                  type empty;
                }
                leaf sum {
                  description
                    "The sum of media rate variation from the configured rate for the RTP stream";
                  type empty;
                }
              }
            }
          }
        }
        uses flow-name-grouping;
        container nntp {
          description
            "Network news transfer protocol";
          leaf group-name {
            description
              "NNTP Group name";
            type empty;
          }
        }
        container pop3 {
          description
            "Post Office Protocol 3";
          leaf server {
            description
              "POP3 Server Name";
            type empty;
          }
        }
        container rtmp {
          description
            "Real Time Messaging Protocol";
          leaf pageUrl {
            description
              "RTMP page url address";
            type empty;
          }
        }
        container rtsp {
          description
            "Real Time Streaming Protocol";
          leaf host {
            description
              "RTSP Host Name";
            type empty;
          }
        }
        container sip {
          description
            "Session Initiation Protocol";
          leaf contact {
            description
              "The SIP header contact";
            type empty;
          }
          leaf destination {
            description
              "The destination domain of SIP transactions";
            type empty;
          }
          leaf physical-user {
            description
              "The SIP header physical user";
            type empty;
          }
          leaf server {
            description
              "The SIP header server";
            type empty;
          }
          leaf source {
            description
              "The source domain of SIP transactions";
            type empty;
          }
          leaf user-agent {
            description
              "The SIP header user agent";
            type empty;
          }
          leaf via {
            description
              "The SIP header via";
            type empty;
          }
        }
        container smtp {
          description
            "Simple Mail Transfer Protocol";
          leaf sender {
            description
              "SMTP Sender Mail Address";
            type empty;
          }
          leaf server {
            description
              "SMTP Server Name";
            type empty;
          }
        }
        container ssh {
          description
            "Secure Shell";
          leaf ssh-client-cipher {
            description
              "ssh encryption algorithm client";
            type empty;
          }
          leaf ssh-client-kexAlgorythms {
            description
              "ssh client kex algorithm";
            type empty;
          }
          leaf ssh-client-mac {
            description
              "ssh client mac algorithm client to server";
            type empty;
          }
        }
        container ssl {
          description
            "Secure Socket Layer Protocol";
          leaf common-name {
            description
              "Certificate Common Name (CN)";
            type empty;
          }
          leaf session-id {
            description
              "SSL session ID";
            type empty;
          }
        }
        container tftp {
          description
            "Trivial File Transfer Protocol";
          leaf source-file {
            description
              "Source file name";
            type empty;
          }
        }
        uses flow-vendor-version-grouping;
      }
      container connection {
        description
          "Connection fields";
        container client {
          description
            "Client side (flow initiator) related metrics";
          leaf all {
            description
              "All non-key client metrics";
            type empty;
          }
          container counter {
            description
              "Client side counter metrics";
            container bytes {
              description
                "Number of bytes sent by the client";
              leaf long {
                description
                  "64 bits counter";
                type empty;
              }
              container network {
                description
                  "Number of bytes sent by the client";
                leaf long {
                  description
                    "Total number of bytes transmitted by the client";
                  type empty;
                }
              }
              leaf retransmitted {
                description
                  "Number of bytes retransmitted by the client";
                type empty;
              }
              container transport {
                description
                  "Number of bytes sent by the client";
                leaf long {
                  description
                    "64 bit counter";
                  type empty;
                }
              }
            }
            container packets {
              description
                "Number of packets sent by the client";
              leaf long {
                description
                  "64 bits counter";
                type empty;
              }
              leaf retransmitted {
                description
                  "Number of packets retransmitted by the client";
                type empty;
              }
            }
          }
          uses flow-client-ipv4-ipv6-transport-grouping;
        }
        container delay {
          description
            "Connection delay metrics";
          leaf all {
            description
              "All non-key client metrics";
            type empty;
          }
          container application {
            description
              "Application time metrics";
            leaf max {
              description
                "Maximum application response time";
              type empty;
            }
            leaf min {
              description
                "Minimum application response time";
              type empty;
            }
            leaf sum {
              description
                "Total application response time";
              type empty;
            }
          }
          container network {
            description
              "Network time metrics";
            container client-to-server {
              description
                "RTT between the client and the server";
              leaf max {
                description
                  "Maximum network time";
                type empty;
              }
              leaf min {
                description
                  "Minimum network time";
                type empty;
              }
              leaf num-samples {
                description
                  "The number of CSND samples";
                type empty;
              }
              leaf sum {
                description
                  "Total network time";
                type empty;
              }
            }
            container long-lived {
              description
                "Long-lived network delay metrics";
              container client-to-serve {
                description
                  "Long-lived network delay client-to-server metrics";
                leaf sum {
                  description
                    "Total network time";
                  type empty;
                }
              }
              container to-client {
                description
                  "Long-lived network delay to-client metrics";
                leaf sum {
                  description
                    "Total network time";
                  type empty;
                }
              }
              container to-serve {
                description
                  "Long-lived network delay to-server metrics";
                leaf sum {
                  description
                    "Total network time";
                  type empty;
                }
              }
            }
            container to-client {
              description
                "RTT from observation point to the client";
              leaf max {
                description
                  "Maximum network time";
                type empty;
              }
              leaf min {
                description
                  "Minimum network time";
                type empty;
              }
              leaf num-samples {
                description
                  "The number of CND samples";
                type empty;
              }
              leaf sum {
                description
                  "Total network time";
                type empty;
              }
            }
            container to-server {
              description
                "RTT from observation point to the server";
              leaf max {
                description
                  "Maximum network time";
                type empty;
              }
              leaf min {
                description
                  "Minimum network time";
                type empty;
              }
              leaf num-samples {
                description
                  "The number of SND samples";
                type empty;
              }
              leaf sum {
                description
                  "Total network time";
                type empty;
              }
            }
          }
          container response {
            description
              "Response time metrics";
            container client-to-server {
              description
                "Response time as seen by the client";
              leaf max {
                description
                  "Maximum response time";
                type empty;
              }
              leaf min {
                description
                  "Minimum response time";
                type empty;
              }
              leaf sum {
                description
                  "Total response time";
                type empty;
              }
            }
            container to-server {
              description
                "Response time as seen from observation point";
              leaf histogram {
                description
                  "Histogram for response time";
                type enumeration {
                  enum all;
                  enum bucket1;
                  enum bucket2;
                  enum bucket3;
                  enum bucket4;
                  enum bucket5;
                  enum bucket6;
                  enum bucket7;
                  enum late;
                }
              }
              leaf max {
                description
                  "Maximum response time";
                type empty;
              }
              leaf min {
                description
                  "Minimum response time";
                type empty;
              }
              leaf sum {
                description
                  "Total response time";
                type empty;
              }
            }
          }
        }
        container id {
          description
            "A 32 bit identifier for a connection between client and server";
          presence "true";
          leaf long {
            description
              "A 64 bit identifier for a connection between client and server";
            type empty;
          }
        }
        uses flow-id-initiator-grouping;
        leaf new-connections {
          description
            "The number of connection initiations observed";
          type empty;
        }
        container server {
          description
            "Server side (flow responder) related metrics";
          leaf all {
            description
              "All non-key server metrics";
            type empty;
          }
          container counter {
            description
              "Server side counter metrics";
            container bytes {
              description
                "Number of bytes sent by the server";
              leaf long {
                description
                  "64 bits counter";
                type empty;
              }
              container network {
                description
                  "Number of bytes sent by the server";
                leaf long {
                  description
                    "Total number of bytes transmitted by the server";
                  type empty;
                }
              }
              leaf retransmitted {
                description
                  "Number of bytes retransmitted by the server";
                type empty;
              }
              container transport {
                description
                  "Number of bytes sent by the server";
                leaf long {
                  description
                    "64 bit counter";
                  type empty;
                }
              }
            }
            container packets {
              description
                "Number of packets sent by the server";
              leaf long {
                description
                  "64 bits counter";
                type empty;
              }
              leaf retransmitted {
                description
                  "Number of packets retransmitted by the server";
                type empty;
              }
            }
            leaf responses {
              description
                "Number of responses sent by the server";
              type empty;
            }
          }
          uses flow-server-ipv4-ipv6-transport-grouping;
        }
        leaf sum-duration {
          description
            "The overall time in seconds for all connections";
          type empty;
        }
        container transaction {
          description
            "Transaction related metrics";
          leaf all {
            description
              "All non-key transaction metrics";
            type empty;
          }
          container counter {
            description
              "Transaction counter metrics";
            leaf complete {
              description
                "Number of completed transactions";
              type empty;
            }
          }
          container duration {
            description
              "Transaction duration metrics";
            leaf max {
              description
                "Maximum transaction time";
              type empty;
            }
            leaf min {
              description
                "Minimum transaction time";
              type empty;
            }
            leaf sum {
              description
                "Total transaction time";
              type empty;
            }
          }
        }
        uses flow-transaction-id-grouping;
      }
      container counter {
        description
          "Counter fields";
        container bytes {
          description
            "Total number of bytes";
          presence "true";
          leaf long {
            description
              "Total number of bytes (64 bit counter)";
            type empty;
          }
          container sdwan {
            description
              "SDWAN fields";
            container dropped {
              description
                "SDWAN dropped fields";
              leaf long {
                description
                  "Total number of dropped bytes (64 bit counter)";
                type empty;
              }
            }
          }
          container rate {
            description
              "Byte rate for the flow";
            presence "true";
            container per-flow {
              description
                "Average byte rate for the flow";
              presence "true";
              leaf max {
                description
                  "Maximum byte rate among the aggregated flows";
                type empty;
              }
              leaf min {
                description
                  "Minimum byte rate among the aggregated flows";
                type empty;
              }
            }
          }
          container squared {
            description
              "Total of the square of the number of bytes";
            leaf long {
              description
                "Total of the square of the packet length in bytes (64 bit counter)";
              type empty;
            }
          }
          container layer2 {
            description
              "Total number of layer 2 bytes";
            leaf long {
              description
                "Total number of layer 2 bytes (64 bit counter)";
              type empty;
            }
          }
          container appqoe {
            description
              "AppQoe fields";
            leaf ssl-read {
              description
                "Total number of bytes that were read by SSL";
              type empty;
            }
            leaf ssl-written {
              description
                "Total number of bytes that were written by SSL";
              type empty;
            }
            leaf ssl-en-read {
              description
                "Total number of bytes encrypted and read by ssl";
              type empty;
            }
            leaf ssl-en-written {
              description
                "Total number of bytes encrypted and written by ssl";
              type empty;
            }
            leaf ssl-de-read {
              description
                "Total number of bytes decrypted and read by ssl";
              type empty;
            }
            leaf ssl-de-written {
              description
                "Total number of bytes decrypted and written by ssl";
              type empty;
            }
          }
        }
        leaf flows {
          description
            "Total number of flows";
          type empty;
        }
        container packets {
          description
            "Total number of packets";
          presence "true";
          leaf dropped {
            description
              "Dropped packets";
            type empty;
          }
          leaf long {
            description
              "Total number of packets (64 bit counter)";
            type empty;
          }
          container sdwan {
            description
              "SDWAN fields";
            container dropped {
              description
                "SDWAN dropped fields";
              leaf long {
                description
                  "Total number of dropped packets (64 bit counter)";
                type empty;
              }
            }
            leaf pkt-cxp-d-pkts {
              description
                "Total number of Cloud Express packets (32 bit counter)";
              type empty;
            }
          }
          container appqoe {
            description
              "AppQoe fields";
            leaf fec-d-pkts {
              description
                "Total number of packets subjected to FEC";
              type empty;
            }
            leaf fec-r-pkts {
              description
                "Total number of packets reconstructed by FEC";
              type empty;
            }
            leaf pkt-dup-d-pkts-orig {
              description
                "Total number of Packet Duplicate packets on the original tunnel";
              type empty;
            }
            leaf pkt-dup-d-pkts-dup {
              description
                "Total number of Packet Duplicate packets on the duplicate tunnel";
              type empty;
            }
            leaf pkt-dup-r-pkts {
              description
                "Total number of packets that were recovered by Packet Duplicate";
              type empty;
            }
          }
          container rate {
            description
              "Packet rate for the flow";
            presence "true";
            container per-flow {
              description
                "Average packet rate for aggregated flows";
              presence "true";
              leaf max {
                description
                  "Maximum packet rate in the aggregated flows";
                type empty;
              }
              leaf min {
                description
                  "Minimum packet rate in the aggregated flows";
                type empty;
              }
            }
          }
        }
      }
      container datalink {
        description
          "Datalink (layer2) fields";
        uses flow-datalink-grouping;
      }
      container flow {
        description
          "Flow identifying fields";
        uses flow-flow-common-grouping;
        leaf end-reason {
          description
            "The reason for a flow ending";
          type empty;
        }
      }
      container interface {
        description
          "Interface fields";
        uses flow-interface-grouping;
      }
      container ipv4 {
        description
          "IPv4 fields";
        uses flow-ipv4-grouping;
      }
      container ipv6 {
        description
          "IPv6 fields";
        uses flow-ipv6-grouping;
      }
      container metadata {
        description
          "Metadata fields";
        leaf clock-rate {
          description
            "Metadata clock-rate";
          type empty;
        }
        leaf global-session-id {
          description
            "Metadata global-session-id";
          type empty;
        }
        leaf multi-party-session-id {
          description
            "Metadata multi-party-session-id";
          type empty;
        }
      }
      container monitor {
        description
          "monitor fields";
        leaf event {
          description
            "Flags indicating monitor events";
          type empty;
        }
      }
      container mpls {
        description
          "MPLS fields";
        uses flow-mpls-grouping;
      }
      container network {
        description
          "network metrics";
        uses flow-network-grouping;
      }
      container overlay {
        description
          "Overlay network";
        uses flow-overlay-grouping;
      }
      container pfr {
        description
          "PfR metrics";
        uses flow-pfr-grouping;
      }
      container policy {
        description
          "policy fields";
        uses flow-policy-grouping;
      }
      container routing {
        description
          "Routing attributes";
        uses flow-routing-grouping;
      }
      container services {
        description
          "Services fields";
        uses flow-services-grouping;
      }
      container timestamp {
        description
          "Timestamp fields";
        container absolute {
          description
            "Timestamps based on the epoch of 00:00 UTC 1st Jan 1970";
          leaf first {
            description
              "Absolute time the first packet was seen (milliseconds)";
            type empty;
          }
          leaf last {
            description
              "Absolute time the most recent packet was seen (milliseconds)";
            type empty;
          }
          container monitoring-interval {
            description
              "Monitoring interval timestamps";
            leaf end {
              description
                "Absolute end time of a monitoring interval (milliseconds)";
              type empty;
            }
            leaf start {
              description
                "Absolute start time of a monitoring interval (milliseconds)";
              type empty;
            }
          }
        }
        leaf interval {
          description
            "Epoch of a monitoring interval";
          type empty;
        }
        container sys-uptime {
          description
            "Timestamps based on the sys-uptime";
          leaf first {
            description
              "Time the first packet was seen";
            type empty;
          }
          leaf last {
            description
              "Time the most recent packet was seen";
            type empty;
          }
        }
      }
      container transport {
        description
          "Transport layer fields";
        container bytes {
          description
            "Bytes fields";
          leaf expected {
            description
              "Transport bytes expected";
            type empty;
          }
          container lost {
            description
              "Transport bytes lost";
            presence "true";
            leaf rate {
              description
                "Transport bytes lost rate";
              type empty;
            }
          }
          leaf out-of-order {
            description
              "Total number of out-of-order bytes";
            type empty;
          }
        }
        uses flow-transport-common-grouping;
        container event {
          description
            "Transport event fields";
          container packet-loss {
            description
              "Transport event packet-loss fields";
            container counter {
              description
                "Count of sets of packets that were lost";
              presence "true";
              leaf max {
                description
                  "Highest packet loss counter when multiple flows are aggregated";
                type empty;
              }
              leaf min {
                description
                  "Lowest packet loss counter when multiple flows are aggregated";
                type empty;
              }
            }
          }
        }
        container packets {
          description
            "Transport packet fields";
          container expected {
            description
              "Transport packets expected fields";
            leaf counter {
              description
                "Expected number of packets from sequencing information";
              type empty;
            }
          }
          container lost {
            description
              "Transport packets lost fields";
            container counter {
              description
                "A count of the number of lost packets from sequencing information";
              presence "true";
              leaf max {
                description
                  "Highest lost packet count seen among the aggregated flows";
                type empty;
              }
              leaf min {
                description
                  "Lowest lost packet count seen among the aggregated flows";
                type empty;
              }
            }
            container rate {
              description
                "Packet loss rate from sequencing information";
              presence "true";
              leaf max {
                description
                  "Maximum packet loss rate in the aggregated flows";
                type empty;
              }
              leaf min {
                description
                  "Minimum packet loss rate in the aggregated flows";
                type empty;
              }
            }
          }
          leaf out-of-order {
            description
              "Total number of out-of-order bytes";
            type empty;
          }
        }
        container round-trip-time {
          description
            "RTT calculation for flow";
          presence "true";
          leaf max {
            description
              "Highest RTT among all flows";
            type empty;
          }
          leaf min {
            description
              "Lowest RTT among all flows";
            type empty;
          }
          leaf samples {
            description
              "RTT samples";
            type empty;
          }
          leaf sum {
            description
              "Sum RTT for all flows";
            type empty;
          }
        }
        container rtp {
          description
            "RTP fields";
          container flow {
            description
              "RTP  flow";
            leaf count {
              description
                "Number of RTP flows";
              type empty;
            }
          }
          container jitter {
            description
              "RTP jitter fields";
            leaf maximum {
              description
                "Maximum jitter for the RTP stream";
              type empty;
            }
            container mean {
              description
                "Mean jitter for the RTP stream";
              presence "true";
              leaf sum {
                description
                  "The sum of jitter mean for the RTP stream";
                type empty;
              }
            }
            leaf minimum {
              description
                "Minimum jitter for the RTP stream";
              type empty;
            }
          }
          leaf payload-type {
            description
              "RTP payload type";
            type empty;
          }
          leaf ssrc {
            description
              "RTP SSRC";
            type empty;
          }
        }
      }
      container wireless {
        description
          "Wireless fields";
        uses flow-wireless-grouping;
      }
      container drop {
        description
          "Drop fields";
        container cause {
          description
            "Drop cause fields";
          leaf id {
            description
              "Drop cause id in dataplane";
            type empty;
          }
        }
      }
      container sdwan {
        description
          "SDWAN fields";
        leaf sla-not-met {
          description
            "Sla is met or not";
          type empty;
        }
        leaf preferred-color-not-met {
          description
            "Preferred color in dataplane is met or not";
          type empty;
        }
        leaf qos-queue-id {
          description
            "SDWAN queue id";
          type empty;
        }
        leaf traffic-category {
          description
            "The type of traffic category";
          type empty;
        }
        leaf service-area {
          description
            "The type of service area";
          type empty;
        }
        leaf cxp-path-type {
          description
            "The type of Cloud SaaS path type";
          type empty;
        }
        leaf region-id {
          description
            "Region ID Fields";
          type empty;
        }
        leaf remote-access-flags {
          description
            "Indicate Remote Access Fields";
          type empty;
        }
      }
      container appqoe {
        description
          "AppQoe Fields";
        container ssl {
          description
            "AppQoe SSL fields";
          container service {
            description
              "AppQoe SSL Service fields";
            leaf type {
              description
                "AppQoe SSL Service Type";
              type empty;
            }
          }
          container traffic {
            description
              "AppQoe SSL Traffic fields";
            leaf type {
              description
                "AppQoe SSL Traffic Type";
              type empty;
            }
          }
          container policy {
            description
              "AppQoe SSL Policy fields";
            leaf action {
              description
                "AppQoe SSL Policy Action";
              type empty;
            }
          }
        }
        leaf action {
          description
            "AppQoe Action for AppQoe Multi-SN";
          type empty;
        }
        leaf sn-ip {
          description
            "AppQoe Sn-ip for AppQoe Multi-SN";
          type empty;
        }
        leaf pass-reason {
          description
            "AppQoe Pass Reason for AppQoe Multi-SN";
          type empty;
        }
        leaf dre-input-bytes {
          description
            "AppQoe Input Bytes for Data Redundancy Elimination";
          type empty;
        }
        leaf dre-input-packets {
          description
            "AppQoe Input Packets for Data Redundancy Elimination";
          type empty;
        }
        leaf flags {
          description
            "AppQoe Flags";
          type empty;
        }
      }
      container ulogging {
        description
          "Unified Logging Fields";
        leaf fw-zp-id {
          description
            "firewall zone pair id";
          type empty;
        }
        leaf fw-user-name {
          description
            "firewall user name";
          type empty;
        }
        leaf fw-zone-id-array {
          description
            "firewall src/dst zone id";
          type empty;
        }
        leaf fw-class-id {
          description
            "firewall class id";
          type empty;
        }
        leaf fw-policy-id {
          description
            "firewall policy id";
          type empty;
        }
        leaf fw-proto-id {
          description
            "firewall protocol id";
          type empty;
        }
        leaf fw-action {
          description
            "firewall action id";
          type empty;
        }
        leaf fw-drop-reason-id {
          description
            "firewall drop reason id";
          type empty;
        }
        leaf fw-end-flow-reason {
          description
            "firewall end flow reason id";
          type empty;
        }
        leaf fw-src-ipv4-addr-translated {
          description
            "firewall nat translated ipv4 source address";
          type empty;
        }
        leaf fw-dst-ipv4-addr-translated {
          description
            "firewall nat translated ipv4 destination address";
          type empty;
        }
        leaf fw-src-port-translated {
          description
            "firewall nat translated source port overlord";
          type empty;
        }
        leaf fw-dst-port-translated {
          description
            "firewall nat translated destination port overload";
          type empty;
        }
        leaf utd-policy-id-array {
          description
            "utd policy ids list";
          type empty;
        }
        leaf utd-action-id-array {
          description
            "utd action id array";
          type empty;
        }
        leaf utd-ips-policy-id {
          description
            "utd ips policy id";
          type empty;
        }
        leaf utd-ips-action-id {
          description
            "utd ips action id";
          type empty;
        }
        leaf utd-ips-pri {
          description
            "utd ips pri id";
          type empty;
        }
        leaf utd-ips-sid {
          description
            "utd ips sid";
          type empty;
        }
        leaf utd-ips-gid {
          description
            "utd ips group id";
          type empty;
        }
        leaf utd-ips-cid {
          description
            "utd ips cid";
          type empty;
        }
        leaf utd-urlf-policy-id {
          description
            "utd urlf policy id";
          type empty;
        }
        leaf utd-urlf-action-id {
          description
            "utd urlf action id";
          type empty;
        }
        leaf utd-urlf-url-hash {
          description
            "utd urlf url hash value";
          type empty;
        }
        leaf utd-urlf-url-category {
          description
            "utd urlf url category";
          type empty;
        }
        leaf utd-urlf-url-reputation {
          description
            "utd urlf url reputation";
          type empty;
        }
        leaf utd-urlf-app-name {
          description
            "utd urlf application name";
          type empty;
        }
        leaf utd-urlf-reason-id {
          description
            "utd urlf reason id";
          type empty;
        }
        leaf utd-amp-policy-id {
          description
            "utd amp policy id";
          type empty;
        }
        leaf utd-amp-action-id {
          description
            "utd amp action id";
          type empty;
        }
        leaf utd-amp-dispos {
          description
            "utd amp disposition id";
          type empty;
        }
        leaf utd-amp-filename-hash {
          description
            "utd amp filename hash value";
          type empty;
        }
        leaf utd-amp-file-type {
          description
            "utd amp file type";
          type empty;
        }
        leaf utd-amp-file-hash {
          description
            "utd amp file hash value";
          type empty;
        }
        leaf utd-amp-malname-hash {
          description
            "utd amp malicious software name hash value";
          type empty;
        }
        leaf utd-drop-reason-id {
          description
            "utd drop reason id";
          type empty;
        }
        leaf sdvt-drop-reason-id {
          description
            "service divert drop reason id";
          type empty;
        }
        leaf flow-direction {
          description
            "Direction the flow was monitored in";
          type empty;
        }
      }
    }
    container drop {
      description
        "Drop fields";
      container cause {
        description
          "Drop fields";
        leaf id {
          description
            "Drop cause id in dataplane";
          type empty;
        }
      }
    }
    container sdwan {
      description
        "SDWAN fields";
      leaf sla-not-met {
        description
          "Sla is met or not";
        type empty;
      }
      leaf preferred-color-not-met {
        description
          "Preferred color in dataplane is met or not";
        type empty;
      }
      leaf qos-queue-id {
        description
          "Queue id";
        type empty;
      }
      leaf traffic-category {
        description
          "The type of traffic category";
        type empty;
      }
    }
    container appqoe {
      description
        "AppQoe Fields";
      container ssl {
        description
          "AppQoe SSL fields";
        container service {
          description
            "AppQoe SSL Service fields";
          leaf type {
            description
              "AppQoe SSL Service Type";
            type empty;
          }
        }
        container traffic {
          description
            "AppQoe SSL Traffic fields";
          leaf type {
            description
              "AppQoe SSL Traffic Type";
            type empty;
          }
        }
        container policy {
          description
            "AppQoe SSL Policy fields";
          leaf action {
            description
              "AppQoe SSL Policy Action";
            type empty;
          }
        }
      }
      leaf action {
        description
          "AppQoe Action for AppQoe Multi-SN";
        type empty;
      }
      leaf sn-ip {
        description
          "AppQoe Sn-ip for AppQoe Multi-SN";
        type empty;
      }
      leaf pass-reason {
        description
          "AppQoe Pass Reason for AppQoe Multi-SN";
        type empty;
      }
      container ulogging {
        description
          "Unified Logging Fields";
        leaf fw-zp-id {
          description
            "firewall zone pair id";
          type empty;
        }
        leaf fw-user-name {
          description
            "firewall user name";
          type empty;
        }
        leaf fw-zone-id-array {
          description
            "firewall src/dst zone id";
          type empty;
        }
        leaf fw-class-id {
          description
            "firewall class id";
          type empty;
        }
        leaf fw-policy-id {
          description
            "firewall policy id";
          type empty;
        }
        leaf fw-proto-id {
          description
            "firewall protocol id";
          type empty;
        }
        leaf fw-action {
          description
            "firewall action id";
          type empty;
        }
        leaf fw-drop-reason-id {
          description
            "firewall drop reason id";
          type empty;
        }
        leaf fw-end-flow-reason {
          description
            "firewall end flow reason id";
          type empty;
        }
        leaf fw-src-ipv4-addr-translated {
          description
            "firewall nat translated ipv4 source address";
          type empty;
        }
        leaf fw-dst-ipv4-addr-translated {
          description
            "firewall nat translated ipv4 destination address";
          type empty;
        }
        leaf fw-src-port-translated {
          description
            "firewall nat translated source port overlord";
          type empty;
        }
        leaf fw-dst-port-translated {
          description
            "firewall nat translated destination port overload";
          type empty;
        }
        leaf utd-policy-id-array {
          description
            "utd policy ids list";
          type empty;
        }
        leaf utd-action-id-array {
          description
            "utd action id array";
          type empty;
        }
        leaf utd-ips-pri {
          description
            "utd ips pri id";
          type empty;
        }
        leaf utd-ips-sid {
          description
            "utd ips sid";
          type empty;
        }
        leaf utd-ips-gid {
          description
            "utd ips group id";
          type empty;
        }
        leaf utd-ips-cid {
          description
            "utd ips cid";
          type empty;
        }
        leaf utd-urlf-url-hash {
          description
            "utd urlf url hash value";
          type empty;
        }
        leaf utd-urlf-url-category {
          description
            "utd urlf url category";
          type empty;
        }
        leaf utd-urlf-url-reputation {
          description
            "utd urlf url reputation";
          type empty;
        }
        leaf utd-urlf-app-name {
          description
            "utd urlf application name";
          type empty;
        }
        leaf utd-amp-dispos {
          description
            "utd amp disposition id";
          type empty;
        }
        leaf utd-amp-filename-hash {
          description
            "utd amp filename hash value";
          type empty;
        }
        leaf utd-amp-file-type {
          description
            "utd amp file type";
          type empty;
        }
        leaf utd-amp-file-hash {
          description
            "utd amp file hash value";
          type empty;
        }
        leaf utd-amp-malname-hash {
          description
            "utd amp malicious software name hash value";
          type empty;
        }
        leaf utd-drop-reason-id {
          description
            "utd drop reason id";
          type empty;
        }
        leaf sdvt-drop-reason-id {
          description
            "service divert drop reason id";
          type empty;
        }
      }
    }
  }

  grouping flow-record-match-grouping {
    container match {
      description
        "Specify a key field";
      container application {
        description
          "Application fields";
        uses flow-name-grouping;
        uses flow-vendor-version-grouping;
      }
      container connection {
        description
          "Connection fields";
        container client {
          description
            "Client side (flow initiator) related metrics";
          uses flow-client-ipv4-ipv6-transport-grouping;
        }
        leaf id {
          description
            "A 32 bit identifier for a connection between client and server";
          type empty;
        }
        uses flow-id-initiator-grouping;
        container server {
          description
            "Server side (flow responder) related metrics";
          uses flow-server-ipv4-ipv6-transport-grouping;
        }
        uses flow-transaction-id-grouping;
      }
      container datalink {
        description
          "Datalink (layer2) fields";
        uses flow-datalink-grouping;
      }
      container flow {
        description
          "Flow identifying fields";
        uses flow-flow-common-grouping;
      }
      container interface {
        description
          "Interface fields";
        uses flow-interface-grouping;
      }
      container ipv4 {
        description
          "IPv4 fields";
        uses flow-ipv4-grouping;
      }
      container ipv6 {
        description
          "IPv6 fields";
        uses flow-ipv6-grouping;
      }
      container metadata {
        description
          "Metadata fields";
        leaf global-session-id {
          description
            "Metadata global-session-id";
          type empty;
        }
        leaf multi-party-session-id {
          description
            "Metadata multi-party-session-id";
          type empty;
        }
      }
      container mpls {
        description
          "MPLS fields";
        uses flow-mpls-grouping;
      }
      container network {
        description
          "network metrics";
        uses flow-network-grouping;
      }
      container overlay {
        description
          "Overlay network";
        uses flow-overlay-grouping;
      }
      container pfr {
        description
          "PfR metrics";
        uses flow-pfr-grouping;
      }
      container policy {
        description
          "policy fields";
        uses flow-policy-grouping;
      }
      container routing {
        description
          "Routing attributes";
        uses flow-routing-grouping;
      }
      container services {
        description
          "Services fields";
        uses flow-services-grouping;
      }
      container timestamp {
        description
          "Timestamp fields";
        container absolute {
          description
            "Timestamps based on the epoch of 00:00 UTC 1st Jan 1970";
          container monitoring-interval {
            description
              "Monitoring interval timestamps";
            leaf start {
              description
                "Absolute start time of a monitoring interval (milliseconds)";
              type empty;
            }
          }
        }
      }
      container transport {
        description
          "Transport layer fields";
        container bytes {
          description
            "Bytes fields";
          leaf expected {
            description
              "Transport bytes expected";
            type empty;
          }
          container lost {
            description
              "Transport bytes lost";
            presence "true";
            leaf rate {
              description
                "Transport bytes lost rate";
              type empty;
            }
          }
        }
        container rtp {
          description
            "RTP fields";
          leaf ssrc {
            description
              "RTP SSRC";
            type empty;
          }
        }
        uses flow-transport-common-grouping;
      }
      container vxlan {
        description
          "VXLAN fields";
        leaf flags {
          description
            "VXLAN flag field";
          type empty;
        }
        leaf sgt {
          description
            "VXLAN segment field";
          type empty;
        }
        leaf vnid {
          description
            "vxlan vnid field";
          type empty;
        }
      }
      container wireless {
        description
          "Wireless fields";
        uses flow-wireless-grouping;
      }
    }
  }

  grouping flow-monitor-record-netflow-grouping {
    container as {
      description
        "AS aggregation schemes";
      presence "true";
      leaf peer {
        description
          "AS aggregation scheme with peer ASs";
        type empty;
      }
    }
    container destination-prefix {
      description
        "Destination Prefix aggregation schemes";
      presence "true";
      leaf peer {
        description
          "Destination Prefix aggregation scheme with peer AS";
        type empty;
      }
    }
    container original-input {
      description
        "Traditional IPv6 input NetFlow with ASs";
      presence "true";
      leaf peer {
        description
          "Traditional IPv6 input NetFlow with peer ASs";
        type empty;
      }
    }
    container original-output {
      description
        "Traditional IPv6 output NetFlow with ASs";
      presence "true";
      leaf peer {
        description
          "Traditional IPv6 output NetFlow with peer ASs";
        type empty;
      }
    }
    container prefix {
      description
        "Source and Destination Prefixes aggregation schemes";
      presence "true";
      leaf peer {
        description
          "Source and Destination Prefixes aggregation scheme with peer ASs";
        type empty;
      }
    }
    leaf protocol-port {
      description
        "Protocol and Ports aggregation scheme";
      type empty;
    }
    container source-prefix {
      description
        "Source AS and Prefix aggregation schemes";
      presence "true";
      leaf peer {
        description
          "Source AS and Prefix aggregation scheme with peer AS";
        type empty;
      }
    }
  }

  grouping flow-monitor-grouping {
    leaf accessTunnel {
      description
        "Filter traffic from access tunnel";
      if-feature "ios-features:switching-platform";
      type empty;
    }
    container cache {
      description
        "Monitor cache entries";
      leaf entries {
        description
          "Number of cache entries";
        type uint32 {
          range "16..2000000";
        }
      }
      container timeout {
        description
          "Cache timeout";
        leaf active {
          description
            "Active timeout";
          type uint32 {
            range "1..604800";
          }
        }
        container event {
          description
            "Timeout event";
          leaf transaction-end {
            description
              "Transaction-end event";
            type empty;
          }
        }
        leaf inactive {
          description
            "Inactive timeout";
          type uint32 {
            range "1..604800";
          }
        }
        leaf synchronized {
          description
            "Synchronized timeout";
          type uint32 {
            range "1..86400";
          }
        }
        leaf update {
          description
            "Update timeout";
          type uint32 {
            range "1..604800";
          }
        }
      }
      leaf type {
        description
          "Cache type";
        type enumeration {
          enum immediate;
          enum normal;
          enum permanent;
          enum synchronized;
        }
      }
    }
    leaf description {
      description
        "Provide a description for this Flow Monitor";
      type string;
    }
    list exporter {
      description
        "Add an Exporter to use to export records";
      key "name";
      leaf name {
        type flow-name;
      }
    }
    container history {
      description
        "Monitor history intervals";
      leaf size {
        description
          "History size";
        type uint8 {
          range "0..60";
        }
      }
      leaf timeout {
        description
          "Specify timeout interval";
        type uint8 {
          range "1..30";
        }
      }
    }
    container record {
      description
        "Specify Flow Record to use to define Cache";
      leaf type {
        type union {
          type enumeration {
            enum default-rtp;
            enum default-tcp;
            enum netflow-original;
          }
          type flow-name;
        }
      }
      container netflow {
        description
          "Traditional NetFlow collection schemes";
        container ipv4 {
          description
            "Traditional IPv4 NetFlow collection schemes";
          uses flow-monitor-record-netflow-grouping;
          container as-tos {
            description
              "AS and TOS aggregation schemes";
            presence "true";
            leaf peer {
              description
                "AS and TOS aggregation scheme with peer ASs";
              type empty;
            }
          }
          leaf assurance {
            description
              "Assurance metrics";
            type empty;
          }
          leaf assurance-rtp {
            description
              "Assurance rtp metrics";
            type empty;
          }
          leaf assurance-dns {
            description
              "Assurance DNS metrics";
            type empty;
          }
          leaf assurance-dhcp {
            description
              "Assurance DHCP metrics";
            type empty;
          }
          container bgp-nexthop-tos {
            description
              "BGP next-hop and TOS aggregation schemes";
            presence "true";
            leaf peer {
              description
                "BGP next-hop and TOS aggregation scheme with peer ASs";
              type empty;
            }
          }
          container destination-prefix-tos {
            description
              "Destination Prefix and TOS  aggregation schemes";
            presence "true";
            leaf peer {
              description
                "Destination Prefix and TOS aggregation scheme with peer AS";
              type empty;
            }
          }
          leaf prefix-port {
            description
              "Prefixes and Ports aggregation scheme";
            type empty;
          }
          container prefix-tos {
            description
              "Prefixes and TOS aggregation schemes";
            presence "true";
            leaf peer {
              description
                "Prefixes and TOS aggregation scheme with peer ASs";
              type empty;
            }
          }
          leaf protocol-port-tos {
            description
              "Protocol, Ports and TOS aggregation scheme";
            type empty;
          }
          container source-prefix-tos {
            description
              "Source Prefix and TOS aggregation schemes";
            presence "true";
            leaf peer {
              description
                "Source Prefix and TOS aggregation scheme with peer AS";
              type empty;
            }
          }
          leaf app-client-server-stats {
            description
              "Application client server statistics";
            if-feature "ios-features:switching-platform";
            type empty;
          }
          leaf app-client-server-trans-stats {
            description
              "Application client server transaction";
            if-feature "ios-features:switching-platform";
            type empty;
          }
          leaf app-stats-input {
            description
              "Application statistics - input";
            if-feature "ios-features:switching-platform";
            type empty;
          }
          leaf app-stats-output {
            description
              "Application statistics - output";
            if-feature "ios-features:switching-platform";
            type empty;
          }
        }
        container ipv6 {
          description
            "Traditional IPv6 NetFlow collection schemes";
          uses flow-monitor-record-netflow-grouping;
          container bgp-nexthop {
            description
              "BGP next-hop aggregation schemes";
            presence "true";
            leaf peer {
              description
                "BGP next-hop aggregation scheme with peer ASs";
              type empty;
            }
          }
          leaf assurance {
            description
              "Assurance metrics";
            type empty;
          }
          leaf assurance-rtp {
            description
              "Assurance rtp metrics";
            type empty;
          }
          leaf assurance-dns {
            description
              "Assurance DNS metrics";
            type empty;
          }
          leaf assurance-dhcp {
            description
              "Assurance DHCP metrics";
            type empty;
          }
        }
      }
      container wireless {
        description
          "Templates for wireless traffics";
        container avc {
          description
            "Schemas for Application Visibility Control";
          choice template-choice {
            leaf basic {
              type empty;
            }
            container ipv4 {
              leaf assurance {
                description
                  "Assurance metrics";
                type empty;
              }
              leaf assurance-rtp {
                description
                  "Assurance rtp metrics";
                type empty;
              }
              leaf assurance-dns {
                description
                  "Assurance DNS metrics";
                type empty;
              }
              leaf assurance-dhcp {
                description
                  "Assurance DHCP metrics";
                type empty;
              }
              leaf basic {
                type empty;
              }
            }
            container ipv6 {
              leaf assurance {
                description
                  "Assurance metrics";
                type empty;
              }
              leaf assurance-rtp {
                description
                  "Assurance rtp metrics";
                type empty;
              }
              leaf assurance-dns {
                description
                  "Assurance DNS metrics";
                type empty;
              }
              leaf assurance-dhcp {
                description
                  "Assurance DHCP metrics";
                type empty;
              }
              leaf basic {
                type empty;
              }
            }
            leaf statistics {
              type empty;
            }
          }
        }
      }
    }
    leaf skipouter {
      description
        "Skip the outer header information";
      if-feature "ios-features:switching-platform";
      type empty;
    }
    container statistics {
      description
        "Collect statistics";
      container packet {
        description
          "Collect packet statistics";
        leaf protocol {
          description
            "Collect packet protocol distribution statistics";
          type empty;
        }
        leaf size {
          description
            "Collect packet size distribution statistics";
          type empty;
        }
      }
    }
    container collect {
      description
        "Collect tloc loopback interface";
      container tloc {
        description
          "Collect SDWAN tloc loopback interface";
        leaf loopback {
          description
            "Collect SDWAN tloc loopback interface instead of physical interface";
          default "false";
          type boolean;
        }
      }
    }
  }

  grouping flow-default-monitor-grouping {
    container cache {
      description
        "Monitor cache entries";
      leaf entries {
        description
          "Maximum flow entries in the Flow Cache";
        type empty;
      }
      container timeout {
        description
          "Configure flow cache timeout parameters";
        leaf active {
          description
            "Specify the active flow timeout";
          type empty;
        }
        container event {
          description
            "Event-based export";
          leaf transaction-end {
            description
              "Export on transaction end event";
            type empty;
          }
        }
        leaf inactive {
          description
            "Specify the inactive flow timeout";
          type empty;
        }
        leaf synchronized {
          description
            "Specify the timeout for a synchronized Flow Cache";
          type empty;
        }
        leaf update {
          description
            "Specify the update timeout for a permanent Flow Cache";
          type empty;
        }
      }
      leaf type {
        description
          "Set the type of the Flow Cache";
        type empty;
      }
    }
    leaf description {
      description
        "Provide a description for this Flow Monitor";
      type empty;
    }
    leaf exporter {
      description
        "Add an Exporter to use to export records";
      type empty;
    }
    leaf record {
      description
        "Specify Flow Record to use to define Cache";
      type empty;
    }
    container statistics {
      description
        "Collect statistics";
      container packet {
        description
          "Collect packet statistics";
        leaf protocol {
          description
            "Collect packet protocol distribution statistics";
          type empty;
        }
        leaf size {
          description
            "Collect packet size distribution statistics";
          type empty;
        }
      }
    }
    container collect {
      description
        "Collect tloc loopback interface";
      container tloc {
        description
          "Collect SDWAN tloc loopback interface";
        leaf loopback {
          description
            "Collect SDWAN tloc loopback interface instead of physical interface";
          default "false";
          type boolean;
        }
      }
    }
  }

  grouping flow-exporter-option-timeout-grouping {
    leaf timeout {
      description
        "Option resend time";
      type uint32 {
        range "1..86400";
      }
    }
    leaf export-spread {
      description
        "Export spread time";
      type uint32 {
        range "1..86400";
      }
    }
  }

  grouping flow-exporter-grouping {
    leaf description {
      description
        "Provide a description for this Flow Exporter";
      type string;
    }
    container destination {
      description
        "Export destination configuration";
      choice destination-choice {
        container ipdest {
          leaf ip {
            type inet:ip-address;
          }
          leaf vrf {
            description
              "Optional VRF label";
            type string;
          }
        }
        container local {
          description
            "Export to a local collector";
          leaf wlc {
            description
              "WLC local collector";
            type empty;
          }
          leaf sdwan {
            if-feature "ios-features:sdwan";
            description
              "SDWAN local collector";
            type empty;
          }
          leaf controller {
            if-feature "ios-features:routing-platform";
            description
              "SD-routing local collector";
            type empty;
          }
          container file-export {
            description
              "File export using 'flow file-export default' configuration";
            leaf default {
              description
                "Default File Export";
              type empty;
            }
          }
        }
      }
    }
    leaf dscp {
      description
        "Optional DSCP";
      type uint8 {
        range "0..63";
      }
    }
    leaf export-protocol {
      description
        "Export protocol version";
      type enumeration {
        enum ipfix;
        enum netflow-v5;
        enum netflow-v9;
      }
      default "netflow-v9";
    }
    leaf mtu {
      description
        "Optional MTU";
      type uint16 {
        range "1..65535";
      }
    }
    container option {
      description
        "Select an option for exporting";
      container application-attributes {
        description
          "Application Attributes Table Option";
        presence "true";
        uses flow-exporter-option-timeout-grouping;
      }
      container application-table {
        description
          "Application Table Option";
        presence "true";
        uses flow-exporter-option-timeout-grouping;
      }
      container c3pl-class-table {
        description
          "C3PL class cce-id table";
        presence "true";
        uses flow-exporter-option-timeout-grouping;
      }
      container c3pl-policy-table {
        description
          "C3PL policy cce-id table";
        presence "true";
        uses flow-exporter-option-timeout-grouping;
      }
      container exporter-stats {
        description
          "Exporter Statistics Option";
        presence "true";
        uses flow-exporter-option-timeout-grouping;
      }
      container interface-table {
        description
          "Interface SNMP-index-to-name Table Option";
        presence "true";
        uses flow-exporter-option-timeout-grouping;
      }
      container metadata-version-table {
        description
          "Metadata Version Table Option";
        presence "true";
        uses flow-exporter-option-timeout-grouping;
      }
      container sampler-table {
        description
          "Export Sampler Option";
        presence "true";
        uses flow-exporter-option-timeout-grouping;
      }
      container sub-application-table {
        description
          "Sub Application Table Option";
        presence "true";
        uses flow-exporter-option-timeout-grouping;
      }
      container vrf-attributes {
        description
          "VRF Attributes Table Option";
        presence "true";
        uses flow-exporter-option-timeout-grouping;
      }
      container vrf-table {
        description
          "VRF ID-to-name Table Option";
        presence "true";
        uses flow-exporter-option-timeout-grouping;
      }
      container tunnel-tloc-table {
        description
          "tunnel-to-tloc Table Option";
        presence "true";
        uses flow-exporter-option-timeout-grouping;
      }
      container ssid-table {
        description
          "SSID ID-to-name Table Option";
        presence "true";
        uses flow-exporter-option-timeout-grouping;
      }
      container drop-cause-table {
        description
          "Drop Cause Table Option";
        presence "true";
        uses flow-exporter-option-timeout-grouping;
      }
      container fw-drop-reason-table {
        description
          "Firewall drop reason table";
        presence "true";
        uses flow-exporter-option-timeout-grouping;
      }
      container fw-proto-table {
        description
          "Firewall protocol table";
        presence "true";
        uses flow-exporter-option-timeout-grouping;
      }
      container fw-zone-table {
        description
          "Firewall zone id to name mapping table";
        presence "true";
        uses flow-exporter-option-timeout-grouping;
      }
      container fw-zone-pair-table {
        description
          "Firewall zone-pair id to name mapping table";
        presence "true";
        uses flow-exporter-option-timeout-grouping;
      }
      container fw-action-table {
        description
          "Firewall action to name mapping table";
        presence "true";
        uses flow-exporter-option-timeout-grouping;
      }
      container fw-end-flow-reason-table {
        description
          "Firewall end flow reason to name mapping table";
        presence "true";
        uses flow-exporter-option-timeout-grouping;
      }
      container utd-policy-table {
        description
          "Utd Policy name Table Option";
        presence "true";
        uses flow-exporter-option-timeout-grouping;
      }
      container utd-file-type-table {
        description
          "Utd Amp File Type Table Option";
        presence "true";
        uses flow-exporter-option-timeout-grouping;
      }
      container utd-category-table {
        description
          "Utd Url Category Table Option";
        presence "true";
        uses flow-exporter-option-timeout-grouping;
      }
      container utd-urlf-reason-table {
        description
          "Utd Url Reason Table Option";
        presence "true";
        uses flow-exporter-option-timeout-grouping;
      }
      container utd-action-table {
        description
          "Utd Action Table Option";
        presence "true";
        uses flow-exporter-option-timeout-grouping;
      }
      container utd-disposition-table {
        description
          "Utd Disposition Table Option";
        presence "true";
        uses flow-exporter-option-timeout-grouping;
      }
      container utd-url-table {
        description
          "Utd URL Table Option";
        presence "true";
        uses flow-exporter-option-timeout-grouping;
      }
      container utd-filename-table {
        description
          "Utd Filename Table Option";
        presence "true";
        uses flow-exporter-option-timeout-grouping;
      }
      container utd-malware-table {
        description
          "Utd malicious software name Table Option";
        presence "true";
        uses flow-exporter-option-timeout-grouping;
      }
      container utd-drop-reason-table {
        description
          "Utd Drop reason Table Option";
        presence "true";
        uses flow-exporter-option-timeout-grouping;
      }
      container sdvt-drop-reason-table {
        description
          "Service divert Drop reason Table Option";
        presence "true";
        uses flow-exporter-option-timeout-grouping;
      }
      container multi-tenant-vpn-table {
        description
          "Device vpn id to tenant vpn id mapping table Option";
        presence "true";
        uses flow-exporter-option-timeout-grouping;
      }
      container utd-ips-action-table {
        description
          "Utd IPS Action Table Option";
        presence "true";
        uses flow-exporter-option-timeout-grouping;
      }
      container utd-urlf-action-table {
        description
          "Utd URLF Action Table Option";
        presence "true";
        uses flow-exporter-option-timeout-grouping;
      }
      container utd-amp-action-table {
        description
          "Utd AMP Action Table Option";
        presence "true";
        uses flow-exporter-option-timeout-grouping;
      }
      container bfd-metrics-table {
        description
          "BFD Metrics Table Option";
        presence "true";
        uses flow-exporter-option-timeout-grouping;
      }
    }
    container output-features {
      status obsolete;
      presence "true";
    }
    container source {
      description
        "Originating interface";
      uses ios-ifc:interface-grouping;
    }
    container template {
      description
        "Flow Exporter template configuration";
      container data {
        description
          "Flow Exporter data configuration";
        leaf timeout {
          description
            "Resend data based on a timeout";
          type uint32 {
            range "1..86400";
          }
        }
      }
    }
    container transport {
      description
        "Transport protocol";
      leaf udp {
        description
          "UDP transport protocol";
        type uint16;
      }
    }
    leaf ttl {
      description
        "Optional TTL or hop limit";
      type uint8;
    }
    container match {
      description
        "Only export flows that match a criteria";
      container counter {
        description
          "Match based on the value of a counter";
        container packets {
          description
            "Match based on the number of packets in the flow";
          container long {
            description
              "Match based on the long version of the packet counter";
            choice op-choice {
              case gt {
                leaf gt {
                  description
                    "Greater than match";
                  type uint32 {
                    range "1..4294967295";
                  }
                }
              }
            }
          }
        }
      }
    }
  }

  grouping flow-default-exporter-grouping {
    leaf description {
      description
        "Provide a description for this Flow Exporter";
      type empty;
    }
    leaf destination {
      description
        "Export destination";
      type empty;
    }
    leaf dscp {
      description
        "Optional DSCP";
      type empty;
    }
    leaf export-protocol {
      description
        "Export protocol version";
      type empty;
    }
    container option {
      description
        "Select an option for exporting";
      container application-attributes {
        description
          "Application Attributes Table Option";
        presence "true";
      }
      container c3pl-class-table {
        description
          "C3PL class cce-id table";
        presence "true";
      }
      container c3pl-policy-table {
        description
          "C3PL policy cce-id table";
        presence "true";
      }
      container exporter-stats {
        description
          "Exporter Statistics Option";
        presence "true";
      }
      container interface-table {
        description
          "Interface SNMP-index-to-name Table Option";
        presence "true";
      }
      container metadata-version-table {
        description
          "Metadata Version Table Option";
        presence "true";
      }
      container sampler-table {
        description
          "Export Sampler Option";
        presence "true";
      }
      container sub-application-table {
        description
          "Sub Application Table Option";
        presence "true";
      }
      container vrf-attributes {
        description
          "VRF Attributes Table Option";
        presence "true";
      }
      container vrf-table {
        description
          "VRF ID-to-name Table Option";
        presence "true";
      }
      container tunnel-tloc-table {
        description
          "tunnel-to-tloc Table Option";
        presence "true";
      }
      container ssid-table {
        description
          "VRF ID-to-name Table Option";
        presence "true";
      }
      leaf drop-cause-table {
        description
          "Drop Cause Table Option";
        type empty;
      }
      leaf fw-drop-reason-table {
        description
          "Firewall drop reason table";
        type empty;
      }
      leaf fw-proto-table {
        description
          "Firewall protocol table";
        type empty;
      }
      leaf fw-zone-table {
        description
          "Firewall zone id to name mapping table";
        type empty;
      }
      leaf fw-zone-pair-table {
        description
          "Firewall zone-pair id to name mapping table";
        type empty;
      }
      leaf fw-action-table {
        description
          "Firewall action to name mapping table";
        type empty;
      }
      leaf fw-end-flow-reason-table {
        description
          "Firewall end flow reason to name mapping table";
        type empty;
      }
      leaf utd-policy-table {
        description
          "Utd Policy name Table Option";
        type empty;
      }
      leaf utd-file-type-table {
        description
          "Utd Amp File Type Table Option";
        type empty;
      }
      leaf utd-category-table {
        description
          "Utd Url Category Table Option";
        type empty;
      }
      leaf utd-urlf-reason-table {
        description
          "Utd Url Reason Table Option";
        type empty;
      }
      leaf utd-action-table {
        description
          "Utd Action Table Option";
        type empty;
      }
      leaf utd-disposition-table {
        description
          "Utd Disposition Table Option";
        type empty;
      }
      leaf utd-url-table {
        description
          "Utd URL Table Option";
        type empty;
      }
      leaf utd-filename-table {
        description
          "Utd Filename Table Option";
        type empty;
      }
      leaf utd-malware-table {
        description
          "Utd malicious software name Table Option";
        type empty;
      }
      leaf utd-drop-reason-table {
        description
          "Utd Drop reason Table Option";
        type empty;
      }
      leaf sdvt-drop-reason-table {
        description
          "Service divert Drop reason Table Option";
        type empty;
      }
      leaf multi-tenant-vpn-table {
        description
          "Device vpn id to tenant vpn id mapping table Option";
        type empty;
      }
      leaf utd-ips-action-table {
        description
          "Utd IPS Action Table Option";
        type empty;
      }
      leaf utd-urlf-action-table {
        description
          "Utd URLF Action Table Option";
        type empty;
      }
      leaf utd-amp-action-table {
        description
          "Utd AMP Action Table Option";
        type empty;
      }
      leaf bfd-metrics-table {
        description
          "BFD Metrics Table Option";
        type empty;
      }
    }
    container template {
      description
        "Flow Exporter template configuration";
      container data {
        description
          "Flow Exporter data configuration";
        leaf timeout {
          description
            "Resend data based on a timeout";
          type empty;
        }
      }
    }
    leaf transport {
      description
        "Transport protocol";
      type empty;
    }
    leaf ttl {
      description
        "Optional TTL or hop limit";
      type empty;
    }
    leaf match {
      description
        "flows match criteria";
      type empty;
    }
  }

  grouping flow-default-file-export-grouping {
    leaf destination {
      description
        "Flow File export destination configuration";
      type empty;
    }
    container file {
      description
        "File export properties configuration";
      leaf max-count {
        description
          "Max export pending files on device";
        type empty;
      }
      leaf max-create-interval {
        description
          "Max time interval between files creation";
        type empty;
      }
      leaf max-size {
        description
          "File max size in megabytes before compression";
        type empty;
      }
    }
  }

  grouping config-flow-grouping {
    list record {
      description
        "Define a Flow Record";
      key "name";
      leaf name {
        type flow-name;
      }
      leaf type {
        description
          "Type of the Flow Record";
        type enumeration {
          enum performance-monitor;
        }
      }
      uses flow-record-collect-grouping;
      container default {
        description
          "Set a command to its defaults";
        uses flow-record-collect-grouping;
        leaf description {
          description
            "Provide a description for this Flow Record";
          type string;
        }
        uses flow-record-match-grouping;
      }
      leaf description {
        description
          "Provide a description for this Flow Record";
        type string;
      }
      uses flow-record-match-grouping;
    }
    list exporter {
      description
        "Define a Flow Exporter";
      key "name";
      leaf name {
        type flow-name;
      }
      uses flow-exporter-grouping;
      container default {
        description
          "Set a command to its defaults";
        uses flow-default-exporter-grouping;
      }
    }
    list monitor {
      description
        "Define a Flow Monitor";
      key "name";
      leaf name {
        type flow-name;
      }
      leaf type {
        description
          "Type of the Flow Monitor";
        type enumeration {
          enum performance-monitor;
        }
      }
      uses flow-monitor-grouping;
      container default {
        description
          "Set a command to its defaults";
        uses flow-default-monitor-grouping;
      }
    }
    container file-export {
      container default {
        presence "true";
        container destination-cfg {
          leaf destination {
            type string;
          }
          leaf transport {
            type enumeration {
              enum http;
              enum https;
            }
          }
          leaf dest-port {
            type uint32 {
              range "1..65535";
            }
          }
          leaf upload-path {
            type string;
          }
        }
        container file {
          description
            "File export properties configuration";
          leaf max-count {
            description
              "Max export pending files on device";
            type uint8 {
              range "1..10";
            }
            default "5";
          }
          leaf max-create-interval {
            description
              "Max time interval between files creation";
            type uint8 {
              range "1..60";
            }
            default "10";
          }
          leaf max-size {
            description
              "File max size in megabytes before compression";
            type uint8 {
              range "1..50";
            }
            default "10";
          }
          container header {
            description
              "Define headers sent in each exported file";
            leaf option-data {
              description
                "All option data";
              type boolean;
              default "true";
            }
            leaf templates {
              description
                "All current templates";
              type boolean;
              default "true";
            }
          }
        }
        container metadata {
          description
            "Metadata file options";
          container producer {
            description
              "Enable or disable a specific metadata producer";
            leaf deviceInfo {
              description
                "Device information";
              type boolean;
              default "true";
            }
            leaf fnfMonitorStats {
              description
                "Netflow monitors statistics";
              type boolean;
              default "true";
            }
            leaf intfQosStats {
              description
                "Quality of service statistics";
              type boolean;
              default "true";
            }
            leaf intfStats {
              description
                "Interface statistics";
              type boolean;
              default "true";
            }
            leaf netflowStatistics {
              description
                "Netflow templates statistics";
              type boolean;
              default "true";
            }
            leaf statsLoggerWdavc {
              description
                "WDAVC serviceability";
              type boolean;
              default "true";
            }
          }
        }
        container default {
          description
            "Set a command to its defaults";
          uses flow-default-file-export-grouping;
        }
      }
    }
  }

  grouping config-ip-flow-export-grouping {
    container flow-export {
      description
        "Specify host/port to send flow statistics";
      container destination {
        description
          "Specify the Destination IP address";
        leaf ip {
          type ios-types:host-type;
        }
        leaf port {
          type uint16 {
            range "1..65535";
          }
        }
      }
      container source {
        description
          "Specify the interface for source address";
        uses ios-ifc:interface-grouping;
      }
      leaf version {
        description
          "Specify the version number";
        type enumeration {
          enum 1;
          enum 5;
          enum 9;
        }
      }
    }
  }

  grouping config-ip-flow-cache-grouping {
    container flow-cache {
      description
        "Configure netflow cache parameters";
      container timeout {
        description
          "Specify flow cache timeout parameters";
        leaf active {
          description
            "Specify the active flow timeout";
          type uint16 {
            range "1..60";
          }
        }
      }
    }
  }

  grouping config-sampler-grouping {
    leaf description {
      description
        "Provide a description for this Sampler";
      type string;
    }
    container mode {
      description
        "Sampling mode";
      container deterministic {
        description
          "Deterministic mode of sampling";
        leaf number {
          type uint8;
        }
        leaf out-of {
          description
            "Select M packets out of an N packet window";
          type uint16 {
            range "2..32768";
          }
        }
      }
      container hash {
        description
          "Hash mode of sampling";
        leaf number {
          type uint8;
        }
        leaf out-of {
          description
            "Select 1 packets out of an N packets based on hash of ip-id and udp / tcp checksum";
          type uint16 {
            range "1..65535";
          }
        }
      }
      container random {
        description
          "Random mode of sampling";
        leaf number {
          type uint8;
        }
        leaf out-of {
          description
            "Select M packets out of an N packet window";
          type uint16 {
            range "1..65535";
          }
        }
      }
    }
    container granularity {
      description
        "Specify sampler granularity";
      leaf connection {
        type empty;
      }
      leaf packet {
        type empty;
      }
    }
  }

  grouping interface-ip-monitor-grouping {
    list monitor-new {
      description
        "Apply a Flow Monitor";
      key "name direction";
      leaf name {
        description
          "User defined";
        type leafref {
          path "/ios:native/ios:flow/ios-flow:monitor/ios-flow:name";
        }
      }
      leaf direction {
        type enumeration {
          enum input;
          enum output;
        }
      }
      leaf sampler {
        type flow-name;
      }
      leaf subtraffic {
        type enumeration {
          enum unicast;
          enum multicast;
        }
      }
    }
    list monitor {
      description
        "Apply a Flow Monitor";
      status deprecated;
      key "name";
      leaf name {
        description
          "User defined";
        status deprecated;
        type leafref {
          path "/ios:native/ios:flow/ios-flow:monitor/ios-flow:name";
        }
      }
      list sampler {
        description
          "Optional Sampler to apply to this Flow Monitor";
        status deprecated;
        key "direction";
        leaf direction {
          description
            "Apply Flow Monitor on input/output traffic";
          status deprecated;
          type enumeration {
            enum input;
            enum output;
          }
        }
        leaf name {
          description
            "User defined";
          status deprecated;
          type flow-name;
        }
      }
      leaf input {
        status deprecated;
        description
          "Apply Flow Monitor on input traffic";
        type empty;
      }
      leaf output {
        status deprecated;
        description
          "Apply Flow Monitor on input traffic";
        type empty;
      }
      leaf multicast {
        status deprecated;
        type empty;
      }
      leaf unicast {
        status deprecated;
        type empty;
      }
    }
  }

  grouping config-interface-ip-flow-grouping {
    container flow {
      description
        "NetFlow related commands";
      leaf ingress {
        description
          "Enable inbound NetFlow";
        type empty;
      }
      leaf egress {
        description
          "Enable outbound NetFlow";
        type empty;
      }
      uses interface-ip-monitor-grouping;
    }
  }

  grouping config-interface-ipv6-flow-grouping {
    container flow {
      description
        "NetFlow related commands";
      leaf ingress {
        description
          "Enable inbound NetFlow";
        type empty;
      }
      leaf egress {
        description
          "Enable outbound NetFlow";
        type empty;
      }
      uses interface-ip-monitor-grouping;
    }
  }

  grouping config-ip-visibility-flow-grouping {
    container flow {
      description
        "Apply flow visibility";
      container monitor {
        description
          "Apply a Flow Monitor";
        container sdwan_flow_monitor {
          if-feature "ios-features:sdwan";
          description
            "Apply SDWAN flow monitor";
          choice input-sampler-choice {
            leaf input {
              description
                "Apply Flow Monitor on input traffic";
              type empty;
            }
            container sampler {
              description
                "Optional sampler for SDWAN flow monitor";
              container sdwan_flow_sampler {
                description
                  "Apply SDWAN sampler";
                leaf input {
                  description
                    "Apply Flow Monitor on input traffic";
                  type empty;
                }
              }
            }
          }
        }
      }
    }
  }

  grouping config-ip-visibility-grouping {
    container global {
      description
        "Apply global visibility";
      uses config-ip-visibility-flow-grouping;
    }
    container policy {
      description
        "Apply global visibility";
      uses config-ip-visibility-flow-grouping;
    }
  }

  grouping config-ipv6-visibility-flow-grouping {
    container flow {
      description
        "Apply flow visibility";
      container monitor {
        description
          "Apply a Flow Monitor";
        container sdwan_flow_monitor_ipv6 {
          description
            "Apply SDWAN flow monitor";
          choice input-sampler-choice {
            leaf input {
              description
                "Apply Flow Monitor on input traffic";
              type empty;
            }
            container sampler {
              description
                "Optional sampler for SDWAN flow monitor";
              container sdwan_flow_sampler_ipv6 {
                description
                  "Apply SDWAN sampler";
                leaf input {
                  description
                    "Apply Flow Monitor on input traffic";
                  type empty;
                }
              }
            }
          }
        }
      }
    }
  }

  grouping config-ipv6-visibility-grouping {
    container global {
      description
        "Apply global visibility";
      uses config-ipv6-visibility-flow-grouping;
    }
    container policy {
      description
        "Apply global visibility";
      uses config-ipv6-visibility-flow-grouping;
    }
  }

  augment "/ios:native/ios:flow" {
    uses config-flow-grouping;
  }

  augment "/ios:native/ios:sampler" {
    uses config-sampler-grouping;
  }

  augment "/ios:native/ios:interface/ios:FastEthernet/ios:ip" {
    uses config-interface-ip-flow-grouping;
  }

  augment "/ios:native/ios:interface/ios:GigabitEthernet/ios:ip" {
    uses config-interface-ip-flow-grouping;
  }

  augment "/ios:native/ios:interface/ios:TenGigabitEthernet/ios:ip" {
    uses config-interface-ip-flow-grouping;
  }

  augment "/ios:native/ios:interface/ios:FiveGigabitEthernet/ios:ip" {
    uses config-interface-ip-flow-grouping;
  }

  augment "/ios:native/ios:interface/ios:AppGigabitEthernet/ios:ip" {
    uses config-interface-ip-flow-grouping;
  }

  augment "/ios:native/ios:interface/ios:TwentyFiveGigE/ios:ip" {
    uses config-interface-ip-flow-grouping;
  }

  augment "/ios:native/ios:interface/ios:TwoGigabitEthernet/ios:ip" {
    uses config-interface-ip-flow-grouping;
  }

  augment "/ios:native/ios:interface/ios:FortyGigabitEthernet/ios:ip" {
    uses config-interface-ip-flow-grouping;
  }

  augment "/ios:native/ios:interface/ios:HundredGigE/ios:ip" {
    uses config-interface-ip-flow-grouping;
  }

  augment "/ios:native/ios:interface/ios:Port-channel/ios:ip" {
    uses config-interface-ip-flow-grouping;
  }

  augment "/ios:native/ios:interface/ios:Loopback/ios:ip" {
    uses config-interface-ip-flow-grouping;
  }

  augment "/ios:native/ios:interface/ios:Tunnel/ios:ip" {
    uses config-interface-ip-flow-grouping;
  }

  augment "/ios:native/ios:interface/ios:Serial/ios:ip" {
    uses config-interface-ip-flow-grouping;
  }

  augment "/ios:native/ios:interface/ios:Dialer/ios:ip" {
    uses config-interface-ip-flow-grouping;
  }

  augment "/ios:native/ios:interface/ios:Cellular/ios:ip" {
    uses config-interface-ip-flow-grouping;
  }

  augment "/ios:native/ios:interface/ios:Service-Engine/ios:ip" {
    uses config-interface-ip-flow-grouping;
  }

  augment "/ios:native/ios:interface/ios:Embedded-Service-Engine/ios:ip" {
    uses config-interface-ip-flow-grouping;
  }

  augment "/ios:native/ios:interface/ios:Multilink/ios:ip" {
    uses config-interface-ip-flow-grouping;
  }

  augment "/ios:native/ios:interface/ios:ATM/ios:ip" {
    uses config-interface-ip-flow-grouping;
  }

  augment "/ios:native/ios:interface/ios:ATM-subinterface/ios:ATM/ios:ip" {
    uses config-interface-ip-flow-grouping;
  }

  augment "/ios:native/ios:interface/ios:Vlan/ios:ip" {
    uses config-interface-ip-flow-grouping;
  }

  augment "/ios:native/ios:interface/ios:FastEthernet/ios:ipv6" {
    uses config-interface-ipv6-flow-grouping;
  }

  augment "/ios:native/ios:interface/ios:GigabitEthernet/ios:ipv6" {
    uses config-interface-ipv6-flow-grouping;
  }

  augment "/ios:native/ios:interface/ios:TenGigabitEthernet/ios:ipv6" {
    uses config-interface-ipv6-flow-grouping;
  }

  augment "/ios:native/ios:interface/ios:FiveGigabitEthernet/ios:ipv6" {
    uses config-interface-ipv6-flow-grouping;
  }

  augment "/ios:native/ios:interface/ios:AppGigabitEthernet/ios:ipv6" {
    uses config-interface-ipv6-flow-grouping;
  }

  augment "/ios:native/ios:interface/ios:TwentyFiveGigE/ios:ipv6" {
    uses config-interface-ipv6-flow-grouping;
  }

  augment "/ios:native/ios:interface/ios:TwoGigabitEthernet/ios:ipv6" {
    uses config-interface-ipv6-flow-grouping;
  }

  augment "/ios:native/ios:interface/ios:FortyGigabitEthernet/ios:ipv6" {
    uses config-interface-ipv6-flow-grouping;
  }

  augment "/ios:native/ios:interface/ios:HundredGigE/ios:ipv6" {
    uses config-interface-ipv6-flow-grouping;
  }

  augment "/ios:native/ios:interface/ios:Port-channel/ios:ipv6" {
    uses config-interface-ipv6-flow-grouping;
  }

  augment "/ios:native/ios:interface/ios:Loopback/ios:ipv6" {
    uses config-interface-ipv6-flow-grouping;
  }

  augment "/ios:native/ios:interface/ios:Tunnel/ios:ipv6" {
    uses config-interface-ipv6-flow-grouping;
  }

  augment "/ios:native/ios:interface/ios:Serial/ios:ipv6" {
    uses config-interface-ip-flow-grouping;
  }

  augment "/ios:native/ios:interface/ios:Dialer/ios:ipv6" {
    uses config-interface-ip-flow-grouping;
  }

  augment "/ios:native/ios:interface/ios:Cellular/ios:ipv6" {
    uses config-interface-ip-flow-grouping;
  }

  augment "/ios:native/ios:interface/ios:Service-Engine/ios:ipv6" {
    uses config-interface-ip-flow-grouping;
  }

  augment "/ios:native/ios:interface/ios:Embedded-Service-Engine/ios:ipv6" {
    uses config-interface-ip-flow-grouping;
  }

  augment "/ios:native/ios:interface/ios:Multilink/ios:ipv6" {
    uses config-interface-ipv6-flow-grouping;
  }

  augment "/ios:native/ios:interface/ios:ATM/ios:ipv6" {
    uses config-interface-ipv6-flow-grouping;
  }

  augment "/ios:native/ios:interface/ios:ATM-subinterface/ios:ATM/ios:ipv6" {
    uses config-interface-ipv6-flow-grouping;
  }

  augment "/ios:native/ios:interface/ios:Vlan/ios:ipv6" {
    uses config-interface-ipv6-flow-grouping;
  }

  augment "/ios:native/ios:ip/ios:visibility" {
    uses config-ip-visibility-grouping;
  }

  augment "/ios:native/ios:ipv6/ios:visibility" {
    uses config-ipv6-visibility-grouping;
  }
}
