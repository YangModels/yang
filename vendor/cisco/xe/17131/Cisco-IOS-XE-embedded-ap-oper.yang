module Cisco-IOS-XE-embedded-ap-oper {
  yang-version 1.1;
  namespace "http://cisco.com/ns/yang/Cisco-IOS-XE-embedded-ap-oper";
  prefix em-ap-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for embedded access point operational data.
     Copyright (c) 2021-2022 by Cisco Systems, Inc.
     All rights reserved.";

  revision 2022-11-01 {
    description
      "Update yang-version to 1.1";
    reference
      "1.1.0";
    cisco-semver:module-version "1.1.0";
  }
  revision 2021-07-01 {
    description
      "Initial revision";
    reference
      "1.0.0";
    cisco-semver:module-version "1.0.0";
  }

  typedef radio-band {
    type enumeration {
      enum band-24ghz {
        value 0;
        description
          "2.4GHz Band";
      }
      enum band-5ghz {
        value 1;
        description
          "5GHz Band";
      }
      enum band-all {
        value 2;
        description
          "All Bands";
      }
    }
    description
      "Wireless LAN Radio Band";
  }

  typedef channel-width {
    type enumeration {
      enum chan-bw-20mhz {
        value 0;
        description
          "20MHz bandwidth";
      }
      enum chan-bw-40mhz {
        value 1;
        description
          "40MHz bandwidth";
      }
      enum chan-bw-80mhz {
        value 2;
        description
          "80MHz bandwidth";
      }
      enum chan-bw-160mhz {
        value 3;
        description
          "160MHz bandwidth";
      }
    }
    description
      "Wireless LAN Channel Bandwidth";
  }

  typedef wlan-client-status {
    type enumeration {
      enum wlan-client-state-idle {
        value 0;
        description
          "Represents the client in idle state";
      }
      enum wlan-client-state-aaa-pending {
        value 1;
        description
          "The client is in the the process of authenticating";
      }
      enum wlan-client-state-authenticated {
        value 2;
        description
          "The client has been authenticated";
      }
      enum wlan-client-state-associated {
        value 3;
        description
          "The client has associated to the Access Point";
      }
      enum wlan-client-state-power-save {
        value 4;
        description
          "The client is in power save mode";
      }
      enum wlan-client-state-disassociated {
        value 5;
        description
          "The client is disassociated";
      }
      enum wlan-client-state-to-delete {
        value 6;
        description
          "The client deletion is in progress";
      }
      enum wlan-client-state-probing {
        value 7;
        description
          "The client is probing";
      }
      enum wlan-client-state-unknown {
        value 8;
        description
          "The client is in an unknown state";
      }
    }
    description
      "Wireless LAN Client Status";
  }

  grouping radio-info {
    description
      "Radio Info";
    leaf band {
      type em-ap-ios-xe-oper:radio-band;
      description
        "The band of this radio";
    }
    leaf channel {
      type uint16;
      description
        "Operating channel of this radio";
    }
    leaf channel-bandwidth {
      type em-ap-ios-xe-oper:channel-width;
      description
        "Operating channel-width of this radio";
    }
    leaf client-count {
      type uint16;
      description
        "Current client number on this radio";
    }
  }

  grouping wlan-client-key {
    description
      "Identification of a client";
    leaf wlan-id {
      type uint32;
      description
        "ID of Virtual AP";
    }
    leaf mac-address {
      type yang:mac-address;
      description
        "Client MAC Address";
    }
  }

  grouping client-info {
    description
      "Wireless client operational data";
    leaf band {
      type em-ap-ios-xe-oper:radio-band;
      description
        "Radio band of the client";
    }
    leaf ssid {
      type string;
      description
        "SSID the Client is Associated with";
    }
    leaf status {
      type em-ap-ios-xe-oper:wlan-client-status;
      description
        "Operational status of the client";
    }
    leaf ip-address {
      type inet:ip-address;
      description
        "Discovered IP address of the client";
    }
    leaf device-type {
      type string;
      description
        "Discovered device type of the client ";
    }
    leaf rssi {
      type uint16;
      description
        "Received signal strength indication of the client";
    }
  }

  grouping vap-info {
    description
      "Virtual AP Info";
    leaf wlan-id {
      type uint32;
      description
        "ID of this virtual AP";
    }
    leaf admin-up {
      type boolean;
      description
        "This virtual AP is administratively up";
    }
    leaf oper-up {
      type boolean;
      description
        "This virtual AP is operationally up";
    }
    leaf band {
      type em-ap-ios-xe-oper:radio-band;
      description
        "Radio band for this virtual AP";
    }
    leaf vlan-id {
      type uint16;
      description
        "VLAN ID associated with this virtual AP";
    }
    leaf client-count {
      type uint16;
      description
        "Current number of clients associated with this virtual AP";
    }
    leaf max-client-count {
      type uint16;
      description
        "Max number of clients supported on this virtual AP";
    }
    leaf ssid {
      type string;
      description
        "SSID of this Virtual AP";
    }
  }

  container embedded-ap-oper-data {
    config false;
    description
      "The top level container for embedded access point operational data";
    list embedded-ap-wlan {
      key "wlan-id";
      description
        "Wireless LAN Virtual AP Info";
      uses em-ap-ios-xe-oper:vap-info;
    }
    list embedded-ap-client {
      key "wlan-id mac-address";
      description
        "Wireless LAN Client Info";
      uses em-ap-ios-xe-oper:client-info;
      uses em-ap-ios-xe-oper:wlan-client-key;
    }
    list embedded-ap-radio {
      key "band";
      description
        "Wireless LAN Radio Info";
      uses em-ap-ios-xe-oper:radio-info;
    }
  }
}
