module Cisco-IOS-XE-sanet-deviation {
  yang-version 1.1;
  namespace "http://cisco.com/ns/yang/Cisco-IOS-XE-sanet-deviation";
  prefix ios-sanet-d;

  import cisco-semver {
    prefix cisco-semver;
  }
  import Cisco-IOS-XE-native {
    prefix ios;
  }
  import Cisco-IOS-XE-sanet {
    prefix ios-sanet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Deviation Session Aware Networking (SaNet) Yang model.
     Copyright (c) 2019-2020 by Cisco Systems, Inc.
     All rights reserved.";

  revision 2022-11-01 {
    description
      "- Update yang-version to 1.1";
    cisco-semver:module-version "1.1.0";
  }
  revision 2020-07-01 {
    description
      "Added not supported deviation for authentication cli on port-channel";
    cisco-semver:module-version "1.0.1";
  }

  deviation "/ios:native/ios:interface/ios:Port-channel/ios-sanet:authentication" {
    deviate not-supported;
  }
}
