module Cisco-IOS-XE-ezpm {
  yang-version 1.1;
  namespace "http://cisco.com/ns/yang/Cisco-IOS-XE-ezpm";
  prefix ios-ezpm;

  import cisco-semver {
    prefix cisco-semver;
  }
  import ietf-inet-types {
    prefix inet;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Easy Performance Monitor (ezPM) Yang model.
     Copyright (c) 2016-2022 by Cisco Systems, Inc.
     All rights reserved.";

  revision 2023-11-01 {
    description
      "- Add application-aggregation and app-visibility profiles for ezPM context
       - Add local-controller as export destination option
       - Add support for Port-channel sub-interface";
    cisco-semver:module-version "5.1.0";
  }
  revision 2022-11-01 {
    description
      "- Update yang-version to 1.1
       - Added new traffic-monitors, time based sampler, per VPN metric
         and attach points to apply context";
    cisco-semver:module-version "5.0.0";
  }
  revision 2022-07-01 {
    description
      "- Added spread-opt-tables option for ezPM context exporters";
    cisco-semver:module-version "4.3.0";
  }
  revision 2022-03-01 {
    description
      "- Add local-file and local-wlc as export destination options";
    cisco-semver:module-version "4.2.0";
  }
  revision 2021-11-01 {
    description
      "- Add sdwan-fnf profile for ezPM context";
    cisco-semver:module-version "4.1.0";
  }
  revision 2021-03-01 {
    description
      "- Update constraint for container application-response-time and container media
       - Change mode valid only when profile is 'application-performance'";
    cisco-semver:module-version "4.0.0";
  }
  revision 2020-11-01 {
    description
      "- Add sdwan-performance profile for ezPM context";
    cisco-semver:module-version "3.0.0";
  }
  revision 2020-03-01 {
    description
      "- Added mode for ezPM context";
    cisco-semver:module-version "2.1.0";
  }
  revision 2019-11-01 {
    description
      "Added new assurance monitor config";
    cisco-semver:module-version "2.0.0";
  }
  revision 2019-07-01 {
    description
      "Establish semantic version baseline";
    cisco-semver:module-version "1.0.0";
  }
  revision 2019-01-22 {
    description
      "Added leaf for App-hosting Gigabit Ethernet interface";
  }
  revision 2018-12-14 {
    description
      "This revision has below changes
       - Under exporter added dscp option
       - Added performance monitor profile
       - Added support for missing interfaces";
  }
  revision 2017-11-27 {
    description
      "Added Change 25GE name";
  }
  revision 2017-11-14 {
    description
      "This revision has changes for new 40 and 100GE interface addition";
  }
  revision 2017-09-14 {
    description
      "This revision has changes for new 2gig interface addition";
  }
  revision 2017-08-12 {
    description
      "This revision has changes for new 5gig and 25gig interfaces addition";
  }
  revision 2017-02-07 {
    description
      "Initial revision";
  }

  typedef color-enum {
    type enumeration {
      enum default {
        value 1;
      }
      enum mpls;
      enum metro-ethernet;
      enum biz-internet;
      enum public-internet;
      enum lte;
      enum 3g;
      enum red;
      enum green;
      enum blue;
      enum gold;
      enum silver;
      enum bronze;
      enum custom1;
      enum custom2;
      enum custom3;
      enum private1;
      enum private2;
      enum private3;
      enum private4;
      enum private5;
      enum private6;
    }
  }

  typedef ezpm-exp-des-type {
    type union {
      type inet:ip-address;
      type enumeration {
        enum local-sdwan;
        enum local-file;
        enum local-wlc;
        enum local-controller;
      }
    }
  }

  grouping pm-context-traffic-monitor-app-traffic-stats-grouping {
    leaf cache-size {
      description
        "Maximum flow entries in the Flow Cache";
      type uint32 {
        range "64..2000000";
      }
    }
    leaf class-replace {
      description
        "Replace traffic classification";
      type string;
    }
    leaf interval-timeout {
      description
        "The exporting interval timeout";
      type uint32 {
        range "1..604800";
      }
    }
  }

  grouping pm-context-traffic-monitor-ip-grouping {
    leaf ipv4 {
      description
        "Activate monitor for ipv4 traffic";
      type empty;
    }
    leaf ipv6 {
      description
        "Activate monitor for ipv6 traffic";
      type empty;
    }
  }

  grouping performance-monitor-context-grouping {
    list exporter-config {
      description
        "Create exporter";
      key "destination source";
      leaf destination {
        description
          "Export destination configuration";
        type ezpm-exp-des-type;
      }
      leaf source {
        description
          "Originating interface";
        type string;
      }
      leaf dscp {
        description
          "Optional DSCP value";
        type uint8 {
          range "1..63";
        }
      }
      leaf port {
        description
          "Optional port value";
        type uint16;
      }
      leaf transport {
        description
          "UDP transport protocol";
        type enumeration {
          enum udp;
        }
      }
      leaf vrf {
        description
          "VRF label";
        type string;
      }
      leaf spread-opt-tables {
        description
          "Enable export spread for optional tables";
        type empty;
      }
    }
    container exporter {
      status deprecated;
      description
        "Create exporter";
      leaf destination {
        status deprecated;
        description
          "Export destination configuration";
        type inet:ip-address;
      }
      leaf source {
        status deprecated;
        description
          "Originating interface";
        type string;
      }
      leaf dscp {
        status deprecated;
        description
          "optional dscp value";
        type uint8 {
          range "1..255";
        }
      }
      leaf port {
        status deprecated;
        description
          "port";
        type uint16;
      }
      leaf transport {
        status deprecated;
        description
          "transport";
        type enumeration {
          enum udp;
        }
      }
      leaf vrf {
        status deprecated;
        description
          "vrf";
        type string;
      }
    }
    container traffic-monitor {
      description
        "Select traffic monitor";
      container all {
        description
          "All traffic monitors in this profile";
        when "../../profile = 'application-experience' or ../../profile = 'application-performance' or ../../profile = 'application-assurance'";
        presence "true";
        leaf ipv4 {
          description
            "Activate monitor for ipv4 traffic";
          type empty;
        }
        leaf ipv6 {
          description
            "Activate monitor for ipv6 traffic";
          type empty;
        }
      }
      container assurance-rtp-monitor {
        description
          "Per application rtp assurance metrics";
        when "../../profile = 'application-assurance'";
        presence "true";
        leaf cache-size {
          description
            "Maximum flow entries in the Flow Cache";
          type uint32 {
            range "64..2000000";
          }
        }
        leaf interval-timeout {
          description
            "The exporting interval timeout";
          type uint32 {
            range "1..604800";
          }
        }
        uses pm-context-traffic-monitor-ip-grouping;
      }
      container assurance-monitor {
        description
          "Per application assurance metrics";
        when "../../profile = 'application-assurance'";
        presence "true";
        leaf cache-size {
          description
            "Maximum flow entries in the Flow Cache";
          type uint32 {
            range "64..2000000";
          }
        }
        leaf interval-timeout {
          description
            "The exporting interval timeout";
          type uint32 {
            range "1..604800";
          }
        }
        uses pm-context-traffic-monitor-ip-grouping;
      }
      container application-response-time {
        description
          "Application response time (ART) metrics and counters for TCP traffic";
        when "../../profile = 'application-experience' or ../../profile = 'application-performance' or ../../profile = 'sdwan-performance'";
        presence "true";
        uses pm-context-traffic-monitor-app-traffic-stats-grouping;
        leaf cache-type {
          description
            "The type of the Flow Cache";
          type enumeration {
            enum normal;
            enum synchronized;
          }
        }
        leaf class-and {
          description
            "Narrow down default traffic classification";
          type string;
        }
        uses pm-context-traffic-monitor-ip-grouping;
      }
      container art-cor-saas {
        description
          "Application response time Cloud On Ramp SAAS (ART-COR-SAAS) metrics and counters for TCP traffic";
        when "../../profile = 'sdwan-performance'";
        presence "true";
        uses pm-context-traffic-monitor-app-traffic-stats-grouping;
        leaf cache-type {
          description
            "The type of the Flow Cache";
          type enumeration {
            enum normal;
            enum synchronized;
          }
        }
        leaf class-and {
          description
            "Narrow down default traffic classification";
          type string;
        }
        uses pm-context-traffic-monitor-ip-grouping;
      }
      container art-aggregated {
        description
          "Application response time aggregated metrics and counters for TCP traffic";
        when "../../profile = 'sdwan-performance' or ../../profile = 'application-aggregation'";
        presence "true";
        must 'not((../application-response-time) or (../art-cor-saas))' {
          error-message "art-aggregated and other art monitors cannot be configured at the same time";
        }
        uses pm-context-traffic-monitor-app-traffic-stats-grouping;
        leaf cache-type {
          description
            "The type of the Flow Cache";
          type enumeration {
            enum normal;
            enum synchronized;
          }
        }
        leaf class-and {
          description
            "Narrow down default traffic classification";
          type string;
        }
        leaf sampling-interval {
          description
            "Time-based sampling interval";
          type uint32 {
            range "10..32768";
          }
          units "milliseconds";
        }
        uses pm-context-traffic-monitor-ip-grouping;
      }
      container application-traffic-stats {
        description
          "Application level counters for dns and dht protocol";
        when "../../profile = 'application-experience'";
        presence "true";
        uses pm-context-traffic-monitor-app-traffic-stats-grouping;
      }
      container conversation-traffic-stats {
        description
          "Conversation level counters for IP traffic";
        when "../../profile = 'application-experience'";
        presence "true";
        uses pm-context-traffic-monitor-app-traffic-stats-grouping;
        leaf cache-type {
          description
            "The type of the Flow Cache";
          type enumeration {
            enum normal;
            enum synchronized;
          }
        }
        uses pm-context-traffic-monitor-ip-grouping;
      }
      container media {
        description
          "Media metrics and counters for rtp and telepresence-media traffic";
        when "../../profile = 'application-experience' or ../../profile = 'application-performance' or ../../profile = 'sdwan-performance'";
        presence "true";
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        uses pm-context-traffic-monitor-ip-grouping;
      }
      container media-aggregated {
        description
          "Media aggregated metrics and counters for rtp and telepresence-media traffic";
        when "../../profile = 'sdwan-performance'";
        presence "true";
        must 'not(../media)' {
          error-message "media-aggregated and other media monitors cannot be configured at the same time";
        }
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        leaf sampling-interval {
          description
            "Time-based sampling interval";
          type uint32 {
            range "10..32768";
          }
          units "milliseconds";
        }
        uses pm-context-traffic-monitor-ip-grouping;
      }
      container url {
        description
          "URL information, application response time (ART) metrics and counters";
        when "../../profile = 'application-experience' or ../../profile = 'application-performance'";
        presence "true";
        leaf cache-size {
          description
            "Maximum flow entries in the Flow Cache";
          type uint32 {
            range "64..2000000";
          }
        }
        leaf class-and {
          description
            "Narrow down default traffic classification";
          type string;
        }
        leaf class-replace {
          description
            "Replace traffic classification";
          type string;
        }
        uses pm-context-traffic-monitor-ip-grouping;
        leaf sampling-rate {
          description
            "Sampling rate of flow sampler";
          type uint32 {
            range "1..32768";
          }
        }
      }
      container application-client-server-stats {
        description
          "Per interface, client, server and application statistics";
        presence "true";
        when "../../profile = 'application-performance' or ../../profile = 'application-statistics'";
        uses pm-context-traffic-monitor-app-traffic-stats-grouping;
        leaf cache-type {
          description
            "The type of the Flow Cache";
          type enumeration {
            enum normal;
            enum synchronized;
          }
        }
        uses pm-context-traffic-monitor-ip-grouping;
      }
      container application-stats {
        description
          "Per application and interface statistics";
        presence "true";
        when "../../profile = 'application-performance' or ../../profile = 'application-statistics'";
        uses pm-context-traffic-monitor-app-traffic-stats-grouping;
      }
      container sdwan-fnf-vpn0-stats {
        description
          "SDWAN VPN interface statistics";
        presence "true";
        when "../../profile = 'sdwan-fnf'";
        leaf cache-size {
          description
            "Maximum flow entries in the Flow Cache";
          type uint32 {
            range "64..2000000";
          }
        }
        leaf interval-timeout {
          description
            "The exporting interval timeout";
          type uint32 {
            range "1..604800";
          }
        }
        leaf sampling-rate {
          description
            "Sampling rate of flow sampler";
          type uint32 {
            range "1..32768";
          }
        }
        uses pm-context-traffic-monitor-ip-grouping;
      }
      container app-visibility-stats {
        description
          "Application visibility statistics";
        presence "true";
        when "../../profile = 'app-visibility'";
        leaf cache-size {
          description
            "Maximum flow entries in the Flow Cache";
          type uint32 {
            range "64..2000000";
          }
        }
        leaf interval-timeout {
          description
            "The exporting interval timeout";
          type uint32 {
            range "1..604800";
          }
        }
        leaf sampling-rate {
          description
            "Sampling rate of flow sampler";
          type uint32 {
            range "1..32768";
          }
        }
        uses pm-context-traffic-monitor-ip-grouping;
      }
    }
  }

  grouping performance-monitor-context-default-grouping {
    container exporter {
      description
        "Create exporter";
      leaf destination {
        description
          "Export destination configuration";
        type inet:ip-address;
      }
      leaf source {
        description
          "Originating interface";
        type string;
      }
      leaf port {
        description
          "port";
        type uint16;
      }
      leaf transport {
        description
          "transport";
        type enumeration {
          enum udp;
        }
      }
      leaf vrf {
        description
          "vrf";
        type string;
      }
    }
    container traffic-monitor {
      description
        "Select traffic monitor";
      container all {
        description
          "All traffic monitors in this profile";
        when "../../../profile = 'application-experience' or ../../../profile = 'application-performance' or ../../../profile = 'application-assurance' or ../../../profile = 'sdwan-performance'";
        presence "true";
        leaf ipv4 {
          description
            "Activate monitor for ipv4 traffic";
          type empty;
        }
        leaf ipv6 {
          description
            "Activate monitor for ipv6 traffic";
          type empty;
        }
      }
      container assurance-rtp-monitor {
        description
          "Per application rtp assurance metrics";
        when "../../../profile = 'application-assurance'";
        presence "true";
        leaf cache-size {
          description
            "Maximum flow entries in the Flow Cache";
          type uint32 {
            range "64..2000000";
          }
        }
        leaf interval-timeout {
          description
            "The exporting interval timeout";
          type uint32 {
            range "1..604800";
          }
        }
        uses pm-context-traffic-monitor-ip-grouping;
      }
      container assurance-monitor {
        description
          "Per application assurance metrics";
        when "../../../profile = 'application-assurance'";
        presence "true";
        leaf cache-size {
          description
            "Maximum flow entries in the Flow Cache";
          type uint32 {
            range "64..2000000";
          }
        }
        leaf interval-timeout {
          description
            "The exporting interval timeout";
          type uint32 {
            range "1..604800";
          }
        }
        uses pm-context-traffic-monitor-ip-grouping;
      }
      container application-response-time {
        description
          "Application response time (ART) metrics and counters for TCP traffic";
        when "../../../profile = 'application-experience' or ../../../profile = 'application-performance'";
        presence "true";
        uses pm-context-traffic-monitor-app-traffic-stats-grouping;
        leaf cache-type {
          description
            "The type of the Flow Cache";
          type enumeration {
            enum normal;
            enum synchronized;
          }
        }
        leaf class-and {
          description
            "Narrow down default traffic classification";
          type string;
        }
        uses pm-context-traffic-monitor-ip-grouping;
      }
      container application-traffic-stats {
        description
          "Application level counters for dns and dht protocol";
        when "../../../profile = 'application-experience'";
        presence "true";
        uses pm-context-traffic-monitor-app-traffic-stats-grouping;
      }
      container conversation-traffic-stats {
        description
          "Conversation level counters for IP traffic";
        when "../../../profile = 'application-experience'";
        presence "true";
        uses pm-context-traffic-monitor-app-traffic-stats-grouping;
        leaf cache-type {
          description
            "The type of the Flow Cache";
          type enumeration {
            enum normal;
            enum synchronized;
          }
        }
        uses pm-context-traffic-monitor-ip-grouping;
      }
      container media {
        description
          "Media metrics and counters for rtp and telepresence-media traffic";
        when "../../../profile = 'application-experience' or ../../../profile = 'application-performance'";
        presence "true";
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        uses pm-context-traffic-monitor-ip-grouping;
      }
      container url {
        description
          "URL information, application response time (ART) metrics and counters";
        when "../../../profile = 'application-experience' or ../../../profile = 'application-performance'";
        presence "true";
        leaf cache-size {
          description
            "Maximum flow entries in the Flow Cache";
          type uint32 {
            range "64..2000000";
          }
        }
        leaf class-and {
          description
            "Narrow down default traffic classification";
          type string;
        }
        leaf class-replace {
          description
            "Replace traffic classification";
          type string;
        }
        uses pm-context-traffic-monitor-ip-grouping;
        leaf sampling-rate {
          description
            "Sampling rate of flow sampler";
          type uint32 {
            range "1..32768";
          }
        }
      }
      container application-client-server-stats {
        description
          "Per interface, client, server and application statistics";
        presence "true";
        when "../../../profile = 'application-performance' or ../../../profile = 'application-statistics'";
        uses pm-context-traffic-monitor-app-traffic-stats-grouping;
        leaf cache-type {
          description
            "The type of the Flow Cache";
          type enumeration {
            enum normal;
            enum synchronized;
          }
        }
        uses pm-context-traffic-monitor-ip-grouping;
      }
      container application-stats {
        description
          "Per application and interface statistics";
        presence "true";
        when "../../../profile = 'application-performance' or ../../../profile = 'application-statistics'";
        uses pm-context-traffic-monitor-app-traffic-stats-grouping;
      }
    }
  }

  grouping config-ezpm-grouping {
    container monitor {
      description
        "monitor";
      list apply {
        description
          "Apply ezPM context";
        key "name";
        leaf name {
          type leafref {
            path "../../context/name";
          }
        }
        leaf sdwan-tunnel {
          description
            "sdwan tunnel interfaces";
          type empty;
        }
        leaf color-all-dia {
          description
            "sdwan all dia colors";
          type empty;
        }
        leaf-list color-list {
          description
            "sdwan color list";
          must 'not(../color-all-dia)' {
            error-message "ezPM context cannot be applied to color-all-dia and color-list at the same time";
          }
          type color-enum;
        }
        leaf sdwan-sig {
          description
            "sdwan sig interfaces";
          type empty;
        }
      }
      leaf sampling-rate {
        description
          "Enable performance monitor global sampling mode";
        type uint32 {
          range "2..32768";
        }
      }
      leaf per-vpn-metric {
        description
          "Enable per VPN metric for aggregated monitors";
        type boolean;
        default "false";
      }
      list context {
        description
          "Define ezPM context";
        key "name";
        leaf name {
          type string;
        }
        leaf profile {
          description
            "Select ezPM profile";
          type enumeration {
            enum application-assurance;
            enum application-experience;
            enum application-performance;
            enum application-statistics;
            enum sdwan-performance;
            enum sdwan-fnf;
            enum application-aggregation;
            enum app-visibility;
          }
        }
        container default {
          description
            "Set a command to its defaults";
          leaf description {
            description
              "Provide a description for ezPM context";
            type empty;
          }
          uses performance-monitor-context-default-grouping;
        }
        leaf description {
          description
            "Provide a description for ezPM context";
          type string;
        }
        container mode {
          description
            "Set mode for ezPM context";
          when "../profile = 'application-performance'";
          leaf optimized {
            description
              "Set ezPM context to be optimized mode";
            type boolean;
            default "true";
          }
        }
        uses performance-monitor-context-grouping;
      }
      container observation-point {
        description
          "Select observation point";
        leaf encrypted-text {
          description
            "Select clear text for observation";
          type empty;
        }
      }
      container profile {
        description
          "Load ezPM profile";
        leaf load {
          description
            "Load ezPM XML profile from devices";
          type string {
            pattern '(((bootflash:)|(flash:)|(ftp:)|(http:)|(https:)|(nvram:)|(param:)|(scp:)|(syslog)|(system:)|(tftp:)|(tmpsys:)).*)';
          }
        }
        leaf force {
          description
            "Force";
          type empty;
        }
      }
    }
  }

  grouping config-interface-ezpm-grouping {
    container performance {
      description
        "Global performance monitor configuration";
      container monitor {
        description
          "monitor";
        list context-config {
          description
            "Select ezPM context";
          key "name";
          leaf name {
            must "not ((local-name(../../../..) = 'Tunnel') and /ios:native/ios:performance/monitor/apply[name=current()]/sdwan-tunnel)" {
              error-message "ezPM context cannot be applied to sdwan-tunnel and individual tunnel interface at the same time";
            }
            must "not ((local-name(../../../..) = 'Tunnel') and /ios:native/ios:performance/monitor/apply[name=current()]/sdwan-sig)" {
              error-message "ezPM context cannot be applied to sdwan-sig and individual tunnel interface at the same time";
            }
            must "not (not(local-name(../../../..) = 'Tunnel') and /ios:native/ios:performance/monitor/apply[name=current()]/color-all-dia)" {
              error-message "ezPM context cannot be applied to color-all-dia and individual non-tunnel interface at the same time";
            }
            must "not (not(local-name(../../../..) = 'Tunnel') and /ios:native/ios:performance/monitor/apply[name=current()]/color-list)" {
              error-message "ezPM context cannot be applied to color-list and individual non-tunnel interface at the same time";
            }
            type leafref {
              path "/ios:native/ios:performance/monitor/context/name";
            }
          }
        }
        leaf-list context {
          status deprecated;
          description
            "Select ezPM context";
          type string;
        }
      }
    }
  }

  augment "/ios:native/ios:performance" {
    uses config-ezpm-grouping;
  }

  augment "/ios:native/ios:interface/ios:FastEthernet" {
    uses config-interface-ezpm-grouping {
      if-feature "ios-features:ezpm";
    }
  }

  augment "/ios:native/ios:interface/ios:GigabitEthernet" {
    uses config-interface-ezpm-grouping {
      if-feature "ios-features:ezpm";
    }
  }

  augment "/ios:native/ios:interface/ios:TenGigabitEthernet" {
    uses config-interface-ezpm-grouping {
      if-feature "ios-features:ezpm";
    }
  }

  augment "/ios:native/ios:interface/ios:FiveGigabitEthernet" {
    uses config-interface-ezpm-grouping {
      if-feature "ios-features:ezpm";
    }
  }

  augment "/ios:native/ios:interface/ios:AppGigabitEthernet" {
    uses config-interface-ezpm-grouping {
      if-feature "ios-features:ezpm";
    }
  }

  augment "/ios:native/ios:interface/ios:TwentyFiveGigE" {
    uses config-interface-ezpm-grouping {
      if-feature "ios-features:ezpm";
    }
  }

  augment "/ios:native/ios:interface/ios:TwoGigabitEthernet" {
    uses config-interface-ezpm-grouping {
      if-feature "ios-features:ezpm";
    }
  }

  augment "/ios:native/ios:interface/ios:FortyGigabitEthernet" {
    uses config-interface-ezpm-grouping {
      if-feature "ios-features:ezpm";
    }
  }

  augment "/ios:native/ios:interface/ios:HundredGigE" {
    uses config-interface-ezpm-grouping {
      if-feature "ios-features:ezpm";
    }
  }

  augment "/ios:native/ios:interface/ios:Tunnel" {
    uses config-interface-ezpm-grouping {
      if-feature "ios-features:ezpm";
    }
  }

  augment "/ios:native/ios:interface/ios:Loopback" {
    uses config-interface-ezpm-grouping {
      if-feature "ios-features:ezpm";
    }
  }

  augment "/ios:native/ios:interface/ios:Port-channel" {
    uses config-interface-ezpm-grouping {
      if-feature "ios-features:ezpm";
    }
  }

  augment "/ios:native/ios:interface/ios:Serial" {
    uses config-interface-ezpm-grouping {
      if-feature "ios-features:ezpm";
    }
  }

  augment "/ios:native/ios:interface/ios:Multilink" {
    uses config-interface-ezpm-grouping {
      if-feature "ios-features:ezpm";
    }
  }

  augment "/ios:native/ios:interface/ios:Cellular" {
    uses config-interface-ezpm-grouping {
      if-feature "ios-features:ezpm";
    }
  }

  augment "/ios:native/ios:interface/ios:Service-Engine" {
    uses config-interface-ezpm-grouping {
      if-feature "ios-features:ezpm";
    }
  }

  augment "/ios:native/ios:interface/ios:Embedded-Service-Engine" {
    uses config-interface-ezpm-grouping {
      if-feature "ios-features:ezpm";
    }
  }

  augment "/ios:native/ios:interface/ios:ATM" {
    uses config-interface-ezpm-grouping {
      if-feature "ios-features:ezpm";
    }
  }

  augment "/ios:native/ios:interface/ios:Dialer" {
    uses config-interface-ezpm-grouping {
      if-feature "ios-features:ezpm";
    }
  }

  augment "/ios:native/ios:interface/ios:LISP" {
    uses config-interface-ezpm-grouping {
      if-feature "ios-features:ezpm";
    }
  }

  augment "/ios:native/ios:interface/ios:Ethernet" {
    uses config-interface-ezpm-grouping {
      if-feature "ios-features:ezpm";
    }
  }

  augment "/ios:native/ios:interface/ios:Vlan" {
    uses config-interface-ezpm-grouping {
      if-feature "ios-features:ezpm";
    }
  }

  augment "/ios:native/ios:interface/ios:Port-channel-subinterface/ios:Port-channel" {
    uses config-interface-ezpm-grouping {
      if-feature "ios-features:ezpm";
    }
  }
}
