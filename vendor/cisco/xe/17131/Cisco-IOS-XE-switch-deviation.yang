module Cisco-IOS-XE-switch-deviation {
  yang-version 1.1;
  namespace "http://cisco.com/ns/yang/Cisco-IOS-XE-switch-deviation";
  prefix ios-sw-d;

  import cisco-semver {
    prefix cisco-semver;
  }
  import Cisco-IOS-XE-native {
    prefix ios;
  }
  import Cisco-IOS-XE-policy {
    prefix ios-policy;
  }
  import Cisco-IOS-XE-switch {
    prefix ios-sw;
  }

  organization
    "Cisco Systems";
  description
    "Cisco XE Native Deviation YANG module for IOS
     Copyright (c) 2016-2019 by Cisco Systems, Inc.
     All rights reserved.";

  revision 2023-11-01 {
    description
      " - Move line vty range to quake/switch deviation files";
    cisco-semver:module-version "1.5.0";
  }
  revision 2023-07-01 {
    description
      "- Add deviation for autohangup";
  }
  revision 2022-11-01 {
    description
      "- Update yang-version to 1.1";
    cisco-semver:module-version "1.4.0";
  }
  revision 2021-07-01 {
    description
      "- Updated range for priority to <8-100000000> kbps";
    cisco-semver:module-version "1.3.0";
  }
  revision 2019-11-01 {
    description
      "- Added IP routing default value deviation";
    cisco-semver:module-version "1.2.0";
  }
  revision 2019-07-01 {
    description
      "Establish semantic version baseline";
    cisco-semver:module-version "1.0.0";
  }
  revision 2016-12-01 {
    description
      "Added interface switchport deviation";
  }

  deviation "/ios:native/ios:policy/ios-policy:class-map/ios-policy:match/ios-policy:access-group/ios-policy:index" {
    deviate replace {
      type uint32 {
        range "1..2799";
      }
    }
  }

  deviation "/ios:native/ios:policy/ios-policy:policy-map/ios-policy:class/ios-policy:action-list/ios-policy:action-param/ios-policy:bandwidth-case/ios-policy:bandwidth/ios-policy:bits" {
    deviate replace {
      type uint32 {
        range "100..40000000";
      }
    }
  }

  deviation "/ios:native/ios:policy/ios-policy:policy-map/ios-policy:class/ios-policy:action-list/ios-policy:action-param/ios-policy:priority-case/ios-policy:priority/ios-policy:priority-type/ios-policy:kilo-bits/ios-policy:kilo-bits" {
    deviate replace {
      type uint32 {
        range "8..100000000";
      }
    }
  }

  deviation "/ios:native/ios:interface/ios:FastEthernet/ios:switchport-config/ios:switchport/ios-sw:port-security-config/ios-sw:port-security/ios-sw:maxcount/ios-sw:max-addresses" {
    deviate replace {
      type uint16 {
        range "1..4096";
      }
    }
  }

  deviation "/ios:native/ios:interface/ios:GigabitEthernet/ios:switchport-config/ios:switchport/ios-sw:port-security-config/ios-sw:port-security/ios-sw:maxcount/ios-sw:max-addresses" {
    deviate replace {
      type uint16 {
        range "1..4096";
      }
    }
  }

  deviation "/ios:native/ios:interface/ios:TenGigabitEthernet/ios:switchport-config/ios:switchport/ios-sw:port-security-config/ios-sw:port-security/ios-sw:maxcount/ios-sw:max-addresses" {
    deviate replace {
      type uint16 {
        range "1..4096";
      }
    }
  }

  deviation "/ios:native/ios:interface/ios:Port-channel/ios:switchport-config/ios:switchport/ios-sw:port-security-config/ios-sw:port-security/ios-sw:maxcount/ios-sw:max-addresses" {
    deviate replace {
      type uint16 {
        range "1..4096";
      }
    }
  }

  deviation "/ios:native/ios:interface/ios:Port-channel-subinterface/ios:Port-channel/ios:switchport-config/ios:switchport/ios-sw:port-security-config/ios-sw:port-security/ios-sw:maxcount/ios-sw:max-addresses" {
    deviate replace {
      type uint16 {
        range "1..4096";
      }
    }
  }

  deviation "/ios:native/ios:ip/ios:routing-conf/ios:routing" {
    deviate replace {
      default "false";
    }
  }

  deviation "/ios:native/ios:line/ios:console/ios:autohangup_only" {
    deviate not-supported;
  }

  deviation "/ios:native/ios:line/ios:aux/ios:autohangup_only" {
    deviate not-supported;
  }

  deviation "/ios:native/ios:line/ios:vty/ios:autohangup_only" {
    deviate not-supported;
  }

  deviation "/ios:native/ios:line/ios:line-list/ios:autohangup_only" {
    deviate not-supported;
  }

  deviation "/ios:native/ios:line/ios:async-line-single/ios:autohangup_only" {
    deviate not-supported;
  }

  deviation "/ios:native/ios:line/ios:async-line-range/ios:autohangup_only" {
    deviate not-supported;
  }

  deviation "/ios:native/ios:line/ios:console/ios:autohangup" {
    deviate not-supported;
  }

  deviation "/ios:native/ios:line/ios:aux/ios:autohangup" {
    deviate not-supported;
  }

  deviation "/ios:native/ios:line/ios:vty/ios:autohangup" {
    deviate not-supported;
  }

  deviation "/ios:native/ios:line/ios:line-list/ios:autohangup" {
    deviate not-supported;
  }

  deviation "/ios:native/ios:line/ios:async-line-single/ios:autohangup" {
    deviate not-supported;
  }

  deviation "/ios:native/ios:line/ios:async-line-range/ios:autohangup" {
    deviate not-supported;
  }
}
