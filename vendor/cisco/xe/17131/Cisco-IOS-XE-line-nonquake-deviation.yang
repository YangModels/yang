module Cisco-IOS-XE-line-nonquake-deviation {
  yang-version 1.1;
  namespace "http://cisco.com/ns/yang/Cisco-IOS-XE-line-nonquake-deviation";
  prefix ios-line-d;

  import cisco-semver {
    prefix cisco-semver;
  }
  import Cisco-IOS-XE-native {
    prefix ios;
  }

  organization
    "Cisco Systems, Inc.";
  description
    "Cisco XE Native Line, Non-Quake Deviation Yang Model.
     Copyright (c) 2023 by Cisco Systems, Inc.
     All rights reserved.";

  revision 2023-11-01 {
    description
      "- Add switch deviation for line vty range";
  }

  deviation "/ios:native/ios:line/ios:vty/ios:first" {
    deviate replace {
      type uint16 {
        range "0..97";
      }
    }
  }

  deviation "/ios:native/ios:line/ios:vty/ios:last" {
    deviate replace {
      type uint16 {
        range "1..97";
      }
    }
  }
}
