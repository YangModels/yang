module Cisco-IOS-XE-wireless-afc-types {
  yang-version 1.1;
  namespace "http://cisco.com/ns/yang/Cisco-IOS-XE-wireless-afc-types";
  prefix wireless-afc-types;

  import Cisco-IOS-XE-wireless-enum-types {
    prefix wireless-enum-types;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing AFC
     Copyright (c) 2022-2023 by Cisco Systems, Inc.
     All rights reserved.";

  revision 2023-11-01 {
    description
      "Initial revision";
    reference
      "1.0.0";
    cisco-semver:module-version "1.0.0";
  }

  grouping afc-point {
    description
      "AFC device location is represented as a point";
    leaf longitude {
      type decimal64 {
        fraction-digits 2;
      }
      description
        "AFC device location longitude";
    }
    leaf latitude {
      type decimal64 {
        fraction-digits 2;
      }
      description
        "AFC device location latitude";
    }
  }

  grouping afc-ellipse {
    description
      "Device ellipse location";
    container center {
      description
        "Device ellipse center";
      uses wireless-afc-types:afc-point;
    }
    leaf major-axis {
      type uint16;
      description
        "Device ellipse major axis";
    }
    leaf minor-axis {
      type uint16;
      description
        "Device ellipse minor axis";
    }
    leaf orientation {
      type decimal64 {
        fraction-digits 2;
      }
      description
        "Device ellipse orientation";
    }
  }

  grouping afc-linear-polygon {
    description
      "Device linear polygon location";
    list points {
      description
        "Device linear polygon points";
      uses wireless-afc-types:afc-point;
    }
  }

  grouping afc-elevation {
    description
      "Device elevation";
    leaf height {
      type int16;
      units "meters";
      description
        "Device elevation height";
    }
    leaf height-type {
      type wireless-enum-types:afc-height-type;
      description
        "Device elevation height type";
    }
    leaf uncertainty {
      type uint16;
      units "meters";
      description
        "Device elevation uncertainty";
    }
  }

  grouping afc-location {
    description
      "AFC device location";
    leaf loc-type {
      type wireless-enum-types:afc-location-type;
      description
        "AFC device location type";
    }
    container ellipse {
      description
        "AFC device location ellipse";
      uses wireless-afc-types:afc-ellipse;
    }
    container linear-pol {
      description
        "AFC device location linear polygon";
      uses wireless-afc-types:afc-linear-polygon;
    }
    container elevation {
      description
        "Device elevation";
      uses wireless-afc-types:afc-elevation;
    }
    leaf deployment {
      type wireless-enum-types:afc-deployment-type;
      description
        "AFC device deployment type";
    }
    leaf area-of-uncertainty {
      when "../loc-type='afc-loc-ellipse'";
      type uint32;
      units "square meters";
      description
        "AP geolocation area of uncertainty";
    }
  }

  grouping afc-cert-id {
    description
      "Device certification ID";
    leaf id {
      type string;
      description
        "AFC certification ID";
    }
    leaf ruleset-id {
      type string;
      description
        "AFC ruleset ID";
    }
  }

  grouping afc-device-descriptor {
    description
      "AFC device descriptor";
    leaf serial-number {
      type string;
      description
        "Device serial number";
    }
    list cert-id {
      description
        "AFC certification IDs";
      uses wireless-afc-types:afc-cert-id;
    }
  }

  grouping afc-band-req {
    description
      "AFC band request";
    leaf global-oper-class {
      type uint16;
      description
        "AFC request band global operating class";
    }
    leaf-list channel-cfi {
      type uint16;
      ordered-by user;
      description
        "AFC band channels";
    }
    leaf enabled {
      type boolean;
      description
        "AFC band is requested";
    }
  }

  grouping afc-request-data {
    description
      "AFC request data";
    container device {
      description
        "Device information";
      uses wireless-afc-types:afc-device-descriptor;
    }
    container location {
      description
        "AFC request location information";
      uses wireless-afc-types:afc-location;
    }
    container band20 {
      description
        "AFC request information for 20 Mhz channels";
      uses wireless-afc-types:afc-band-req;
    }
    container band40 {
      description
        "AFC request information for 40 Mhz channels";
      uses wireless-afc-types:afc-band-req;
    }
    container band80 {
      description
        "AFC request information for 80 Mhz channels";
      uses wireless-afc-types:afc-band-req;
    }
    container band160 {
      description
        "AFC request information for 160 Mhz channels";
      uses wireless-afc-types:afc-band-req;
    }
    container band80plus {
      description
        "AFC request information for 80+ Mhz channels";
      uses wireless-afc-types:afc-band-req;
    }
    leaf min-desired-power {
      type decimal64 {
        fraction-digits 2;
      }
      description
        "AFC minimal desired power";
    }
  }

  grouping afc-resp-code {
    description
      "AFC response code data";
    leaf code {
      type int16;
      description
        "AFC response code";
    }
    leaf description {
      type string;
      description
        "AFC response description";
    }
    leaf supplemental-info {
      type string;
      description
        "AFC response additional information";
    }
  }

  grouping afc-chan-resp {
    description
      "AFC response channel";
    leaf avail-channel-cfi {
      type uint16;
      description
        "AFC response available channel";
    }
    leaf max-eirp {
      type decimal64 {
        fraction-digits 2;
      }
      description
        "AFC response channel maximal effective isotropic radiated power";
    }
  }

  grouping afc-band-resp {
    description
      "AFC response band";
    leaf global-oper-class {
      type uint16;
      description
        "AFC response band global operating class";
    }
    list channels {
      description
        "AFC response band channels";
      uses wireless-afc-types:afc-chan-resp;
    }
  }

  grouping afc-response-data {
    description
      "AFC response data";
    leaf request-id {
      type uint64;
      description
        "AFC request ID";
    }
    leaf ruleset-id {
      type string;
      description
        "AFC response ruleset ID";
    }
    container resp-code {
      description
        "AFC response code";
      uses wireless-afc-types:afc-resp-code;
    }
    container band20 {
      description
        "AFC response information for 20 Mhz channels";
      uses wireless-afc-types:afc-band-resp;
    }
    container band40 {
      description
        "AFC response information for 40 Mhz channels";
      uses wireless-afc-types:afc-band-resp;
    }
    container band80 {
      description
        "AFC response information for 80 Mhz channels";
      uses wireless-afc-types:afc-band-resp;
    }
    container band160 {
      description
        "AFC response information for 160 Mhz channels";
      uses wireless-afc-types:afc-band-resp;
    }
    container band80plus {
      description
        "AFC response information for 80+ Mhz channels";
      uses wireless-afc-types:afc-band-resp;
    }
    leaf expire-time {
      type yang:date-and-time;
      description
        "AFC response expiration time";
    }
    leaf resp-rcvd-timestamp {
      type yang:date-and-time;
      description
        "AFC response received timestamp";
    }
  }

  grouping afc-httpcon-error {
    description
      "AFC health check HTTP error codes";
    leaf http-error-code {
      type uint32;
      description
        "HTTP error code";
    }
    leaf httpcon-error-code {
      type uint32;
      description
        "HTTP connection error";
    }
  }

  grouping afc-hc-error-status {
    description
      "AFC health check error status";
    choice hc-error-choice {
      description
        "Type of health check error";
      case afc-hc-err-http-con {
        container httpcon-error {
          description
            "HTTP connection error codes";
          uses wireless-afc-types:afc-httpcon-error;
        }
      }
      case afc-hc-err-prov {
        leaf fw-status {
          type wireless-enum-types:afc-provider-status;
          description
            "AFC provider status";
        }
      }
      case afc-hc-err-token {
        leaf no-valid-token {
          type boolean;
          description
            "Device does not have a valid token to communicate with cloud services";
        }
      }
      case afc-hc-err-otp {
        leaf not-otp-upgraded {
          type boolean;
          description
            "Device is not OTP upgraded";
        }
      }
      case afc-hc-err-onboard {
        leaf device-not-onboarded {
          type boolean;
          description
            "Device is not on boarded";
        }
      }
      case afc-hc-err-unknown {
        leaf error-unknown {
          type boolean;
          description
            "Error status is unknown";
        }
      }
    }
  }

  grouping afc-healthcheck {
    description
      "AFC health check status";
    leaf hc-timestamp {
      type yang:date-and-time;
      description
        "Cloud health check timestamp";
    }
    leaf query-in-progress {
      type boolean;
      description
        "Cloud health check query in progress";
    }
    leaf country-not-supported {
      type boolean;
      description
        "Country not supported by AFC, cloud health check not applicable";
    }
    leaf num-hc-down {
      type uint32;
      description
        "Number of times cloud health check failed";
    }
    choice cloud-status-choice {
      description
        "Type of health check status";
      case afc-cloud-error {
        container hc-error-status {
          description
            "AFC cloud health check error";
          uses wireless-afc-types:afc-hc-error-status;
        }
      }
      case afc-cloud-ok {
        leaf cloud-hc-ok {
          type boolean;
          description
            "AFC cloud health check status OK";
        }
      }
      case afc-cloud-unknown {
        leaf cloud-hc-unknown {
          type boolean;
          description
            "AFC cloud health check status is unknown";
        }
      }
    }
  }
}
