module Cisco-IOS-XE-http-deviation {
  yang-version 1.1;
  namespace "http://cisco.com/ns/yang/Cisco-IOS-XE-http-deviation";
  prefix ios-http-d;

  import cisco-semver {
    prefix cisco-semver;
  }
  import Cisco-IOS-XE-native {
    prefix ios;
  }
  import Cisco-IOS-XE-http {
    prefix ios-http;
  }

  organization
    "Cisco Systems";
  description
    "Cisco XE Native Deviation YANG module for IOS
     Copyright (c) 2023 by Cisco Systems, Inc.
     All rights reserved.";

  revision 2023-07-01 {
    description
      "- Added default value for http server
       - Added default value for http secure-server";
  }

  deviation "/ios:native/ios:ip/ios-http:http/ios-http:server" {
    deviate replace {
      default "false";
    }
  }

  deviation "/ios:native/ios:ip/ios-http:http/ios-http:secure-server" {
    deviate replace {
      default "false";
    }
  }
}
