submodule Cisco-IOS-XE-ethernet-oam {
  yang-version 1.1;
  belongs-to Cisco-IOS-XE-ethernet {
    prefix ios-eth;
  }

  import cisco-semver {
    prefix cisco-semver;
  }
  include Cisco-IOS-XE-ethernet-cfm-efp;

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Yang model for the following sub modules,
        * ethernet-oam
        * ethernet-lmi
        * ethernet-loopback
     Copyright (c) 2018-2019 by Cisco Systems, Inc.
     All rights reserved.";

  revision 2022-11-01 {
    description
      "- Update yang-version to 1.1";
    cisco-semver:module-version "1.3.0";
  }
  revision 2020-11-01 {
    description
      " - Added mib log file size command
       - Include cfm configurations under interface ethernet";
    cisco-semver:module-version "1.2.0";
  }
  revision 2019-11-01 {
    description
      "Added default values";
    cisco-semver:module-version "1.1.0";
  }
  revision 2019-07-01 {
    description
      "Establish semantic version baseline";
    cisco-semver:module-version "1.0.0";
  }
  revision 2018-12-05 {
    description
      "Initial revision";
  }

  grouping config-ethernet-oam-grouping {
    container oam {
      description
        "Operations Administration and Maintenance";
      container mib {
        description
          "Ethernet OAM MIB commands";
        container log {
          description
            "Ethernet OAM MIB log table";
          leaf size {
            description
              "Log table size - Number of log entries";
            type uint8 {
              range "0..200";
            }
            default "50";
          }
        }
      }
    }
  }

  grouping config-interface-ethernet-oam-grouping {
    container ethernet {
      description
        "Ethernet interface parameters";
      container oam {
        description
          "To enable Ethernet Link OAM";
        presence "true";
        container link-monitor {
          description
            "Ethernet OAM Link Monitor";
          container frame {
            description
              "Errored frames in a period measured by time";
            container threshold {
              description
                "Errored frame threshold";
              container high-frames {
                choice high-value {
                  default "none";
                  leaf value {
                    type uint16 {
                      range "1..65535";
                    }
                  }
                  leaf none {
                    type empty;
                  }
                }
              }
              container high {
                status deprecated;
                description
                  "High Threshold";
                leaf thresh {
                  status deprecated;
                  description
                    "Set the high errored frame threshold in number of frames";
                  type uint16 {
                    range "1..65535";
                  }
                }
                leaf none {
                  status deprecated;
                  description
                    "Disable high threshold";
                  type empty;
                }
              }
              leaf low {
                description
                  "Set the low errored frame threshold in number of frames";
                type uint16 {
                  range "0..65535";
                }
                default "1";
              }
            }
            leaf window {
              description
                "Set window size in multiple of 100 milliseconds (will be rounded off to second)";
              type uint16 {
                range "10..600";
              }
              default "10";
            }
          }
          container frame-period {
            description
              "Errored frames in a period measured by number of frames";
            container threshold {
              description
                "Errored frame-period threshold";
              container high-frames {
                choice high-value {
                  default "none";
                  leaf value {
                    type uint16 {
                      range "1..65535";
                    }
                  }
                  leaf none {
                    type empty;
                  }
                }
              }
              container high {
                status deprecated;
                description
                  "High Threshold";
                leaf f-thresh {
                  status deprecated;
                  description
                    "Set the high errored frame-period threshold in number of frames";
                  type uint16 {
                    range "1..65535";
                  }
                }
                leaf none {
                  status deprecated;
                  description
                    "Disable high threshold";
                  type empty;
                }
              }
              leaf low {
                description
                  "Set the low errored frame-period threshold in number of frames";
                type uint16 {
                  range "0..65535";
                }
                default "1";
              }
            }
            leaf window {
              description
                "Set window size in number of 10000 frames";
              type uint16 {
                range "1..65535";
              }
              default "1000";
            }
          }
          container frame-seconds {
            description
              "Errored frame seconds in a period";
            container threshold {
              description
                "Errored frame-seconds threshold";
              container high-frames {
                choice high-value {
                  default "none";
                  leaf value {
                    type uint16 {
                      range "1..900";
                    }
                  }
                  leaf none {
                    type empty;
                  }
                }
              }
              container high {
                status deprecated;
                description
                  "High Threshold";
                leaf e-thresh {
                  status deprecated;
                  description
                    "Set the high errored frame-seconds threshold in number of frames";
                  type uint16 {
                    range "1..900";
                  }
                }
                leaf none {
                  status deprecated;
                  description
                    "Disable high threshold";
                  type empty;
                }
              }
              leaf low {
                description
                  "Set the low errored frame-seconds threshold in number of seconds";
                type uint16 {
                  range "1..900";
                }
                default "1";
              }
            }
            leaf window {
              description
                "Set window size in multiple of 100 milliseconds (will be rounded off to second)";
              type uint16 {
                range "100..9000";
              }
              default "100";
            }
          }
          container high-threshold {
            description
              "Additional high threshold configuration";
            container action {
              description
                "Specify an action when the high threshold is crossed";
              leaf error-disable-interface {
                description
                  "Error-disable the interface";
                type empty;
              }
            }
          }
          leaf on {
            description
              "Enable link monitoring on the interface";
            type empty;
          }
          container receive-crc {
            description
              "Received frames with CRC errors in a period";
            container threshold {
              description
                "Errored frame-seconds threshold";
              container high-frames {
                choice high-value {
                  default "none";
                  leaf value {
                    type uint16 {
                      range "1..65535";
                    }
                  }
                  leaf none {
                    type empty;
                  }
                }
              }
              container high {
                description
                  "High Threshold";
                status deprecated;
                leaf crc-thresh {
                  status deprecated;
                  description
                    "Set the high received crc error threshold in number of frames";
                  type uint16 {
                    range "1..65535";
                  }
                }
                leaf none {
                  status deprecated;
                  description
                    "Disable high threshold";
                  type empty;
                }
              }
              leaf low {
                description
                  "Set the low received crc error threshold in number of frames";
                type uint16 {
                  range "0..65535";
                }
                default "10";
              }
            }
            leaf window {
              description
                "Set window size in multiple of 100 milliseconds (will be rounded off to second)";
              type uint16 {
                range "10..1800";
              }
              default "10";
            }
          }
          leaf supported {
            description
              "Support link monitoring on the interface";
            type empty;
          }
          container symbol-period {
            description
              "Errored symbols in a period";
            container threshold {
              description
                "Error symbol-period threshold";
              container high-symbols {
                choice high-value {
                  default "none";
                  leaf value {
                    type uint16 {
                      range "1..65535";
                    }
                  }
                  leaf none {
                    type empty;
                  }
                }
              }
              container high {
                description
                  "High Threshold";
                status deprecated;
                leaf err-thresh {
                  status deprecated;
                  description
                    "Set the high error symbol-period threshold in number of symbols";
                  type uint16 {
                    range "1..65535";
                  }
                }
                leaf none {
                  status deprecated;
                  description
                    "Disable high threshold";
                  type empty;
                }
              }
              leaf low {
                description
                  "Set the low error symbol-period threshold in number of symbols";
                type uint16 {
                  range "0..65535";
                }
                default "1";
              }
            }
            leaf window {
              description
                "Set window size in number of 1048576 symbols";
              type uint16 {
                range "1..65535";
              }
              default "100";
            }
          }
        }
        leaf max-rate {
          type uint8 {
            range "1..10";
          }
        }
        leaf min-rate {
          type uint8 {
            range "1..10";
          }
        }
        leaf mode {
          type enumeration {
            enum active;
            enum passive;
          }
        }
        container remote-failure {
          description
            "Ethernet OAM remote failure indication";
          container critical-event {
            description
              "Critical event";
            container action {
              description
                "Specify an action when a remote failure is detected";
              leaf error-disable-interface {
                description
                  "Error-disable the interface";
                type empty;
              }
            }
          }
          container dying-gasp {
            description
              "Dying gasp";
            container action {
              description
                "Specify an action when a remote failure is detected";
              presence "true";
              leaf error-disable-interface {
                description
                  "Error-disable the interface";
                type empty;
              }
            }
          }
          container link-fault {
            description
              "Link fault";
            container action {
              description
                "Specify an action when a remote failure is detected";
              presence "true";
              leaf error-disable-interface {
                description
                  "Error-disable the interface";
                type empty;
              }
            }
          }
        }
        container remote-loopback {
          description
            "Ethernet OAM Remote Loopback";
          leaf supported {
            description
              "Support remote loopback functionality";
            type empty;
          }
          leaf timeout {
            description
              "Set timeout value in number of seconds";
            type uint8 {
              range "1..10";
            }
          }
        }
        leaf timeout {
          type uint8 {
            range "2..30";
          }
        }
      }
      container dot1ad {
        description
          "ethernet dot1ad port";
        choice dot1ad-choice {
          leaf nni {
            description
              "dot1ad nni port";
            type empty;
          }
          container uni {
            description
              "dot1ad uni";
            choice uni-choice {
              leaf c-port {
                description
                  "dot1ad uni customer bridge port";
                type empty;
              }
              leaf s-port {
                description
                  "dot1ad uni s bridge port";
                type empty;
              }
            }
          }
        }
      }
      container loopback {
        description
          "Ethernet Dataplane Loopback";
        container permit {
          description
            "Allow data plane loopback to be activated";
          leaf external {
            description
              "Allow to loopback the traffic from the wire";
            type empty;
          }
          leaf internal {
            description
              "Allow to loopback the traffic from the relay";
            type empty;
          }
        }
      }
      uses config-interface-ethernet-cfm-grouping;
    }
  }

  grouping config-ethernet-lmi-grouping {
    container lmi {
      description
        "Local Management Interface";
      leaf ce {
        description
          "Ethernet LMI Customer Edge";
        type empty;
      }
      leaf global {
        description
          "Ethernet LMI is enabled on all supported Interfaces";
        type empty;
      }
    }
  }
}
