module Cisco-IOS-XE-dhcp-deviation {
  yang-version 1.1;
  namespace "http://cisco.com/ns/yang/Cisco-IOS-XE-dhcp-deviation";
  prefix ios-dhcp-d;

  import cisco-semver {
    prefix cisco-semver;
  }
  import Cisco-IOS-XE-native {
    prefix ios;
  }
  import Cisco-IOS-XE-dhcp {
    prefix ios-dhcp;
  }

  organization
    "Cisco Systems, Inc.";
  description
    "Cisco XE Native Dynamic Host Configuration Protocol (DHCP)
     Deviation Yang model.
     Copyright (c) 2023 by Cisco Systems, Inc.
     All rights reserved.";

  revision 2023-07-01 {
    description
      "- Update yang-version to 1.1
       - Add deviation for interface IP DHCP Snooping";
  }

  deviation "/ios:native/ios:interface/ios:Ethernet/ios:ip/ios:dhcp/ios-dhcp:snooping" {
    deviate not-supported;
  }

  deviation "/ios:native/ios:interface/ios:FastEthernet/ios:ip/ios:dhcp/ios-dhcp:snooping" {
    deviate not-supported;
  }

  deviation "/ios:native/ios:interface/ios:GigabitEthernet/ios:ip/ios:dhcp/ios-dhcp:snooping" {
    deviate not-supported;
  }

  deviation "/ios:native/ios:interface/ios:TenGigabitEthernet/ios:ip/ios:dhcp/ios-dhcp:snooping" {
    deviate not-supported;
  }

  deviation "/ios:native/ios:interface/ios:FiveGigabitEthernet/ios:ip/ios:dhcp/ios-dhcp:snooping" {
    deviate not-supported;
  }

  deviation "/ios:native/ios:interface/ios:AppGigabitEthernet/ios:ip/ios:dhcp/ios-dhcp:snooping" {
    deviate not-supported;
  }

  deviation "/ios:native/ios:interface/ios:TwentyFiveGigE/ios:ip/ios:dhcp/ios-dhcp:snooping" {
    deviate not-supported;
  }

  deviation "/ios:native/ios:interface/ios:TwoGigabitEthernet/ios:ip/ios:dhcp/ios-dhcp:snooping" {
    deviate not-supported;
  }

  deviation "/ios:native/ios:interface/ios:FortyGigabitEthernet/ios:ip/ios:dhcp/ios-dhcp:snooping" {
    deviate not-supported;
  }

  deviation "/ios:native/ios:interface/ios:HundredGigE/ios:ip/ios:dhcp/ios-dhcp:snooping" {
    deviate not-supported;
  }

  deviation "/ios:native/ios:interface/ios:Port-channel/ios:ip/ios:dhcp/ios-dhcp:snooping" {
    deviate not-supported;
  }

  deviation "/ios:native/ios:interface/ios:Loopback/ios:ip/ios:dhcp/ios-dhcp:snooping" {
    deviate not-supported;
  }

  deviation "/ios:native/ios:interface/ios:Tunnel/ios:ip/ios:dhcp/ios-dhcp:snooping" {
    deviate not-supported;
  }

  deviation "/ios:native/ios:interface/ios:Vlan/ios:ip/ios:dhcp/ios-dhcp:snooping" {
    deviate not-supported;
  }

  deviation "/ios:native/ios:interface/ios:Dialer/ios:ip/ios:dhcp/ios-dhcp:snooping" {
    deviate not-supported;
  }

  deviation "/ios:native/ios:interface/ios:vasileft/ios:ip/ios:dhcp/ios-dhcp:snooping" {
    deviate not-supported;
  }

  deviation "/ios:native/ios:interface/ios:vasiright/ios:ip/ios:dhcp/ios-dhcp:snooping" {
    deviate not-supported;
  }

  deviation "/ios:native/ios:interface/ios:ATM/ios:ip/ios:dhcp/ios-dhcp:snooping" {
    deviate not-supported;
  }

  deviation "/ios:native/ios:interface/ios:ATM-subinterface/ios:ATM/ios:ip/ios:dhcp/ios-dhcp:snooping" {
    deviate not-supported;
  }
}
