module Cisco-IOS-XE-meraki-connect-oper {
  yang-version 1.1;
  namespace "http://cisco.com/ns/yang/Cisco-IOS-XE-meraki-connect-oper";
  prefix meraki-connect-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring all parameters of Cloud Monitoring with Meraki Dashboard in a Network Element.
     Copyright (c) 2013 by Cisco Systems, Inc.
     All rights reserved.";

  revision 2023-11-01 {
    description
      "Initial revision";
    reference
      "1.0.0";
    cisco-semver:module-version "1.0.0";
  }

  typedef meraki-fetch-state {
    type enumeration {
      enum meraki-config-fetch-init {
        value 0;
        description
          "Config fetch init";
      }
      enum meraki-config-fetch-retry {
        value 1;
        description
          "Config fetch init retry";
      }
      enum meraki-config-fetch-failed {
        value 2;
        description
          "Config fetch failed";
      }
      enum meraki-config-fetch-succeeded {
        value 3;
        description
          "Config fetch succeeded";
      }
    }
    description
      "Possible fetch states for Meraki Nextunnel";
  }

  typedef meraki-nextunnel-state {
    type enumeration {
      enum meraki-tunnel-down {
        value 0;
        description
          "Meraki Nextunnel is down";
      }
      enum meraki-tunnel-up {
        value 1;
        description
          "Meraki Nextunnel is up";
      }
    }
    description
      "Possible states of the Meraki Nextunnel";
  }

  typedef meraki-reg-state {
    type enumeration {
      enum reg-init {
        value 0;
        description
          "Device registering";
      }
      enum reg-succeeded {
        value 1;
        description
          "Device register succeeded";
      }
      enum reg-failed {
        value 2;
        description
          "Device register failed";
      }
      enum reg-empty {
        value 3;
        description
          "Device is not registered";
      }
    }
    description
      "Possible device registration states with Meraki dashboard";
  }

  typedef meraki-device-pid {
    type enumeration {
      enum c9200l-48pl-4g {
        value 0;
        description
          "Catalyst 9200 48-port partial PoE+, 4 of 1 Gigabit fixed uplink";
      }
      enum c9200l-48pl-4x {
        value 1;
        description
          "Catalyst 9200 48-port partial PoE+, 4 of 1/10 Gigabit fixed uplink";
      }
      enum c9200l-48pxg-4x {
        value 2;
        description
          "Catalyst 9200 48 ports full POE+ (12 mGig ports up to 10 Gigabit, 36 ports up to 1 Gigabit), 4 of 1/10 Gigabit fixed uplink";
      }
      enum c9200l-24pxg-4x {
        value 3;
        description
          "Catalyst 9200 24 ports full PoE+ (8 mGig ports up to 10 Gigabit, 16 ports up to 1 Gigabit), 4 of 1/10 Gigabit fixed uplink";
      }
      enum c9200l-48p-4x {
        value 4;
        description
          "Catalyst 9200 48 ports full PoE+, 4 of 1/10 Gigabit fixed uplink";
      }
      enum c9200l-24p-4x {
        value 5;
        description
          "Catalyst 9200 24 ports full PoE+, 4 of 1/10 Gigabit fixed uplink";
      }
      enum c9200l-24t-4g {
        value 6;
        description
          "Catalyst 9200 24 ports data, 4 of 1 Gigabit fixed uplink";
      }
      enum c9200l-24p-4g {
        value 7;
        description
          "Catalyst 9200 24 ports full PoE+, 4 of 1 Gigabit fixed uplink";
      }
      enum c9200l-48t-4g {
        value 8;
        description
          "Catalyst 9200 48 ports data, 4 of 1 Gigabit fixed uplink";
      }
      enum c9200l-48p-4g {
        value 9;
        description
          "Catalyst 9200 48 ports full POE+, 4 of 1 Gigabit fixed uplink";
      }
      enum c9200l-24t-4x {
        value 10;
        description
          "Catalyst 9200 24 ports data, 4 of 1/10 Gigabit fixed uplink";
      }
      enum c9200l-48t-4x {
        value 11;
        description
          "Catalyst 9200 48 ports data, 4 of 1/10 Gigabit fixed uplink";
      }
      enum c9200l-24pxg-2y {
        value 12;
        description
          "Catalyst 9200 24 ports full PoE+ (8 mGig ports up to 10 Gigabit, 16 ports up to 1 Gigabit), 2 of 1/10/25 Gigabit fixed uplink";
      }
      enum c9200l-48pxg-2y {
        value 13;
        description
          "Catalyst 9200 48 ports full POE+ (8 mGig ports up to 10 Gigabit, 40 ports up to 1 Gigabit), 2 of 1/10/25 Gigabit fixed uplink";
      }
      enum c9200-24t {
        value 14;
        description
          "Catalyst 9200 24 ports data, Modular uplink options";
      }
      enum c9200-24p {
        value 15;
        description
          "Catalyst 9200 24 ports full PoE+, Modular uplink options";
      }
      enum c9200-24pb {
        value 16;
        description
          "Catalyst 9200 24 ports full PoE+, Modular uplink options";
      }
      enum c9200-24pxg {
        value 17;
        description
          "Catalyst 9200 24 ports full PoE+ (8 mGig ports up to 10 Gigabit, 16 ports up to 1 Gigabit), Modular uplink options";
      }
      enum c9200-48t {
        value 18;
        description
          "Catalyst 9200 48 ports data, Modular uplink options";
      }
      enum c9200-48p {
        value 19;
        description
          "Catalyst 9200 48 ports full PoE+, Modular uplink options";
      }
      enum c9200-48pb {
        value 20;
        description
          "Catalyst 9200 48 ports full PoE+, Modular uplink options";
      }
      enum c9200-48pl {
        value 21;
        description
          "Catalyst 9200 48 ports full PoE+, Modular uplink options";
      }
      enum c9200-48pxg {
        value 22;
        description
          "Catalyst 9200 48 ports full PoE+ (8 mGig ports up to 10 Gigabit, 40 ports up to 1 Gigabit), Modular uplink options";
      }
      enum c9200cx-12t-2x2g {
        value 23;
        description
          "Catalyst 9200 12 ports data, 2 of 1 Gigabit copper, 1 of 1 Gigabit Class 6, 2 of 10 Gigabit SFP+ fixed uplink";
      }
      enum c9200cx-8p-2x2g {
        value 24;
        description
          "Catalyst 9200 8 ports full PoE+, 2 of 1 Gigabit copper, 2 of 10 Gigabit SFP+ fixed uplink";
      }
      enum c9200cx-12p-2x2g {
        value 25;
        description
          "Catalyst 9200 12 ports PoE+, 2 of 1 Gigabit copper, 2 of 10 Gigabit SFP+ fixed uplink";
      }
      enum c9200cx-8uxg-2x {
        value 26;
        description
          "Catalyst 9200 8 ports UPOE (4 mGig ports up to 10 Gigabit, 4 ports up to 1 Gigabit), 2 of 10 Gigabit SFP+ fixed uplink";
      }
      enum c9200cx-8p-2xgh {
        value 27;
        description
          "Catalyst 9200 8 ports full PoE+, 2 of 1 Gigabit copper, 2 of 10 Gigabit SFP+ fixed uplink";
      }
      enum c9200cx-12p-2xgh {
        value 28;
        description
          "Catalyst 9200 12 ports PoE+, 2 of 1 Gigabit copper, 2 of 10 Gigabit SFP+ fixed uplink";
      }
      enum c9200cx-8uxg-2xh {
        value 29;
        description
          "Catalyst 9200 8 ports UPOE (4 mGig ports up to 10 Gigabit, 4 ports up to 1 Gigabit), 2 of 10 Gigabit SFP+ fixed uplink";
      }
      enum c9300l-48uxg-4x {
        value 30;
        description
          "Catalyst 9300 Series Switch with 36 of x1 Gigabit 12 of mGig UPOE downlink 4 of 10 Gigabit fixed uplink";
      }
      enum c9300l-24p-4g {
        value 31;
        description
          "Catalyst 9300 Series Switch with 24 of 1 Gigabit POE+ downlink 4 of 1 Gigabit fixed uplink";
      }
      enum c9300l-24p-4x {
        value 32;
        description
          "Catalyst 9300 Series Switch with 24 of 1 Gigabit POE+ downlink 4 of 10 Gigabit Fixed uplink";
      }
      enum c9300l-24t-4g {
        value 33;
        description
          "Catalyst 9300 Series Switch with 24 of 1 Gigabit non-POE downlink 4 of 1 Gigabit fixed uplink";
      }
      enum c9300l-24t-4x {
        value 34;
        description
          "Catalyst 9300 Series Switch with 24 of 1 Gigabit non-POE downlink 4 of 10 Gigabit fixed Uplink";
      }
      enum c9300l-24uxg-2q {
        value 35;
        description
          "Catalyst 9300 Series Switch with 16 of 1 Gigabit 8 of mGig UPOE downlink 2 of 40 Gigabit fixed uplink";
      }
      enum c9300l-24uxg-4x {
        value 36;
        description
          "Catalyst 9300 Series Switch with 16 of 1 Gigabit 8 of mGig UPOE downlink 4 of 10 Gigabit fixed uplink";
      }
      enum c9300l-48p-4g {
        value 37;
        description
          "Catalyst 9300 Series Switch with 48 of 1 Gigabit POE+ downlink 4 of 1 Gigabit fixed uplink";
      }
      enum c9300l-48p-4x {
        value 38;
        description
          "Catalyst 9300 Series Switch with 48 of 1 Gigabit POE+ downlink 4 of 10 Gigabit fixed uplink";
      }
      enum c9300l-48t-4g {
        value 39;
        description
          "Catalyst 9300 Series Switch with 48 of 1 Gigabit non-POE downlink 4 of 1 Gigabit fixed uplink";
      }
      enum c9300l-48t-4x {
        value 40;
        description
          "Catalyst 9300 Series Switch with 48 of 1 Gigabit non-POE downlink 4 of 10 Gigabit fixed uplink";
      }
      enum c9300l-48uxg-2q {
        value 41;
        description
          "Catalyst 9300 Series Switch with 36 of 1 Gigabit 12 of mGig UPOE downlink 2 of 40 Gigabit fixed uplink";
      }
      enum c9300l-48pf-4x {
        value 42;
        description
          "Catalyst 9300 Series Switch with 48 of 1 Gigabit POE+ downlink 4 of 10 Gigabit fixed uplink";
      }
      enum c9300l-48pf-4g {
        value 43;
        description
          "Catalyst 9300 Series Switch with 48 of 1 Gigabit POE+ downlink 4 of 1 Gigabit fixed uplink";
      }
      enum c9300lm-24u-4y-a-e {
        value 44;
        description
          "Catalyst 9300 Series Switch with 24 of 1 Gigabit UPOE downlink 4 of 25 Gigabit fixed uplink";
      }
      enum c9300lm-48t-4y-a-e {
        value 45;
        description
          "Catalyst 9300 Series Switch with 48 of 1 Gigabit downlink 4 of 25 Gigabit fixed uplink";
      }
      enum c9300lm-48u-4y-a-e {
        value 46;
        description
          "Catalyst 9300 Series Switch with 48 of 1 Gigabit UPOE downlink 4 of 25 Gigabit fixed uplink";
      }
      enum c9300lm-48ux-4y-a-e {
        value 47;
        description
          "Catalyst 9300 Series Switch with 40 of 1 Gigabit 8 of mGig UPOE downlink 4 of 25 Gigabit fixed uplink";
      }
      enum c9300-24t {
        value 48;
        description
          "Catalyst 9300 Series Switch with 24 of 1 Gigabit Interfaces";
      }
      enum c9300-24p {
        value 49;
        description
          "Catalyst 9300 Series Switch with 24 of 1 Gigabit POE Interfaces";
      }
      enum c9300-24u {
        value 50;
        description
          "Catalyst 9300 Series Switch";
      }
      enum c9300-24ub {
        value 51;
        description
          "Catalyst 9300 Series Switch with 24 of 1 Gigabit UPOE Interfaces";
      }
      enum c9300-24h {
        value 52;
        description
          "Catalyst 9300 Series Switch with 24 of 1 Gigabit UPOE+ Interfaces";
      }
      enum c9300-24ux {
        value 53;
        description
          "Catalyst 9300 Series Switch with 24 of 10 Gigabit UPOE Interfaces";
      }
      enum c9300-24uxb {
        value 54;
        description
          "Catalyst 9300 Series Switch with 24 of 10 Gigabit UPOE Interfaces";
      }
      enum c9300-48t {
        value 55;
        description
          "Catalyst 9300 Series Switch with 48 of 1 Gigabit Interfaces";
      }
      enum c9300-48p {
        value 56;
        description
          "Catalyst 9300 Series Switch with 48 of 1 Gigabit POE Interfaces";
      }
      enum c9300-48u {
        value 57;
        description
          "Catalyst 9300 Series Switch with 48 of 1 Gigabit UPOE Interfaces";
      }
      enum c9300-48ub {
        value 58;
        description
          "Catalyst 9300 Series Switch with 48 of 1 Gigabit UPOE Interfaces";
      }
      enum c9300-48h {
        value 59;
        description
          "Catalyst 9300 Series Switch with 48 of 1 Gigabit UPOE+ Interfaces";
      }
      enum c9300-48uxm {
        value 60;
        description
          "Catalyst 9300 Series Switch with 36 2.5G and 12 mGig UPOE Interfaces";
      }
      enum c9300-48un {
        value 61;
        description
          "Catalyst 9300 Series Switch with 48 of 5 Gigabit UPOE Interface";
      }
      enum c9300x-24hx {
        value 62;
        description
          "Catalyst 9300 Series Switch with 24 mGig UPOE Interfaces";
      }
      enum c9300x-48tx {
        value 63;
        description
          "Catalyst 9300 Series Switch with 48 mGig non-POE Interfaces";
      }
      enum c9300x-48hxn {
        value 64;
        description
          "Catalyst 9300 Series Switch with 40 of 5 Gigabit 8 of mGig UPOE Interfaces";
      }
      enum c9300x-48hx {
        value 65;
        description
          "Catalyst 9300 Series Switch with 48 mGig UPOE Interfaces";
      }
      enum c9300x-12y {
        value 66;
        description
          "Catalyst 9300 Series Switch with 12 of 25 Gigabit Interfaces";
      }
      enum c9300x-24y {
        value 67;
        description
          "Catalyst 9300 Series Switch with 24 of 25 Gigabit Interfaces";
      }
      enum c9500x-60l4d {
        value 68;
        description
          "Catalyst 9500 Series fixed switch with 60 of 50 Gigabit ports and 4 of 400 Gigabit ports";
      }
      enum c9500x-28c8d {
        value 69;
        description
          "Catalyst 9500 industry Gigabit switch";
      }
      enum c9500-32qc {
        value 70;
        description
          "Catalyst 9500 series with 32 Ports of 40 Gigabit/16 Ports of 100 Gigabit";
      }
      enum c9500-32c {
        value 71;
        description
          "Catalyst 9500 series with 32 Ports of 40 Gigabit/16 Ports of 100 Gigabit";
      }
      enum c9500-48y4c {
        value 72;
        description
          "Catalyst 9500 series with 48 Ports of 1 Gigabit/10 Gigabit/25 Gigabit + 4 Ports of 40 Gigabit/100 Gigabit";
      }
      enum c9500-24y4c {
        value 73;
        description
          "Catalyst 9500 is 1 RU fixed chassis with 24 Ports of 1 Gigabit/10 Gigabit/25 Gigabit + 4 Ports of 40 Gigabit/100 Gigabit";
      }
      enum c9500-24q {
        value 74;
        description
          "Catalyst 9500 24-port 40 Gigabit data only switch";
      }
      enum c9500-12q {
        value 75;
        description
          "Catalyst 9500 12-port 40 Gigabit data only switch";
      }
      enum c9500-40x {
        value 76;
        description
          "Catalyst 9500 40-port 10 Gigabit data only switch";
      }
      enum c9500-16x {
        value 77;
        description
          "Catalyst 9500 16-port 10 Gigabit data only switch";
      }
      enum c9800-40-k9 {
        value 78;
        description
          "Catalyst 9800-40 Wireless Controller";
      }
      enum c9800-80-k9 {
        value 79;
        description
          "Catalyst 9800-80 Wireless Controller";
      }
      enum c9800-l-c-k9 {
        value 80;
        description
          "Catalyst 9800-L-C Wireless Controller";
      }
      enum c9800-l-f-k9 {
        value 81;
        description
          "Catalyst 9800-L-F Wireless Controller";
      }
    }
    description
      "Possible devices enabled with Meraki monitoring";
  }

  grouping meraki-tunnel-config {
    description
      "Nextunnel configuration";
    leaf config-server {
      type string;
      description
        "Configuration server URL";
    }
    leaf primary {
      type string;
      description
        "Primary Nextunnel";
    }
    leaf secondary {
      type string;
      description
        "Secondary Nextunnel";
    }
    leaf client-ipv6-addr {
      type inet:ipv6-address;
      description
        "Client IPV6 address";
    }
    leaf server-ipv6-addr {
      type inet:ipv6-address;
      description
        "Server IPV6 address";
    }
    leaf backend-name {
      type string;
      description
        "Back end proxy URL";
    }
  }

  grouping meraki-tunnel-config-state {
    description
      "State of Nextunnel configuration";
    leaf last-fetch {
      type yang:date-and-time;
      description
        "Timestamp of the last Nextunnel configuration fetch";
    }
    leaf next-fetch {
      type yang:date-and-time;
      description
        "Timestamp of the next Nextunnel configuration fetch";
    }
    leaf fetch-state {
      type meraki-connect-ios-xe-oper:meraki-fetch-state;
      description
        "Nextunnel configuration fetches state";
    }
    leaf fetch-fail-detail {
      type string;
      description
        "Detail of Nextunnel configuration fetch fails reason";
    }
  }

  grouping meraki-connect {
    description
      "Details of the meraki connect";
    container config {
      description
        "Details of the tunnel configuration";
      uses meraki-connect-ios-xe-oper:meraki-tunnel-config;
    }
    container config-state {
      description
        "Details of the tunnel configuration state";
      uses meraki-connect-ios-xe-oper:meraki-tunnel-config-state;
    }
    leaf status {
      type boolean;
      description
        "The status of Meraki connect";
    }
  }

  grouping meraki-tunnel-state {
    description
      "The status of the Nextunnel connects to Meraki Dashboard";
    leaf primary {
      type meraki-connect-ios-xe-oper:meraki-nextunnel-state;
      description
        "Primary Nextunnel status";
    }
    leaf secondary {
      type meraki-connect-ios-xe-oper:meraki-nextunnel-state;
      description
        "Secondary Nextunnel status";
    }
    leaf primary-last-change {
      type yang:date-and-time;
      description
        "Timestamp of the last primary Nextunnel change";
    }
    leaf secondary-last-change {
      type yang:date-and-time;
      description
        "Timestamp of the last secondary Nextunnel change";
    }
    leaf client-last-restart {
      type yang:date-and-time;
      description
        "Timestamp of the last client restart";
    }
  }

  grouping meraki-tunnel-interface {
    description
      "The status of the Nextunnel interface";
    leaf status {
      type boolean;
      description
        "The Nextunnel interface status";
    }
    leaf rx-packets {
      type uint64;
      description
        "Number of packets received by the Nextunnel";
    }
    leaf tx-packets {
      type uint64;
      description
        "Number of packets transmitted by the Nextunnel";
    }
    leaf rx-errors {
      type uint64;
      description
        "Number of error packets received by the Nextunnel";
    }
    leaf tx-errors {
      type uint64;
      description
        "Number of error packets transmitted by the Nextunnel";
    }
    leaf rx-drop-packets {
      type uint64;
      description
        "Number of receiving packets dropped by the Nextunnel";
    }
    leaf tx-drop-packets {
      type uint64;
      description
        "Number of transmitting packets dropped by the Nextunnel";
    }
  }

  grouping device-reg-information {
    description
      "Details of the device registration information";
    leaf device-number {
      type uint8;
      description
        "Device number";
    }
    leaf pid {
      type meraki-connect-ios-xe-oper:meraki-device-pid;
      description
        "Product ID";
    }
    leaf serial-number {
      type string;
      description
        "Device serial number";
    }
    leaf mac-address {
      type yang:mac-address;
      description
        "Device MAC address ";
    }
    leaf meraki-id {
      type string;
      description
        "Meraki ID received from Meraki dashboard";
    }
    leaf status {
      type meraki-connect-ios-xe-oper:meraki-reg-state;
      description
        "The status of the device registration";
    }
    leaf err-detail {
      type string;
      description
        "Error message of the device registration";
    }
    leaf timestamp {
      type yang:date-and-time;
      description
        "Timestamp of updating device registration";
    }
  }

  grouping meraki-registration {
    description
      "Details of the device registration information";
    leaf url {
      type string;
      description
        "Meraki Dashboard URL";
    }
    list device-reg {
      key "device-number";
      description
        "A list of device registration information";
      uses meraki-connect-ios-xe-oper:device-reg-information;
    }
  }

  container meraki-connect-oper-data {
    config false;
    description
      "Operational data model for Meraki connect";
    container connect {
      presence "connect";
      description
        "Details of the Meraki connect";
      uses meraki-connect-ios-xe-oper:meraki-connect;
    }
    container tunnel-state {
      presence "tunnel-state";
      description
        "Details of the Nextunnel state";
      uses meraki-connect-ios-xe-oper:meraki-tunnel-state;
    }
    container tunnel-if {
      presence "tunnel-if";
      description
        "Details of the Nextunnel interface";
      uses meraki-connect-ios-xe-oper:meraki-tunnel-interface;
    }
    container reg {
      presence "reg";
      description
        "Details of the device registration with Meraki Dashboard";
      uses meraki-connect-ios-xe-oper:meraki-registration;
    }
  }
}
