module cisco-xe-openconfig-acl-deviation {
  namespace "http://cisco.com/ns/cisco-xe-openconfig-acl-deviation";

  prefix acl-devs;

  import openconfig-acl {
    prefix oc-acl;
  }

  import tailf-common { prefix tailf; }

  organization
    "Cisco Systems, Inc.";

  contact
    "Cisco Systems, Inc.
    Customer Service

    Postal: 170 W Tasman Drive
    San Jose, CA 95134

    Tel: +1 1800 553-NETS

    E-mail: cs-yang@cisco.com";

  description
    "This module defines deviation statements for openconfig-acl module.";

  revision 2017-08-25 {
    description
      "Added deviation to remove leafref from ingress/egress acls because of IOS allowing
       access-groups on interfaces when the access-group doesn't exit";
  }

  revision 2017-08-22 {
    description
      "Remove deviation to require at least one ingress or egress acl on interface";
  }

  revision 2017-05-04 {
    description
      "Add";
  }

  deviation "/oc-acl:acl/oc-acl:acl-sets/oc-acl:acl-set" {
    deviate add {
      unique "oc-acl:name";
    }
  }
 deviation "/oc-acl:acl/oc-acl:acl-sets/oc-acl:acl-set" {
    deviate add {
      must "type != 'oc-acl:ACL_L2'" {
        error-message "L2 access lists not supported";
      }
    }
  }

  deviation "/oc-acl:acl/oc-acl:acl-sets/oc-acl:acl-set/oc-acl:acl-entries/oc-acl:acl-entry/oc-acl:l2" {
    deviate  not-supported;
  }


  deviation "/oc-acl:acl/oc-acl:acl-sets/oc-acl:acl-set/oc-acl:acl-entries/oc-acl:acl-entry"
    + "/oc-acl:actions/oc-acl:config/oc-acl:log-action" {
    deviate add {
      must ". = 'oc-acl:LOG_NONE' or ../../../../../type != 'oc-acl:ACL_L2'" {
        error-message "Log action not supported for L2 ACL sets";
      }
    }
  }
  deviation "/oc-acl:acl/oc-acl:interfaces/oc-acl:interface/oc-acl:ingress-acl-sets/oc-acl:ingress-acl-set"
    + "/oc-acl:config/oc-acl:set-name" {
    deviate replace {
      type leafref {
        tailf:no-leafref-check;
        path "../../../../../../acl-sets/acl-set/config/name";
      }
    }
  }
  deviation "/oc-acl:acl/oc-acl:interfaces/oc-acl:interface/oc-acl:ingress-acl-sets/oc-acl:ingress-acl-set"
    + "/oc-acl:config/oc-acl:type" {
    deviate replace {
      type leafref {
        tailf:no-leafref-check;
        path "../../../../../../acl-sets/acl-set[name=current()/../set-name]" +
          "/config/type";
      }
    }
  }
  deviation "/oc-acl:acl/oc-acl:interfaces/oc-acl:interface/oc-acl:egress-acl-sets/oc-acl:egress-acl-set"
    + "/oc-acl:config/oc-acl:set-name" {
    deviate replace {
      type leafref {
        tailf:no-leafref-check;
        path "../../../../../../acl-sets/acl-set/config/name";
      }
    }
  }
  deviation "/oc-acl:acl/oc-acl:interfaces/oc-acl:interface/oc-acl:egress-acl-sets/oc-acl:egress-acl-set"
    + "/oc-acl:config/oc-acl:type" {
    deviate replace {
      type leafref {
        tailf:no-leafref-check;
        path "../../../../../../acl-sets/acl-set[name=current()/../set-name]" +
          "/config/type";
      }
    }
  }
}
