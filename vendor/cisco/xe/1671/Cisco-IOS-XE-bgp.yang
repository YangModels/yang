module Cisco-IOS-XE-bgp {
  namespace "http://cisco.com/ns/yang/Cisco-IOS-XE-bgp";
  prefix ios-bgp;

  import ietf-inet-types {
    prefix inet;
  }


  import Cisco-IOS-XE-types {
    prefix ios-types;
  }

  import Cisco-IOS-XE-features {
    prefix ios-features;
  }

  import Cisco-IOS-XE-interface-common {
    prefix ios-ifc;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Border Gateway Protocol (BGP) Yang model.
     Copyright (c) 2017 by Cisco Systems, Inc.
     All rights reserved.";

  // =========================================================================
  // REVISION
  // =========================================================================
  revision 2017-09-18 {
    description
      "BGP neighbor should match a v4/v6 address";
  }
  revision 2017-09-08 {
    description
      "Add show no for enhanced-error";
  }
  revision 2017-08-17 {
    description
      "send-community delete before change";
  }
  revision 2017-08-10 {
    description
      "Add bgp mpls-local-label, import path selection all, bgp bestpath as-path ignore";
  }
  revision 2017-08-02 {
    description
      "Fix delete for redistribute connected";
  }
  revision 2017-07-30 {
    description
      "adding neighbor remove-privare-as support";
  }
  revision 2017-07-27 {
    description
      "Fix delete for redistribute connected";
  }
  revision 2017-07-17 {
    description
      "adding neighbor send-label";
  }
  revision 2017-07-10 {
    description
      "adding redistribute ospfv3";
  }
  revision 2017-05-25 {
    description
      "adding neighber listen and next-hop-self all";
  }
  revision 2017-04-28 {
    description
      "inet:ipv6-prefix changed to ios-types:ipv6-prefix";
  }
  revision 2017-03-02 {
    description
      "NED extension - add version4 for bgp template peer-session";
  }
  revision 2017-02-08 {
    description
      "NED extension - router bgp address-family options - 
                   soo, max paths, import path";
  }
  revision 2017-02-07 {
    description
      "Initial revision";
  }


  grouping address-family-no-vrf-grouping {
    container no-vrf {
      list ipv4 {
        description
          "Address family";
        key "af-name";
        leaf af-name {
          type ios-types:bgp_ipv4_af_type;
        }
        uses bgp-ipv4-af-aggregate-address-grouping;
        uses bgp-address-family-grouping;
      }
      list ipv6 {
        description
          "Address family";
        key "af-name";
        leaf af-name {
          type ios-types:bgp_ipv6_af_type;
        }
        uses bgp-ipv6-af-aggregate-address-grouping;
        uses bgp-address-family-grouping;
      }
      // router bgp * / address-family vpnv4
      list vpnv4 {
        description
          "Address family";
        key "af-name";
        leaf af-name {
          type enumeration {
            enum "unicast" {
            }
            enum "multicast" {
            }
            enum "flowspec" {
            }
          }
        }
        uses bgp-address-family-grouping;
      }
      // router bgp * / address-family vpnv6
      list vpnv6 {
        description
          "Address family";
        key "af-name";
        leaf af-name {
          type enumeration {
            enum "unicast" {
            }
            enum "multicast" {
            }
            enum "flowspec" {
            }
          }
        }
        uses bgp-address-family-grouping;
      }
      // router bgp * / address-family nsap
      list nsap {
        description
          "Address family";
        key "af-name";
        leaf af-name {
          type enumeration {
            enum "unicast" {
            }
          }
        }
        uses bgp-address-family-grouping;
      }
      // router bgp * / address-family l2vpn
      list l2vpn {
        if-feature ios-features:l2vpn;
        description
          "Address family";
        key "af-name";
        leaf af-name {
          type enumeration {
            enum "evpn" {
            }
            enum "vpls" {
            }
          }
        }
        uses bgp-address-family-grouping;
      }
      // router bgp * / address-family rtfilter
      list rtfilter {
        description
          "Address family";
        key "af-name";
        leaf af-name {
          type enumeration {
            enum "unicast" {
            }
          }
        }
        uses bgp-address-family-grouping;
      }
    }
  }

  grouping neighbor-description-grouping {
      // router bgp * / neighbor * description
      leaf description {
        description
          "Neighbor specific description";
        type string;
      }
  }
  grouping neighbor-password-grouping {
      // router bgp * / neighbor * password
      container password {
        description
          "Set a password";
        leaf enctype {
          type uint8 {
            range "0..7";
          }
        }
        leaf text {
          type string;
        }
      }
  }
  grouping neighbor-peer-group-grouping {
      // router bgp * / neighbor * peer-group
      container peer-group {
        description
          "Member of the peer-group";
        presence "true";
        leaf peer-group-name {
          description
            "WORD;;peer-group name";
          type string;
        }
      }
  }
  grouping neighbor-remote-as-grouping {
      // router bgp * / neighbor * remote-as
      leaf remote-as {
        description
          "Specify a BGP neighbor";
        type union {
          type uint32 {
            range "1..4294967295";
          }
          type string;
        }
      }
    }
  grouping neighbor-update-source-grouping {
      // router bgp * / neighbor * update-source
      container update-source {
        description
          "Source of routing updates";
        uses ios-ifc:interface-grouping;
      }
  }
  grouping neighbor-version-grouping {
      // router bgp * / neighbor * version
      leaf version {
        description
          "Set the BGP version to match a neighbor";
        type uint16 {
          range "4";
        }
      }
  }
  grouping ip-community-list-standard-grouping {
    container deny {
      description
        "Specify community to reject";
      leaf-list deny-list {
        type union {
          type ios-types:community-number-type;
          type ios-types:community-well-known-type;
        }
      }
    }
    container permit {
      description
        "Specify community to accept";
      leaf-list permit-list {
        type union {
          type ios-types:community-number-type;
          type ios-types:community-well-known-type;
        }
      }
    }
  }

  grouping ip-community-list-expanded-grouping {
    container deny {
      description
        "Specify community to reject";
      leaf-list deny-list {
        ordered-by user;
        type string;
      }
    }
    container permit {
      description
        "Specify community to accept";
      leaf-list permit-list {
        ordered-by user;
        type string;
      }
    }
  }

  grouping ip-extcommunity-list-standard-grouping {
    container deny {
      description
        "Specify community to reject";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
    container permit {
      description
        "Specify community to accept";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
  }


  grouping config-ip-community-list-grouping {
    container community-list {
      description
        "Add a community list entry";
      list number-standard {
        key "no";
        leaf no {
          type uint16 {
            range "1..99";
          }
        }
        uses ip-community-list-standard-grouping;
      }
      list number-expanded {
        key "no";
        leaf no {
          type uint16 {
            range "100..500";
          }
        }
        uses ip-community-list-expanded-grouping;
      }
      list expanded {
        description
          "Add an expanded community-list entry";
        key "name";
        leaf name {
          type string;
        }
        uses ip-community-list-expanded-grouping;
      }
      list standard {
        description
          "Add a standard community-list entry";
        key "name";
        leaf name {
          type string;
        }
        uses ip-community-list-standard-grouping;
      }
    }
  }

  grouping config-ip-extcommunity-list-grouping {
    container extcommunity-list {
      description
        "Extended a community list entry";
      list number-standard {
        key "no";
        leaf no {
          type uint16 {
            range "1..99";
          }
        }
        uses ip-extcommunity-list-standard-grouping;
      }
      list number-expanded {
        key "no";
        leaf no {
          type uint16 {
            range "100..500";
          }
        }
        uses ip-community-list-expanded-grouping;
      }
      list expanded {
        description
          "Extended an expanded community-list entry";
        key "name";
        leaf name {
          type string;
        }
        uses ip-community-list-expanded-grouping;
      }
      list standard {
        description
          "Extended a standard community-list entry";
        key "name";
        leaf name {
          type string;
        }
        uses ip-extcommunity-list-standard-grouping;
      }
    }
  }

  grouping config-ip-as-path-grouping {
    // ip as-path access-list *
    list access-list {
      description
        "Specify an access list number";
      key "name";
      leaf name {
        type uint16 {
          range "1..500";
        }
      }
      uses ip-community-list-expanded-grouping;
    }
  }

  grouping max-path-grouping {
    container max-path {
      leaf max {
        type uint16 {
          range "1..32";
        }
      }
    }
    container external-rtfilter {
      description
        "VPN prefix multipath on external RTFilter peers";
      leaf max {
        type uint16 {
          range "1..32";
        }
      }
    }
  }

  grouping metric-route-map-grouping {
    leaf metric {
      description
        "Metric for redistributed routes";
      type uint32 {
        range "0..4294967295";
      }
    }
    leaf route-map {
      description
        "Route map reference";
      type string;
    }
  }

  grouping route-map-metric-grouping {
    leaf route-map {
      description
        "Route map reference";
      type string;
    }
    leaf metric {
      description
        "Metric for redistributed routes";
      type uint32 {
        range "0..4294967295";
      }
    }
  }

  grouping redistribute-isis-grouping {
    choice osi-ip-choice {
      leaf ip {
        description
          "Redistribution of IP dynamic routes";
        type empty;
      }
      leaf clns {
        description
          "Redistribution of OSI dynamic routes";
        type empty;
      }
    }
    leaf routes {
      type enumeration {
        enum "level-1";
        enum "level-2";
        enum "level-1-2";
      }
    }
    uses metric-route-map-grouping;
  }

  grouping bgp-ipv4-af-aggregate-address-grouping {
    container aggregate-address {
      description
        "Configure BGP aggregate entries";
      leaf ipv4-address {
        type inet:ipv4-address;
      }
      leaf ipv4-mask {
        type inet:ipv4-address;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping bgp-ipv6-af-aggregate-address-grouping {
    container aggregate-address {
      description
        "Configure BGP aggregate entries";
      leaf ipv6-address {
        type ios-types:ipv6-prefix;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  grouping redistribute-ospf-non-vrf-grouping {
    container match {
      leaf internal {
        description
          "Redistribute OSPF internal routes";
        type empty;
      }
      leaf external {
        description
          "Redistribute OSPF external routes";
        type ios-types:redist-ospf-external-type;
      }
      leaf external2 {
        description
          "Redistribute OSPF external routes";
        type ios-types:redist-ospf-external-type;
      }
      leaf nssa-external {
        description
          "Redistribute OSPF NSSA external routes";
        type ios-types:redist-ospf-external-type;
      }
      uses metric-route-map-grouping;
    }
    uses metric-route-map-grouping;
  }

  grouping bgp-address-family-grouping {
    // router bgp * / import
    container import {
      description "Configure path import";
      container path {
        description "Path selection and path limit";
        leaf limit {
          description "Per net imported path limit";
          type uint8 {
            range "2..255";
          }
        }
        container selection {
          description
            "Path selection policy";
          leaf all {
            description
              "Import all available paths";
            type empty;
          }
        }
      }
    }
    // router bgp * / bgp
    container bgp {
      description
        "BGP specific commands";
      // router bgp * / bgp router-id
      leaf router-id {
        description
          "Override configured router identifier (peers will reset)";
        type inet:ipv4-address;
      }
      // router bgp * / bgp always-compare-med
      leaf always-compare-med {
        description
          "Allow comparing MED from different neighbors";
        type empty;
      }
      // router bgp * / bgp aggregate-timer
      leaf aggregate-timer {
        description
          "Timer interval";
        type uint8 {
          range "6..60";
        }
      }

      // router bgp * / bgp asnotation
      container asnotation {
        description "Change the default asplain notation";
        leaf dot {
          description "asdot notation";
          type empty;
        }
      }

      // router bgp * / bgp nopeerup-delay
      container nopeerup-delay {
        description
          "Set how long BGP will wait for the first peer to come up before beginning the update delay or graceful restart timers (in seconds)";
        leaf cold-boot {
          description
            "Delay in seconds";
          type uint16 {
            range "1..3600";
          }
        }
        leaf nsf-switchover {
          description
            "Delay in seconds";
          type uint16 {
            range "1..3600";
          }
        }
        leaf post-boot {
          description
            "Delay in seconds";
          type uint16 {
            range "1..3600";
          }
        }
        leaf user-initiated {
          description
            "Delay in seconds";
          type uint16 {
            range "1..3600";
          }
        }
      }
      // router bgp * / bgp recursion
      container recursion {
        description
          "recursion rule for the nexthops";
        leaf host {
          description
            "recursion via host for the nexthops";
          type empty;
        }
      }
      // router bgp * / bgp advertise-best-external
      leaf advertise-best-external {
        description
          "Advertise best external path to internal peers";
        type empty;
      }
      // router bgp * / bgp additional-paths
      container additional-paths {
        description
          "Additional paths in the BGP table";
        leaf install {
          description
            "Additional paths to install into RIB";
          type empty;
        }
        leaf receive {
          description
            "Receive additional paths from neighbors";
          type empty;
        }
        container select {
          description
            "Selection criteria to pick the paths";
          container all {
            description
              "Select all available paths";
            presence "true";
            container best {
              description
                "Select best N paths";
              list range {
                key "range";
                leaf range {
                  description
                    "Number of best paths in additional paths to be selected";
                  type uint8 {
                    range "2..3";
                  }
                }
                leaf group-best {
                  description
                    "Select group-best path";
                  type empty;
                }
              }
            }
            container group-best {
              description
                "Select group-best path";
              presence "true";
              leaf best {
                description
                  "Number of best paths in additional paths to be selected";
                type uint8 {
                  range "2..3";
                }
              }
            }
          }
          container backup {
            description
              "Select backup path";
            presence "true";
            leaf best-external {
              description
                "Select best-external path";
              type empty;
            }
          }
          container best {
            description
              "Select best N paths";
            list range {
              key "range";
              leaf range {
                description
                  "Number of best paths in additional paths to be selected";
                type uint8 {
                  range "2..3";
                }
              }
              leaf all {
                description
                  "Select all available paths";
                type empty;
              }
              container group-best {
                description
                  "Select group-best path";
                presence "true";
                leaf all {
                  description
                    "Select all available paths";
                  type empty;
                }
              }
            }
          }
          container best-external {
            description
              "Select best-external path";
            presence "true";
            leaf backup {
              description
                "Select backup path";
              type empty;
            }
          }
          container group-best {
            description
              "Select group-best path";
            presence "true";
            leaf all {
              description
                "Select all available paths";
              type empty;
            }
            leaf best {
              description
                "Number of best paths in additional paths to be selected";
              type uint8 {
                range "2..3";
              }
            }
          }
        }
        container send {
          description
            "Send additional paths to neighbors";
          presence "true";
          leaf receive {
            description
              "Receive additional paths from neighbors";
            type empty;
          }
        }
      }
      // router bgp * / bgp bestpath
      container bestpath {
        description
          "Change the default bestpath selection";
        leaf as-path {
          type enumeration {
            enum "ignore";
          }
        }
        leaf compare-routerid {
          type empty;
        }
        container cost-community {
          description
            "cost community";
          leaf ignore {
            description
              "Ignore cost communities in bestpath selection";
            type empty;
          }
        }
        container igp-metric {
          description
            "igp metric";
          leaf ignore {
            description
              "Ignore igp metric in bestpath selection";
            type empty;
          }
        }
        container med {
          description
            "MED attribute";
          choice med-choice {
            container confed {
              description
                "Compare MED among confederation paths";
              presence "Compare MED among confederation paths";
              leaf missing-at-worst {
                description
                  "Treat missing MED as the least preferred one";
                type empty;
              }
            }
            leaf missing-at-worst {
              description
                "Treat missing MED as the least preferred one";
              type empty;
            }
          }
        }
      }
      // router bgp * / bgp client-to-client
      container client-to-client {
        description
          "Configure client to client route reflection";
        leaf reflection {
          description
            "reflection of routes allowed";
          type empty;
        }
      }
      // router bgp * / bgp cluster-id
      leaf cluster-id {
        type union {
          type uint32 {
            range "1..4294967295";
          }
          type inet:ipv4-address;
        }
      }
      // router bgp * / bgp confederation
      container confederation {
        description
          "AS confederation parameters";
        leaf identifier {
          type inet:as-number;
        }
        container peers {
          description
            "Peer ASs in BGP confederation";
          leaf-list peers-as {
            type inet:as-number;
          }
        }
      }
      // router bgp * / bgp consistency-checker
      container consistency-checker {
        description
          "Consistency-checker";
        container auto-repair {
          description
            "Auto-Repair";
          presence "true";
          leaf interval {
            description
              "Interval (minutes)";
            type uint16 {
              range "5..1440";
            }
          }
        }
        container error-message {
          description
            "Log Error-Msg";
          presence "true";
          leaf interval {
            description
              "Interval (minutes)";
            type uint16 {
              range "5..1440";
            }
          }
        }
      }
      // router bgp * / bgp dampening
      container dampening {
        description
          "Enable route-flap dampening";
        presence "enable bgp route-flap dampening";
        choice dampening-choice {
          leaf route-map {
            description
              "Route-map to specify criteria for dampening";
            type string;
          }
          container dampen {
            leaf half-life-time {
              type uint8 {
                range "1 .. 45";
              }
            }
            leaf reuse-time {
              type uint16 {
                range "1 .. 20000";
              }
            }
            leaf suppress-time {
              type uint16 {
                range "1 .. 20000";
              }
            }
            leaf max-suppress-time {
              type uint8 {
                range "1 .. 255";
              }
            }
          }
        }
      }
      // router bgp * / bgp default
      container default {
        description
          "Configure BGP defaults";
        choice default-choice {
          leaf ipv4-unicast {
            description
              "Activate ipv4-unicast for a peer by default";
            type boolean;
          }
          leaf ipv6-nexthop {
            description
              "Default IPv6 nexthop format";
            type empty;
          }
          leaf local-preference {
            description
              "local preference (higher=more preferred)";
            type uint32 {
              range "1..4294967295";
            }
          }
          leaf route-target {
            description
              "Control behavior based on Route-Target attributes";
            type enumeration {
              enum "filter";
            }
          }
        }
      }
      // router bgp * / bgp deterministic-med
      leaf deterministic-med {
        description
          "Pick the best-MED path among paths advertised from the neighboring AS";
        type empty;
      }
      // router bgp * / bgp dmzlink-bw
      leaf dmzlink-bw {
        description
          "Use DMZ Link Bandwidth as weight for BGP multipaths";
        type empty;
      }
      // router bgp * / bgp enforce-first-as
      leaf enforce-first-as {
        description
          "Enforce the first AS for EBGP routes(default)";
        type empty;
      }
      //router bgp * /bgp enhanced-error
      leaf enhanced-error {
        description
          "Enabled BGP Enhanced error handling";
        type boolean;
      }
      // router bgp * / bgp fast-external-fallover
      leaf fast-external-fallover {
        description
          "Immediately reset session if a link to a directly connected external peer goes down";
        type boolean;
      }
      // router bgp * / bgp graceful-restart
      container graceful-restart {
        description
          "Graceful restart capability parameters";
        presence "Graceful restart capability parameters";
        leaf extended {
          type empty;
        }
        leaf restart-time {
          description
            "Set the max time needed to restart and come back up";
          type uint16 {
            range "1..3600";
          }
        }
        leaf stalepath-time {
          description
            "Set the max time to hold onto restarting peer's stale paths";
          type uint16 {
            range "1..3600";
          }
        }
      }
      // router bgp * / bgp ha-mode
      container ha-mode {
        description
          "Select BGP High Availability mode";
        container sso {
          description
            "BGP High Availability NSR sso mode";
          presence "true";
          leaf prefer {
            description
              "Perfer BGP High Availability NSR sso mode";
            type empty;
          }
        }
      }
      // router bgp * / bgp inject-map *
      list inject-map {
        description
          "Routemap which specifies prefixes to inject";
        key "name";
        leaf name {
          type string;
        }
        leaf exist-map {
          description
            "Routemap which specifies exist condition";
          type string;
        }
        leaf copy-attributes {
          description
            "Copy attributes from aggregate";
          type empty;
        }
      }
      // router bgp * / bgp log-neighbor-changes
      leaf log-neighbor-changes {
        description
          "Log neighbor up/down and reset reason";
        type empty;
      }
      // router bgp * / bgp listen 
      container listen {
        description
          "Neighbor subnet range listener";
        leaf limit {
          description
            "Set the max limit for the dynamic subnet range neighbors";
          type uint16 {
            range "1..10000";
          }
        }
        list range {
          description
            "Subnet network range";
          key "network-range peer-group";
          leaf network-range {
            type union {
              type inet:ipv4-prefix;
              type ios-types:ipv6-prefix;
            }
          }
          leaf peer-group {
            description
              "Member of the peer-group";
            type string;
          }
        }
      }
      // router bgp * / bgp maxas-limit
      leaf maxas-limit {
        description
          "Allow AS-PATH attribute from any neighbor imposing a limit on number of ASes";
        type uint16 {
          range "1..2000";
        }
      }
      // router bgp * / bgp maxcommunity-limit
      leaf maxcommunity-limit {
        description
          "Number of communities in the COMMUNITY attribute";
        type uint16 {
          range "1..1018";
        }
      }
      //router bgp * / bgp route-map
      container route-map {
        description
          "bgp route-map commands";
        leaf priority {
          description
            "Have route-map set commands take priority over BGP commands such ";
          type empty;
        }
      }
      // router bgp * / bgp slow-peer
      container slow-peer {
        description
          "Configure slow-peer";
        container detection {
          description
            "Slow-peer detection";
          presence "true";
          leaf disable {
            description
              "Disable slow-peer detection";
            type empty;
          }
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      // router bgp * / bgp update-group
      container update-group {
        description
          "Manage peers in bgp update groups";
        container split {
          description
            "Split update groups based on Policy";
          leaf as-override {
            description
              "Keep peers with as-override in different update groups";
            type empty;
          }
        }
      }
      // router bgp * / bgp nexthop
      container nexthop {
        description
          "Nexthop tracking commands";
        container trigger {
          description
            "Nexthop triggering";
          leaf delay {
            description
              "Set the delay to tigger nexthop tracking";
            type uint8 {
              range "0..100";
            }
          }
          leaf enable {
            description
              "Enable nexthop tracking";
            type boolean;
          }
        }
        leaf route-map {
          description
            "Route map for valid nexthops";
          type string;
        }
      }
      // router bgp * / bgp  mpls-local-label
      leaf mpls-local-label {
        description
          "Installs local label for ALL /32 prefixes";
        type empty;
      }
      // router bgp * / bgp redistribute-internal
      leaf redistribute-internal {
        description
          "Allow redistribution of iBGP into IGPs (dangerous)";
        type empty;
      }
      // router bgp * / bgp regexp
      container regexp {
        description
          "Select regular expression engine";
        leaf deterministic {
          description
            "Enable bounded-execution-time regular expression engine";
          type empty;
        }
      }
      // router bgp * / bgp scan-time
      leaf scan-time {
        description
          "Configure background scanner interval";
        type uint8 {
          range "5..60";
        }
      }
      // router bgp * / bgp soft-reconfig-backup
      leaf soft-reconfig-backup {
        description
          "Use soft-reconfiguration inbound only when route-refresh is not negotiated";
        type empty;
      }// router bgp * / bgp suppress-inactive
      leaf suppress-inactive {
        description
          "Suppress routes that are not in the routing table";
        type empty;
      }
      //rotuer bgp * /transport //MOVED from router bgp to router bgp bgp
      container transport {
        description
          "Transport options";
        leaf path-mtu-discovery {
          description
            "Use transport path MTU discovery";
          type boolean;
        }
      }
      // router bgp * / bgp update-delay
      leaf update-delay {
        description
          "Set the max initial delay for sending update";
        type uint16 {
          range "1..3600";
        }
      }
    }//bgp
    // router bgp * / default-information
    container default-information {
      description
        "Control distribution of default information";
      leaf originate {
        description
          "Distribute a default route";
        type empty;
      }
    }
    // router bgp * / default-metric
    leaf default-metric {
      description
        "Set metric of redistributed routes";
      type uint32 {
        range "1..4294967295";
      }
    }
    // router bgp * / distance
    container distance {
      description
        "Define an administrative distance";
      container bgp {
        description
          "BGP distance";
        leaf extern-as {
          type uint16 {
            range "1..255";
          }
        }
        leaf internal-as {
          type uint16 {
            range "1..255";
          }
        }
        leaf local {
          type uint16 {
            range "1..255";
          }
        }
      }
      list adm-distance {
        key "distance srcip wildbits";
        leaf distance {
          type uint16 {
            range "1..255";
          }
        }
        leaf srcip {
          type inet:ipv4-address;
        }
        leaf wildbits {
          type inet:ipv4-address;
        }
        leaf acl {
          type union {
            type uint16 {
              range "1..99";
            }
            type uint16 {
              range "1300..1999";
            }
            type string {
              pattern "[a-zA-Z].*";
            }
          }
        }
      }
    }
    // router bgp * / distribute-list
    list distribute-list {
      description
        "Filter networks in routing updates";
      key "id";
      leaf id {
        type ios-types:bgp-distribute-list-type;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
    // router bgp * / maximum-paths
    container maximum-paths {
      description
        "Forward packets over multiple paths";
      uses max-path-grouping;
      choice max-path-choice {
          leaf eibgp {
            description
              "Both eBGP and iBGP paths as multipath";
            type uint16 {
              range "1..32";
            }
          }
          container ibgp {
            description
              "iBGP-multipath";
            choice ibgp-choice {
                leaf unequal-cost {
                  description
                    "Perform Un-Equal cost multipath selection";
                  type uint16 {
                    range "1..32";
                  }
                }
                leaf max {
                  type uint16 {
                    range "1..32";
                  }
                }
            }
          }
      }
    }
    // router bgp * / neighbor *
    list neighbor {
      description
        "Specify a neighbor router";
      ordered-by user;
      must "count(*) > 1" {
      }
      key "id";
      leaf id {
        type union {
          type inet:ipv4-address;
          type inet:ipv6-address;
          type string;
        }
      }
      uses neighbor-peer-group-grouping;
      uses neighbor-remote-as-grouping;
      // router bgp * / neighbor * local-as
      container local-as {
        description
          "Specify a local-as number";
        presence "Specify a local-as number";
        leaf as-no {
          type ios-types:bgp-as-number-type;
        }
        leaf no-prepend {
          description
            "Do not prepend local-as to updates from ebgp peers";
          type empty;
        }
        leaf replace-as {
          description
            "Replace real AS with local AS in the EBGP updates";
          type empty;
        }
        leaf dual-as {
          description
            "Accept either real AS or local AS from the ebgp peer";
          type empty;
        }
      }
      // router bgp * / neighbor * activate
      leaf activate {
        description
          "Enable the Address Family for this Neighbor";
              //must "(../remote-as or ../peer-group)" {
              // }
        type empty;
      }
      // router bgp * / neighbor * additional paths
      container additional-paths {
        leaf disable {
          description
            "Disable additional paths for this neighbor";
          type empty;
        }
        leaf receive {
          description
            "Receive additional paths from neighbors";
          type empty;
        }
        container send {
          description
            "Send additional paths to this neighbor";
          presence "true";
          leaf receive {
            description
              "Receive additional paths from this neighbor";
            type empty;
          }
        }
      }
      // router bgp */ neighbor * advertise
      container advertise {
        description
          "Advertise to this neighbor";
        container additional-paths {
          description
            "Advertise additional paths";
          container all {
            description
              "Select all available paths";
            presence "true";
            container best {
              description
                "Select best N paths";
              list best-range {
                key "range";
                leaf range {
                  description
                    "Number of best paths in additional paths to be selected";
                  type uint8 {
                    range "2..3";
                  }
                }
                leaf group-best {
                  description
                    "Select group-best paths";
                  type empty;
                }
              }
            }
            container group-best {
              description
                "Select group-best paths";
              presence "true";
              leaf best {
                description
                  "Number of best paths in additional paths to be selected";
                type uint8 {
                  range "2..3";
                }
              }
            }
          }
          container best {
            description
              "Select best N paths";
            list best-range {
              key "range";
              leaf range {
                description
                  "Number of best paths in additional paths to be selected";
                type uint8 {
                  range "2..3";
                }
              }
              leaf all {
                description
                  "Select all available paths";
                type empty;
              }
              container group-best {
                description
                  "Select group-best paths";
                presence "true";
                leaf all {
                  description
                    "Select all available paths";
                  type empty;
                }
              }
            }
          }
          container group-best {
            description
              "Select group-best paths";
            presence "true";
            leaf all {
              description
                "Select all available paths";
              type empty;
            }
            leaf best {
              description
                "Number of best paths in additional paths to be selected";
              type uint8 {
                range "2..3";
              }
            }
          }
        }
        leaf best-external {
          description
            "Advertise best-external (at RRs best-internal) path";
          type empty;
        }
        container diverse-path {
          description
            "Advertise diverse path";
          container backup {
            description
              "Diverse path can be backup path";
            presence "true";
            leaf mpath {
              description
                "Diverse path can be multipath";
              type empty;
            }
          }
          leaf mpath {
            description
              "Diverse path can be multipath";
            type empty;
          }
        }
      }
      // router bgp */ neighbor * advertise-map
      container advertise-map {
        description
          "specify route-map for conditional advertisement";
        list name {
          key "word";
          leaf word {
            description
              "advertise route-map name";
            type string;
          }
          leaf exist-map {
            description
              "condition route-map name";
            type string;
          }
          leaf non-exist-map {
            description
              "condition route-map name";
            type string;
          }
        }
      }
      // router bgp */ neighbor * aigp
      container aigp {
        description
          "Enable a AIGP on neighbor";
        presence "true";
        container send {
          description
            "Cost community or MED carrying AIGP VALUE";
          container cost-community {
            description
              "Cost extended community carrying AIGP Value";
            list cc-range {
              key "range";
              leaf range {
                description
                  "Community ID";
                type uint8 {
                  range "0..255";
                }
              }
              container poi {
                description
                  "Point of Insertion";
                container igp-cost {
                  description
                    "Point of Insertion After IGP";
                  presence "true";
                  leaf transitive {
                    description
                      "Cost community is Transitive";
                    type empty;
                  }
                }
                container pre-bestpath {
                  description
                    "Point of Insertion At Beginning";
                  presence "true";
                  leaf transitive {
                    description
                      "Cost community is Transitive";
                    type empty;
                  }
                }
              }
            }
          }
          leaf med {
            description
              "Med carrying AIGP Value";
            type empty;
          }
        }
      }
      //router bgp * /neighbor * allow-policy
      leaf allow-policy {
        description
          "Enable the policy support for this IBGP Neighbor";
        type empty;
      }
      //router bgp * /neighbor * announce
      container announce {
        description
          "Announce RPKI State using an Extended Community";
        container rpki {
          description
            "Announce RPKI information using an Extended Community";
          leaf state {
            description
              "Announce RPKI State information using an Extended Community";
            type empty;
          }
        }
      }
      // router bgp * / neighbor * advertisement-interval
      leaf advertisement-interval {
        description
          "Minimum interval between sending BGP routing updates";
        type uint16 {
          range "0..600";
        }
      }
      // router bgp * / neighbor * allowas-in
      container allowas-in {
        description
          "Accept as-path with my AS present in it";
        presence "accept as-paths";
        leaf as-number {
          type uint8 {
            range "1..10";
          }
        }
      }
      // router bgp * / neighbor * as-override
      container as-override {
        description
          "Override matching AS-number while sending update";
        presence "true";
        leaf disable {
          type empty;
        }
      }
      // router bgp * / neighbor * capability
      container capability {
        description
          "Advertise capability to the peer";
        container orf {
          description
            "Advertise ORF capability to the peer";
          leaf-list prefix-list {
            description
              "Advertise prefixlist ORF capability to this neighbor";
            max-elements "1";
            type enumeration {
              enum "both";
              enum "receive";
              enum "send";
            }
          }
        }
      }
      // router bgp * / neighbor * cluster-id
      leaf cluster-id {
        type union {
          type uint32 {
            range "1..4294967295";
          }
          type inet:ipv4-address;
        }
      }
      // router bgp * / neighbor * default-originate
      container default-originate {
        description
          "Originate default route to this neighbour";
        presence "enable originate default route to this neighbour";
        leaf route-map {
          description
            "Route-map to specify criteria to originate default";
          type string;
        }
      }
      uses neighbor-description-grouping;
      // router bgp * / neighbor * disable-connected-check
      leaf disable-connected-check {
        description
          "One-hop away EBGP peer using loopback address";
        type empty;
      }
      // router bgp * / neighbor * distribute-list *
      list distribute-list {
        description
          "Filter updates to/from this neighbor";
        key "inout";
        leaf inout {
          type enumeration {
            enum "in" {
            }
            enum "out" {
            }
          }
        }
        leaf accesslist {
          type ios-types:bgp-distribute-list-type2;
          mandatory true;
        }
      }
      // router bgp * / neighbor * dmzlink-bw
      leaf dmzlink-bw {
        description
          "Propagate the DMZ link bandwidth";
        type empty;
      }
      // router bgp * / neighbor * ebgp-multihop
      container ebgp-multihop {
        description
          "Allow EBGP neighbors not on directly connected networks";
        presence "Allow EBGP neighbors not on directly connected networks";
        leaf max-hop {
          type uint8 {
            range "1..255";
          }
        }
      }
      // router bgp * / neighbor * fall-over
      container fall-over {
        description
          "session fall on peer route lost";
        container bfd {
          description
            "Use BFD to detect failure";
          presence "true";
        }
      }
      // router bgp * / neighbor * filter-list *
      list filter-list {
        description
          "Establish BGP filters";
        key "inout";
        leaf inout {
          type enumeration {
            enum "in" {
            }
            enum "out" {
            }
          }
        }
        leaf as-path-list {
          type uint16 {
            range "1..500";
          }
          mandatory true;
        }
      }
      // router bgp * / neighbor * inherit
      container inherit {
        description
          "Inherit a template";
        leaf peer-policy {
          description
            "Inherit a peer-policy template";
          type string;
        }
        leaf peer-session {
          description
            "Inherit a peer-session template";
          type string;
        }
      }
      // router bgp * / neighbor * log-neighbor-changes
      container log-neighbor-changes {
        description
          "Log neighbor up/down and reset reason";
        presence "true";
        leaf disable {
          description
            "disable";
          type empty;
        }
      }
      // router bgp * / neighbor * maximum-prefix
      container maximum-prefix {
        description
          "Maximum number of prefixes accepted from this peer";
        leaf max-prefix-no {
          type uint32 {
            range "1..2147483647";
          }
        }
        leaf threshold {
          type uint8 {
            range "1..100";
          }
        }
        leaf restart {
          description
            "Restart bgp connection after limit is exceeded";
          type uint16 {
            range "1..65535";
          }
        }
        leaf warning-only {
          description
            "Only give warning message when limit is exceeded";
          type empty;
        }
      }
      // router bgp * / neighbor * next-hop-self
      container next-hop-self {
        description
          "Disable the next hop calculation for this neighbor";
        presence "true";
        leaf all {
          description
            "Enable next-hop-self for both eBGP and iBGP received paths";
          type empty;
        }
      }
      // router bgp * / neighbor * next-hop-unchanged
      leaf next-hop-unchanged {
        description
          "Propagate the iBGP paths's next hop unchanged for this neighbor";
        type empty;
      }
      uses neighbor-password-grouping;
      // router bgp * / neighbor * prefix-list *
      list prefix-list {
        description
          "Filter updates to/from this neighbor";
        key "inout";
        leaf inout {
          type enumeration {
            enum "in" {
            }
            enum "out" {
            }
          }
        }
        leaf prefix-list-name {
          type string;
          mandatory true;
        }
      }
      // router bgp * / neighbor * path-attribute
      container path-attribute {
        description
          "BGP optional attribute filtering";
        container discard {
          description
            "Discard matching path-attribute for this neighbor";
          uses bgp-path-range-grouping;
        }
        container treat-as-withdraw {
          description
            "Treat-as-withdraw matching path-attribute for this neighbor";
          uses bgp-path-range-grouping;
        }
      }
      // router bgp * / neighbor * remove-private-as
      container remove-private-as {
        description
          "Remove private AS number from outbound updates";
        presence true;
        container all {
          description
            "Remove all private AS numbers";
          presence true;
          leaf replace-as {
            description
              "Replace all private AS numbers with local AS";
            type empty;
          }
        }
      }
      // router bgp * / neighbor * route-map *
      list route-map {
        description
          "Apply route map to neighbor";
        key "inout";
        leaf inout {
          type enumeration {
            enum "in" {
            }
            enum "out" {
            }
          }
        }
        leaf route-map-name {
          type string;
          mandatory true;
        }
      }
      // router bgp * / neighbor * route-reflector-client
      leaf route-reflector-client {
        description
          "Configure a neighbor as Route Reflector client";
        type empty;
      }
      //router bgp * / neighbor * route-reflector-cluster-id
      leaf route-reflector-cluster-id {
        type union {
          type uint32 {
            range "1..4294967295";
          }
          type inet:ipv4-address;
        }
      }
      // router bgp * / neighbor * send-community
      container send-community {
        description
          "Send Community attribute to this neighbor";
        presence "true";
        leaf send-community-where {
          type enumeration {
            enum "both";
            enum "extended";
            enum "standard" {
            }
          }
        }
      }
      // router bgp * / neighbor * send-label
      container send-label {
        description
          "Send NLRI + MPLS Label to this peer";
        presence "true";
        leaf send-label-explicit {
          type enumeration {
            enum "explicit-null" {
            }
          }
        }
      }
      // router bgp * / neighbor * soo
      leaf soo {
        description
          "ASN:nn or IP-address:nn  VPN extended community";
        type string;
      }
      // router bgp * / neighbor * shutdown
      leaf shutdown {
        description
          "Administratively shut down this neighbor";
        type empty;
      }
      // router bgp * / neighbor * soft-reconfiguration
      leaf soft-reconfiguration {
        description
          "Per neighbor soft reconfiguration";
        type enumeration {
          enum "inbound";
        }
      }
      // router bgp * / neighbor slow-peer
      container slow-peer {
        description
          "Configure slow-peer";
        container detection {
          description
            "Slow-peer detection";
          presence "true";
          leaf threshold {
            description
              "Threshold value (seconds)";
            type uint16 {
              range "120..3600";
            }
          }
        }
        container split-update-group {
          description
            "Configure slow-peer split-update-group";
          container dynamic {
            description
              "Dynamically split the slow peer to slow-update group";
            presence "true";
            leaf permanent {
              description
                "Keep the slow-peer permanently in slow-update group";
              type empty;
            }
          }
        }
      }
      // router bgp * / neighbor * timers
      container timers {
        description
          "BGP per neighbor timers";
        leaf keepalive-interval {
          type uint16 {
            range "0..65535";
          }
        }
        leaf holdtime {
          type uint16 {
            range "0..65535";
          }
        }
        leaf minimum-neighbor-hold {
          type uint16 {
            range "0..65535";
          }
        }
      }
      // router bgp * / neighbor * translate-update
      container translate-update {
        description
          "Translate Update to MBGP format";
        container ipv4 {
          description
            "Address Family";
          container multicast {
            description
              "Address Family modifier";
            presence "Address Family modifier";
            leaf unicast {
              description
                "Address Family modifier";
              type empty;
            }
          }
        }
      }
      // router bgp * / neighbor * transport
      container transport {
        description
          "Transport options";
        leaf connection-mode {
          description
            "Specify passive or active connection";
          type enumeration {
            enum "active" {
            }
            enum "passive" {
            }
          }
        }
        leaf multi-session {
          description
            "Use Multi-session for transport";
          type empty;
        }
        container path-mtu-discovery {
          description
            "Use transport path MTU discovery";
          presence "true";
          leaf disable {
            description
              "disable";
            type empty;
          }
        }
      }
      // router bgp * / neighbor * ttl-security
      container ttl-security {
        description
          "BGP ttl security check";
        leaf hops {
          description
            "IP hops";
          type uint8 {
            range "1..254";
          }
        }
      }
      // router bgp * / neighbor * unsuppress-map
      leaf unsuppress-map {
        description
          "Route-map to selectively unsuppress suppressed routes";
        type string;
      }
      uses neighbor-update-source-grouping;
      uses neighbor-version-grouping;
      // router bgp * / neighbor * weight
      leaf weight {
        description
          "Set default weight for routes from this neighbor";
        type uint16 {
          range "0..65535";
        }
      }
      // router bgp * / neighbor * ha-mode
      container ha-mode {
        description
          "high availability mode";
        container graceful-restart {
          description
            "graceful-restart for this peer";
          presence "true";
          leaf disable {
            description
              "disable graceful-restart";
            type empty;
          }
        }
        container sso {
          description
            "stateful-switchover support for this peer";
          presence "true";
          leaf disable {
            description
              "disable stateful-switchover";
            type empty;
          }
        }
      }
    }
    // router bgp * / network
    list network {
      description
        "Specify a network to announce via BGP";
      key "number";
      leaf number {
        type union {
          type inet:ipv4-address;
          type ios-types:ipv6-prefix;
        }
      }
      leaf backdoor {
        description
          "Specify a BGP backdoor route";
        type empty;
      }
      leaf mask {
        description
          "Network mask";
        type inet:ipv4-address;
      }
      leaf route-map {
        description
          "Route-map to modify the attributes";
        type string;
      }
    }
    // router bgp * / redistribute
    container redistribute {
      description
        "Redistribute information from another routing protocol";
      container application {
        description
          "Application";
        presence "true";
        list name {
          key "name";
          leaf name {
            description
              "WORD;;Route map name";
            type string;
          }
          uses metric-route-map-grouping;
        }
      }
      container bgp {
        description
          "Border Gateway Protocol (BGP)";
        leaf as-no {
          type ios-types:bgp-as-number-type;
        }
        uses metric-route-map-grouping;
      }
      container connected {
        description
          "Connected";
        presence "Connected";
        uses metric-route-map-grouping;
      }
      container dvmrp {
        description
          "Redistribution of DVMRP into BGP IPv4 Multicast";
        presence "Redistribution of DVMRP into BGP IPv4 Multicast";
        uses route-map-metric-grouping;
      }
      container eigrp {
        description
          "Enhanced Interior Gateway Routing Protocol (EIGRP)";
        leaf as-no {
          type uint16 {
            range "1..65535";
          }
        }
        uses metric-route-map-grouping;
      }
      container isis {
        description
          "ISO IS-IS";
        list isis-area {
          key "name";
          leaf name {
            type string;
          }
          uses redistribute-isis-grouping;
        }
        container default {
          uses redistribute-isis-grouping;
        }
      }
      container lisp {
        description
          "Locator/ID Separation Protocol";
        presence "lisp";
        leaf include-connected {
          type empty;
        }
        uses metric-route-map-grouping;
      }
      container iso-igrp {
        description
          "IGRP for OSI networks";
        list iso-igrp-area {
          key "name";
          leaf name {
            type string;
          }
          uses route-map-metric-grouping;
        }
        container default {
          uses route-map-metric-grouping;
        }
      }
      container mobile {
        presence "Mobile routes";
        description
          "Mobile routes";
        uses metric-route-map-grouping;
      }
      container odr {
        presence "On Demand stub Routes";
        description
          "On Demand stub Routes";
        uses metric-route-map-grouping;
      }
      list ospf {
        description
          "Open Shortest Path First (OSPF)";
        key "id";
        leaf id {
          type uint16 {
            range "1..65535";
          }
        }
        list vrf {
          description
            "VPN Routing/Forwarding Instance";
          key "name";
          leaf name {
            type string;
          }
          container match;
          uses metric-route-map-grouping;
        }
        container non-vrf {
          uses redistribute-ospf-non-vrf-grouping;
        }
      }
      list ospfv3 {
        description
          "OSPFv3";
        key "id";
        leaf id {
          type uint16 {
            range "1..65535";
          }
        }
        uses redistribute-ospf-non-vrf-grouping;
      }
      container rip {
        presence "Routing Information Protocol (RIP)";
        description
          "Routing Information Protocol (RIP)";
        uses metric-route-map-grouping;
        leaf name {
          description "User selected string identifying this process";
          type string;
        }
      }
      container static {
        presence "Static routes";
        description
          "Static routes";
        container clns {
          description
            "Redistribution of OSI dynamic routes";
          presence "true";
          uses route-map-metric-grouping;
        }
        container ip {
          presence "true";
          uses metric-route-map-grouping;
        }
        uses metric-route-map-grouping;
      }
    }
    // router bgp * / synchronization
    leaf synchronization {
      description
        "Perform IGP synchronization";
      type empty;
    }
    // router bgp * / auto-summary
    leaf auto-summary {
      description
        "Enable automatic network number summarization";
      type boolean;
    }
    // router bgp * / table-map
    container table-map {
      presence "true";
      description
        "Map external entry attributes into routing table";
      leaf name {
        description
          "WORD;;route-map name";
        type string;
      }
      leaf filter {
        type empty;
      }
    }
    // router bgp * / snmp
    container snmp {
      description
        "Modify snmp parameters";
      presence "true";
      container context {
        description
          "Configure a SNMP context";
        list context_word {
          key "context_word";
          leaf context_word {
            description
              "Context Name";
            type string;
          }
        }
      }
    }
  }

  // neighbor path-attribute grouping
  grouping bgp-path-range-grouping {
    container attibute_type {
      leaf type {
        description
          "path attribute type";
        type uint8 {
          range "1..255";
        }
      }
      leaf in {
        description
          "Perform inbound path-attribute filtering";
        type empty;
      }
    }
    container range {
      leaf start_value {
        description
          "path attribute range start value";
        type uint8 {
          range "1..255";
        }
      }
      leaf end_value {
        description
          "path attribute range end value";
        type uint8 {
          range "1..255";
        }
      }
      leaf in {
        description
          "Perform inbound path-attribute filtering";
        type empty;
      }
    }
  }

  grouping config-bgp-grouping {
    list bgp { 
      description
        "Border Gateway Protocol (BGP)";
      key "id";
      max-elements "1";
      leaf id {
        type ios-types:bgp-as-number-type;
      }

      uses bgp-address-family-grouping;

      // router bgp * / address-family
      container address-family {
        description
          "Enter Address Family command mode";
        // router bgp * / address-family ipv4 vrf
        container with-vrf {
          list ipv4 {
            description
              "Address family";
            key "af-name";
            leaf af-name {
              type ios-types:bgp_ipv4_af_type;
            }
            // router bgp * / address-family ipv4 vrf *
            list vrf {
              key "name";
              leaf name {
                type string;
              }
              uses bgp-ipv4-af-aggregate-address-grouping;
              uses bgp-address-family-grouping;
            }
          }
          // router bgp * / address-family ipv6
          list ipv6 {
            description
              "Address family";
            key "af-name";
            leaf af-name {
              type ios-types:bgp_ipv6_af_type;
            }
            list vrf {
              key "name";
              leaf name {
                type string;
              }
              uses bgp-ipv6-af-aggregate-address-grouping;
              uses bgp-address-family-grouping;
            }
          }
        }
        container no-vrf {
          list ipv4 {
            description
              "Address family";
            key "af-name";
            leaf af-name {
              type ios-types:bgp_ipv4_af_type;
            }
            uses bgp-ipv4-af-aggregate-address-grouping;
            uses bgp-address-family-grouping;
          }
          list ipv6 {
            description
              "Address family";
            key "af-name";
            leaf af-name {
              type ios-types:bgp_ipv6_af_type;
            }
            uses bgp-ipv6-af-aggregate-address-grouping;
            uses bgp-address-family-grouping;
          }
          // router bgp * / address-family vpnv4
          list vpnv4 {
            description
              "Address family";
            key "af-name";
            leaf af-name {
              type enumeration {
                enum "unicast" {
                }
                enum "multicast" {
                }
                enum "flowspec" {
                }
              }
            }
            uses bgp-address-family-grouping;
          }
          // router bgp * / address-family vpnv6
          list vpnv6 {
            description
              "Address family";
            key "af-name";
            leaf af-name {
              type enumeration {
                enum "unicast" {
                }
                enum "multicast" {
                }
                enum "flowspec" {
                }
              }
            }
            uses bgp-address-family-grouping;
          }
          // router bgp * / address-family nsap
          list nsap {
            description
              "Address family";
            key "af-name";
            leaf af-name {
              type enumeration {
                enum "unicast" {
                }
              }
            }
            uses bgp-address-family-grouping;
          }
          // router bgp * / address-family l2vpn
          list l2vpn {
            if-feature ios-features:l2vpn;
            description
              "Address family";
            key "af-name";
            leaf af-name {
              type enumeration {
                enum "evpn" {
                }
                enum "vpls" {
                }
              }
            }
            uses bgp-address-family-grouping;
          }
          // router bgp * / address-family rtfilter
          list rtfilter {
            description
              "Address family";
            key "af-name";
            leaf af-name {
              type enumeration {
                enum "unicast" {
                }
              }
            }
            uses bgp-address-family-grouping;
          }
        }
      }
      // router bgp * / template
      container template {
        description
          "Enter template command mode";
        list peer-policy {
          description
            "Template configuration for policy parameters";
          key "name";
          leaf name {
            type string;
          }
          list route-map {
            description
              "Apply route map to neighbor";
            key "name";
            leaf name {
              type string;
            }
            leaf in {
              description
                "Apply map to incoming routes";
              type empty;
            }
            leaf out {
              description
                "Apply map to outgong routes";
              type empty;
            }
          }
          list  filter-list {
            description "Establish BGP filters";
            key "filter-range";
            leaf filter-range {
              description "AS path access list";
              type uint16 {
                range "1..500";
              }
            }
            leaf in {
              description "Filter incoming routes";
              type empty;
            }
            leaf out {
              description "Filter outgoing routes";
              type empty;
            }
          }
          container inherit {
            description "Inherit a template";
            container peer-policy {
              list template {
                key "name";
                leaf name {
                  description "Template name";
                  type string;
                }
                leaf range {
                  description "Sequence number";
                  type uint16 {
                    range "1..65535";
                  }
                }
              }
            }
          }
        }
        list peer-session {
          description
            "Template configuration for session parameters";
          key "name";
          leaf name {
            type string;
          }
          container ha-mode {
            description
              "high availability mode";
            container graceful-restart {
              description
                "graceful-restart for this peer";
              presence "true";
              leaf disable {
                description
                  "disable graceful-restart";
                type empty;
              }
            }
          }

          container password {
            description "Set a password";
            list password-range {
              key "encruption-type-range";
              leaf encruption-type-range {
                description "Encryption type (0 to disable encryption, 7 for proprietary)";
                type uint8 {
                  range "0..7";
                }
              }
              leaf password {
                description "The password";
                type string;
              }
            }
            leaf password {
              description "The password";
              type string;
            }
          }
          leaf remote-as {
            description "Specify a BGP neighbor";
            type ios-types:bgp-as-number-type;
          }
          container update-source {
            description "Source of routing updates";
            uses ios-ifc:interface-grouping;
          }
          leaf version {
            description "Set the BGP version to match a neighbor";
            type uint8 {
              range "4";
            }
          }
        }
      }
      // router bgp * / timers
      container timers {
        description
          "Adjust routing timers";
        container bgp {
          description
            "BGP timers";
          leaf keepalive-interval {
            type uint16 {
              range "0..65535";
            }
          }
          leaf holdtime {
            type uint16 {
              range "0..65535";
            }
          }
          leaf minimum-neighbor-hold {
            type uint16 {
              range "0..65535";
            }
          }
        }
      }
      container scope {
        container global {
          presence true;
          list neighbor {
              description
                "Specify a neighbor router";
              ordered-by user;
              must "count(*) > 1" {
              }
              key "id";
              leaf id {
                type union {
                  type inet:ipv4-address;
                  type inet:ipv6-address;
                  type string;
                }
              }
              uses neighbor-peer-group-grouping;
              uses neighbor-remote-as-grouping;
              uses neighbor-description-grouping;
              uses neighbor-password-grouping;
              uses neighbor-update-source-grouping;
              uses neighbor-version-grouping;
          }
          container address-family {
            description
              "Enter Address Family command mode";
            // router bgp * / address-family ipv4 vrf
            uses address-family-no-vrf-grouping;
          }
        }
        list vrf {
              key "id";
              leaf id {
                type union {
                  type inet:ipv4-address;
                  type inet:ipv6-address;
                  type string;
                }
              }
          list neighbor {
              description
                "Specify a neighbor router";
              ordered-by user;
              must "count(*) > 1" {
              }
              key "id";
              leaf id {
                type union {
                  type inet:ipv4-address;
                  type inet:ipv6-address;
                  type string;
                }
              }
              uses neighbor-peer-group-grouping;
              uses neighbor-remote-as-grouping;
          }
          container address-family {
            description
              "Enter Address Family command mode";
            // router bgp * / address-family ipv4 vrf
            uses address-family-no-vrf-grouping;
          }
        }
      }
    }
  }

  /////////////////////////////////////////////////////////
  // native / router / bgp
  /////////////////////////////////////////////////////////
  augment "/ios:native/ios:router" {
    uses config-bgp-grouping;
  }

    /////////////////////////////////////////////////////////
  // ip / community list
  /////////////////////////////////////////////////////////
  augment "/ios:native/ios:ip" {
    uses config-ip-community-list-grouping;
  }

  /////////////////////////////////////////////////////////
  // ip / extcommunity list
  /////////////////////////////////////////////////////////
  augment "/ios:native/ios:ip" {
    uses config-ip-extcommunity-list-grouping;
  }

  /////////////////////////////////////////////////////////
  // ip / as-path
  /////////////////////////////////////////////////////////
  augment "/ios:native/ios:ip/ios:as-path" {
    uses config-ip-as-path-grouping;
  }
}
