module Cisco-IOS-XE-lldp-oper {
  yang-version 1;
  namespace "http://cisco.com/ns/yang/Cisco-IOS-XE-lldp-oper";
  prefix lldp-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of LLDP state information.
     Copyright (c) 2016-2017 by Cisco Systems, Inc.
     All rights reserved.";

  revision 2017-02-07 {
    description
      "Initial revision";
    reference "1.0.0";
  }

  grouping lldp-capabilities {
    description
      "LLDP device type";
    leaf repeater {
      type empty;
      description
        "Repeater";
    }
    leaf bridge {
      type empty;
      description
        "Bridge";
    }
    leaf access-point {
      type empty;
      description
        "Access point";
    }
    leaf router {
      type empty;
      description
        "Router";
    }
    leaf telephone {
      type empty;
      description
        "Phone";
    }
    leaf docsis {
      type empty;
      description
        "Docsis";
    }
    leaf station {
      type empty;
      description
        "Station";
    }
    leaf other {
      type empty;
      description
        "Other";
    }
  }

  grouping lldp-entry-key {
    description
      "Unique LLDP entry identifier";
    leaf device-id {
      type string;
      description
        "Device ID of the link";
    }
    leaf local-interface {
      type string;
      description
        "Name of the local interface on the current device";
    }
    leaf connecting-interface {
      type string;
      description
        "Name of the connected interface to 'local-interface'";
    }
  }

  grouping lldp-entry {
    description
      "LLDP entry details";
    leaf ttl {
      type uint32;
      description
        "TTL denoting hold-time of this link entry";
    }
    container capabilities {
      description
        "LLD device capabilities";
      uses lldp-ios-xe-oper:lldp-capabilities;
    }
  }

  container lldp-entries {
    config false;
    description
      "Data nodes for lldp entries";
    list lldp-entry {
      key "device-id local-interface connecting-interface";
      description
        "The list of LLDP entries";
      uses lldp-ios-xe-oper:lldp-entry-key;
      uses lldp-ios-xe-oper:lldp-entry;
    }
  }
}
