module cisco-xe-openconfig-if-ethernet-deviation {
  // namespace
  namespace "http://openconfig.net/yang/cisco-xe-openconfig-if-ethernet-deviation";

  prefix oc-if-eth-devs;

  import openconfig-interfaces {
    prefix oc-if;
  }
  import openconfig-if-ethernet {
    prefix oc-if-eth;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-if-ethernet module.";

  revision 2017-09-01{
    description
      "CSR1K PD Ethernet feature deviations";
  }

  revision 2017-02-21 {
    description
      "Initial Revision";

    reference
      "RFC 6020: YANG - A Data Modeling Language for the
       Network Configuration Protocol (NETCONF)";
  }

  deviation "/oc-if:interfaces/oc-if:interface/oc-if-eth:ethernet" +
            "/oc-if-eth:config/oc-if-eth:enable-flow-control" {
      deviate not-supported;
  }
  deviation "/oc-if:interfaces/oc-if:interface/oc-if-eth:ethernet" +
            "/oc-if-eth:config/oc-if-eth:port-speed" {
      deviate not-supported;
  }

  deviation "/oc-if:interfaces/oc-if:interface/oc-if-eth:ethernet" +
            "/oc-if-eth:config/oc-if-eth:duplex-mode" {
      deviate not-supported;
  }

}
