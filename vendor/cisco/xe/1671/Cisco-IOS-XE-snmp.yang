module Cisco-IOS-XE-snmp {
  namespace "http://cisco.com/ns/yang/Cisco-IOS-XE-snmp";
  prefix ios-snmp;

  import Cisco-IOS-XE-types {
    prefix ios-types;
  }

  import Cisco-IOS-XE-interface-common {
    prefix ios-ifc;
  }

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Simple Network Management Protocol (SNMP) Yang model.
     Copyright (c) 2016-2017 by Cisco Systems, Inc.
     All rights reserved.";

  // =========================================================================
  // REVISION
  // =========================================================================

  revision 2017-08-11 {
    description
      "This revision has changes for new 5gig and 25gig interfaces addition";
  }

  revision 2017-02-07 {
    description
      "Initial revision";
  }

  grouping config-snmp-server-grouping {
      // snmp-server chassis-id *       String to uniquely identify this chassis
      leaf chassis-id {
        description
          "String to uniquely identify this chassis";
        type string;
      }
      // snmp-server community *
      list community {
        description
          "Enable SNMP; set community string and access privs";
        key "name";
        leaf name {
          type string;
        }
        leaf view {
          description
            "Restrict this community to a named MIB view";
          type string;
        }
        choice access-choice {
          leaf RO {
            description
              "Read-only access with this community string";
            type empty;
          }
          leaf RW {
            description
              "Read-write access with this community string";
            type empty;
          }
        }
            leaf ipv6 {
          description "Specify IPv6 Named Access-List";
              type string;
            }
            leaf access-list-name {
           description "Access-list name";
              type ios-types:std-acl-type;
            }
          }
      leaf contact {
        description
          "Text for mib object sysContact";
        type string;
      }
      // context           Create/Delete a context apart from default
      list context {
        description
          "Create/Delete a context apart from default";
        key "name";
        leaf name {
          type string;
        }
      }
      // drop              Silently drop SNMP packets

      // snmp-server enable
      container enable {
        description
          "Enable SNMP Traps or Informs";
        container enable-choice {
          leaf informs {
            description
              "Enable SNMP Informs";
            type empty;
          }
          // snmp-server enable traps
          container traps {
            description
              "Enable SNMP Traps";
            presence true;
            leaf aaa_server {
              description
                "Enable SNMP AAA Server traps";
              type empty;
            }
            container trustsec-sxp {
              description "Enable SNMP CISCO-TRUSTSEC-SXP-MIB traps";
              presence true;
              leaf binding-conflict {
                type empty;
              }
              leaf binding-err {
                type empty;
              }
              leaf binding-expn-fail {
                type empty;
              }
              leaf conn-config-err {
                type empty;
              }
              leaf conn-down {
                type empty;
              }
              leaf conn-srcaddr-err {
                type empty;
              }
              leaf conn-up {
                type empty;
              }
              leaf msg-parse-err {
                type empty;
              }
              leaf oper-nodeid-change {
                type empty;
              }
            }
            container vswitch {
              description "Enable SNMP Virtual Switch notifications";
              presence true;
              container dual-active {
                description "Enable SNMP Virtual Switch (Dual Active) notification";
                presence true;
                leaf vsl {
                  description "Enable SNMP Virtual Switch Link (VSL) notification";
                  type empty;
                }
              }
            }
            container trustsec-server {
              description "Enable SNMP CISCO-TRUSTSEC-SERVER-MIB traps";
              presence true;
              container radius-server {
                description "Enable ctsvNoRadiusServerNotif notification";
                presence true;
                leaf provision-secret {
                  description "Enable ctsvNoProvisionSecretNotif notification";
                  type empty;
                }
              }
            }
            container trustsec {
              description "Enable SNMP CISCO-TRUSTSEC-MIB traps";
              presence true;
              container authz-file-error {
                description "Enable ctsAuthzCacheFileErrNotif notifications";
                presence true;
                container cache-file-error {
                  description "Enable ctsCacheFileAccessErrNotif notifications";
                  presence true;
                  container keystore-file-error {
                    description "Enable ctsSwKeystoreFileErrNotif notifications";
                    presence true;
                    container keystore-sync-fail {
                      description "Enable ctsSwKeystoreSyncFailNotif notifications";
                      presence true;
                      container random-number-fail {
                        description "Enable ctsSapRandonNumberFailNotif notifications";
                        presence true;
                        leaf src-entropy-fail {
                          description "Enable ctsSrcEntropyFailNotif notifications";
                          type empty;
                        }
                      }
                    }
                  }
                }
              }
            }
            container trustsec-interface {
              description "Enable SNMP CISCO-TRUSTSEC-INTERFACE-MIB traps";
              presence true;
              container unauthorized {
                description "Enable ctsiIfUnauthorizedNotifEnable trap";
                presence true;
                container sap-fail {
                  description "Enable ctsiIfSapNegotiationFailNotif trap";
                  presence true;
                  container authc-fail {
                    description "Enable ctsiIfAuthenticationFailNotif trap";
                    presence true;
                    container supplicant-fail {
                      description "Enable ctsiIfAddSupplicantFailNotif trap";
                      presence true;
                      leaf authz-fail {
                        description "Enable ctsiAuthorizationFailNotif trap";
                        type empty;
                      }
                    }
                  }
                }
              }
            }
            container trustsec-policy {
              description "Enable SNMP CISCO-TRUSTSEC-POLICY-MIB traps";
              presence true;
              container peer-policy-updated {
                description "Enable ctspPeerPolicyUpdatedNotif notifications";
                presence true;
                leaf authz-sgacl-fail {
                  description "Enable ctspAuthorizationSgaclFailNotif notifications";
                  type empty;
                }
              }
            }
            container ospfv3 {
              description "Enable OSPFv3 traps";
              leaf state-change {
                description "State change traps";
                type empty;
              }
              leaf errors {
                description "Error traps";
                type empty;
              }
            }
            container ike {
              description "Enable IKE traps";
              container policy {
                description "Enable IKE Policy traps";
                leaf add {
                  description "Enable IKE Policy add trap";
                  type empty;
                }
                leaf delete {
                  description "Enable IKE Policy delete trap";
                  type empty;
                }
              }
              container tunnel {
                description "Enable IKE Tunnel traps";
                leaf start {
                  description "Enable IKE Tunnel start trap";
                  type empty;
                }
                leaf stop {
                  description "Enable IKE Tunnel stop trap";
                  type empty;
                }
              }
            }
            leaf local-auth {
              description "Enable SNMP local auth traps";
              type empty;
            }


            container alarms {
              description
                "Enable SNMP alarms traps";
              presence "true";
              leaf alarm-type {
                type union {
                  type uint8 {
                    range "1..4";
                  }
                  type enumeration {
                    enum "critical";
                    enum "informational";
                    enum "major";
                    enum "minor";
                  }
                }
              }
            }
            container atm {
              description
                "Enable SNMP atm traps";
              container pvc {
                description
                  "Enable SNMP atm pvc traps";
                presence "true";
                container extension {
                  description
                    "Enable SNMP atm pvc extension traps";
                  leaf down {
                    description
                      "Enable SNMP atm pvc extended down trap";
                    type empty;
                  }
                  leaf up {
                    description
                      "Enable SNMP atm pvc extended up traps";
                    type empty;
                  }
                  leaf mibversion {
                    description
                      "Extension MIB version to be used";
                    type enumeration {
                      enum "1";
                      enum "2";
                    }
                  }
                  container oam {
                    description
                      "Enable SNMP atm pvc extended oam trap";
                    container failure {
                      description
                        "Enable SNMP atm pvc extended any oam failure trap";
                      leaf loopback {
                        description
                          "Enable SNMP atm pvc extended oam loopback failure trap";
                        type empty;
                      }
                    }
                  }
                }
                leaf interval {
                  description
                    "minimum period between successive traps";
                  type uint16 {
                    range "1..3600";
                  }
                }
                leaf fail-interval {
                  description
                    "minimum period for storing the failed timestamp";
                  type uint16 {
                    range "0..3600";
                  }
                }
              }
              container subif {
                description
                  "Enable SNMP atm subinterface traps";
                presence "true";
                leaf interval {
                  description
                    "Interval duration in which to limit the number of traps sent";
                  type uint16 {
                    range "0..3600";
                  }
                }
                leaf count {
                  description
                    "Maximum number of traps sent per interval";
                  type uint16 {
                    range "1..1000";
                  }
                }
              }
            }
            leaf authenticate-fail {
              description
                "Enable SNMP 802.11 Authentication Fail Trap";
              type empty;
            }
            container auth-framework {
              presence "true";
              leaf sec-violation {
                type empty;
              }
            }
            leaf bfd {
              type empty;
            }
            container bgp-conf {
              leaf cbgp2 {
                description "Enable BGP MIBv2 traps";
                type empty;
              }
            }
            leaf bgp {
              description
                "Enable BGP traps";
              type empty;
            }
            container bridge {
              presence "true";
              leaf newroot {
                type empty;
              }
              leaf topologychange {
                type empty;
              }
            }
            leaf bstun {
              description
                "Enable SNMP BSTUN traps";
              type empty;
            }
            container bulkstat {
              description
                "Enable Data-Collection-MIB Collection notifications";
              presence "true";
              leaf collection {
                description
                  "Enable Data-Collection-MIB Collection notifications";
                type empty;
              }
              leaf transfer {
                description
                  "Enable Data-Collection-MIB Transfer notifications";
                type empty;
              }
            }
            container call-home {
              description
                "Enable CISCO-CALLHOME-MIB traps";
              presence "true";
              leaf message-send-fail {
                type empty;
              }
              leaf server-fail {
                type empty;
              }
            }
            leaf c2900 {
              description
                "Enable SNMP c2900 traps";
              type empty;
            }
            container c6kxbar {
              description
                "Enable SNMP CISCO-CAT6K-CROSSBAR-MIB traps";
              presence "true";
              leaf intbus-crcexcd {
                description
                  "Enable SNMP cc6kxbarIntBusCRCErrExcdNotif notification";
                type empty;
              }
              leaf intbus-crcrcvrd {
                description
                  "Enable SNMP cc6kxbarIntBusCRCErrRcvrdNotif notification";
                type empty;
              }
              leaf swbus {
                description
                  "Enable SNMP cc6kxbarSwBusStatusChangeNotif notification";
                type empty;
              }
            }
            leaf casa {
              description
                "Enable SNMP casa traps";
              type empty;
            }
            leaf ccme {
              type empty;
            }
            container cef {
              leaf resource-failure {
                type empty;
              }
              leaf peer-state-change {
                type empty;
              }
              leaf peer-fib-state-change {
                type empty;
              }
              leaf inconsistency {
                type empty;
              }
            }
            leaf cluster {
              description
                "Enable Cluster traps";
              type empty;
            }
            leaf channel {
              description
                "Enable SNMP channel traps";
              type empty;
            }
            leaf chassis {
              description
                "Enable SNMP chassis traps";
              type empty;
            }
            leaf cnpd {
              description
                "Enable NBAR Protocol Discovery traps";
              type empty;
            }
            leaf config {
              description
                "Enable SNMP config traps";
              type empty;
            }
            leaf copy-config {
              description
                "Enable SNMP copy-config traps";
              type empty;
            }
            leaf config-copy {
              description
                "Enable SNMP config-copy traps";
              type empty;
            }
            leaf config-ctid {
              type empty;
            }
            // snmp-server enable traps cpu
            container cpu {
              description
                "Allow cpu related traps";
              presence "true";
              leaf threshold {
                description
                  "Allow CPU utilization threshold violation traps";
                type empty;
              }
            }
            leaf cpu_threshold {
              description
                "Enables CPU threshold notifications";
              type empty;
            }
            container csg {
              description
                "Enable SNMP CSG traps";
              presence "true";
              leaf agent {
                description
                  "Enable SNMP Agent Server traps";
                type empty;
              }
              leaf database {
                description
                  "Enable SNMP CSG database traps";
                type empty;
              }
              leaf quota-server {
                description
                  "Enable SNMP Quota Server traps";
                type empty;
              }
            }
            leaf dial {
              description
                "Enable SNMP dial control traps";
              type empty;
            }
            leaf director {
              description
                "Enable SNMP Distributed Director traps";
              type empty;
            }
            leaf dlsw {
              description
                "Enable SNMP dlsw traps";
              type empty;
            }
            leaf deauthenticate {
              description
                "Enable SNMP 802.11 Deauthentication Trap";
              type empty;
            }
            leaf disassociate {
              description
                "Enable SNMP 802.11 Disassociation Trap";
              type empty;
            }
            leaf dnis {
              description
                "Enable SNMP DNIS traps";
              type empty;
            }
            leaf dot11-qos {
              description
                "Enable SNMP 802.11 QoS Change Trap";
              type empty;
            }
            container dot1x {
              leaf auth-fail-vlan {
                type empty;
              }
              leaf guest-vlan {
                type empty;
              }
              leaf no-auth-fail-vlan {
                type empty;
              }
              leaf no-guest-vlan {
                type empty;
              }
            }
            leaf ds0-busyout {
              description
                "Enable ds0-busyout traps";
              type empty;
            }
            leaf ds1 {
              description
                "Enable SNMP DS1 traps";
              type empty;
            }
            leaf ds1-loopback {
              description
                "Enable ds1-loopback traps";
              type empty;
            }
            leaf ds3 {
              description
                "Enable SNMP DS3 traps";
              type empty;
            }
            container dsp {
              description
                "Enable SNMP dsp traps";
              presence "true";
              leaf card-status {
                description
                  "Enable SNMP card status of dsp traps";
                type empty;
              }
              leaf oper-state {
                type empty;
              }
            }
            leaf eigrp {
              description
                "Enable SNMP EIGRP traps";
              type empty;
            }
            container energywise {
              presence "true";
              leaf event-occured {
                type empty;
              }
              leaf level-change {
                type empty;
              }
              leaf neighbor-added {
                type empty;
              }
              leaf neighbor-deleted {
                type empty;
              }
            }
            leaf entity {
              description
                "Enable SNMP entity traps";
              type empty;
            }
            container entity-diag {
              description
                "Enable SNMP CISCO-ENTITY-DIAG-MIB traps";
              presence "true";
              leaf boot-up-fail {
                description
                  "Enable SNMP ceDiagBootUpFailedNotif traps";
                type empty;
              }
              leaf hm-test-recover {
                description
                  "Enable SNMP ceDiagHMTestRecoverNotif traps";
                type empty;
              }
              leaf hm-thresh-reached {
                description
                  "Enable SNMP ceDiagHMThresholdReachedNotif traps";
                type empty;
              }
              leaf scheduled-test-fail {
                description
                  "Enable SNMP ceDiagScheduledTestFailedNotif traps";
                type empty;
              }
            }
            container envmon {
              description
                "Enable SNMP environmental monitor traps";
              presence "true";
              leaf fan {
                type empty;
              }
              leaf shutdown {
                type empty;
              }
              leaf supply {
                type empty;
              }
              leaf temperature {
                type empty;
              }
              leaf status {
                type empty;
              }
            }
            container errdisable {
              description
                "Enable SNMP errdisable notifications";
              presence "true";
              leaf notification-rate {
                description
                  "Number of notifications per minute";
                type uint16 {
                  range "0..10000";
                }
              }
            }
            leaf ether-oam {
              type empty;
            }
            container ethernet {
              container cfm {
                leaf alarm {
                  description
                    "Enable SNMP Ethernet CFM fault alarm trap";
                  type empty;
                }
                // snmp-server enable traps ethernet cfm cc
                container cc {
                  presence "true";
                  leaf config {
                    type empty;
                  }
                  leaf cross-connect {
                    type empty;
                  }
                  leaf loop {
                    type empty;
                  }
                  leaf mep-down {
                    type empty;
                  }
                  leaf mep-up {
                    type empty;
                  }
                }
                // snmp-server enable traps ethernet cfm crosscheck
                container crosscheck {
                  presence "true";
                  leaf mep-missing {
                    type empty;
                  }
                  leaf mep-unknown {
                    type empty;
                  }
                  leaf service-up {
                    type empty;
                  }
                }
              }
              container evc {
                description
                  "Enable SNMP Ethernet EVC traps";
                presence "true";
                leaf create {
                  description
                    "Enable SNMP Ethernet EVC create traps";
                  type empty;
                }
                leaf delete {
                  description
                    "Enable SNMP Ethernet EVC delete traps";
                  type empty;
                }
                leaf status {
                  description
                    "Enable SNMP Ethernet EVC status traps";
                  type empty;
                }
              }
            }
            leaf event-manager {
              description
                "Enable SNMP Embedded Event Manager traps";
              type empty;
            }
            container firewall {
              presence "true";
              leaf serverstatus {
                type empty;
              }
            }
            container flash {
              description
                "Enable SNMP FLASH notifications";
              presence "true";
              leaf insertion {
                description
                  "Enable SNMP Flash Insertion notifications";
                type empty;
              }
              leaf removal {
                description
                  "Enable SNMP Flash Removal notifications";
                type empty;
              }
            }
            leaf flowmon {
              description
                "Enabel SNMP flowmon notifications";
              type empty;
            }
            container flex-links {
              description
                "Enable SNMP FLEX Links traps";
              presence "true";
              leaf status {
                description
                  "Enable SNMP FLEX Links status change traps";
                type empty;
              }
            }
            container frame-relay {
              description
                "Enable SNMP frame-relay traps";
              presence "true";
              container multilink {
                description
                  "Enable MFR traps";
                leaf bundle-mismatch {
                  description
                    "Enable MFR trap for inconsistent bundle event";
                  type empty;
                }
              }
              container subif {
                description
                  "Enable SNMP frame-relay subinterface traps";
                presence "true";
              }
            }
            leaf fru-ctrl {
              description
                "Enable SNMP entity FRU control traps";
              type empty;
            }
            leaf gatekeeper {
              description
                "Enable SNMP gatekeeper traps";
              type empty;
            }
            leaf hsrp {
              description
                "Enable SNMP HSRP traps";
              type empty;
            }
            leaf icsudsu {
              description
                "Enable SNMP ICSUDSU traps";
              type empty;
            }
            leaf ima {
              description
                "Enable SNMP ATM IMA traps";
              type empty;
            }
            leaf ipmobile {
              description
                "Enable SNMP ipmobile traps";
              type empty;
            }
            leaf ipmulticast {
              description
                "Enable SNMP ipmulticast traps";
              type empty;
            }
            container ipsec {
              description
                "Enable IPsec traps";
              container cryptomap {
                leaf add {
                  description
                    "Enable IPsec Cryptomap add trap";
                  type empty;
                }
                leaf attach {
                  description
                    "Enable IPsec Cryptomap Attach trap";
                  type empty;
                }
                leaf delete {
                  description
                    "Enable IPsec Cryptomap delete trap";
                  type empty;
                }
                leaf detach {
                  description
                    "Enable IPsec Cryptomap Detach trap";
                  type empty;
                }
              }
              container tunnel {
                description
                  "Enable IPsec Tunnel traps";
                leaf start {
                  description
                    "Enable IPsec Tunnel Start trap";
                  type empty;
                }
                leaf stop {
                  description
                    "Enable IPsec Tunnel Stop trap";
                  type empty;
                }
              }
              leaf too-many-sas {
                description
                  "Enable IPsec Tunnel Start trap";
                type empty;
              }
            }
            container isakmp {
              description
                "Enable ISAKMP traps traps";
              container policy {
                description
                  "Enable ISAKMP traps";
                leaf add {
                  description
                    "Enable ISAKMP Policy add trap";
                  type empty;
                }
                leaf delete {
                  description
                    "Enable ISAKMP Policy delete trap";
                  type empty;
                }
              }
              container tunnel {
                description
                  "Enable ISAKMP Tunnel traps";
                leaf start {
                  description
                    "Enable ISAKMP Tunnel start trap";
                  type empty;
                }
                leaf stop {
                  description
                    "Enable ISAKMP Tunnel stop trap";
                  type empty;
                }
              }
            }
            container isdn {
              description
                "Enable SNMP isdn traps";
              presence "true";
              leaf call-information {
                description
                  "Enable SNMP isdn call information traps";
                type empty;
              }
              leaf chan-not-avail {
                description
                  "Enable SNMP isdn channel not avail traps";
                type empty;
              }
              leaf ietf {
                description
                  "Enable SNMP isdn ietf traps";
                type empty;
              }
              leaf layer2 {
                description
                  "Enable SNMP isdn layer2 transition traps";
                type empty;
              }
            }
            leaf ipsla {
              description
                "Enable IPSLA traps traps";
              type empty;
            }
            leaf isis {
              description
                "Enable ISIS traps traps";
              type empty;
            }
            container l2tc {
              description
                "Enable SNMP L2 Tunnel Config traps";
              presence "true";
              leaf sys-threshold {
                description
                  "Enable SNMP L2TC System threshold traps";
                type empty;
              }
              leaf threshold {
                description
                  "Enable SNMP L2 Tunnel Config threshold traps";
                type empty;
              }
            }
            container l2tun {
              description
                "Enable SNMP L2 tunnel protocol traps";
              leaf session {
                description
                  "Enable SNMP l2tun session traps";
                type empty;
              }
              container pseudowire {
                leaf status {
                  type empty;
                }
              }
            }
            container license {
              description
                "Enable license traps";
              presence true;
              leaf deploy {
                description
                  "Enable license deployment traps";
                type empty;
              }
              leaf error {
                description
                  "Enable license error traps";
                type empty;
              }
              leaf usage {
                description
                  "Enable license usage traps";
                type empty;
              }
            }
            container mac-notification {
              description
                "Enable SNMP MAC Notification traps";
              presence "true";
              leaf change {
                description
                  "Enable SNMP Change traps";
                type empty;
              }
              leaf move {
                description
                  "Enable SNMP Move traps";
                type empty;
              }
              leaf threshold {
                description
                  "Enable SNMP Threshold traps";
                type empty;
              }
            }
            container mac-notification2 {
              description
                "Enable SNMP MAC Notification traps";
              presence "true";
              leaf change {
                description
                  "Enable SNMP Change traps";
                type empty;
              }
              leaf move {
                description
                  "Enable SNMP Move traps";
                type empty;
              }
              leaf threshold {
                description
                  "Enable SNMP Threshold traps";
                type empty;
              }
            }
            container memory {
              description
                "Enable SNMP Memory traps";
              presence "true";
              leaf bufferpeak {
                description
                  "Enable SNMP Memory Bufferpeak traps";
                type empty;
              }
            }
            leaf module {
              description
                "Enable SNMP module traps";
              type empty;
            }
            // snmp-server enable traps mpls
            container mpls {
              description
                "Enable SNMP MPLS traps";
              presence "true";
              container traffic-eng {
                presence "true";
                leaf up {
                  description "Enable MPLS TE tunnel up traps";
                  type empty;
                }
                leaf down {
                  description "Enable MPLS TE tunnel down traps";
                  type empty;
                }
                leaf reroute {
                  description "Enable MPLS TE tunnel reroute traps";
                  type empty;
                }
              }
              // snmp-server enable traps mpls fast-reroute
              container fast-reroute {
                presence "true";
                leaf protected {
                  type empty;
                }
              }
              container rfc {
                presence "true";
                leaf ldp {
                  type empty;
                }
              }
              container ldp {
                description
                  "SNMP MPLS label distribution protocol traps";
                presence "true";
                leaf pv-limit {
                  description
                    "Enable MPLS LDP path vector limit mismatch traps";
                  type empty;
                }
                leaf session-down {
                  description
                    "Enable MPLS LDP session down traps";
                  type empty;
                }
                leaf session-up {
                  description
                    "Enable MPLS LDP session up traps";
                  type empty;
                }
                leaf threshold {
                  description
                    "Enable MPLS LDP threshold exceeded traps";
                  type empty;
                }
              }
              leaf vpn {
                type empty;
              }
            }
            leaf msdp {
              description
                "Enable SNMP MSDP traps";
              type empty;
            }
            leaf mvpn {
              description
                "Enable Multicast Virtual Private Networks traps";
              type empty;
            }
            container nhrp {
              presence "true";
              container nhs {
                presence "true";
              }
              container nhc {
                presence "true";
              }
              container nhp {
                presence "true";
              }
              container quota-exceeded {
                presence "true";
              }
            }
            container ospf {
              description
                "Enable OSPF traps";
              container state-change {
                description
                  "State change traps";
                presence "true";
                leaf if-state-change {
                  description
                    "Non-virtual interface state changes";
                  type empty;
                }
                leaf neighbor-state-change {
                  description
                    "Non-virtual neighbor state changes";
                  type empty;
                }
                leaf virtif-state-change {
                  description
                    "Virtual interface state changes";
                  type empty;
                }
                leaf virtneighbor-state-change {
                  description
                    "Non-virtual neighbor state changes";
                  type empty;
                }
              }
              container errors {
                description
                  "Error traps";
                presence "true";
              }
              container retransmit {
                description
                  "Packet retransmit traps";
                presence "true";
                leaf packets {
                  description
                    "Packet retransmission on non-virtual interfaces";
                  type empty;
                }
                leaf virt-packets {
                  description
                    "Packet retransmission on virtual interfaces";
                  type empty;
                }
              }
              container lsa {
                description
                  "Lsa related traps";
                presence "true";
                leaf lsa-maxage {
                  description
                    "Lsa aged to maxage";
                  type empty;
                }
                leaf lsa-originate {
                  description
                    "New lsa originated";
                  type empty;
                }
              }
              container cisco-specific {
                description
                  "Cisco specific traps";
                presence "true";
                container state-change {
                  description
                    "State change traps";
                  presence "true";
                  leaf nssa-trans-change {
                    description
                      "Nssa translator state changes";
                    type empty;
                  }
                  container shamlink {
                    description
                      "Sham link state change traps";
                    presence "true";
                    leaf interface {
                      description
                        "Sham link interface state changes";
                      type empty;
                    }
                    leaf interface-old {
                      description
                        "Sham link interface state changes (deprecated)";
                      type empty;
                    }
                    leaf neighbor {
                      description
                        "Sham link neighbor state changes";
                      type empty;
                    }
                  }
                }
                container errors {
                  description
                    "Error traps";
                  presence "true";
                }
                container errdisable {
                  description
                    "Enable SNMP errdisable notifications";
                  presence "true";
                  leaf notification-rate {
                    description
                      "Number of notifications per minute";
                    type uint16 {
                      range "0..10000";
                    }
                  }
                }
                container retransmit {
                  description
                    "Packet retransmit traps";
                  presence "true";
                }
                container lsa {
                  description
                    "Lsa related traps";
                  presence "true";
                  leaf lsa-maxage {
                    description
                      "Lsa aged to maxage";
                    type empty;
                  }
                  leaf lsa-originate {
                    description
                      "New lsa originated";
                    type empty;
                  }
                }
              }
            }
            container pim {
              description
                "Enable SNMP PIM traps";
              presence "true";
              leaf invalid-pim-message {
                description
                  "Enable invalid pim message trap";
                type empty;
              }
              leaf neighbor-change {
                description
                  "Enable neighbor change trap";
                type empty;
              }
              leaf rp-mapping-change {
                description
                  "Enable rp mapping change trap";
                type empty;
              }
            }
            container plogd {
              description
                "Enable SNMP plogd traps";
              presence "true";
            }
            container port-security {
              description
                "Enable SNMP port security traps";
              presence "true";
              leaf trap-rate {
                description
                  "Number of traps per second";
                type uint16 {
                  range "0..1000";
                }
              }
            }
            container power-ethernet {
              description
                "Enable SNMP power ethernet traps";
              leaf group {
                description
                  "Enable SNMP inline power group based traps";
                type string;
              }
              leaf police {
                description
                  "Enable Policing Trap";
                type empty;
              }
            }
            leaf pppoe {
              description
                "Enable SNMP pppoe traps";
              type empty;
            }
            container pw {
              presence "true";
              leaf vc {
                type empty;
              }
            }
            leaf rep {
              type empty;
            }
            leaf resource-policy {
              type empty;
            }
            leaf rf {
              description
                "Enable all SNMP traps defined in CISCO-RF-MIB";
              type empty;
            }
            leaf rogue-ap {
              description
                "Enable SNMP 802.11 Rogue AP Trap";
              type empty;
            }
            leaf rsvp {
              description
                "Enable RSVP flow change traps";
              type empty;
            }
            leaf rtr {
              description
                "Enable SNMP Response Time Reporter traps";
              type empty;
            }
            container slb {
              description
                "Enable SNMP SLB traps";
              presence "true";
              leaf csrp {
                description
                  "Enable SNMP SLB Fault Tolerance Replication Protocol traps";
                type empty;
              }
              leaf real {
                description
                  "Enable SNMP SLB Real Server traps";
                type empty;
              }
              leaf virtual {
                description
                  "Enable SNMP SLB Virtual Server traps";
                type empty;
              }
            }
            container snmp {
              description
                "Enable SNMP traps";
              leaf authentication {
                description
                  "Enable authentication trap";
                type empty;
              }
              leaf coldstart {
                description
                  "Enable coldStart trap";
                type empty;
              }
              leaf linkdown {
                description
                  "Enable linkDown trap";
                type empty;
              }
              leaf linkup {
                description
                  "Enable linkUp trap";
                type empty;
              }
              leaf warmstart {
                description
                  "Enable warmStart trap";
                type empty;
              }
            }
            leaf sonet {
              description
                "Enable SNMP SONET traps";
              type empty;
            }
            leaf srst {
              type empty;
            }
            leaf srp {
              description
                "Enable SRP protocol traps";
              type empty;
            }
            container stackwise {
              description
                "Enable SNMP stackwise traps";
              presence "true";
              leaf GLS {
                description
                  "Enable STACKWISE stack power GLS trap";
                type empty;
              }
              leaf ILS {
                description
                  "Enable STACKWISE stack power ILS trap";
                type empty;
              }
              leaf SRLS {
                description
                  "Enable STACKWISE stack power SRLS trap";
                type empty;
              }
              leaf insufficient-power {
                description
                  "Enable STACKWISE stack power unbalanced power supplies trap";
                type empty;
              }
              leaf invalid-input-current {
                description
                  "Enable STACKWISE stack power invalid input current trap";
                type empty;
              }
              leaf invalid-output-current {
                description
                  "Enable STACKWISE stack power invalid output current trap";
                type empty;
              }
              leaf member-removed {
                description
                  "Enable STACKWISE stack member removed trap";
                type empty;
              }
              leaf member-upgrade-notification {
                description
                  "Enable STACKWISE member to be reloaded for upgrade trap";
                type empty;
              }
              leaf new-master {
                description
                  "Enable STACKWISE new master trap";
                type empty;
              }
              leaf new-member {
                description
                  "Enable STACKWISE stack new member trap";
                type empty;
              }
              leaf port-change {
                description
                  "Enable STACKWISE port change trap";
                type empty;
              }
              leaf power-budget-warning {
                description
                  "Enable STACKWISE stack power budget warning trap";
                type empty;
              }
              leaf power-invalid-topology {
                description
                  "Enable STACKWISE stack power invalid topology trap";
                type empty;
              }
              leaf power-link-status-changed {
                description
                  "Enable STACKWISE stack power link status changed trap";
                type empty;
              }
              leaf power-oper-status-changed {
                description
                  "Enable STACKWISE stack power port oper status changed trap";
                type empty;
              }
              leaf power-priority-conflict {
                description
                  "Enable STACKWISE stack power priority conflict trap";
                type empty;
              }
              leaf power-version-mismatch {
                description
                  "Enable STACKWISE stack power version mismatch discovered trap";
                type empty;
              }
              leaf ring-redundant {
                description
                  "Enable STACKWISE stack ring redundant trap";
                type empty;
              }
              leaf stack-mismatch {
                description
                  "Enable STACKWISE stack mismatch trap";
                type empty;
              }
              leaf unbalanced-power-supplies {
                description
                  "Enable STACKWISE stack power unbalanced power supplies trap";
                type empty;
              }
              leaf under-budget {
                description
                  "Enable STACKWISE stack power under budget trap";
                type empty;
              }
              leaf under-voltage {
                description
                  "Enable STACKWISE stack power under voltage trap";
                type empty;
              }
            }
            container stpx {
              presence "true";
              leaf inconsistency {
                type empty;
              }
              leaf root-inconsistency {
                type empty;
              }
              leaf loop-inconsistency {
                type empty;
              }
            }
            leaf stun {
              description
                "Enable SNMP STUN traps";
              type empty;
            }
            leaf switch-over {
              description
                "Enable SNMP 802.11 Standby Switch-over Trap";
              type empty;
            }
            leaf syslog {
              description
                "Enable SNMP syslog traps";
              type empty;
            }
            container transceiver {
              leaf all {
                type empty;
              }
            }
            leaf tty {
              description
                "Enable TCP connection traps";
              type empty;
            }
            container udld {
              description
                "Enable SNMP CISCO-UDLDP-MIB traps";
              presence "true";
              leaf link-fail-rpt {
                description
                  "Enable SNMP cudldpFastHelloLinkFailRptNotification traps";
                type empty;
              }
              leaf status-change {
                description
                  "Enable SNMP cudldpFastHelloStatusChangeNotification traps";
                type empty;
              }
            }
            leaf vlancreate {
              type empty;
            }
            leaf vlandelete {
              type empty;
            }
            leaf vlan-mac-limit {
              description
                "Enable SNMP L2 Control VLAN MAC Limit notifications";
              type empty;
            }
            leaf vlan-membership {
              type empty;
            }
            leaf voice {
              description
                "Enable SNMP voice traps";
              type empty;
            }
            container vrfmib {
              leaf vrf-up {
                type empty;
              }
              leaf vrf-down {
                type empty;
              }
              leaf vnet-trunk-up {
                type empty;
              }
              leaf vnet-trunk-down {
                type empty;
              }
            }
            leaf vrrp {
              description
                "Enable SNMP vrrp traps";
              type empty;
            }
            leaf vsimaster {
              description
                "Allow SNMP vsimaster traps";
              type empty;
            }
            container vstack {
              description
                "Enable SNMP Smart Install traps";
              presence "true";
              leaf addition {
                description
                  "Enable client added trap";
                type empty;
              }
              leaf failure {
                description
                  "Enable file upload/download failure trap";
                type empty;
              }
              leaf lost {
                description
                  "Enable client lost trap";
                type empty;
              }
              leaf operation {
                description
                  "Enable operation mode change trap";
                type empty;
              }
            }
            leaf vtp {
              type empty;
            }
            leaf wlan-wep {
              description
                "Enable SNMP 802.11 WLAN WEP Trap";
              type empty;
            }
            leaf xgcp {
              description
                "Enable XGCP protocol traps";
              type empty;
            }
            container wireless {
              description
                "wireless";
              presence true;
              container bsnMobileStation {
                description
                  "Controls wireless client traps";
                presence true;
                container bsnAccessPoint {
                  description
                    "Access Point traps";
                  presence true;
                  leaf bsnRogue {
                    description
                      "Rogue related traps";
                    type empty;
                  }
                }
              }
            }
          }
        }
      }
      // snmp-server engine-id
      container engineID {
        description
          "Configure a local or remote SNMPv3 engineID";
        leaf local {
          description
            "engineID of the local agent";
          type string {
            length "1..24";
          }
        }
        container remote;
      }
      // file-transfer     File transfer related commands

      // snmp-server group *
      list group {
        description
          "Define a User Security Model group";
        key "id";
        leaf id {
          type string;
        }
        choice security-model {
          container v1;
          container v2c;
          container v3 {
            description
              "group using the User Security Model (SNMPv3)";
            leaf security-level {
              type enumeration {
                enum "auth";
                enum "noauth";
                enum "priv";
              }
            }
            leaf context {
              description
                "specify a context to associate these views for the group";
              type string;
            }
            leaf match {
              description
                "context name match criteria";
              type enumeration {
                enum "exact";
                enum "prefix";
              }
            }
            leaf read {
              description
                "specify a read view for the group";
              type string;
            }
            leaf write {
              description
                "specify a write view for the group";
              type string;
            }
            leaf notify {
              description
                "specify a notify view for the group";
              type string;
            }
            leaf access {
              description
                "specify an access-list associated with this group";
              type union {
                type uint8 {
                  range "1..99";
                }
                type string;
              }
            }
          }
        }
      }// snmp-server host *
      list host {
        description
          "Specify hosts to receive SNMP notifications";
        key "ip-address community-string";
        leaf ip-address {
          type ios-types:host-type;
        }
        // snmp-server host * community-string
        leaf community-string {
          type string;
        }
        leaf vrf {
          description
            "VPN Routing instance for this host";
          type string;
        }
        choice informs-traps-choice {
          leaf informs {
            description
              "Send Inform messages to this host";
            type empty;
          }
          leaf traps {
            description
              "Send Trap messages to this host";
            type empty;
          }
        }
        // snmp-server host * version
        leaf version {
          description
            "SNMP version to use for notification messages";
          type enumeration {
            enum "1";
            enum "2c";
            enum "3";
          }
        }
        leaf security-level {
          type enumeration {
            enum "auth";
            enum "noauth";
            enum "priv";
          }
        }
        container trap-enable {
          leaf aaa_server {
            description
              "Allow SNMP AAA traps";
            type empty;
          }
          leaf alarms {
            description
              "Allow SNMP alarms traps";
            type empty;
          }
          leaf atm {
            description
              "Allow SNMP atm traps";
            type empty;
          }
          leaf bfd {
            description
              "Allow SNMP BFD traps";
            type empty;
          }
          leaf bgp {
            description
              "Allow BGP state change traps";
            type empty;
          }
          leaf bstun {
            description
              "Allow bstun event traps";
            type empty;
          }
          leaf bulkstat {
            description
              "Allow Data-Collection-MIB traps";
            type empty;
          }
          leaf call-home {
            description
              "Allow SNMP CISCO-CALLHOME-MIB traps";
            type empty;
          }
          leaf casa {
            description
              "Allow casa event traps";
            type empty;
          }
          leaf cef {
            description
              "Allows cef traps";
            type empty;
          }
          leaf cnpd {
            description
              "Allow NBAR Protocol Discovery traps";
            type empty;
          }
          leaf config {
            description
              "Allow SNMP config traps";
            type empty;
          }
          leaf config-copy {
            description
              "Allow SNMP config-copy traps";
            type empty;
          }
          leaf config-ctid {
            description
              "Allow SNMP config-ctid traps";
            type empty;
          }
          leaf cpu {
            description
              "Allow cpu related traps";
            type empty;
          }
          leaf dhcp {
            description
              "Allow dhcp traps";
            type empty;
          }
          leaf dlsw {
            description
              "Allow dlsw traps";
            type empty;
          }
          leaf ds1 {
            description
              "Allow SNMP ds1 traps";
            type empty;
          }
          leaf dsp {
            description
              "Allow SNMP DSP traps";
            type empty;
          }
          leaf dspu {
            description
              "Allow dspu event traps";
            type empty;
          }
          leaf eigrp {
            description
              "Allow SNMP EIGRP traps";
            type empty;
          }
          leaf entity {
            description
              "Allow SNMP entity traps";
            type empty;
          }
          leaf entity-diag {
            description
              "Allow SNMP CISCO-ENTITY-DIAG-MIB traps";
            type empty;
          }
          leaf entity-qfp {
            description
              "Allow SNMP CISCO-ENTITY-QFP-MIB traps";
            type empty;
          }
          leaf entity-state {
            description
              "Allow ENTITY-STATE-MIB traps";
            type empty;
          }
          leaf ethernet-cfm {
            description
              "Allow SNMP Ethernet CFM traps";
            type empty;
          }
          leaf evc {
            description
              "Allow SNMP EVC traps";
            type empty;
          }
          leaf event-manager {
            description
              "Allow SNMP Embedded Event Manager traps";
            type empty;
          }
          leaf firewall {
            description
              "Allow SNMP Firewall traps";
            type empty;
          }
          leaf flash {
            description
              "Allow SNMP FLASH traps";
            type empty;
          }
          leaf flowmon {
            description
              "Allow SNMP flow monitor notifications";
            type empty;
          }
          leaf frame-relay {
            description
              "Allow SNMP frame-relay traps";
            type empty;
          }
          leaf fru-ctrl {
            description
              "Allow entity FRU control traps";
            type empty;
          }
          leaf gdoi {
            description
              "Allows gdoi traps";
            type empty;
          }
          leaf hsrp {
            description
              "Allow SNMP HSRP traps";
            type empty;
          }
          leaf iplocalpool {
            description
              "Allow SNMP IP Local Pool traps";
            type empty;
          }
          leaf ipmulticast {
            description
              "Allow SNMP ipmulticast traps";
            type empty;
          }
          leaf ipsec {
            description
              "Allow SNMP IPsec traps";
            type empty;
          }
          leaf ipsla {
            description
              "Allow SNMP Host IP SLA traps";
            type empty;
          }
          leaf isakmp {
            description
              "Allow SNMP ISAKMP traps";
            type empty;
          }
          leaf isg-mib {
            description
              "Allow SNMP isgmib traps";
            type empty;
          }
          leaf isis {
            description
              "Allow IS-IS traps";
            type empty;
          }
          leaf l2tun-pseudowire-status {
            description
              "Allow SNMP L2 pseudowire status traps";
            type empty;
          }
          leaf l2tun-session {
            description
              "Allow SNMP L2 session traps";
            type empty;
          }
          leaf license {
            description
              "Allow license traps";
            type empty;
          }
          leaf memory {
            description
              "Allow SNMP Mempool traps";
            type empty;
          }
          leaf mpls-fast-reroute {
            description
              "Allow SNMP MPLS traffic engineering fast reroute traps";
            type empty;
          }
          leaf mpls-ldp {
            description
              "Allow SNMP MPLS label distribution protocol traps";
            type empty;
          }
          leaf mpls-traffic-eng {
            description
              "Allow SNMP MPLS traffic engineering traps";
            type empty;
          }
          leaf mpls-vpn {
            description
              "Allow SNMP MPLS Virtual Private Network traps";
            type empty;
          }
          leaf msdp {
            description
              "Allow SNMP MSDP traps";
            type empty;
          }
          leaf mvpn {
            description
              "Allow Multicast Virtual Private Network traps";
            type empty;
          }
          leaf nhrp {
            description
              "Allow SNMP NHRP traps";
            type empty;
          }
          leaf ospf {
            description
              "Allow OSPF traps";
            type empty;
          }
          leaf ospfv3 {
            description
              "Allow OSPFv3 traps";
            type empty;
          }
          leaf pfr {
            description
              "Allow SNMP PfR traps";
            type empty;
          }
          leaf pim {
            description
              "Allow SNMP PIM traps";
            type empty;
          }
          leaf pw-vc {
            description
              "Allow SNMP Pseudowire VC traps";
            type empty;
          }
          leaf resource-policy {
            description
              "Enable CISCO-ERM-MIB notifications";
            type empty;
          }
          leaf rf {
            description
              "Allow all SNMP traps defined in CISCO-RF-MIB";
            type empty;
          }
          leaf rsrb {
            description
              "Allow rsrb event traps";
            type empty;
          }
          leaf rsvp {
            description
              "Allow RSVP flow change traps";
            type empty;
          }
          leaf sdlc {
            description
              "Allow sdlc event traps";
            type empty;
          }
          leaf sdllc {
            description
              "Allow sdllc event traps";
            type empty;
          }
          leaf snmp {
            description
              "Allow SNMP-type notifications";
            type empty;
          }
          leaf sonet {
            description
              "Allow SNMP SONET traps";
            type empty;
          }
          leaf srp {
            description
              "Allow SRP protocol traps";
            type empty;
          }
          leaf stun {
            description
              "Allow stun event traps";
            type empty;
          }
          leaf syslog {
            description
              "Allow SNMP syslog traps";
            type empty;
          }
          leaf trustsec-sxp {
            description
              "Allow SNMP CISCO-TRUSTSEC-SXP-MIB traps";
            type empty;
          }
          leaf tty {
            description
              "Allow TCP connection traps";
            type empty;
          }
          leaf udp-port {
            description
              "The notification host's UDP port number (default port 162)";
            type uint16;
          }
          leaf voice {
            description
              "Allow SNMP Voice traps";
            type empty;
          }
          leaf vrfmib {
            description
              "Allow SNMP vrfmib traps";
            type empty;
          }
          leaf vrrp {
            description
              "Allow SNMP vrrp traps";
            type empty;
          }
          leaf x25 {
            description
              "Allow x25 event traps";
            type empty;
          }
        }
      }
      // snmp-server ip
      container ip {
        description
          "IP ToS configuration for SNMP traffic";
        leaf dscp {
          description
            "IP DSCP value for SNMP traffic";
          type uint8 {
            range "0..63";
          }
        }
        // snmp-server ip precedence
        leaf precedence {
          description
            "IP Precedence value for SNMP traffic";
          type uint8 {
            range "0..7";
          }
        }
      }
      // snmp-server ifindex
      container ifindex {
        description
          "Enable ifindex persistence";
        leaf persist {
          description
            "Persist interface indices";
          type empty;
        }
      }
      // inform            Configure SNMP Informs options

      // snmp-server location
      leaf location {
        description
          "Text for mib object sysLocation";
        type string;
      }
      // snmp-server manager
      container manager {
        description
          "Modify SNMP manager parameters";
        presence "true";
        leaf session-timeout {
          description
            "Timeout value for destroying sessions";
          type uint32 {
            range "10..2147483";
          }
        }
      }
      // snmp-server packetsize        Largest SNMP packet size
      leaf packetsize {
        description
          "Largest SNMP packet size";
        type uint32 {
          range "484..17924";
        }
      }
      // snmp-server queue-length
      leaf queue-length {
        description
          "Message queue length for each TRAP host";
        type uint16 {
          range "1..5000";
        }
      }
      // snmp-server source-interface
      container source-interface {
        description
          "Assign an source interface";
        container informs {
          description
            "source interface for informs";
          uses ios-ifc:interface-grouping;
        }
        container traps {
          description
            "source interface for traps";
          uses ios-ifc:interface-grouping;
        }
      }
      // snmp-server system-shutdown   Enable use of the SNMP reload command
      leaf system-shutdown {
        description
          "Enable use of the SNMP reload command";
        type empty;
      }
      // snmp-server tftp-server-list  Limit TFTP servers used via SNMP
      leaf tftp-server-list {
        description
          "Limit TFTP servers used via SNMP";
        type union {
          type uint8 {
            range "1..99";
          }
          type string;
        }
      }
      // snmp-server trap
      container trap {
        description
          "SNMP trap options";
        container link {
          description
            "Assign/Enable SNMP link traps";
          leaf ietf {
            description
              "Use IETF standard for SNMP traps";
            type empty;
          }
          leaf switchover {
            description
              "Enable link up/down traps during switchover";
            type empty;
          }
        }
        leaf timeout {
          description
            "Set timeout for TRAP message retransmissions";
          type uint16 {
            range "1..1000";
          }
        }
      }
      // snmp-server trap-source
      container trap-source {
        description
          "Assign an interface for the source address of all traps";
        uses ios-ifc:interface-grouping;
      }
      // trap-timeout      Set timeout for TRAP message retransmissions
      // user              Define a user who can access the SNMP engine
      container user {
        description 
          "Define a user who can access the SNMP engine";
        list names {
          key "username grpname";
          leaf username {
            description 
              "Name of the user";
            type string;
          }
          leaf grpname {
            description 
              "Group to which the user belongs";
            type string;
          }
          container v3 {
            description 
              "user using the v3 security model";
            presence true;
            container auth {
              description 
                "authentication parameters for the user";
              container sha {
                description 
                  "Use HMAC SHA algorithm for authentication";
                container auth {
                  leaf authpass {
                    description 
                      "authentication password for user";
                    type string;
                  }
                  container priv {
                    description 
                      "encryption parameters for the user";
                    container aes {
                      description 
                        "Use AES algorithm for encryption";
                      container algo128 {
                        description 
                          "Use 128 bit AES algorithm for encryption";
                        container privpass {
                          leaf privpass {
                            description 
                              "privacy password for user";
                            type string;
                          }
                          leaf access {
                            description 
                              "Access-list name";
                            type string;
                          }
                        }
                      }
                    }
                  }
                }
              }
            }
          }
        }
      }
      // snmp-server view *
      list view {
        description
          "Define an SNMPv2 MIB view";
        key "name mib";
        leaf name {
          type string;
        }
        leaf mib {
          type string;
        }
        leaf inc-exl {
          type enumeration {
            enum "excluded";
            enum "included";
          }
        }
      }
  }
  grouping router-snmp-grouping {
    container snmp {
      description
        "Modify snmp parameters";
      list context {
        description
          "Configure a SNMP context";
        key "name";
        leaf name {
          description
            "Context Name";
          type string;
        }
        container community {
          description
            "Configure a SNMP v2c Community string and access privs";
          leaf community-string {
            type string;
          }
          container access {
            leaf standard-acl {
              type uint32 {
                range "1..99";
              }
            }
            leaf expanded-acl {
              type uint32 {
                range "1300..1999";
              }
            }
            leaf acl-name {
              type string;
            }
            leaf ipv6 {
              description
                "Specify IPv6 Named Access-List";
              type string;
            }
            leaf ro {
              description
                "Read-only access with this community string";
              type empty;
            }
            leaf rw {
              description
                "Read-write access with this community string";
              type empty;
            }
          }
        }
        container user {
          description
            "Configure a SNMP v3 user";
          leaf name {
            type string;
          }
          container permisssion {
            container access {
              description
                "specify an access-list associated with this group";
              leaf standard-acl {
                type uint32;
              }
              leaf acl-name {
                type string;
              }
              leaf ipv6 {
                type string;
              }
            }
            container auth {
              description
                "authentication parameters for the user";
              leaf md5 {
                description
                  "Use HMAC MD5 algorithm for authentication";
                type string;
              }
              leaf sha {
                description
                  "Use HMAC SHA algorithm for authentication";
                type string;
              }
            }
            leaf credential {
              description
                "If the user password is already configured and saved";
              type empty;
            }
            leaf encrypted {
              description
                "specifying passwords as MD5 or SHA digests";
              type empty;
            }
          }
        }
      }
    }
  }

  grouping config-snmp-grouping {
    container ifmib {
      description
        "IF-MIB commands";
      // snmp ifmib ifindex
      container ifindex {
        description
          "ifindex persistence";
        leaf persist {
          description
            "Persist interface indices";
          type empty;
        }
      }
      // snmp ifmib ifalias long
      container ifalias {
        description
          "ifAlias description option, by default it is limited to 64 character";
        leaf long {
          description
            "ifAlias description can be up to 256 characters";
          type empty;
        }
      }
    }
    // snmp mib
    container mib {
      description
  "MIB commands";
      container community-map {
        description "Community Mapping as per RFC-2576";
        list community-map-list {
          description "SNMP community string";
          key "name";
          leaf name {
            type string;
          }
          leaf engineid {
            description "Engine ID for the community mapping";
            type string;
          }
        }
      }

      // snmp mib bulkstat
      container bulkstat {
        description
          "Bulkstat Configuration commands";
        list object-list {
          description
            "Configure an Object List.";
          key "name";
          leaf name {
            type string;
          }
        }
      }
      // snmp mib persist
      container persist {
        description
          "Persistence for MIBS";
        presence "true";
        leaf persist-enum {
          type enumeration {
            enum "cbqos";
            enum "circuit";
            enum "v3mibs";
          }
        }
      }
    }
  }

  grouping config-interface-snmp-grouping {
    container snmp {
      description
        "Modify SNMP interface parameters";
      container ifindex {
        description
          "Persist ifindex for the interface";
        choice ifindex-choice {
          leaf persist {
            description
              "Enable/Disable ifIndex persistence ";
            type empty;
          }
          leaf clear {
            description
              "Clear Enable/Disable ifIndex persistence";
            type boolean;
          }
        }
      }

      // interface * / snmp trap
      container trap {
        description
          "Allow a specific SNMP trap";

        leaf link-status {
          description
            "Allow SNMP LINKUP and LINKDOWN traps";
          type boolean;
        }

        container link-status-capas {
          container link-status {
            description
              "Allow SNMP LINKUP and LINKDOWN traps";
            container permit {
              description
                "Permit the following capability";
              leaf duplicates {
                description
                  "Permit duplicate SNMP LINKUP and LINKDOWN traps";
                type empty;
              }
            }
          }
        }
      }
    }
  }

  /////////////////////////////////////////////////////////
  // native / snmp
  /////////////////////////////////////////////////////////
  augment "/ios:native/ios:snmp" {
    uses config-snmp-grouping;
  }

  /////////////////////////////////////////////////////////
  // native / snmp-server
  /////////////////////////////////////////////////////////
  augment "/ios:native/ios:snmp-server" {
    uses config-snmp-server-grouping;
  }

  /////////////////////////////////////////////////////////
  // native / interface * / snmp
  /////////////////////////////////////////////////////////
  augment "/ios:native/ios:interface/ios:FastEthernet" {
    uses config-interface-snmp-grouping;
  }

  augment "/ios:native/ios:interface/ios:GigabitEthernet" {
    uses config-interface-snmp-grouping;
  }

  augment "/ios:native/ios:interface/ios:TenGigabitEthernet" {
    uses config-interface-snmp-grouping;
  }

  augment "/ios:native/ios:interface/ios:FiveGigabitEthernet" {
    uses config-interface-snmp-grouping;
  }

  augment "/ios:native/ios:interface/ios:TwentyFiveGigabitEthernet" {
    uses config-interface-snmp-grouping;
  }


  augment "/ios:native/ios:interface/ios:Loopback" {
    uses config-interface-snmp-grouping;
  }

  augment "/ios:native/ios:interface/ios:Port-channel" {
    uses config-interface-snmp-grouping;
  }

  augment "/ios:native/ios:interface/ios:Tunnel" {
    uses config-interface-snmp-grouping;
  }

  augment "/ios:native/ios:interface/ios:Virtual-Template" {
    uses config-interface-snmp-grouping;
  }

  augment "/ios:native/ios:interface/ios:VirtualPortGroup" {
    uses config-interface-snmp-grouping;
  }
}
