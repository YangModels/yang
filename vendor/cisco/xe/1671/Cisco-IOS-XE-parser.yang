submodule Cisco-IOS-XE-parser {
  belongs-to Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Parser Yang model.
     Copyright (c) 2016 by Cisco Systems, Inc.
     All rights reserved.";

  // =========================================================================
  // REVISION
  // =========================================================================
  revision 2017-02-07 {
    description
      "Initial revision";
  }

  grouping config-parser-grouping {
    container parser { //40048
      description
        "Configure parser";
      container config {
        description
          "Configure config generation";
        leaf cache {
          description
            "Cache the configuration";
          type enumeration {
            enum "interface";
          }
        }
        leaf partition {
          description
            "Enable configuration Partitioning";
          type empty;
        }
      }
    }
  }

  grouping config-privilege-grouping {
    container privilege { //55368
      description
        "Command privilege parameters";
      // privilege exec
      container exec {
        description
          "Exec mode";
        // privilege exec level
        list level {
          description
            "Set privilege level of command";
          key "privilege";
          leaf privilege {
            type uint8;
          }
          list command-list {
            key "command";
            leaf command {
	      description
	        "There are side effects";
              type string {
                pattern "(show.*)|(write.*)";
              }
            }
          }
        }
      }
    }
  }
}
