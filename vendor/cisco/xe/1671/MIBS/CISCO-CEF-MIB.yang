/*
 * Generated by confdc --mib2yang-std
 * Source: mgmt/dmi/model/mib/src/CISCO-CEF-MIB.mib
 */
/*
 * This YANG module has been generated by smidump 0.5.0:
 *
 *      smidump -f yang CISCO-CEF-MIB
 *
 * Do not edit. Edit the source file instead!
 */

module CISCO-CEF-MIB {

  namespace "urn:ietf:params:xml:ns:yang:smiv2:CISCO-CEF-MIB";
  prefix CISCO-CEF-MIB;

  import CISCO-CEF-TC {
    prefix "cisco-cef";
  }

  import CISCO-TC {
    prefix "cisco-tc";
  }

  import ENTITY-MIB {
    prefix "entity-mib";
  }

  import IF-MIB {
    prefix "if-mib";
  }

  import INET-ADDRESS-MIB {
    prefix "inet-address";
  }

  import MPLS-VPN-MIB {
    prefix "mpls-vpn";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco System, Inc.";

  contact
   "Postal: Cisco Systems, Inc.
    170 West Tasman Drive
    San Jose, CA 95134-1706
    USA
    
    Tel: +1 800 553-NETS
    
    E-mail: cs-cef@cisco.com";

  description
   "Cisco Express Forwarding (CEF) describes a high speed 
    switching mechanism that a router uses to forward packets
    from the inbound to the outbound interface. 
    
    CEF uses two sets of data structures
    or tables, which it stores in router memory:
    
    Forwarding information base (FIB) - Describes a database
    of information used to make forwarding decisions. It is 
    conceptually similar to a routing table or route-cache, 
    although its implementation is different.
    
    Adjacency - Two nodes in the network are said to be 
    adjacent if they can reach each other via a single hop 
    across a link layer.           
    
    CEF path is a valid route to reach to a destination 
    IP prefix. Multiple paths may exist out of a router to the 
    same destination prefix. CEF Load balancing capability 
    share the traffic to the destination IP prefix over all 
    the active paths. 
    
    After obtaining the prefix in the CEF table with the
    longest match, output forwarding follows the chain of 
    forwarding elements. 
    
    Forwarding element (FE) may process the packet, forward 
    the packet, drop or punt the packet or it may also
    pass the packet to the next forwarding element in the 
    chain for further processing.
    
    Forwarding Elements are of various types
    but this MIB only represents the forwarding elements of
    adjacency and label types. Hence a forwarding element 
    chain will be represented as a list of labels and
    adjacency. The adjacency may point to a forwarding element
    list again, if it is not the last forwarding element in this
    chain. 
    
    For the simplest IP forwarding case, the prefix entry will 
    point at an adjacency forwarding element.
    The IP adjacency processing function will apply the output
    features, add the encapsulation (performing any required 
    fixups), and may send the packet out.
    
    If loadbalancing is configured, the prefix entry will point 
    to lists of forwarding elements. One of these lists will be 
    selected to forward the packet. 
    
    Each forwarding element list dictates which of a set of 
    possible packet transformations to apply on the way to 
    the same neighbour. 
    
    The following diagram represents relationship
    between three of the core tables in this MIB module.
    
     cefPrefixTable             cefFESelectionTable
    
     +---------------+  points           +--------------+   
     |   |     |     |  a set     +----> |   |   |   |  | 
     |---------------|  of FE     |      |--------------|   
     |   |     |     |  Selection |      |   |   |   |  |
     |---------------|  Entries   |      |--------------|    
     |   |     |     |------------+      |              |<----+ 
     |---------------|                   |--------------|     |
     |               |    +--------------|   |   |   |  |     |
     +---------------+    |              +--------------+     |
                          |                                   |
                    points to an                              |
                    adjacency entry                           |
                          |                                   |
                          |   cefAdjTable                     |
                          |  +---------------+  may point     |
                          +->|   |     |     |  to a set      |
                             |---------------|  of FE         |
                             |   |     |     |  Selection     |
                             |---------------|  Entries       | 
                             |   |     |     |----------------+
                             |---------------| 
                             |               | 
                             +---------------+ 
    
    Some of the Cisco series routers (e.g. 7500 & 12000) 
    support distributed CEF (dCEF), in which the line cards 
    (LCs) make the packet forwarding decisions using locally 
    stored copies of the same Forwarding information base (FIB)
    and adjacency tables as the Routing Processor (RP).
              
    Inter-Process Communication (IPC) is the protocol used 
    by routers that support distributed packet forwarding. 
    CEF updates are encoded as external Data Representation 
    (XDR) information elements inside IPC messages. 
             
    This MIB reflects the distributed nature of CEF, e.g. CEF
    has different instances running on the RP and the line cards.
    
    There may be instances of inconsistency between the
    CEF forwarding databases(i.e between CEF forwarding 
    database on line cards and the CEF forwarding database
    on the RP). CEF consistency checkers (CC) detects 
    this inconsistency.
    
    When two databases are compared by a consistency checker, 
    a set of records from the first (master) database is 
    looked up in the second (slave).
    
    There are two types of consistency checkers, 
    active and passive. Active consistency checkers 
    are invoked in response to some stimulus, i.e. 
    when a packet cannot be forwarded because the 
    prefix is not in the forwarding table or 
    in response to a Management Station request.
    
    Passive consistency checkers operate in the background, 
    scanning portions of the databases on a periodic basis.
    
    The full-scan checkers are active consistency checkers
    which are invoked in response to a Management Station
    Request.
    
    If 64-bit counter objects in this MIB are supported,
    then their associated 32-bit counter objects 
    must also be supported. The 32-bit counters will
    report the low 32-bits of the associated 64-bit 
    counter count (e.g., cefPrefixPkts will report the 
    least significant 32 bits of cefPrefixHCPkts).
    The same rule should be applied for the 64-bit gauge
    objects and their assocaited 32-bit gauge objects.
    
    If 64-bit counters in this MIB are not supported,
    then an agent MUST NOT instantiate the corresponding
    objects with an incorrect value; rather, it MUST 
    respond with the appropriate error/exception 
    condition (e.g., noSuchInstance or noSuchName). 
    
    Counters related to CEF accounting (e.g.,
    cefPrefixPkts) MUST NOT be instantiated if the
    corresponding accounting method has been disabled.  
     
    This MIB allows configuration and monitoring of CEF 
    related objects.";

  revision 2006-01-30 {
    description
     "Initial version of this MIB module.";
  }


  container CISCO-CEF-MIB {
    config false;

    container cefFIB {
      smiv2:oid "1.3.6.1.4.1.9.9.492.1.1";

      leaf cefLMPrefixSpinLock {
        type snmpv2-tc:TestAndIncr;
        description
         "An advisory lock used to allow cooperating SNMP
          Command Generator applications to coordinate their
          use of the Set operation in creating Longest
          Match Prefix Entries in cefLMPrefixTable.
          
          When creating a new longest prefix match entry,
          the value of cefLMPrefixSpinLock should be retrieved.  
          The destination address should be determined to be
          unique by the SNMP Command Generator application by
          consulting the cefLMPrefixTable. Finally, the longest 
          prefix entry may be created (Set), including the
          advisory lock.
                 
          If another SNMP Command Generator application has
          altered the longest prefix entry in the meantime, 
          then the spin lock's value will have changed, 
          and so this creation will fail because it will specify
          the wrong value for the spin lock.
          
          Since this is an advisory lock, the use of this lock
          is not enforced, but not using this lock may lead
          to conflict with the another SNMP command responder 
          application which may also be acting on the
          cefLMPrefixTable.";
        smiv2:max-access "read-write";
        smiv2:oid "1.3.6.1.4.1.9.9.492.1.1.3";
      }
    }

    container cefCC {
      smiv2:oid "1.3.6.1.4.1.9.9.492.1.7";

      leaf entLastInconsistencyDetectTime {
        type yang:timestamp;
        description
         "The value of sysUpTime at the time an
          inconsistency is detecetd.";
        smiv2:max-access "read-only";
        smiv2:oid "1.3.6.1.4.1.9.9.492.1.7.4";
      }

      leaf cefInconsistencyReset {
        type cisco-cef:CefCCAction;
        description
         "Setting the value of this object to ccActionStart(1)
          will reset all the active consistency checkers.
          
          The Management station should poll the 
          cefInconsistencyResetStatus object to get the 
          state of inconsistency reset operation.
          
          This operation once started, cannot be aborted.
          Hence, the value of this object cannot be set to
          ccActionAbort(2).
          
          The value of this object can't be set to ccActionStart(1), 
          if the value of object cefInconsistencyResetStatus
          is ccStatusRunning(2).";
        smiv2:defval "ccActionNone";
        smiv2:max-access "read-write";
        smiv2:oid "1.3.6.1.4.1.9.9.492.1.7.5";
      }

      leaf cefInconsistencyResetStatus {
        type cisco-cef:CefCCStatus;
        description
         "Indicates the status of the consistency reset
          request.";
        smiv2:max-access "read-only";
        smiv2:oid "1.3.6.1.4.1.9.9.492.1.7.6";
      }
    }

    container cefNotifCntl {
      smiv2:oid "1.3.6.1.4.1.9.9.492.1.9";

      leaf cefResourceFailureNotifEnable {
        type boolean;
        description
         "Indicates whether or not a notification should be
          generated on the detection of CEF resource Failure.";
        smiv2:max-access "read-write";
        smiv2:oid "1.3.6.1.4.1.9.9.492.1.9.1";
      }

      leaf cefPeerStateChangeNotifEnable {
        type boolean;
        description
         "Indicates whether or not a notification should be
          generated on the detection of CEF peer state change.";
        smiv2:max-access "read-write";
        smiv2:oid "1.3.6.1.4.1.9.9.492.1.9.2";
      }

      leaf cefPeerFIBStateChangeNotifEnable {
        type boolean;
        description
         "Indicates whether or not a notification should be
          generated on the detection of CEF FIB peer state change.";
        smiv2:max-access "read-write";
        smiv2:oid "1.3.6.1.4.1.9.9.492.1.9.3";
      }

      leaf cefNotifThrottlingInterval {
        type int32 {
          range "0..3600";
        }
        units "seconds";
        description
         "This object controls the generation of the
          cefInconsistencyDetection notification.
          
          If this object has a value of zero,
          then the throttle control is disabled.
          
          If this object has a non-zero value, then the agent
          must not generate more than one 
          cefInconsistencyDetection 'notification-event' in the 
          indicated period, where a 'notification-event' is the
          transmission of a single trap
          or inform PDU to a list of notification destinations.
          
          If additional inconsistency is detected within the 
          throttling period, then notification-events
          for these inconsistencies should be suppressed by the agent
          until the current throttling period expires.  At the end of a
          throttling period, one notification-event should be generated
          if any inconsistency was detected since the start of the 
          throttling period. In such a case,  another throttling period
          is started right away.
          
          An NMS should periodically poll cefInconsistencyRecordTable
          to detect any missed cefInconsistencyDetection
          notification-events, e.g., due to throttling or transmission
          loss.
           
          If cefNotifThrottlingInterval notification generation
          is enabled, the suggested default throttling period is
          60 seconds, but generation of the cefInconsistencyDetection
          notification should be disabled by default.
          
          If the agent is capable of storing non-volatile
          configuration, then the value of this object must be
          restored after a re-initialization of the management
          system.
          
          The actual transmission of notifications is controlled
          via the MIB modules in RFC 3413.";
        smiv2:defval "0";
        smiv2:max-access "read-write";
        smiv2:oid "1.3.6.1.4.1.9.9.492.1.9.4";
      }

      leaf cefInconsistencyNotifEnable {
        type boolean;
        description
         "Indicates whether cefInconsistencyDetection notification
          should be generated for this managed device.";
        smiv2:max-access "read-write";
        smiv2:oid "1.3.6.1.4.1.9.9.492.1.9.5";
      }
    }

    container cefFIBSummaryTable {
      description
       "This table contains the summary information
        for the cefPrefixTable.";
      smiv2:oid "1.3.6.1.4.1.9.9.492.1.1.1.1";

      list cefFIBSummaryEntry {
        key "entPhysicalIndex cefFIBIpVersion";
        description
         "If CEF is enabled on the Managed device,
          each entry contains the FIB summary related
          attributes for the managed entity.
          
          A row may exist for each IP version type
          (v4 and v6) depending upon the IP version
          supported on the device.
          
          entPhysicalIndex is also an index for this
          table which represents entities of
          'module' entPhysicalClass which are capable
          of running CEF.";
        smiv2:oid "1.3.6.1.4.1.9.9.492.1.1.1.1.1";

        leaf entPhysicalIndex {
          type leafref {
            path "/entity-mib:ENTITY-MIB/entity-mib:entPhysicalTable/entity-mib:entPhysicalEntry/entity-mib:entPhysicalIndex";
          }
        }

        leaf cefFIBIpVersion {
          type cisco-cef:CefIpVersion;
          description
           "The version of IP forwarding.";
          smiv2:max-access "not-accessible";
          smiv2:oid "1.3.6.1.4.1.9.9.492.1.1.1.1.1.1";
        }

        leaf cefFIBSummaryFwdPrefixes {
          type uint32;
          description
           "Total number of forwarding Prefixes
            in FIB for the IP version specified
            by cefFIBIpVersion object.";
          smiv2:max-access "read-only";
          smiv2:oid "1.3.6.1.4.1.9.9.492.1.1.1.1.1.2";
        }
      }
    }

    container cefPrefixTable {
      description
       "A list of CEF forwarding prefixes.";
      smiv2:oid "1.3.6.1.4.1.9.9.492.1.1.2";

      list cefPrefixEntry {
        key "entPhysicalIndex cefPrefixType cefPrefixAddr cefPrefixLen";
        description
         "If CEF is enabled on the Managed device,
          each entry contains the forwarding 
          prefix attributes. 
          
          CEF prefix based non-recursive stats are maintained
          in internal and external buckets (depending upon the 
          value of cefIntNonrecursiveAccouting object in the 
          CefIntEntry).
          
          entPhysicalIndex is also an index for this
          table which represents entities of
          'module' entPhysicalClass which are capable
          of running CEF.";
        smiv2:oid "1.3.6.1.4.1.9.9.492.1.1.2.1";

        leaf entPhysicalIndex {
          type leafref {
            path "/entity-mib:ENTITY-MIB/entity-mib:entPhysicalTable/entity-mib:entPhysicalEntry/entity-mib:entPhysicalIndex";
          }
        }

        leaf cefPrefixType {
          type inet-address:InetAddressType;
          description
           "The Network Prefix Type.
            This object specifies the address type
            used for cefPrefixAddr.
            
            Prefix entries are only valid for the address
            type of ipv4(1) and ipv6(2).";
          smiv2:max-access "not-accessible";
          smiv2:oid "1.3.6.1.4.1.9.9.492.1.1.2.1.1";
        }

        leaf cefPrefixAddr {
          type inet-address:InetAddress;
          description
           "The Network Prefix Address.
            The type of this address is determined by
            the value of the cefPrefixType object.
            This object is a Prefix Address containing the 
            prefix with length specified by cefPrefixLen. 
            Any bits beyond the length specified by
            cefPrefixLen are zeroed.";
          smiv2:max-access "not-accessible";
          smiv2:oid "1.3.6.1.4.1.9.9.492.1.1.2.1.2";
        }

        leaf cefPrefixLen {
          type inet-address:InetAddressPrefixLength;
          description
           "Length in bits of the FIB Address prefix.";
          smiv2:max-access "not-accessible";
          smiv2:oid "1.3.6.1.4.1.9.9.492.1.1.2.1.3";
        }

        leaf cefPrefixForwardingInfo {
          type snmp-framework:SnmpAdminString;
          description
           "This object indicates the associated forwarding element
            selection entries in cefFESelectionTable.
            The value of this object is index value (cefFESelectionName)
            of cefFESelectionTable.";
          smiv2:max-access "read-only";
          smiv2:oid "1.3.6.1.4.1.9.9.492.1.1.2.1.4";
        }

        leaf cefPrefixPkts {
          type yang:counter32;
          units "packets";
          description
           "If CEF accounting is set to enable per prefix
            accounting (value of cefCfgAccountingMap object in 
            the cefCfgEntry is set to enable 'perPrefix' 
            accounting), then this object represents the 
            number of packets switched to this prefix.";
          smiv2:max-access "read-only";
          smiv2:oid "1.3.6.1.4.1.9.9.492.1.1.2.1.5";
        }

        leaf cefPrefixHCPkts {
          type yang:counter64;
          units "packets";
          description
           "If CEF accounting is set to enable per prefix
            accounting (value of cefCfgAccountingMap object in 
            the cefCfgEntry is set to enable 'perPrefix' 
            accounting), then this object represents the 
            number of packets switched to this prefix. 
            
            This object is a 64-bit version of 
            cefPrefixPkts.";
          smiv2:max-access "read-only";
          smiv2:oid "1.3.6.1.4.1.9.9.492.1.1.2.1.6";
        }

        leaf cefPrefixBytes {
          type yang:counter32;
          units "bytes";
          description
           "If CEF accounting is set to enable per prefix
            accounting (value of cefCfgAccountingMap object in 
            the cefCfgEntry is set to enable 'perPrefix' 
            accounting), then this object represents the 
            number of bytes switched to this prefix.";
          smiv2:max-access "read-only";
          smiv2:oid "1.3.6.1.4.1.9.9.492.1.1.2.1.7";
        }

        leaf cefPrefixHCBytes {
          type yang:counter64;
          units "bytes";
          description
           "If CEF accounting is set to enable per prefix
            accounting (value of cefCfgAccountingMap object in 
            the cefCfgEntry is set to enable 'perPrefix' 
            accounting), then this object represents the 
            number of bytes switched to this prefix.
            
            This object is a 64-bit version of 
            cefPrefixBytes.";
          smiv2:max-access "read-only";
          smiv2:oid "1.3.6.1.4.1.9.9.492.1.1.2.1.8";
        }

        leaf cefPrefixInternalNRPkts {
          type yang:counter32;
          units "packets";
          description
           "If CEF accounting is set to enable non-recursive
            accounting (value of cefCfgAccountingMap object in 
            the cefCfgEntry is set to enable 'nonRecursive' 
            accounting), then this object represents the number
            of non-recursive packets in the internal bucket
            switched using this prefix.";
          smiv2:max-access "read-only";
          smiv2:oid "1.3.6.1.4.1.9.9.492.1.1.2.1.9";
        }

        leaf cefPrefixInternalNRHCPkts {
          type yang:counter64;
          units "packets";
          description
           "If CEF accounting is set to enable non-recursive
            accounting (value of cefCfgAccountingMap object in 
            the cefCfgEntry is set to enable 'nonRecursive' 
            accounting), then this object represents the number
            of non-recursive packets in the internal bucket
            switched using this prefix.
            
            This object is a 64-bit version of 
            cefPrefixInternalNRPkts.";
          smiv2:max-access "read-only";
          smiv2:oid "1.3.6.1.4.1.9.9.492.1.1.2.1.10";
        }

        leaf cefPrefixInternalNRBytes {
          type yang:counter32;
          units "bytes";
          description
           "If CEF accounting is set to enable nonRecursive
            accounting (value of cefCfgAccountingMap object in 
            the cefCfgEntry is set to enable 'nonRecursive' 
            accounting), then this object represents 
            the number of non-recursive bytes in the internal
            bucket switched using this prefix.";
          smiv2:max-access "read-only";
          smiv2:oid "1.3.6.1.4.1.9.9.492.1.1.2.1.11";
        }

        leaf cefPrefixInternalNRHCBytes {
          type yang:counter64;
          units "bytes";
          description
           "If CEF accounting is set to enable nonRecursive
            accounting (value of cefCfgAccountingMap object in 
            the cefCfgEntry is set to enable 'nonRecursive' 
            accounting), then this object represents 
            the number of non-recursive bytes in the internal
            bucket switched using this prefix.
            
            This object is a 64-bit version of 
            cefPrefixInternalNRBytes.";
          smiv2:max-access "read-only";
          smiv2:oid "1.3.6.1.4.1.9.9.492.1.1.2.1.12";
        }

        leaf cefPrefixExternalNRPkts {
          type yang:counter32;
          units "packets";
          description
           "If CEF accounting is set to enable non-recursive
            accounting (value of cefCfgAccountingMap object in 
            the cefCfgEntry is set to enable 'nonRecursive' 
            accounting), then this object represents the number
            of non-recursive packets in the external bucket
            switched using this prefix.";
          smiv2:max-access "read-only";
          smiv2:oid "1.3.6.1.4.1.9.9.492.1.1.2.1.13";
        }

        leaf cefPrefixExternalNRHCPkts {
          type yang:counter64;
          units "packets";
          description
           "If CEF accounting is set to enable non-recursive
            accounting (value of cefCfgAccountingMap object in 
            the cefCfgEntry is set to enable 'nonRecursive' 
            accounting), then this object represents the number
            of non-recursive packets in the external bucket
            switched using this prefix.
            
            This object is a 64-bit version of 
            cefPrefixExternalNRPkts.";
          smiv2:max-access "read-only";
          smiv2:oid "1.3.6.1.4.1.9.9.492.1.1.2.1.14";
        }

        leaf cefPrefixExternalNRBytes {
          type yang:counter32;
          units "bytes";
          description
           "If CEF accounting is set to enable nonRecursive
            accounting (value of cefCfgAccountingMap object in 
            the cefCfgEntry is set to enable 'nonRecursive' 
            accounting), then this object represents 
            the number of non-recursive bytes in the external
            bucket switched using this prefix.";
          smiv2:max-access "read-only";
          smiv2:oid "1.3.6.1.4.1.9.9.492.1.1.2.1.15";
        }

        leaf cefPrefixExternalNRHCBytes {
          type yang:counter64;
          units "bytes";
          description
           "If CEF accounting is set to enable nonRecursive
            accounting (value of cefCfgAccountingMap object in 
            the cefCfgEntry is set to enable 'nonRecursive' 
            accounting), then this object represents 
            the number of non-recursive bytes in the external
            bucket switched using this prefix.
            
            This object is a 64-bit version of 
            cefPrefixExternalNRBytes.";
          smiv2:max-access "read-only";
          smiv2:oid "1.3.6.1.4.1.9.9.492.1.1.2.1.16";
        }
      }
    }

    container cefLMPrefixTable {
      description
       "A table of Longest Match Prefix Query requests.
        
        Generator application should utilize the
        cefLMPrefixSpinLock to try to avoid collisions.
        See DESCRIPTION clause of cefLMPrefixSpinLock.";
      smiv2:oid "1.3.6.1.4.1.9.9.492.1.1.4";

      list cefLMPrefixEntry {
        key "entPhysicalIndex cefLMPrefixDestAddrType cefLMPrefixDestAddr";
        description
         "If CEF is enabled on the managed device, then each
          entry represents a longest Match Prefix request.
          
          A management station wishing to get the longest
          Match prefix for a given destination address
          should create the associate instance of the
          row status. The row status should be set to
          active(1) to initiate the request. Note that 
          this entire procedure may be initiated via a 
          single set request which specifies a row status 
          of createAndGo(4).
          
          Once the request completes, the management station 
          should retrieve the values of the objects of 
          interest, and should then delete the entry.  In order 
          to prevent old entries from clogging the table, 
          entries will be aged out, but an entry will never be 
          deleted within 5 minutes of completion.
          Entries are lost after an agent restart.
          
          I.e. to find out the longest prefix match for 
          destination address of A.B.C.D on entity whose
          entityPhysicalIndex is 1, the Management station
          will create an entry in cefLMPrefixTable with
          cefLMPrefixRowStatus.1(entPhysicalIndex).1(ipv4).A.B.C.D
          set to createAndGo(4). Management Station may query the
          value of objects cefLMPrefix and cefLMPrefixLen
          to find out the corresponding prefix entry from the
          cefPrefixTable once the value of cefLMPrefixState
          is set to matchFound(2).
          
          entPhysicalIndex is also an index for this
          table which represents entities of
          'module' entPhysicalClass which are capable
          of running CEF.";
        smiv2:oid "1.3.6.1.4.1.9.9.492.1.1.4.1";

        leaf entPhysicalIndex {
          type leafref {
            path "/entity-mib:ENTITY-MIB/entity-mib:entPhysicalTable/entity-mib:entPhysicalEntry/entity-mib:entPhysicalIndex";
          }
        }

        leaf cefLMPrefixDestAddrType {
          type inet-address:InetAddressType;
          description
           "The Destination Address Type.
            This object specifies the address type
            used for cefLMPrefixDestAddr.
            
            Longest Match Prefix entries are only valid 
            for the address type of ipv4(1) and ipv6(2).";
          smiv2:max-access "not-accessible";
          smiv2:oid "1.3.6.1.4.1.9.9.492.1.1.4.1.1";
        }

        leaf cefLMPrefixDestAddr {
          type inet-address:InetAddress;
          description
           "The Destination Address.
            The type of this address is determined by
            the value of the cefLMPrefixDestAddrType object.";
          smiv2:max-access "not-accessible";
          smiv2:oid "1.3.6.1.4.1.9.9.492.1.1.4.1.2";
        }

        leaf cefLMPrefixState {
          type cisco-cef:CefPrefixSearchState;
          description
           "Indicates the state of this prefix search request.";
          smiv2:max-access "read-only";
          smiv2:oid "1.3.6.1.4.1.9.9.492.1.1.4.1.3";
        }

        leaf cefLMPrefixAddr {
          type inet-address:InetAddress;
          description
           "The Network Prefix Address. Index to the cefPrefixTable.
            The type of this address is determined by
            the value of the cefLMPrefixDestAddrType object.";
          smiv2:max-access "read-only";
          smiv2:oid "1.3.6.1.4.1.9.9.492.1.1.4.1.4";
        }

        leaf cefLMPrefixLen {
          type inet-address:InetAddressPrefixLength;
          description
           "The Network Prefix Length. Index to the cefPrefixTable.";
          smiv2:max-access "read-only";
          smiv2:oid "1.3.6.1.4.1.9.9.492.1.1.4.1.5";
        }

        leaf cefLMPrefixRowStatus {
          type snmpv2-tc:RowStatus;
          description
           "The status of this table entry.  Once the entry 
            status is set to active(1), the associated entry 
            cannot be modified until the request completes
            (cefLMPrefixState transitions to matchFound(2) 
            or noMatchFound(3)).
            
            Once the longest match request has been created
            (i.e. the cefLMPrefixRowStatus has been made active),
            the entry cannot be modified - the only operation
            possible after this is to delete the row.";
          smiv2:max-access "read-write";
          smiv2:oid "1.3.6.1.4.1.9.9.492.1.1.4.1.6";
        }
      }
    }

    container cefPathTable {
      description
       "CEF prefix path is a valid route to reach to a 
        destination IP prefix. Multiple paths may exist 
        out of a router to the same destination prefix. 
        This table specify lists of CEF paths.";
      smiv2:oid "1.3.6.1.4.1.9.9.492.1.1.5";

      list cefPathEntry {
        key "entPhysicalIndex cefPrefixType cefPrefixAddr cefPrefixLen cefPathId";
        description
         "If CEF is enabled on the Managed device,
          each entry contain a CEF prefix path.
          
          entPhysicalIndex is also an index for this
          table which represents entities of
          'module' entPhysicalClass which are capable
          of running CEF.";
        smiv2:oid "1.3.6.1.4.1.9.9.492.1.1.5.1";

        leaf entPhysicalIndex {
          type leafref {
            path "/entity-mib:ENTITY-MIB/entity-mib:entPhysicalTable/entity-mib:entPhysicalEntry/entity-mib:entPhysicalIndex";
          }
        }

        leaf cefPrefixType {
          type leafref {
            path "/CISCO-CEF-MIB:CISCO-CEF-MIB/CISCO-CEF-MIB:cefPrefixTable/CISCO-CEF-MIB:cefPrefixEntry/CISCO-CEF-MIB:cefPrefixType";
          }
        }

        leaf cefPrefixAddr {
          type leafref {
            path "/CISCO-CEF-MIB:CISCO-CEF-MIB/CISCO-CEF-MIB:cefPrefixTable/CISCO-CEF-MIB:cefPrefixEntry/CISCO-CEF-MIB:cefPrefixAddr";
          }
        }

        leaf cefPrefixLen {
          type leafref {
            path "/CISCO-CEF-MIB:CISCO-CEF-MIB/CISCO-CEF-MIB:cefPrefixTable/CISCO-CEF-MIB:cefPrefixEntry/CISCO-CEF-MIB:cefPrefixLen";
          }
        }

        leaf cefPathId {
          type int32 {
            range "1..2147483647";
          }
          description
           "The locally arbitrary, but unique identifier associated
            with this prefix path entry.";
          smiv2:max-access "not-accessible";
          smiv2:oid "1.3.6.1.4.1.9.9.492.1.1.5.1.1";
        }

        leaf cefPathType {
          type cisco-cef:CefPathType;
          description
           "Type for this CEF Path.";
          smiv2:max-access "read-only";
          smiv2:oid "1.3.6.1.4.1.9.9.492.1.1.5.1.2";
        }

        leaf cefPathInterface {
          type if-mib:InterfaceIndexOrZero;
          description
           "Interface associated with this CEF path.
            
            A value of zero for this object will indicate
            that no interface is associated with this path 
            entry.";
          smiv2:max-access "read-only";
          smiv2:oid "1.3.6.1.4.1.9.9.492.1.1.5.1.3";
        }

        leaf cefPathNextHopAddr {
          type inet-address:InetAddress;
          description
           "Next hop address associated with this CEF path.
            
            The value of this object is only relevant
            for attached next hop and recursive next hop  
            path types (when the object cefPathType is
            set to attachedNexthop(4) or recursiveNexthop(5)).
            and will be set to zero for other path types.
            
            The type of this address is determined by
            the value of the cefPrefixType object.";
          smiv2:max-access "read-only";
          smiv2:oid "1.3.6.1.4.1.9.9.492.1.1.5.1.4";
        }

        leaf cefPathRecurseVrfName {
          type mpls-vpn:MplsVpnId;
          description
           "The recursive vrf name associated with this path.
            
            The value of this object is only relevant
            for recursive next hop path types (when the 
            object cefPathType is set to recursiveNexthop(5)),
            and '0x00' will be returned for other path types.";
          smiv2:max-access "read-only";
          smiv2:oid "1.3.6.1.4.1.9.9.492.1.1.5.1.5";
        }
      }
    }

    container cefAdjSummaryTable {
      description
       "This table contains the summary information
        for the cefAdjTable.";
      smiv2:oid "1.3.6.1.4.1.9.9.492.1.2.1.1";

      list cefAdjSummaryEntry {
        key "entPhysicalIndex cefAdjSummaryLinkType";
        description
         "If CEF is enabled on the Managed device,
          each entry contains the CEF Adjacency  
          summary related attributes for the
          Managed entity. A row exists for
          each adjacency link type.
          
          entPhysicalIndex is also an index for this
          table which represents entities of
          'module' entPhysicalClass which are capable
          of running CEF.";
        smiv2:oid "1.3.6.1.4.1.9.9.492.1.2.1.1.1";

        leaf entPhysicalIndex {
          type leafref {
            path "/entity-mib:ENTITY-MIB/entity-mib:entPhysicalTable/entity-mib:entPhysicalEntry/entity-mib:entPhysicalIndex";
          }
        }

        leaf cefAdjSummaryLinkType {
          type cisco-cef:CefAdjLinkType;
          description
           "The link type of the adjacency.";
          smiv2:max-access "not-accessible";
          smiv2:oid "1.3.6.1.4.1.9.9.492.1.2.1.1.1.1";
        }

        leaf cefAdjSummaryComplete {
          type uint32;
          description
           "The total number of complete adjacencies.
            
            The total number of adjacencies which can be used 
            to switch traffic to a neighbour.";
          smiv2:max-access "read-only";
          smiv2:oid "1.3.6.1.4.1.9.9.492.1.2.1.1.1.2";
        }

        leaf cefAdjSummaryIncomplete {
          type uint32;
          description
           "The total number of incomplete adjacencies.
            
            The total number of adjacencies which cannot be 
            used to switch traffic in their current state.";
          smiv2:max-access "read-only";
          smiv2:oid "1.3.6.1.4.1.9.9.492.1.2.1.1.1.3";
        }

        leaf cefAdjSummaryFixup {
          type uint32;
          description
           "The total number of adjacencies for which
            the Layer 2 encapsulation string (header) may be 
            updated (fixed up) at packet switch time.";
          smiv2:max-access "read-only";
          smiv2:oid "1.3.6.1.4.1.9.9.492.1.2.1.1.1.4";
        }

        leaf cefAdjSummaryRedirect {
          type uint32;
          description
           "The total number of adjacencies for which 
            ip redirect (or icmp redirection) is enabled.
            The value of this object is only relevant for
            ipv4 and ipv6 link type (when the index object 
            cefAdjSummaryLinkType value is ipv4(1) or ipv6(2))
            and will be set to zero for other link types.";
          reference
           "1. Internet Architecture Extensions for Shared Media,
            RFC 1620, May 1994.";
          smiv2:max-access "read-only";
          smiv2:oid "1.3.6.1.4.1.9.9.492.1.2.1.1.1.5";
        }
      }
    }

    container cefAdjTable {
      description
       "A list of CEF adjacencies.";
      smiv2:oid "1.3.6.1.4.1.9.9.492.1.2.2";

      list cefAdjEntry {
        key "entPhysicalIndex ifIndex cefAdjNextHopAddrType cefAdjNextHopAddr cefAdjConnId cefAdjSummaryLinkType";
        description
         "If CEF is enabled on the Managed device,
          each entry contains the adjacency 
          attributes. Adjacency entries may exist
          for all the interfaces on which packets
          can be switched out of the device.
          The interface is instantiated by ifIndex.  
          Therefore, the interface index must have been
          assigned, according to the applicable procedures,
          before it can be meaningfully used.
          Generally, this means that the interface must exist.
          
          entPhysicalIndex is also an index for this
          table which represents entities of
          'module' entPhysicalClass which are capable
          of running CEF.";
        smiv2:oid "1.3.6.1.4.1.9.9.492.1.2.2.1";

        leaf entPhysicalIndex {
          type leafref {
            path "/entity-mib:ENTITY-MIB/entity-mib:entPhysicalTable/entity-mib:entPhysicalEntry/entity-mib:entPhysicalIndex";
          }
        }

        leaf ifIndex {
          type leafref {
            path "/if-mib:IF-MIB/if-mib:ifTable/if-mib:ifEntry/if-mib:ifIndex";
          }
        }

        leaf cefAdjSummaryLinkType {
          type leafref {
            path "/CISCO-CEF-MIB:CISCO-CEF-MIB/CISCO-CEF-MIB:cefAdjSummaryTable/CISCO-CEF-MIB:cefAdjSummaryEntry/CISCO-CEF-MIB:cefAdjSummaryLinkType";
          }
        }

        leaf cefAdjNextHopAddrType {
          type inet-address:InetAddressType;
          description
           "Address type for the cefAdjNextHopAddr.
            This object specifies the address type
            used for cefAdjNextHopAddr. 
            
            Adjacency entries are only valid for the 
            address type of ipv4(1) and ipv6(2).";
          smiv2:max-access "not-accessible";
          smiv2:oid "1.3.6.1.4.1.9.9.492.1.2.2.1.1";
        }

        leaf cefAdjNextHopAddr {
          type inet-address:InetAddress;
          description
           "The next Hop address for this adjacency.
            The type of this address is determined by
            the value of the cefAdjNextHopAddrType object.";
          smiv2:max-access "not-accessible";
          smiv2:oid "1.3.6.1.4.1.9.9.492.1.2.2.1.2";
        }

        leaf cefAdjConnId {
          type uint32 {
            range "0..4294967295";
          }
          description
           "In cases where cefLinkType, interface and the
            next hop address are not able to uniquely define
            an adjacency entry (e.g. ATM and Frame Relay
            Bundles), this object is a unique identifier
            to differentiate between these adjacency entries. 
            
            In all the other cases the value of this 
            index object will be 0.";
          smiv2:max-access "not-accessible";
          smiv2:oid "1.3.6.1.4.1.9.9.492.1.2.2.1.3";
        }

        leaf cefAdjSource {
          type cisco-cef:CefAdjacencySource;
          description
           "If the adjacency is created because some neighbour
            discovery mechanism has discovered a neighbour
            and all the information required to build a frame header to
            encapsulate traffic to the neighbour is available
            then the source of adjacency is set to the mechanism
            by which the adjacency is learned.";
          smiv2:max-access "read-only";
          smiv2:oid "1.3.6.1.4.1.9.9.492.1.2.2.1.4";
        }

        leaf cefAdjEncap {
          type snmp-framework:SnmpAdminString;
          description
           "The layer 2 encapsulation string to be used
            for sending the packet out using this adjacency.";
          smiv2:max-access "read-only";
          smiv2:oid "1.3.6.1.4.1.9.9.492.1.2.2.1.5";
        }

        leaf cefAdjFixup {
          type snmp-framework:SnmpAdminString;
          description
           "For the cases, where the encapsulation string
            is decided at packet switch time, the adjacency 
            encapsulation string specified by object cefAdjEncap 
            require a fixup. I.e. for the adjacencies out of IP 
            Tunnels, the string prepended is an IP header which has 
            fields which can only be setup at packet switch time.
            
            The value of this object represent the kind of fixup
            applied to the packet.
            
            If the encapsulation string doesn't require any fixup,
            then the value of this object will be of zero length.";
          smiv2:max-access "read-only";
          smiv2:oid "1.3.6.1.4.1.9.9.492.1.2.2.1.6";
        }

        leaf cefAdjMTU {
          type uint32 {
            range "0..65535";
          }
          units "bytes";
          description
           "The Layer 3 MTU which can be transmitted using 
            this adjacency.";
          smiv2:max-access "read-only";
          smiv2:oid "1.3.6.1.4.1.9.9.492.1.2.2.1.7";
        }

        leaf cefAdjForwardingInfo {
          type snmp-framework:SnmpAdminString;
          description
           "This object selects a forwarding info entry 
            defined in the cefFESelectionTable. The 
            selected target is defined by an entry in the
            cefFESelectionTable whose index value (cefFESelectionName) 
            is equal to this object.
            
            The value of this object will be of zero length if
            this adjacency entry is the last forwarding 
            element in the forwarding path.";
          smiv2:max-access "read-only";
          smiv2:oid "1.3.6.1.4.1.9.9.492.1.2.2.1.8";
        }

        leaf cefAdjPkts {
          type yang:counter32;
          units "packets";
          description
           "Number of pkts transmitted using this adjacency.";
          smiv2:max-access "read-only";
          smiv2:oid "1.3.6.1.4.1.9.9.492.1.2.2.1.9";
        }

        leaf cefAdjHCPkts {
          type yang:counter64;
          units "packets";
          description
           "Number of pkts transmitted using this adjacency.
            This object is a 64-bit version of cefAdjPkts.";
          smiv2:max-access "read-only";
          smiv2:oid "1.3.6.1.4.1.9.9.492.1.2.2.1.10";
        }

        leaf cefAdjBytes {
          type yang:counter32;
          units "bytes";
          description
           "Number of bytes transmitted using this adjacency.";
          smiv2:max-access "read-only";
          smiv2:oid "1.3.6.1.4.1.9.9.492.1.2.2.1.11";
        }

        leaf cefAdjHCBytes {
          type yang:counter64;
          units "bytes";
          description
           "Number of bytes transmitted using this adjacency.
            This object is a 64-bit version of cefAdjBytes.";
          smiv2:max-access "read-only";
          smiv2:oid "1.3.6.1.4.1.9.9.492.1.2.2.1.12";
        }
      }
    }

    container cefFESelectionTable {
      description
       "A list of forwarding element selection entries.";
      smiv2:oid "1.3.6.1.4.1.9.9.492.1.3.1";

      list cefFESelectionEntry {
        key "entPhysicalIndex cefFESelectionName cefFESelectionId";
        description
         "If CEF is enabled on the Managed device,
          each entry contain a CEF forwarding element
          selection list.
          
          entPhysicalIndex is also an index for this
          table which represents entities of
          'module' entPhysicalClass which are capable
          of running CEF.";
        smiv2:oid "1.3.6.1.4.1.9.9.492.1.3.1.1";

        leaf entPhysicalIndex {
          type leafref {
            path "/entity-mib:ENTITY-MIB/entity-mib:entPhysicalTable/entity-mib:entPhysicalEntry/entity-mib:entPhysicalIndex";
          }
        }

        leaf cefFESelectionName {
          type snmp-framework:SnmpAdminString {
            length "1..32";
          }
          description
           "The locally arbitrary, but unique identifier used
            to select a set of forwarding element lists.";
          smiv2:max-access "not-accessible";
          smiv2:oid "1.3.6.1.4.1.9.9.492.1.3.1.1.1";
        }

        leaf cefFESelectionId {
          type int32 {
            range "1..2147483647";
          }
          description
           "Secondary index to identify a forwarding elements List 
            in this Table.";
          smiv2:max-access "not-accessible";
          smiv2:oid "1.3.6.1.4.1.9.9.492.1.3.1.1.2";
        }

        leaf cefFESelectionSpecial {
          type cisco-cef:CefForwardingElementSpecialType;
          description
           "Special processing for a destination
            is indicated through the use of special 
            forwarding element. 
            
            If the forwarding element list contains the 
            special forwarding element, then this object 
            represents the type of special forwarding element.";
          smiv2:max-access "read-only";
          smiv2:oid "1.3.6.1.4.1.9.9.492.1.3.1.1.3";
        }

        leaf cefFESelectionLabels {
          type cisco-cef:CefMplsLabelList;
          description
           "This object represent the MPLS Labels 
            associated with this forwarding Element List.
            
            The value of this object will be irrelevant and will
            be set to zero length if the forwarding element list 
            doesn't contain a label forwarding element. A zero 
            length label list will indicate that there is no label
            forwarding element associated with this selection entry.";
          smiv2:max-access "read-only";
          smiv2:oid "1.3.6.1.4.1.9.9.492.1.3.1.1.4";
        }

        leaf cefFESelectionAdjLinkType {
          type cisco-cef:CefAdjLinkType;
          description
           "This object represent the link type for
            the adjacency associated with this forwarding 
            Element List.
            
            The value of this object will be irrelevant and will
            be set to unknown(5) if the forwarding element list 
            doesn't contain an adjacency forwarding element.";
          smiv2:max-access "read-only";
          smiv2:oid "1.3.6.1.4.1.9.9.492.1.3.1.1.5";
        }

        leaf cefFESelectionAdjInterface {
          type if-mib:InterfaceIndexOrZero;
          description
           "This object represent the interface for
            the adjacency associated with this forwarding 
            Element List.
            
            The value of this object will be irrelevant and will
            be set to zero if the forwarding element list doesn't 
            contain an adjacency forwarding element.";
          smiv2:max-access "read-only";
          smiv2:oid "1.3.6.1.4.1.9.9.492.1.3.1.1.6";
        }

        leaf cefFESelectionAdjNextHopAddrType {
          type inet-address:InetAddressType;
          description
           "This object represent the next hop address type for
            the adjacency associated with this forwarding 
            Element List.
            
            The value of this object will be irrelevant and will
            be set to unknown(0) if the forwarding element list 
            doesn't contain an adjacency forwarding element.";
          smiv2:max-access "read-only";
          smiv2:oid "1.3.6.1.4.1.9.9.492.1.3.1.1.7";
        }

        leaf cefFESelectionAdjNextHopAddr {
          type inet-address:InetAddress;
          description
           "This object represent the next hop address for
            the adjacency associated with this forwarding 
            Element List.
            
            The value of this object will be irrelevant and will
            be set to zero if the forwarding element list doesn't 
            contain an adjacency forwarding element.";
          smiv2:max-access "read-only";
          smiv2:oid "1.3.6.1.4.1.9.9.492.1.3.1.1.8";
        }

        leaf cefFESelectionAdjConnId {
          type uint32 {
            range "0..4294967295";
          }
          description
           "This object represent the connection id for
            the adjacency associated with this forwarding 
            Element List.
            
            The value of this object will be irrelevant and will
            be set to zero if the forwarding element list doesn't 
            contain an adjacency forwarding element. 
            
            In cases where cefFESelectionAdjLinkType, interface 
            and the next hop address are not able to uniquely 
            define an adjacency entry (e.g. ATM and Frame Relay
            Bundles), this object is a unique identifier
            to differentiate between these adjacency entries.";
          smiv2:max-access "read-only";
          smiv2:oid "1.3.6.1.4.1.9.9.492.1.3.1.1.9";
        }

        leaf cefFESelectionVrfName {
          type mpls-vpn:MplsVpnId;
          description
           "This object represent the Vrf name for
            the lookup associated with this forwarding 
            Element List.
            
            The value of this object will be irrelevant and will
            be set to a string containing the single octet
            0x00 if the forwarding element list 
            doesn't contain a lookup forwarding element.";
          smiv2:max-access "read-only";
          smiv2:oid "1.3.6.1.4.1.9.9.492.1.3.1.1.10";
        }

        leaf cefFESelectionWeight {
          type uint32 {
            range "0..4294967295";
          }
          description
           "This object represent the weighting for 
            load balancing between multiple Forwarding Element
            Lists. The value of this object will be zero if
            load balancing is associated with this selection
            entry.";
          smiv2:max-access "read-only";
          smiv2:oid "1.3.6.1.4.1.9.9.492.1.3.1.1.11";
        }
      }
    }

    container cefCfgTable {
      description
       "This table contains global config parameter 
        of CEF on the Managed device.";
      smiv2:oid "1.3.6.1.4.1.9.9.492.1.4.1";

      list cefCfgEntry {
        key "entPhysicalIndex cefFIBIpVersion";
        description
         "If the Managed device supports CEF, 
          each entry contains the CEF config 
          parameter for the managed entity.
          A row may exist for each IP version type
          (v4 and v6) depending upon the IP version
          supported on the device.
          
          entPhysicalIndex is also an index for this
          table which represents entities of
          'module' entPhysicalClass which are capable
          of running CEF.";
        smiv2:oid "1.3.6.1.4.1.9.9.492.1.4.1.1";

        leaf entPhysicalIndex {
          type leafref {
            path "/entity-mib:ENTITY-MIB/entity-mib:entPhysicalTable/entity-mib:entPhysicalEntry/entity-mib:entPhysicalIndex";
          }
        }

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefCfgAdminState {
          type cisco-cef:CefAdminStatus;
          description
           "The desired state of CEF.";
          smiv2:max-access "read-write";
          smiv2:oid "1.3.6.1.4.1.9.9.492.1.4.1.1.1";
        }

        leaf cefCfgOperState {
          type cisco-cef:CefOperStatus;
          description
           "The current operational state of CEF.
            
            If the cefCfgAdminState is disabled(2), then
            cefOperState will eventually go to the down(2)
            state unless some error has occurred. 
            
            If cefCfgAdminState is changed to enabled(1) then 
            cefCfgOperState should change to up(1) only if the 
            CEF entity is ready to forward the packets using 
            Cisco Express Forwarding (CEF) else it should remain 
            in the down(2) state. The up(1) state for this object 
            indicates that CEF entity is forwarding the packet
            using Cisco Express Forwarding.";
          smiv2:max-access "read-only";
          smiv2:oid "1.3.6.1.4.1.9.9.492.1.4.1.1.2";
        }

        leaf cefCfgDistributionAdminState {
          type cisco-cef:CefAdminStatus;
          description
           "The desired state of CEF distribution.";
          smiv2:max-access "read-write";
          smiv2:oid "1.3.6.1.4.1.9.9.492.1.4.1.1.3";
        }

        leaf cefCfgDistributionOperState {
          type cisco-cef:CefOperStatus;
          description
           "The current operational state of CEF distribution.
            
            If the cefCfgDistributionAdminState is disabled(2), then
            cefDistributionOperState will eventually go to the down(2)
            state unless some error has occurred.  
            
            If cefCfgDistributionAdminState is changed to enabled(1) 
            then cefCfgDistributionOperState should change to up(1) 
            only if the CEF entity is ready to forward the packets 
            using Distributed Cisco Express Forwarding (dCEF) else 
            it should remain in the down(2) state. The up(1) state 
            for this object indicates that CEF entity is forwarding
            the packet using Distributed Cisco Express Forwarding.";
          smiv2:max-access "read-only";
          smiv2:oid "1.3.6.1.4.1.9.9.492.1.4.1.1.4";
        }

        leaf cefCfgAccountingMap {
          type bits {
            bit nonRecursive {
              position "0";
            }
            bit perPrefix {
              position "1";
            }
            bit prefixLength {
              position "2";
            }
          }
          description
           "This object represents a bitmap of network
            accounting options.
            
            CEF network accounting is disabled by default.
            
            CEF network accounting can be enabled 
            by selecting one or more of the following
            CEF accounting option for the value
            of this object.
             
             nonRecursive(0):  enables accounting through 
                               nonrecursive prefixes.
            
             perPrefix(1):     enables the collection of the numbers 
                               of pkts and bytes express forwarded
                               to a destination (prefix)
            
             prefixLength(2):  enables accounting through 
                               prefixlength.        
            
             Once the accounting is enabled, the corresponding stats
             can be retrieved from the cefPrefixTable and
             cefStatsPrefixLenTable.
             ";
          smiv2:max-access "read-write";
          smiv2:oid "1.3.6.1.4.1.9.9.492.1.4.1.1.5";
        }

        leaf cefCfgLoadSharingAlgorithm {
          type enumeration {
            enum "none" {
              value "1";
            }
            enum "original" {
              value "2";
            }
            enum "tunnel" {
              value "3";
            }
            enum "universal" {
              value "4";
            }
          }
          description
           "Indicates the CEF Load balancing algorithm.
            
            Setting this object to none(1) will disable
            the Load sharing for the specified entry.
            
            CEF load balancing can be enabled by setting 
            this object to one of following Algorithms:
            
             original(2)  : This algorithm is based on a 
                            source and destination hash 
            
             tunnel(3)    : This algorithm is used in 
                            tunnels environments or in
                            environments where there are
                            only a few source 
                              
             universal(4)  : This algorithm uses a source and 
                             destination and ID hash
            
            If the value of this object is set to 'tunnel'
            or 'universal', then the FIXED ID for these
            algorithms may be specified by the managed 
            object cefLoadSharingID. ";
          smiv2:max-access "read-write";
          smiv2:oid "1.3.6.1.4.1.9.9.492.1.4.1.1.6";
        }

        leaf cefCfgLoadSharingID {
          type uint32 {
            range "0..4294967295";
          }
          description
           "The Fixed ID associated with the managed object
            cefCfgLoadSharingAlgorithm. The hash of this object
            value may be used by the Load Sharing Algorithm.
            
            The value of this object is not relevant and will
            be set to zero if the value of managed object 
            cefCfgLoadSharingAlgorithm is set to none(1) or original(2).
            The default value of this object is calculated by
            the device at the time of initialization.";
          smiv2:max-access "read-write";
          smiv2:oid "1.3.6.1.4.1.9.9.492.1.4.1.1.7";
        }

        leaf cefCfgTrafficStatsLoadInterval {
          type uint32;
          units "seconds";
          description
           "The interval time over which the CEF traffic statistics
            are collected.";
          smiv2:max-access "read-write";
          smiv2:oid "1.3.6.1.4.1.9.9.492.1.4.1.1.8";
        }

        leaf cefCfgTrafficStatsUpdateRate {
          type uint32 {
            range "0..65535";
          }
          units "seconds";
          description
           "The frequency with which the line card sends the
            traffic load statistics to the Router Processor.
            
            Setting the value of this object to 0 will disable
            the CEF traffic statistics collection.";
          smiv2:max-access "read-write";
          smiv2:oid "1.3.6.1.4.1.9.9.492.1.4.1.1.9";
        }
      }
    }

    container cefResourceTable {
      description
       "This table contains global resource 
        information of CEF on the Managed device.";
      smiv2:oid "1.3.6.1.4.1.9.9.492.1.4.2";

      list cefResourceEntry {
        key "entPhysicalIndex";
        description
         "If the Managed device supports CEF,
          each entry contains the CEF Resource 
          parameters for the managed entity.
          
          entPhysicalIndex is also an index for this
          table which represents entities of
          'module' entPhysicalClass which are capable
          of running CEF.";
        smiv2:oid "1.3.6.1.4.1.9.9.492.1.4.2.1";

        leaf entPhysicalIndex {
          type leafref {
            path "/entity-mib:ENTITY-MIB/entity-mib:entPhysicalTable/entity-mib:entPhysicalEntry/entity-mib:entPhysicalIndex";
          }
        }

        leaf cefResourceMemoryUsed {
          type yang:gauge32;
          units "bytes";
          description
           "Indicates the number of bytes from
            the Processor Memory Pool that
            are currently in use by CEF on the
            managed entity.";
          smiv2:max-access "read-only";
          smiv2:oid "1.3.6.1.4.1.9.9.492.1.4.2.1.1";
        }

        leaf cefResourceFailureReason {
          type cisco-cef:CefFailureReason;
          description
           "The CEF resource failure reason which may lead to CEF
            being disabled on the managed entity.";
          smiv2:max-access "read-only";
          smiv2:oid "1.3.6.1.4.1.9.9.492.1.4.2.1.2";
        }
      }
    }

    container cefIntTable {
      description
       "This Table contains interface specific
        information of CEF on the Managed
        device.";
      smiv2:oid "1.3.6.1.4.1.9.9.492.1.5.1";

      list cefIntEntry {
        key "entPhysicalIndex cefFIBIpVersion ifIndex";
        description
         "If CEF is enabled on the Managed device, 
          each entry contains the CEF attributes 
          associated with an interface.
          The interface is instantiated by ifIndex.  
          Therefore, the interface index must have been
          assigned, according to the applicable procedures,
          before it can be meaningfully used.
          Generally, this means that the interface must exist.
          
          A row may exist for each IP version type
          (v4 and v6) depending upon the IP version
          supported on the device.
          
          entPhysicalIndex is also an index for this
          table which represents entities of
          'module' entPhysicalClass which are capable
          of running CEF.";
        smiv2:oid "1.3.6.1.4.1.9.9.492.1.5.1.1";

        leaf entPhysicalIndex {
          type leafref {
            path "/entity-mib:ENTITY-MIB/entity-mib:entPhysicalTable/entity-mib:entPhysicalEntry/entity-mib:entPhysicalIndex";
          }
        }

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf ifIndex {
          type leafref {
            path "/if-mib:IF-MIB/if-mib:ifTable/if-mib:ifEntry/if-mib:ifIndex";
          }
        }

        leaf cefIntSwitchingState {
          type enumeration {
            enum "cefEnabled" {
              value "1";
            }
            enum "distCefEnabled" {
              value "2";
            }
            enum "cefDisabled" {
              value "3";
            }
          }
          description
           "The CEF switching State for the interface. 
            If CEF is enabled but distributed CEF(dCEF) is
            disabled then CEF is in cefEnabled(1) state.
            
            If distributed CEF is enabled, then CEF is in 
            distCefEnabled(2) state. The cefDisabled(3) state
            indicates that CEF is disabled.
            
            The CEF switching state is only applicable to the
            received packet on the interface.";
          smiv2:max-access "read-write";
          smiv2:oid "1.3.6.1.4.1.9.9.492.1.5.1.1.1";
        }

        leaf cefIntLoadSharing {
          type enumeration {
            enum "perPacket" {
              value "1";
            }
            enum "perDestination" {
              value "2";
            }
          }
          description
           "The status of load sharing on the
            interface.
            
            perPacket(1) : Router to send data packets
                           over successive equal-cost paths
                           without regard to individual hosts
                           or user sessions.
            
            perDestination(2) : Router to use multiple, equal-cost
                                paths to achieve load sharing
            
            Load sharing is enabled by default 
            for an interface when CEF is enabled.";
          smiv2:max-access "read-write";
          smiv2:oid "1.3.6.1.4.1.9.9.492.1.5.1.1.2";
        }

        leaf cefIntNonrecursiveAccouting {
          type enumeration {
            enum "internal" {
              value "1";
            }
            enum "external" {
              value "2";
            }
          }
          description
           "The CEF accounting mode for the interface.
            CEF prefix based non-recursive accounting 
            on an interface can be configured to store 
            the stats for non-recursive prefixes in a internal 
            or external bucket.
            
            internal(1)  :  Count input traffic in the nonrecursive
                            internal bucket
            
            external(2)  :  Count input traffic in the nonrecursive
                            external bucket
            
            The value of this object will only be effective if 
            value of the object cefAccountingMap is set to enable
            nonRecursive(1) accounting.";
          smiv2:max-access "read-write";
          smiv2:oid "1.3.6.1.4.1.9.9.492.1.5.1.1.3";
        }
      }
    }

    container cefPeerTable {
      description
       "Entity acting as RP (Routing Processor) keeps
        the CEF states for the line card entities and
        communicates with the line card entities using
        XDR. This Table contains the CEF information 
        related to peer entities on the managed device.";
      smiv2:oid "1.3.6.1.4.1.9.9.492.1.6.1";

      list cefPeerEntry {
        key "entPhysicalIndex entPeerPhysicalIndex";
        description
         "If CEF is enabled on the Managed device,
          each entry contains the CEF related attributes 
          associated with a CEF peer entity.
          
          entPhysicalIndex and entPeerPhysicalIndex are
          also indexes for this table which represents
          entities of 'module' entPhysicalClass which are
          capable of running CEF.";
        smiv2:oid "1.3.6.1.4.1.9.9.492.1.6.1.1";

        leaf entPhysicalIndex {
          type leafref {
            path "/entity-mib:ENTITY-MIB/entity-mib:entPhysicalTable/entity-mib:entPhysicalEntry/entity-mib:entPhysicalIndex";
          }
        }

        leaf entPeerPhysicalIndex {
          type entity-mib:PhysicalIndex;
          description
           "The entity index for the CEF peer entity.
            Only the entities of 'module' 
            entPhysicalClass are included here.";
          smiv2:max-access "not-accessible";
          smiv2:oid "1.3.6.1.4.1.9.9.492.1.6.1.1.1";
        }

        leaf cefPeerOperState {
          type enumeration {
            enum "peerDisabled" {
              value "1";
            }
            enum "peerUp" {
              value "2";
            }
            enum "peerHold" {
              value "3";
            }
          }
          description
           "The current CEF operational state of the CEF peer entity.
            
            Cef peer entity oper state will be peerDisabled(1) in 
            the following condition:
            
               : Cef Peer entity encounters fatal error i.e. resource
                 allocation failure, ipc failure etc
            
               : When a reload/delete request is received from the Cef 
                 Peer Entity
            
            Once the peer entity is up and no fatal error is encountered,
            then the value of this object will transits to the peerUp(3) 
            state.
            
            If the Cef Peer entity is in held stage, then the value
            of this object will be peerHold(3). Cef peer entity can only
            transit to peerDisabled(1) state from the peerHold(3) state.";
          smiv2:max-access "read-only";
          smiv2:oid "1.3.6.1.4.1.9.9.492.1.6.1.1.2";
        }

        leaf cefPeerNumberOfResets {
          type yang:counter32;
          description
           "Number of times the session with CEF peer entity 
            has been reset.";
          smiv2:max-access "read-only";
          smiv2:oid "1.3.6.1.4.1.9.9.492.1.6.1.1.3";
        }
      }
    }

    container cefPeerFIBTable {
      description
       "Entity acting as RP (Routing Processor) keep
        the CEF FIB states for the line card entities and
        communicate with the line card entities using
        XDR. This Table contains the CEF FIB State 
        related to peer entities on the managed device.";
      smiv2:oid "1.3.6.1.4.1.9.9.492.1.6.2";

      list cefPeerFIBEntry {
        key "entPhysicalIndex entPeerPhysicalIndex cefFIBIpVersion";
        description
         "If CEF is enabled on the Managed device,
          each entry contains the CEF FIB State 
          associated a CEF peer entity.
          
          entPhysicalIndex and entPeerPhysicalIndex are
          also indexes for this table which represents
          entities of 'module' entPhysicalClass which are
          capable of running CEF.";
        smiv2:oid "1.3.6.1.4.1.9.9.492.1.6.2.1";

        leaf entPhysicalIndex {
          type leafref {
            path "/entity-mib:ENTITY-MIB/entity-mib:entPhysicalTable/entity-mib:entPhysicalEntry/entity-mib:entPhysicalIndex";
          }
        }

        leaf entPeerPhysicalIndex {
          type leafref {
            path "/CISCO-CEF-MIB:CISCO-CEF-MIB/CISCO-CEF-MIB:cefPeerTable/CISCO-CEF-MIB:cefPeerEntry/CISCO-CEF-MIB:entPeerPhysicalIndex";
          }
        }

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefPeerFIBOperState {
          type enumeration {
            enum "peerFIBDown" {
              value "1";
            }
            enum "peerFIBUp" {
              value "2";
            }
            enum "peerFIBReloadRequest" {
              value "3";
            }
            enum "peerFIBReloading" {
              value "4";
            }
            enum "peerFIBSynced" {
              value "5";
            }
          }
          description
           "The current CEF FIB Operational State for the 
            CEF peer entity.";
          smiv2:max-access "read-only";
          smiv2:oid "1.3.6.1.4.1.9.9.492.1.6.2.1.1";
        }
      }
    }

    container cefCCGlobalTable {
      description
       "This table contains CEF consistency checker
        (CC) global parameters for the managed device.";
      smiv2:oid "1.3.6.1.4.1.9.9.492.1.7.1";

      list cefCCGlobalEntry {
        key "cefFIBIpVersion";
        description
         "If the managed device supports CEF,
          each entry contains the global consistency 
          checker parameter for the managed device.
          A row may exist for each IP version type
          (v4 and v6) depending upon the IP version
          supported on the device.";
        smiv2:oid "1.3.6.1.4.1.9.9.492.1.7.1.1";

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefCCGlobalAutoRepairEnabled {
          type boolean;
          description
           "Once an inconsistency has been detected, 
            CEF has the ability to repair the problem. 
            This object indicates the status of auto-repair 
            function for the consistency checkers.";
          smiv2:max-access "read-write";
          smiv2:oid "1.3.6.1.4.1.9.9.492.1.7.1.1.1";
        }

        leaf cefCCGlobalAutoRepairDelay {
          type uint32;
          units "seconds";
          description
           "Indiactes how long the consistency checker 
            waits to fix an inconsistency.
            
            The value of this object has no effect when the
            value of object cefCCGlobalAutoRepairEnabled
            is 'false'.";
          smiv2:max-access "read-write";
          smiv2:oid "1.3.6.1.4.1.9.9.492.1.7.1.1.2";
        }

        leaf cefCCGlobalAutoRepairHoldDown {
          type uint32;
          units "seconds";
          description
           "Indicates how long the consistency checker
            waits to re-enable auto-repair after 
            auto-repair runs.
            
            The value of this object has no effect when the
            value of object cefCCGlobalAutoRepairEnabled
            is 'false'.";
          smiv2:max-access "read-write";
          smiv2:oid "1.3.6.1.4.1.9.9.492.1.7.1.1.3";
        }

        leaf cefCCGlobalErrorMsgEnabled {
          type boolean;
          description
           "Enables the consistency checker to generate 
            an error message when it detects an inconsistency.";
          smiv2:max-access "read-write";
          smiv2:oid "1.3.6.1.4.1.9.9.492.1.7.1.1.4";
        }

        leaf cefCCGlobalFullScanAction {
          type cisco-cef:CefCCAction;
          description
           "Setting the value of this object to ccActionStart(1)
            will start the full scan consistency checkers.
            
            The Management station should poll the 
            cefCCGlobalFullScanStatus object to get the 
            state of full-scan operation.
            
            Once the full-scan operation completes (value
            of cefCCGlobalFullScanStatus object is ccStatusDone(3)), 
            the Management station should retrieve the values of the
            related stats object from the cefCCTypeTable.
            
            Setting the value of this object to ccActionAbort(2) will 
            abort the full-scan operation.
            
            The value of this object can't be set to ccActionStart(1), 
            if the value of object cefCCGlobalFullScanStatus
            is ccStatusRunning(2).
            
            The value of this object will be set to cefActionNone(1)
            when the full scan consistency checkers have never
            been activated.
            
            A Management Station cannot set the value of
            this object to cefActionNone(1).";
          smiv2:defval "ccActionNone";
          smiv2:max-access "read-write";
          smiv2:oid "1.3.6.1.4.1.9.9.492.1.7.1.1.5";
        }

        leaf cefCCGlobalFullScanStatus {
          type cisco-cef:CefCCStatus;
          description
           "Indicates the status of the full scan consistency
            checker request.";
          smiv2:max-access "read-only";
          smiv2:oid "1.3.6.1.4.1.9.9.492.1.7.1.1.6";
        }
      }
    }

    container cefCCTypeTable {
      description
       "This table contains CEF consistency
        checker types specific parameters on the managed device.
        
        All detected inconsistency are signaled to the
        Management Station via cefInconsistencyDetection
        notification.";
      smiv2:oid "1.3.6.1.4.1.9.9.492.1.7.2";

      list cefCCTypeEntry {
        key "cefFIBIpVersion cefCCType";
        description
         "If the managed device supports CEF,
          each entry contains the consistency 
          checker statistics for a consistency 
          checker type.
          A row may exist for each IP version type
          (v4 and v6) depending upon the IP version
          supported on the device.";
        smiv2:oid "1.3.6.1.4.1.9.9.492.1.7.2.1";

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefCCType {
          type cisco-cef:CefCCType;
          description
           "Type of the consistency checker.";
          smiv2:max-access "not-accessible";
          smiv2:oid "1.3.6.1.4.1.9.9.492.1.7.2.1.1";
        }

        leaf cefCCEnabled {
          type boolean;
          description
           "Enables the passive consistency checker.
            Passive consistency checkers are disabled
            by default.
            
            Full-scan consistency checkers are always enabled.
            An attempt to set this object to 'false' for
            an active consistency checker will result in
            'wrongValue' error.";
          smiv2:max-access "read-write";
          smiv2:oid "1.3.6.1.4.1.9.9.492.1.7.2.1.2";
        }

        leaf cefCCCount {
          type uint32;
          description
           "The maximum number of prefixes to check per scan.
            
            The default value for this object 
            depends upon the consistency checker type.
            
            The value of this object will be irrelevant 
            for some of the consistency checkers and
            will be set to 0.
            
            A Management Station cannot set the value of
            this object to 0.";
          smiv2:max-access "read-write";
          smiv2:oid "1.3.6.1.4.1.9.9.492.1.7.2.1.3";
        }

        leaf cefCCPeriod {
          type uint32;
          units "seconds";
          description
           "The period between scans for the consistency
            checker.";
          smiv2:max-access "read-write";
          smiv2:oid "1.3.6.1.4.1.9.9.492.1.7.2.1.4";
        }

        leaf cefCCQueriesSent {
          type yang:counter32;
          description
           "Number of prefix consistency queries sent to CEF
            forwarding databases by this consistency checker.";
          smiv2:max-access "read-only";
          smiv2:oid "1.3.6.1.4.1.9.9.492.1.7.2.1.5";
        }

        leaf cefCCQueriesIgnored {
          type yang:counter32;
          description
           "Number of prefix consistency queries for which
            the consistency checks were not performed by this 
            consistency checker. This may be because of some
            internal error or resource failure.";
          smiv2:max-access "read-only";
          smiv2:oid "1.3.6.1.4.1.9.9.492.1.7.2.1.6";
        }

        leaf cefCCQueriesChecked {
          type yang:counter32;
          description
           "Number of prefix consistency queries processed by this 
            consistency checker.";
          smiv2:max-access "read-only";
          smiv2:oid "1.3.6.1.4.1.9.9.492.1.7.2.1.7";
        }

        leaf cefCCQueriesIterated {
          type yang:counter32;
          description
           "Number of prefix consistency queries iterated back to
            the master database by this consistency checker.";
          smiv2:max-access "read-only";
          smiv2:oid "1.3.6.1.4.1.9.9.492.1.7.2.1.8";
        }
      }
    }

    container cefInconsistencyRecordTable {
      description
       "This table contains CEF inconsistency
        records.";
      smiv2:oid "1.3.6.1.4.1.9.9.492.1.7.3";

      list cefInconsistencyRecordEntry {
        key "cefFIBIpVersion cefInconsistencyRecId";
        description
         "If the managed device supports CEF,
          each entry contains the inconsistency 
          record.";
        smiv2:oid "1.3.6.1.4.1.9.9.492.1.7.3.1";

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefInconsistencyRecId {
          type int32 {
            range "1..2147483647";
          }
          description
           "The locally arbitrary, but unique identifier associated
            with this inconsistency record entry.";
          smiv2:max-access "not-accessible";
          smiv2:oid "1.3.6.1.4.1.9.9.492.1.7.3.1.1";
        }

        leaf cefInconsistencyPrefixType {
          type inet-address:InetAddressType;
          description
           "The network prefix type associated with this inconsistency
            record.";
          smiv2:max-access "read-only";
          smiv2:oid "1.3.6.1.4.1.9.9.492.1.7.3.1.2";
        }

        leaf cefInconsistencyPrefixAddr {
          type inet-address:InetAddress;
          description
           "The network prefix address associated with this 
            inconsistency record.
            
            The type of this address is determined by
            the value of the cefInconsistencyPrefixType object.";
          smiv2:max-access "read-only";
          smiv2:oid "1.3.6.1.4.1.9.9.492.1.7.3.1.3";
        }

        leaf cefInconsistencyPrefixLen {
          type inet-address:InetAddressPrefixLength;
          description
           "Length in bits of the inconsistency address prefix.";
          smiv2:max-access "read-only";
          smiv2:oid "1.3.6.1.4.1.9.9.492.1.7.3.1.4";
        }

        leaf cefInconsistencyVrfName {
          type mpls-vpn:MplsVpnId;
          description
           "Vrf name associated with this inconsistency record.";
          smiv2:max-access "read-only";
          smiv2:oid "1.3.6.1.4.1.9.9.492.1.7.3.1.5";
        }

        leaf cefInconsistencyCCType {
          type cisco-cef:CefCCType;
          description
           "The type of consistency checker who generated this
            inconsistency record.";
          smiv2:max-access "read-only";
          smiv2:oid "1.3.6.1.4.1.9.9.492.1.7.3.1.6";
        }

        leaf cefInconsistencyEntity {
          type cisco-tc:EntPhysicalIndexOrZero;
          description
           "The entity for which this inconsistency record was 
            generated. The value of this object will be 
            irrelevant and will be set to 0 when the inconsisency 
            record is applicable for all the entities.";
          smiv2:max-access "read-only";
          smiv2:oid "1.3.6.1.4.1.9.9.492.1.7.3.1.7";
        }

        leaf cefInconsistencyReason {
          type enumeration {
            enum "missing" {
              value "1";
            }
            enum "checksumErr" {
              value "2";
            }
            enum "unknown" {
              value "3";
            }
          }
          description
           "The reason for generating this inconsistency record. 
            
            missing(1):        the prefix is missing
            
            checksumErr(2):    checksum error was found
            
            unknown(3):        reason is unknown";
          smiv2:max-access "read-only";
          smiv2:oid "1.3.6.1.4.1.9.9.492.1.7.3.1.8";
        }
      }
    }

    container cefStatsPrefixLenTable {
      description
       "This table specifies the CEF stats based
        on the Prefix Length.";
      smiv2:oid "1.3.6.1.4.1.9.9.492.1.8.1";

      list cefStatsPrefixLenEntry {
        key "entPhysicalIndex cefFIBIpVersion cefStatsPrefixLen";
        description
         "If CEF is enabled on the Managed device
          and if CEF accounting is set to enable 
          prefix length based accounting (value of 
          cefCfgAccountingMap object in the 
          cefCfgEntry is set to enable 'prefixLength' 
          accounting), each entry contains the traffic 
          statistics for a prefix length.
          A row may exist for each IP version type
          (v4 and v6) depending upon the IP version
          supported on the device.
          
          entPhysicalIndex is also an index for this
          table which represents entities of
          'module' entPhysicalClass which are capable
          of running CEF.";
        smiv2:oid "1.3.6.1.4.1.9.9.492.1.8.1.1";

        leaf entPhysicalIndex {
          type leafref {
            path "/entity-mib:ENTITY-MIB/entity-mib:entPhysicalTable/entity-mib:entPhysicalEntry/entity-mib:entPhysicalIndex";
          }
        }

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefStatsPrefixLen {
          type inet-address:InetAddressPrefixLength;
          description
           "Length in bits of the Destination IP prefix.
            As 0.0.0.0/0 is a valid prefix, hence 
            0 is a valid prefix length.";
          smiv2:max-access "not-accessible";
          smiv2:oid "1.3.6.1.4.1.9.9.492.1.8.1.1.1";
        }

        leaf cefStatsPrefixQueries {
          type yang:counter32;
          description
           "Number of queries received in the FIB database 
            for the specified IP prefix length.";
          smiv2:max-access "read-only";
          smiv2:oid "1.3.6.1.4.1.9.9.492.1.8.1.1.2";
        }

        leaf cefStatsPrefixHCQueries {
          type yang:counter64;
          description
           "Number of queries received in the FIB database
            for the specified IP prefix length.
            This object is a 64-bit version of 
            cefStatsPrefixQueries.";
          smiv2:max-access "read-only";
          smiv2:oid "1.3.6.1.4.1.9.9.492.1.8.1.1.3";
        }

        leaf cefStatsPrefixInserts {
          type yang:counter32;
          description
           "Number of insert operations performed to the FIB 
            database for the specified IP prefix length.";
          smiv2:max-access "read-only";
          smiv2:oid "1.3.6.1.4.1.9.9.492.1.8.1.1.4";
        }

        leaf cefStatsPrefixHCInserts {
          type yang:counter64;
          description
           "Number of insert operations performed to the FIB 
            database for the specified IP prefix length.
            This object is a 64-bit version of 
            cefStatsPrefixInsert.";
          smiv2:max-access "read-only";
          smiv2:oid "1.3.6.1.4.1.9.9.492.1.8.1.1.5";
        }

        leaf cefStatsPrefixDeletes {
          type yang:counter32;
          description
           "Number of delete operations performed to the FIB 
            database for the specified IP prefix length.";
          smiv2:max-access "read-only";
          smiv2:oid "1.3.6.1.4.1.9.9.492.1.8.1.1.6";
        }

        leaf cefStatsPrefixHCDeletes {
          type yang:counter64;
          description
           "Number of delete operations performed to the FIB 
            database for the specified IP prefix length.
            This object is a 64-bit version of 
            cefStatsPrefixDelete.";
          smiv2:max-access "read-only";
          smiv2:oid "1.3.6.1.4.1.9.9.492.1.8.1.1.7";
        }

        leaf cefStatsPrefixElements {
          type yang:gauge32;
          description
           "Total number of elements in the FIB database for the
            specified IP prefix length.";
          smiv2:max-access "read-only";
          smiv2:oid "1.3.6.1.4.1.9.9.492.1.8.1.1.8";
        }

        leaf cefStatsPrefixHCElements {
          type yang:gauge64;
          description
           "Total number of elements in the FIB database for the
            specified IP prefix length.
            This object is a 64-bit version of 
            cefStatsPrefixElements.";
          smiv2:max-access "read-only";
          smiv2:oid "1.3.6.1.4.1.9.9.492.1.8.1.1.9";
        }
      }
    }

    container cefSwitchingStatsTable {
      description
       "This table specifies the CEF switch stats.";
      smiv2:oid "1.3.6.1.4.1.9.9.492.1.8.2";

      list cefSwitchingStatsEntry {
        key "entPhysicalIndex cefFIBIpVersion cefSwitchingIndex";
        description
         "If CEF is enabled on the Managed device,
          each entry specifies the switching stats.
          A row may exist for each IP version type
          (v4 and v6) depending upon the IP version
          supported on the device.
          
          entPhysicalIndex is also an index for this
          table which represents entities of
          'module' entPhysicalClass which are capable
          of running CEF.";
        smiv2:oid "1.3.6.1.4.1.9.9.492.1.8.2.1";

        leaf entPhysicalIndex {
          type leafref {
            path "/entity-mib:ENTITY-MIB/entity-mib:entPhysicalTable/entity-mib:entPhysicalEntry/entity-mib:entPhysicalIndex";
          }
        }

        leaf cefFIBIpVersion {
          type leafref {
            path "/CISCO-CEF-MIB:CISCO-CEF-MIB/CISCO-CEF-MIB:cefFIBSummaryTable/CISCO-CEF-MIB:cefFIBSummaryEntry/CISCO-CEF-MIB:cefFIBIpVersion";
          }
        }

        leaf cefSwitchingIndex {
          type int32 {
            range "1..2147483647";
          }
          description
           "The locally arbitrary, but unique identifier associated
            with this switching stats entry.";
          smiv2:max-access "not-accessible";
          smiv2:oid "1.3.6.1.4.1.9.9.492.1.8.2.1.1";
        }

        leaf cefSwitchingPath {
          type snmp-framework:SnmpAdminString {
            length "1..32";
          }
          description
           "Switch path where the feature was executed.
            Available switch paths are platform-dependent.
            Following are the examples of switching paths:
            
               RIB : switching with CEF assistance
            
               Low-end switching (LES) : CEF switch path
            
               PAS : CEF turbo switch path.";
          smiv2:max-access "read-only";
          smiv2:oid "1.3.6.1.4.1.9.9.492.1.8.2.1.2";
        }

        leaf cefSwitchingDrop {
          type yang:counter32;
          units "packets";
          description
           "Number of packets dropped by CEF.";
          smiv2:max-access "read-only";
          smiv2:oid "1.3.6.1.4.1.9.9.492.1.8.2.1.3";
        }

        leaf cefSwitchingHCDrop {
          type yang:counter64;
          units "packets";
          description
           "Number of packets dropped by CEF.
            This object is a 64-bit version of cefSwitchingDrop.";
          smiv2:max-access "read-only";
          smiv2:oid "1.3.6.1.4.1.9.9.492.1.8.2.1.4";
        }

        leaf cefSwitchingPunt {
          type yang:counter32;
          units "packets";
          description
           "Number of packets that could not be switched
            in the normal path and were punted to the
            next-fastest switching vector.";
          smiv2:max-access "read-only";
          smiv2:oid "1.3.6.1.4.1.9.9.492.1.8.2.1.5";
        }

        leaf cefSwitchingHCPunt {
          type yang:counter64;
          units "packets";
          description
           "Number of packets that could not be switched
            in the normal path and were punted to the
            next-fastest switching vector.
            This object is a 64-bit version of cefSwitchingPunt.";
          smiv2:max-access "read-only";
          smiv2:oid "1.3.6.1.4.1.9.9.492.1.8.2.1.6";
        }

        leaf cefSwitchingPunt2Host {
          type yang:counter32;
          units "packets";
          description
           "Number of packets that could not be switched
            in the normal path and were punted to the host
            (process switching path).
            
            For most of the switching paths, the value of
            this object may be similar to cefSwitchingPunt.";
          smiv2:max-access "read-only";
          smiv2:oid "1.3.6.1.4.1.9.9.492.1.8.2.1.7";
        }

        leaf cefSwitchingHCPunt2Host {
          type yang:counter64;
          units "packets";
          description
           "Number of packets that could not be switched
            in the normal path and were punted to the host
            (process switching path).
            
            For most of the switching paths, the value of
            this object may be similar to cefSwitchingPunt.
            This object is a 64-bit version of cefSwitchingPunt2Host.";
          smiv2:max-access "read-only";
          smiv2:oid "1.3.6.1.4.1.9.9.492.1.8.2.1.8";
        }
      }
    }
  }

  notification cefResourceFailure {
    description
     "A cefResourceFailure notification is generated when 
      CEF resource failure on the managed entity is 
      detected. The reason for this failure is indicated 
      by cefResourcefFailureReason.";
    smiv2:oid "1.3.6.1.4.1.9.9.492.0.1";

    container object-1 {

      leaf entPhysicalIndex {
        type leafref {
          path "/entity-mib:ENTITY-MIB/entity-mib:entPhysicalTable/entity-mib:entPhysicalEntry/entity-mib:entPhysicalIndex";
        }
      }

      leaf cefResourceFailureReason {
        type leafref {
          path "/CISCO-CEF-MIB:CISCO-CEF-MIB/CISCO-CEF-MIB:cefResourceTable/CISCO-CEF-MIB:cefResourceEntry/CISCO-CEF-MIB:cefResourceFailureReason";
        }
      }
    }
  }

  notification cefPeerStateChange {
    description
     "A cefPeerStateChange notification is generated if
      change in cefPeerOperState is detected for the
      peer entity.";
    smiv2:oid "1.3.6.1.4.1.9.9.492.0.2";

    container object-1 {

      leaf entPhysicalIndex {
        type leafref {
          path "/entity-mib:ENTITY-MIB/entity-mib:entPhysicalTable/entity-mib:entPhysicalEntry/entity-mib:entPhysicalIndex";
        }
      }

      leaf entPeerPhysicalIndex {
        type leafref {
          path "/CISCO-CEF-MIB:CISCO-CEF-MIB/CISCO-CEF-MIB:cefPeerTable/CISCO-CEF-MIB:cefPeerEntry/CISCO-CEF-MIB:entPeerPhysicalIndex";
        }
      }

      leaf cefPeerOperState {
        type leafref {
          path "/CISCO-CEF-MIB:CISCO-CEF-MIB/CISCO-CEF-MIB:cefPeerTable/CISCO-CEF-MIB:cefPeerEntry/CISCO-CEF-MIB:cefPeerOperState";
        }
      }
    }
  }

  notification cefPeerFIBStateChange {
    description
     "A cefPeerFIBStateChange notification is generated if
      change in cefPeerFIBOperState is detected for the
      peer entity.";
    smiv2:oid "1.3.6.1.4.1.9.9.492.0.3";

    container object-1 {

      leaf entPhysicalIndex {
        type leafref {
          path "/entity-mib:ENTITY-MIB/entity-mib:entPhysicalTable/entity-mib:entPhysicalEntry/entity-mib:entPhysicalIndex";
        }
      }

      leaf entPeerPhysicalIndex {
        type leafref {
          path "/CISCO-CEF-MIB:CISCO-CEF-MIB/CISCO-CEF-MIB:cefPeerTable/CISCO-CEF-MIB:cefPeerEntry/CISCO-CEF-MIB:entPeerPhysicalIndex";
        }
      }

      leaf cefFIBIpVersion {
        type leafref {
          path "/CISCO-CEF-MIB:CISCO-CEF-MIB/CISCO-CEF-MIB:cefFIBSummaryTable/CISCO-CEF-MIB:cefFIBSummaryEntry/CISCO-CEF-MIB:cefFIBIpVersion";
        }
      }

      leaf cefPeerFIBOperState {
        type leafref {
          path "/CISCO-CEF-MIB:CISCO-CEF-MIB/CISCO-CEF-MIB:cefPeerFIBTable/CISCO-CEF-MIB:cefPeerFIBEntry/CISCO-CEF-MIB:cefPeerFIBOperState";
        }
      }
    }
  }

  notification cefInconsistencyDetection {
    description
     "A cefInconsistencyDetection notification is generated
      when CEF consistency checkers detects an inconsistent 
      prefix in one of the CEF forwarding databases.
      
      Note that the generation of cefInconsistencyDetection
      notifications is throttled by the agent, as specified
      by the 'cefNotifThrottlingInterval' object.";
    smiv2:oid "1.3.6.1.4.1.9.9.492.0.4";

    container object-1 {

      leaf entLastInconsistencyDetectTime {
        type leafref {
          path "/CISCO-CEF-MIB:CISCO-CEF-MIB/CISCO-CEF-MIB:cefCC/CISCO-CEF-MIB:entLastInconsistencyDetectTime";
        }
      }
    }
  }

  smiv2:alias "ciscoCefMIB" {
    smiv2:oid "1.3.6.1.4.1.9.9.492";
  }

  smiv2:alias "ciscoCefMIBNotifs" {
    smiv2:oid "1.3.6.1.4.1.9.9.492.0";
  }

  smiv2:alias "ciscoCefMIBObjects" {
    smiv2:oid "1.3.6.1.4.1.9.9.492.1";
  }

  smiv2:alias "cefFIB" {
    smiv2:oid "1.3.6.1.4.1.9.9.492.1.1";
  }

  smiv2:alias "cefFIBSummary" {
    smiv2:oid "1.3.6.1.4.1.9.9.492.1.1.1";
  }

  smiv2:alias "cefAdj" {
    smiv2:oid "1.3.6.1.4.1.9.9.492.1.2";
  }

  smiv2:alias "cefAdjSummary" {
    smiv2:oid "1.3.6.1.4.1.9.9.492.1.2.1";
  }

  smiv2:alias "cefFE" {
    smiv2:oid "1.3.6.1.4.1.9.9.492.1.3";
  }

  smiv2:alias "cefGlobal" {
    smiv2:oid "1.3.6.1.4.1.9.9.492.1.4";
  }

  smiv2:alias "cefInterface" {
    smiv2:oid "1.3.6.1.4.1.9.9.492.1.5";
  }

  smiv2:alias "cefPeer" {
    smiv2:oid "1.3.6.1.4.1.9.9.492.1.6";
  }

  smiv2:alias "cefCC" {
    smiv2:oid "1.3.6.1.4.1.9.9.492.1.7";
  }

  smiv2:alias "cefStats" {
    smiv2:oid "1.3.6.1.4.1.9.9.492.1.8";
  }

  smiv2:alias "cefNotifCntl" {
    smiv2:oid "1.3.6.1.4.1.9.9.492.1.9";
  }

  smiv2:alias "ciscoCefMIBConform" {
    smiv2:oid "1.3.6.1.4.1.9.9.492.2";
  }

  smiv2:alias "cefMIBGroups" {
    smiv2:oid "1.3.6.1.4.1.9.9.492.2.1";
  }

  smiv2:alias "cefMIBCompliances" {
    smiv2:oid "1.3.6.1.4.1.9.9.492.2.2";
  }

}
