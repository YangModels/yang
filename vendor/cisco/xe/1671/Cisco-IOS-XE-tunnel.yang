module Cisco-IOS-XE-tunnel {
  namespace "http://cisco.com/ns/yang/Cisco-IOS-XE-tunnel";
  prefix ios-tun;

  import ietf-inet-types {
    prefix inet;
  }


  import Cisco-IOS-XE-native {
    prefix ios;
  }

  import Cisco-IOS-XE-types {
    prefix ios-types;
  }

  import Cisco-IOS-XE-mpls {
    prefix ios-mpls;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Tunnel Interfaces Yang model.
     Copyright (c) 2016-2017 by Cisco Systems, Inc.
     All rights reserved.";

  // =========================================================================
  // REVISION
  // =========================================================================
  revision 2017-08-28 {
    description
      "Extend modeling for multicast";
  }
  revision 2017-07-11 {
    description 
      "add tailf dependency extension to order tunnel mode before tunnel key";
  }
  revision 2017-04-28 {
    description
      "inet:ipv6-prefix changed to ios-types:ipv6-prefix";
  }
  revision 2017-02-23 {
    description
      "This revision adds support for MPLS-TE tunnel interface mode";
  }

  revision 2017-02-07 {
    description
      "Initial revision";
  }


  grouping config-interface-tunnel-grouping {
    container nhrp {
      description
        "NHRP Interface commands";
      container event-publisher {
        description
          "Enable NHRP smart spoke feature";
        leaf max-event-timeout {
          description
            "Number of seconds";
          type uint8 {
            range "1..22";
          }
        }
      }
      leaf group {
        description
          "group name string";
        type string;
      }
      container map {
        description
          "Map group name to QoS service policy";
        container group {
          description
            "NHRP group mapping";
          list nhrp-name {
            key "nhrp-name";
            leaf nhrp-name {
              description
                "NHRP group name";
              type string;
            }
            container service-policy {
              description
                "QoS service-policy";
              leaf output {
                description
                  "QoS policy-map name";
                type string;
              }
            }
          }
        }
      }
      leaf route-watch {
        description
          "Enable NHRP route watch";
        type boolean;
      }
    }

    container tunnel {
      description
        "protocol-over-protocol tunneling";
      // interface * / tunnel 6rd
      container tun-6rd {
        description
          "set tunnel 6rd parameters";
        leaf br {
          description
            "Border Relay parameters";
          type inet:ipv4-address;
        }
        container ipv4 {
          description
            "Common IPv4 transport source parameters";
          leaf prefix-len {
            description
              "Common IPv4 transport source prefix length";
            type uint8;
          }
          leaf suffix-len {
            description
              "Common IPv4 transport source suffix length";
            type uint8;
          }
        }
        leaf prefix {
          description
            "Provider selected common IPv6 prefix";
          type ios-types:ipv6-prefix;
        }
        leaf reverse-map-check {
          description
            "Enable source IP address and port verification";
          type empty;
        }
      }

      // interface * / tunnel bandwidth
      container bandwidth {
        description
          "Set tunnel bandwidth informational parameter";
        leaf receive {
          description
            "Receive bandwidth";
          type uint32;
        }
        leaf transmit {
          description
            "Transmit bandwidth";
          type uint32;
        }
      }

      // interface * / tunnel checksum
      leaf checksum {
        description
          "enable end to end checksumming of packets";
        type empty;
      }

      // interface * / tunnel source
      leaf source {
        description
          "source of tunnel packets";
        type string;
      }

      // interface * / tunnel destination
      container destination {
        description
          "destination of tunnel";
        leaf ipaddress-or-host {
          type inet:host;
        }
        container list {
          description
            "List of Tunnel destinations";
          container mpls {
            description
              "MPLS destination list";
              container traffic-eng {
                description
                  "MPLS Traffic Engineering destination list";
                leaf name {
                  description
                    "Specify a destination list by name";
                  type string;
                }
              }
           }
         }
      }

      // interface * / tunnel dst-port
      container dst-port {
        description
          "tunnel destination port";
        choice dst-port-choice {
          case port-num-case {
            leaf port-num {
              type uint16;
            }
          }
          case dynamic-case {
            leaf dynamic {
              description
                "Set Destination Port Dynamically";
              type empty;
            }
          }
        }
      }

      // interface * / tunnel endpoint
      container endpoint {
        description
          "Set endpoint parameter";
        container service-policy {
          description
            "Set service-policy";
          leaf output {
            description
              "apply QoS service policy in the output direction";
            type string;
          }
        }
      }

      // interface * / tunnel entropy
      leaf entropy {
        description
          "Compute hash (entropy) on payload and propagate to tunnel header";
        type empty;
      }

      // interface * / tunnel fixup
      container fixup {
        description
          "fixup on tunnel interface";
        leaf nat {
          description
            "enable post nat fixup ";
          type empty;
        }
      }

      // interface * / tunnel flow
      container flow {
        description
          "flow options";
        leaf egress-records {
          description
            "enable egress flow records ";
          type empty;
        }
      }

      // interface * / tunnel key
      leaf key {
        description
          "security or selector key";
        type uint64 {
          range "0..4294967295";
        }
      }
      // interface * / tunnel mode
      container mode {
        description
          "tunnel encapsulation method";
        choice mode-choice {
          // interface * / tunnel mode ipsec
          container ipsec {
            description
              "IPSec tunnel encapsulation";
            container ipv4 {
              description
                "over IPv4";
              presence "true";
            }
            container ipv6 {
              description
                "over IPv6";
              presence "true";
            }
          }
          // interface * / tunnel mode mpls
          container mpls {
            description
              "MPLS encapsulations";
            container traffic-eng {
              description
                "Traffic engineering tunnels";
              presence "true";
              leaf multilsp {
                description
                  "Multiple LSP mode";
                type empty;
              }
              leaf point-to-multipoint {
                description
                  "point-to-multipoint tunnel mode";
                type empty;
              }
            }
          }
          // interface * / tunnel mode ethernet
          container ethernet {
            description
              "Ethernet over gre";
            leaf gre {
              description
                "Ethernet over gre";
              type enumeration {
                enum "ipv4";
                enum "ipv6";
              }
            }
          }
          // interface * / tunnel mode gre
          container gre {
            description
              "generic route encapsulation protocol";
            leaf ip {
              description
                "over IP";
              type empty;
            }
            leaf ipv6 {
              description
                "over IPv6";
              type empty;
            }
            container multipoint {
              description
                "over IPv4 (multipoint)";
              presence "true";
              leaf ipv6 {
                description
                  "over IPv6";
                type empty;
              }
            }
          }
          // interface * / tunnel mode ipip
          container ipip {
            description
              "IP over IP encapsulation";
            presence "true";
            leaf decapsulate-any {
              description
                "Incoming traffic only";
              type empty;
            }
          }
          // interface * / tunnel mode ipv6
          leaf ipv6 {
            description
              "Generic packet tunneling in IPv6";
            type empty;
          }
          // interface * / tunnel mode ipv6ip
          container ipv6ip {
            description
              "IPv6 over IP encapsulation";
            presence "true";
            leaf auto-6rd {
              description
                "IPv6 automatic tunnelling using 6rd";
              type empty;
            }
            leaf auto-6to4 {
              description
                "IPv6 automatic tunnelling using 6to4";
              type empty;
            }
            leaf isatap {
              description
                "IPv6 automatic tunnelling using ISATAP";
              type empty;
            }
          }
          // interface * / tunnel mode udp
          leaf udp {
            description
              "UDP encapsulation protocol";
            type enumeration {
              enum "ip";
              enum "multipoint";
            }
          }
        }
      }
      // interface * / tunnel network-id
      container network-id {
        description
          "Set network-id";
        leaf id {
          type uint16;
        }
        leaf nexthop {
          description
            "nexthop";
          type inet:ipv4-address;
        }
        leaf qos {
          description
            "QoS profile";
          type string;
        }
        leaf weight {
          description
            "weight";
          type uint16;
        }
      }
      // interface * / tunnel path-mtu-discovery
      container path-mtu-discovery {
        description
          "Enable Path MTU Discovery on tunnel";
        presence "true";
      }
      // interface * / tunnel protection
      container protection {
        description
          "Enable tunnel protection";
        // @mount Cisco-IOS-XE-crypto
      }
      // interface * / tunnel mpls
      container mpls {
        uses ios-mpls:config-tunnel-mpls-grouping;
      }

      // interface * / tunnel raw-packet-interface
      leaf raw-packet-interface {
        description
          "physical interface for all packets entering itto be tunneled and for all packets entering the tunnel to exit";
        type string;
      }

      // interface * / tunnel rbscp
      container rbscp {
        description
          "Set tunnel RBSCP parameters";
        leaf ack-split {
          description
            "ACK splitting";
          type uint8 {
            range "1..32";
          }
        }
        leaf delay {
          description
            "enable delay";
          type empty;
        }
        leaf input-drop {
          description
            "max tunnel queue size (number of bw*delay)";
          type uint8 {
            range "1..10";
          }
        }
        leaf long-drop {
          description
            "Drop non-transmitted packets w/excessive delay";
          type empty;
        }
        leaf report {
          description
            "enable SCTP report chunk";
          type empty;
        }
        leaf window-stuff {
          description
            "Window stuffing";
          type uint8 {
            range "1..20";
          }
        }
      }

      // interface * / tunnel snooping
      leaf snooping {
        description
          "Snooping on tunnel";
        type enumeration {
          enum "enable";
        }
      }

      // interface * / tunnel src-port
      container src-port {
        description
          "tunnel source port";
        choice src-port-choice {
          case port-num-case {
            leaf port-num {
              type uint16;
            }
          }
          case dynamic-case {
            leaf dynamic {
              description
                "Set Source Port Dynamically";
              type empty;
            }
          }
        }
      }

      // interface * / tunnel tos
      leaf tos {
        description
          "set type of sevice byte";
        type uint8;
      }

      // interface * / tunnel ttl
      leaf ttl {
        description
          "set time to live";
        type uint8;
      }

      // interface * / tunnel udlr
      container udlr {
        description
          "associate tunnel with unidirectional interface";
        leaf address-resolution {
          description
            "Enable ARP and NHRP over a UDLR Tunnel";
          type empty;
        }
        leaf receive-only {
          description
            "Tunnel is receive-only capable";
          type string;
        }
        leaf send-only {
          description
            "Tunnel is send-only capable";
          type string;
        }
      }

      // interface * / tunnel vlan
      container vlan {
        description
          "Set vlan-id for ethernet over gre mode";
        leaf id1 {
          type uint16;
        }
        leaf hyphen {
          type empty;
        }
        leaf id2 {
          type uint16;
        }
      }

      // interface * / tunnel vrf
      leaf vrf {
        description
          "set tunnel vrf membership";
        type string;
      }
    }
  }

  /////////////////////////////////////////////////////////
  // native / interface / Tunnel
  /////////////////////////////////////////////////////////
  augment "/ios:native/ios:interface/ios:Tunnel" {
    uses config-interface-tunnel-grouping;
  }

  /////////////////////////////////////////////////////////
  // native / interface / Virtual-Template
  /////////////////////////////////////////////////////////
  augment "/ios:native/ios:interface/ios:Virtual-Template" {
    uses config-interface-tunnel-grouping {
      if-feature ios-features:virtual-template;
    }
  }
}
