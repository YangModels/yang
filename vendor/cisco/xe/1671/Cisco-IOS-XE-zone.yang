module Cisco-IOS-XE-zone {
  namespace "http://cisco.com/ns/yang/Cisco-IOS-XE-zone";
  prefix ios-zone;


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Zone Interfaces Yang model.
     Copyright (c) 2016-2017 by Cisco Systems, Inc.
     All rights reserved.";

  // =========================================================================
  // REVISION
  // =========================================================================
  revision 2017-10-27 {
    description
      "Update supported interfaces";
  }
  revision 2017-08-16 {
    description
      "This revision has changes for new 5gig and 25gig interfaces addition";
  }

  revision 2017-02-07 {
    description
      "Initial revision";
  }

  grouping config-interface-zone-member-grouping {
    // interface * / zone-member
    container zone-member {
      description
        "Apply zone name";
      leaf security {
        description
          "Security zone";
        type string;
      }
    }
  }

  grouping config-zone-grouping {
    list security {
      description
        "Security zone";
      key "id";
      leaf id {
        type string;
      }
      leaf description {
        description
          "Zone description";
        type string;
      }
      leaf protection {
        description
          "config sync cookie protection against sync flood";
        type string;
      }
    }
  }

  grouping config-zone-pair-grouping {
    description
      "Zone pair command";
    list security {
      description
        "Zone-pair name";
      key "id";
      leaf id {
        type string;
      }
      leaf source {
        description
          "Source zone";
        type string;
      }
      leaf destination {
        description
          "Destination zone";
        type string;
      }
      leaf description {
        description
          "Zone description";
        type string {
          length "1..200";
        }
      }
      container service-policy {
        description
          "Configure CBAC Service Policy";
        container type {
          description
            "Service Policy type";
          leaf inspect {
            description
              "Configure CBAC Service Policy type inspect";
            type string;
          }
        }
      }
    }
  }

  /////////////////////////////////////////////////////////
  // native / zone
  /////////////////////////////////////////////////////////
  augment "/ios:native/ios:zone" {
    uses config-zone-grouping;
  }

  /////////////////////////////////////////////////////////
  // native / zone-pair
  /////////////////////////////////////////////////////////
  augment "/ios:native/ios:zone-pair" {
    uses config-zone-pair-grouping;
  }

  /////////////////////////////////////////////////////////
  // native / interface *
  /////////////////////////////////////////////////////////
  augment "/ios:native/ios:interface/ios:FastEthernet" {
    uses config-interface-zone-member-grouping;
  }

  augment "/ios:native/ios:interface/ios:GigabitEthernet" {
    uses config-interface-zone-member-grouping;
  }

  augment "/ios:native/ios:interface/ios:TenGigabitEthernet" {
    uses config-interface-zone-member-grouping;
  }

  augment "/ios:native/ios:interface/ios:FiveGigabitEthernet" {
    uses config-interface-zone-member-grouping;
  }

  augment "/ios:native/ios:interface/ios:TwentyFiveGigabitEthernet" {
    uses config-interface-zone-member-grouping;
  }

  augment "/ios:native/ios:interface/ios:FortyGigabitEthernet" {
    uses config-interface-zone-member-grouping;
  }

  augment "/ios:native/ios:interface/ios:HundredGigE" {
    uses config-interface-zone-member-grouping;
  }

  augment "/ios:native/ios:interface/ios:LISP" {
    uses config-interface-zone-member-grouping;
  }

  augment "/ios:native/ios:interface/ios:Loopback" {
    uses config-interface-zone-member-grouping;
  }

  augment "/ios:native/ios:interface/ios:Tunnel" {
    uses config-interface-zone-member-grouping;
  }

  augment "/ios:native/ios:interface/ios:Virtual-Template" {
    uses config-interface-zone-member-grouping;
  }

  augment "/ios:native/ios:interface/ios:Vlan" {
    uses config-interface-zone-member-grouping;
  }

  augment "/ios:native/ios:interface/ios:vasileft" {
    uses config-interface-zone-member-grouping;
  }

  augment "/ios:native/ios:interface/ios:vasiright" {
    uses config-interface-zone-member-grouping;
  }
}
