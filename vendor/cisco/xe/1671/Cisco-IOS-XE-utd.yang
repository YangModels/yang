module Cisco-IOS-XE-utd {
  namespace "http://cisco.com/ns/yang/Cisco-IOS-XE-utd";
  prefix ios-utd;

  import ietf-inet-types {
    prefix inet;
  }

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Unified Threat Defense (UTD) Yang model.
     Copyright (c) 2016 by Cisco Systems, Inc.
     All rights reserved.";

  // =========================================================================
  // REVISION
  // =========================================================================
  revision 2017-10-27 {
    description
      "Update supported interfaces";
  }
  revision 2017-08-30 {
    description
      "Move utd interface support";
  }
  revision 2017-08-26 {
    description
      "Update model to match CLI's in 16.05.01";
  }
  revision 2017-02-07 {
    description
      "Initial revision";
  }

  typedef utd-category-type {            
    type enumeration {
      enum abortion;
      enum abused-drugs;
      enum adult-and-pornography;
      enum alcohol-and-tobacco;
      enum auctions;
      enum bot-nets;
      enum business-and-economy;
      enum cdns;
      enum cheating;
      enum computer-and-internet-info;
      enum computer-and-internet-security;
      enum confirmed-spam-sources;
      enum cult-and-occult;
      enum dating;
      enum dead-sites;
      enum dynamic-content;
      enum educational-institutions;
      enum entertainment-and-arts;
      enum fashion-and-beauty;
      enum financial-services;
      enum gambling;
      enum games;
      enum government;
      enum gross;
      enum hacking;
      enum hate-and-racism;
      enum health-and-medicine;
      enum home;
      enum hunting-and-fishing;
      enum illegal;
      enum image-and-video-search;
      enum individual-stock-advice-and-tools;
      enum internet-communications;
      enum internet-portals;
      enum job-search;
      enum keyloggers-and-monitoring;
      enum kids;
      enum legal;
      enum local-information;
      enum malware-sites;
      enum marijuana;
      enum military;
      enum motor-vehicles;
      enum music;
      enum news-and-media;
      enum nudity;
      enum online-greeting-cards;
      enum online-personal-storage;
      enum open-http-proxies;
      enum p2p;
      enum parked-sites;
      enum pay-to-surf;
      enum personal-sites-and-blogs;
      enum philosophy-and-political-advocacy;
      enum phishing-and-other-frauds;
      enum private-ip-addresses;
      enum proxy-avoid-and-anonymizers;
      enum questionable;
      enum real-estate;
      enum recreation-and-hobbies;
      enum reference-and-research;
      enum religion;
      enum search-engines;
      enum sex-education;
      enum shareware-and-freeware;
      enum shopping;
      enum social-network;
      enum society;
      enum spam-urls;
      enum sports;
      enum spyware-and-adware;
      enum streaming-media;
      enum swimsuits-and-intimate-apparel;
      enum training-and-tools;
      enum translation;
      enum travel;
      enum uncategorized;
      enum unconfirmed-spam-sources;
      enum violence;
      enum weapons;
      enum web-advertisements;
      enum web-based-email;
      enum web-hosting;
    }
  }

  grouping utd-web-filter-grouping {     
    container web-filter {
      description
        "UTD web-filter profile configuration";
      container block {
        description
          "UTD block profile information";
        container local-server {
          description
            "UTD local block server configuration profile";
          list profile {
            description
              "Provide the profile ID";
            key id;
            leaf id {
              type string;
            }

            container block-page-interface {
              description
                "Provide the interface to be used for the block server";
              leaf Loopback {
                description
                  "Loopback interface";
                type uint32;
              }
            }

            container content {
              description
                "Provide the content to be served from the server";
              choice content-choice {
                leaf text {
                  description
                    "Provide the text to be printed in the web page served";
                  type string;
                }
                leaf file {
                  description
                    "Provide the HTML file to be served";
                  type string;
                }
              }
            }

            leaf http-ports {
              description
                "Provide the HTTP ports to be used";
              type string;
            }
          }
        }

        container page {
          description
            "UTD inline block page response profile";
          list profile {
            description
              "Provide the profile ID";
            key id;
            leaf id {
              type string;
            }
            choice page-choice {
              leaf file {
                description
                  "Specify the file name to be used for the block page";
                type string;
              }

              leaf redirect-url {
                description
                  "Specify the URL to be used for redirection";
                type string;
              }

              leaf text {
                description
                  "Specify the text to be used to be sent back";
                type string;
              }
            }
          }
        }
      }

      container domain {
        description
          "UTD Domain based web-filtering submode";
        list profile {
          description
            "Provide the profile ID";
          key id;
          leaf id {
            type string;
          }

          leaf alert {
            description
              "Provide the logging alert level";
            type enumeration {
              enum all;
              enum blacklist;
              enum whitelist;
            }
          }

          container blacklist {
            description
              "Choose the blacklist parameter-map";
            presence true;

            container parameter-map {
              description
                "Enter the parameter-map information for the regex";
              leaf regex {
                description
                  "Provide the regex parameter-map name";
                type union {
                  type string;
                }
              }
            }
          }

          container redirect-server {
            description
              "Provide the IP address for the redirect server for blocked domains";
            choice id-choice {
              leaf external {
                description
                  "Provide data about the external redirect server";
                type inet:ipv4-address;
              }
              leaf local-block-server {
                description
                  "Use the local block server as the redirect server";
                type string;
              }
            }
          }

          container whitelist {
            description
              "Choose the whitelist parameter-map";
            presence true;

            container parameter-map {
              description
                "Enter the parameter-map information for the regex";
              leaf regex {
                description
                  "Provide the regex parameter-map name";
                type union {
                  type string;
                }
              }
            }
          }
        }
      }

      list sourcedb {
        description
          "UTD Web filtering source DB configuration submode";
        key id;
        leaf id {
          type string;
        }

        container logging {
          description
            "Provide source DB logging information";
          leaf level {
            description
             "Provide the logging level";
            type enumeration {
              enum debug;
              enum error;
              enum info;
              enum trace;
              enum warning;
            }
          }
        }
      }

      container url {
        description
          "UTD URL based web-filtering submode";
        list profile {
          description
            "Provide the profile ID";
          key id;
          leaf id {
            type string;
          }

          leaf-list alert {
            description
              "Provide the logging alert level";
            type enumeration {
              enum all;
              enum blacklist;
              enum categories-reputation;
              enum whitelist;
            }
          }

          container blacklist {
            description
              "Choose the blacklist parameter-map";
            presence true;

            container parameter-map {
              description
                "Enter the parameter-map information for the regex";
              leaf regex {
                description
                  "Provide the regex parameter-map name";
                type union {
                  type string;
                }
              }
            }
          }

          container categories {
            description
              "Choose from a list of categories";

            container allow {
              description
                "Choose the list of categories to be allowed";
              presence true;

              list category {
                key name;
                leaf name {
                  type utd-category-type;
                }
              }
            }

            container block {
              description
                "Choose the list of categories to be blocked";
              presence true;

              list category {
                key name;
                leaf name {
                  type utd-category-type;
                }
              }
            }
          }

          container block {
            description
              "Provide information on the block page/server to be used";

            leaf local-server {
              description
                "Provide the local block server profile ID";
              type string;
            }

            leaf page-profile {
              description
                "Provide the ID of the block page profile to be used";
              type string;
            }
          }

          container log {
            description
              "Choose the URL filtering preprocessor debug log options";
            leaf level {
              description
                "Choose the URL filtering preprocessor log level";
              type enumeration {
                enum detailed;
                enum error;
                enum info;
              }
            }
          }

          container reputation {
            description
              "Choose the reputation range for the URLs to be blocked";
            presence true;

            leaf block-threshold {
              description
                "Block the URLs with reputation at or above the specified level";
              type enumeration {
                enum high-risk;
                enum low-risk;
                enum moderate-risk;
                enum suspicious;
                enum trustworthy;
              }
            }
          }

          container sourcedb {
            description
              "Choose source DB related configs";
            container fail {
              description
                "Choose the fail option to apply when the source DB is down";
              leaf close {
                description
                  "Drop all URL filtering traffic on source DB failure";
                type empty;
              }
            }
          }

          container whitelist {
            description
              "Choose the whitelist parameter-map";
            presence true;
            container parameter-map {
              description
                "Enter the parameter-map information for the regex";
              leaf regex {
                description
                  "Provide the regex parameter-map name";
                type union {
                  type string;
                }
              }
            }
          }
        }
      }
    }
  }

  grouping hour-minute-grouping {
    leaf hours {
      type uint8 {
        range "0..23";
      }
    }
    leaf minutes {
      type uint8 {
        range "0..59";
      }
    }
  }

  grouping username-password-grouping {
    leaf username {
      description
        "Provide the username for authentication";
      type string;
    }
    leaf password {
      description
        "Provide the password for authentication";
      type string;
    }
  }

  grouping utd-engine-standard-grouping {
    container logging {
      description
        "Provide config options for logging the alerts";
      list host {
        description
          "Log the alerts to a host";
        key name;
        leaf name {
          type string;
        }
      }
      leaf syslog {
        description
          "Log the alerts to IOS syslogs";
        type empty;
      }
    }
    container threat-inspection {
      description
        "IPS (or IDS) specific config commands";
      presence "true";
      container signature {
        description
          "Provide config options for the signatures";
        container update {
          description
            "Provide config options for the signature updates";
          container occur-at {
            description
              "Specify update occurence by calendar time";
            choice occur-at-choice {
              leaf daily {
                description
                  "Option for daily update";
                type empty;
              }
              leaf monthly {
                description
                  "Option for monthly update";
                type string;
              }
              leaf weekly {
                description
                  "Option for weekly update";
                type string;
              }
            }
            uses hour-minute-grouping;
          }
          container server {
            description
              "Provide config options for the signature update server";
            container cisco {
              description
                "Use Cisco site to provide updates";
              uses username-password-grouping;
            }
            container url {
              description
                "Enter the complete URL for the path to the update server";
              choice url-uname-passwd {
                case all-case {
                  container all {
                    leaf name {
                      type string;
                    }
                    uses username-password-grouping;
                  }
                }
                case name-only {
                  leaf name {
                    type string;
                  }
                }
              }
            }
          }
        }
      }
    }
    container web-filter {
      description
        "UTD engine standard web-filtering configs";
      presence "true";
      leaf domain-profile {
        description
          "Choose the domain profile to use for web filtering";
        type string;
      }
      leaf sourcedb {
        description
          "Choose the source DB profile to use for web filtering";
        type string;
      }
      leaf url-profile {
        description
          "Choose the url profile to use for web filtering";
        type string;
      }
    }
  }

  grouping utd-engine-threat-inspection-grouping {
    leaf threat {
      description
        "Provide the threat detection/protection option (default=detection)";
      type enumeration {
        enum detection;
        enum protection;
      }
    }
    leaf policy {   
      description
        "Provide the policy option (default=balanced)";
      type enumeration {
        enum balanced;  
        enum connectivity;
        enum security;
      }
    }
    container logging {
      description
        "Provide logging level for the alerts for IPS/IDS";
      leaf level {
        description
          "Provide the log level";
        type enumeration {
          enum emerg;
          enum alert;
          enum crit;
          enum err;
          enum warning;
          enum notice;
          enum info;
          enum debug;
        }
      }
    }
  }

  grouping config-utd-st-grouping {
    container utd-st {
      description
       "Global Unified Threat Defense Engine";
      container utd {
        uses utd-web-filter-grouping;
        container engine {
          description
            "UTD engine";
          container advanced {
            description
              "UTD engine advanced";
            container threat {
              description
                "Provide threat detection";
              presence "true";
              leaf detection {
                description
                  "Provide threat detection";
                type empty;
              }
            }
          }
          container standard {
            description
              "UTD engine standard";
            presence "true";
            uses utd-engine-standard-grouping {
              augment "threat-inspection" {
                uses utd-engine-threat-inspection-grouping;

                leaf whitelist {
                  description
                    "Enable whitelisting under the utd engine";
                  type empty;
                }
              }
            }
          }
        }
        container threat-inspection {
          description
            "UTD Threat Inspection (IPS/IDS) config modes";
          container whitelist {
            description
              "UTD whitelist config submode";
            presence "true";
            list signature {
              description
                "Provide signatures for the whitelist";
              key id;
              leaf id {
                description
                  "Provide signature id for the whitelist";
                type uint32 {
                  range "0..4294967295";
                }
              }
              leaf comment {
                description
                  "Provide a comment for the signature";
                type string;
              }
            }
          }
        }
      }
    }
  }

  grouping config-utd-grouping {
    container utd {
      description
        "Global Unified Threat Defense";
      presence "true";

      leaf all-interfaces {
        description
          "Enable intrusion inspection on all supported interfaces";
        type empty;
      }

      container redirect {
        description
          "Specify the interface connected to the UTD";
        container interface {
          description
            "Specify the interface connected to UTD";
          choice redirect-choice {
            leaf BDI {
              description
                "Bridge-Domain interface";
              type string;
            }
            leaf VirtualPortGroup {
              description
                "Virtual Port Group";
              type uint16;
            }
          }
        }
      }

      container engine {
        description
          "Select UTD engine mode to run";
        presence true;

        leaf mode {
          type enumeration {
            enum standard;
            enum advanced;
          }
        }

        container fail {
          description
            "Enter the UTD engine fail mode operation";
          leaf close {
            description
              "Drop all IPS/IDS traffic on UTD engine failure";
            type empty;
          }
        }  
      }
    }
  }

  grouping config-interface-utd-grouping {
    // interface * / utd
    container utd {
      description
        "UTD support on this interface";
      leaf enable {
        description
          "Enable threat defense on this interface";
        type empty;
      }
    }
  }

  /////////////////////////////////////////////////////////
  // native / utd
  // native / utd-st
  /////////////////////////////////////////////////////////
  augment "/ios:native" {
    uses config-utd-grouping;
    uses config-utd-st-grouping;
  } //augment

  /////////////////////////////////////////////////////////
  // native / interface
  /////////////////////////////////////////////////////////
  augment "/ios:native/ios:interface/ios:FastEthernet" {
    uses config-interface-utd-grouping;
  }

  augment "/ios:native/ios:interface/ios:GigabitEthernet" {
    uses config-interface-utd-grouping;
  }

  augment "/ios:native/ios:interface/ios:TenGigabitEthernet" {
    uses config-interface-utd-grouping;
  }

  augment "/ios:native/ios:interface/ios:FiveGigabitEthernet" {
    uses config-interface-utd-grouping;
  }

  augment "/ios:native/ios:interface/ios:TwentyFiveGigabitEthernet" {
    uses config-interface-utd-grouping;
  }

  augment "/ios:native/ios:interface/ios:FortyGigabitEthernet" {
    uses config-interface-utd-grouping;
  }

  augment "/ios:native/ios:interface/ios:HundredGigE" {
    uses config-interface-utd-grouping;
  }

  augment "/ios:native/ios:interface/ios:LISP" {
    uses config-interface-utd-grouping;
  }

  augment "/ios:native/ios:interface/ios:Loopback" {
    uses config-interface-utd-grouping;
  }

  augment "/ios:native/ios:interface/ios:Tunnel" {
    uses config-interface-utd-grouping;
  }

  augment "/ios:native/ios:interface/ios:Virtual-Template" {
    uses config-interface-utd-grouping;
  }

  augment "/ios:native/ios:interface/ios:Vlan" {
    uses config-interface-utd-grouping;
  }

  augment "/ios:native/ios:interface/ios:vasileft" {
    uses config-interface-utd-grouping;
  }

  augment "/ios:native/ios:interface/ios:vasiright" {
    uses config-interface-utd-grouping;
  }
} //module
