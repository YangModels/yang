module Cisco-IOS-XE-wsma {
  namespace "http://cisco.com/ns/yang/Cisco-IOS-XE-wsma";
  prefix ios-wsma;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Web Services Management Agent (WSMA) Yang model.
     Copyright (c) 2016 by Cisco Systems, Inc.
     All rights reserved.";

  // =========================================================================
  // REVISION
  // =========================================================================
  revision 2017-02-07 {
    description
      "Initial revision";
  }

  grouping config-wsma-grouping {
    container agent {
      description
        "Configure WSMA agents";
      container exec {
        description
          "Start WSMA exec agent";
        leaf-list profile {
          type string;
        }
      }
      container config {
        description
          "Start WSMA config agent";
        leaf-list profile {
          type string;
        }
      }
      container filesys {
        description
          "Start WSMA file system agent";
        leaf-list profile {
          type string;
        }
      }
      container notify {
        description
          "Start WSMA notify agent";
        leaf-list profile {
          type string;
        }
      }
    }
    container profile {
      description
        "Configure WSMA profile";
      list listener {
        description
          "Configure a listener profile";
        key "name";
        leaf name {
          type string;
        }
        leaf transport {
          description
            "The transport to use";
          type enumeration {
            enum "http";
            enum "https";
            enum "ssh";
            enum "tls";
          }
        }
      }
    }
  }

  /////////////////////////////////////////////////////////
  // native / wsma
  /////////////////////////////////////////////////////////
  augment "/ios:native/ios:wsma" {
    uses config-wsma-grouping;
  }
} //module
