module Cisco-IOS-XE-ospf {
  namespace "http://cisco.com/ns/yang/Cisco-IOS-XE-ospf";
  prefix ios-ospf;

  import ietf-inet-types {
    prefix inet;
  }


  import Cisco-IOS-XE-types {
    prefix ios-types;
  }

  import Cisco-IOS-XE-interface-common {
    prefix ios-ifc;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Open Shortest Path First (OSPF) Yang model.
     Copyright (c) 2016-2017 by Cisco Systems, Inc.
     All rights reserved.";

  // =========================================================================
  // REVISION
  // =========================================================================

  revision 2017-08-18 {
    description
      "This revision has changes for new 5gig and 25gig interfaces addition";
  }

  revision 2017-08-15 {
    description
      "add full nsf support and ospf support for BDI interfaces";
  }
  revision 2017-04-28 {
    description
      "inet:ipv6-prefix changed to ios-types:ipv6-prefix";
  }
  revision 2017-03-28 {
    description
      "Added NED Yang Data Model support for MPLS-TE";
  }

  revision 2017-02-07 {
    description
      "Initial revision";
  }

  typedef redist-ospf-external-type {
    type enumeration {
      enum "1";
      enum "2";
    }
  }

  grouping authentication-ipsec-grouping {
    container ipsec {
      description
        "Use IPsec authentication";
      leaf spi {
        description
          "Set the SPI (Security Parameters Index)";
        type uint64 {
          range "256..4294967295";
        }
      }
      container md5 {
        description
          "Use MD5 authentication";
        container key-string {
          leaf encrypt {
            type enumeration {
              enum "0";
              enum "7";
            }
          }
          leaf string {
            type string;
          }
        }
      }
      container sha1 {
        description
          "Use SHA-1 authentication";
        container key-string {
          leaf encrypt {
            type enumeration {
              enum "0";
              enum "7";
            }
          }
          leaf string {
            type string;
          }
        }
      }
    }
  }

  grouping interface-ospf-neighbor-grouping {
    list neighbor {
      description
        "OSPF neighbor";
      ordered-by user;
      must "count(*) > 1" {
      }
      key "id";
      leaf id {
        type inet:ipv6-address;
      }
      leaf cost {
        description
          "OSPF cost for point-to-multipoint neighbor";
        type uint16 {
          range "1..65535";
        }
      }
      container database-filter {
        description
          "Filter OSPF LSA during synchronization and flooding for point-to-multipoint neighbor";
        choice database {
          leaf all {
            description
              "Filter all LSA";
            type enumeration {
              enum "out";
            }
          }
        }
      }
      leaf poll-interval {
        description
          "OSPF dead-router polling interval";
        type uint32 {
          range "0..65535";
        }
      }
      leaf priority {
        description
          "OSPF priority of non-broadcast neighbor";
        type uint8 {
          range "0..255";
        }
      }
    }
  }

  grouping interface-ospf-encryption-grouping {
    container encryption {
      description
        "Enable encryption";
      leaf null {
        description
          "No IPsec encryption on this interface";
        type empty;
      }
      container ipsec {
        description
          "Use IPsec encryption";
        leaf spi {
          description
            "Set the SPI (Security Parameters Index)";
          type uint64;
        }
        leaf esp {
          description
            "Use ESP encapsulation";
          type empty;
        }
        container ipsec_3des {
          description
            "Use 3DES encryption";
          container key-string {
            leaf encrypt {
              type enumeration {
                enum "0";
                enum "7";
              }
            }
            leaf string {
              type string;
            }
          }
        }
        container aes-cbc {
          description
            "Use AES-CBC encryption";
          container aes-cbc-128 {
            description
              "Use 128 bit key";
            container key-string {
              leaf encrypt {
                type enumeration {
                  enum "0";
                  enum "7";
                }
              }
              leaf string {
                type string;
              }
            }
          }
          container aes-192 {
            description
              "Use 192 bit key";
            container key-string {
              leaf encrypt {
                type enumeration {
                  enum "0";
                  enum "7";
                }
              }
              leaf string {
                type string;
              }
            }
          }
          container aes-256 {
            description
              "Use 256 bit key";
            container key-string {
              leaf encrypt {
                type enumeration {
                  enum "0";
                  enum "7";
                }
              }
              leaf string {
                type string;
              }
            }
          }
        }
      }
    }
  }

  grouping interface-ospf-dead-interval-grouping {
    leaf dead-interval {
      description
        "Interval after which a neighbor is declared dead";
      type uint16 {
        range "1..65535";
      }
    }
  }

  grouping interface-ospf-hello-interval-grouping {
    leaf hello-interval {
      description
        "Time between HELLO packets";
      type uint32 {
        range "1..65535";
      }
    }
  }

  grouping interface-ospf-prefix-suppression-grouping {
    container prefix-suppression {
      description
        "OSPF prefix suppression";
      presence "true";
      leaf disable {
        description
          "Disable prefix suppression";
        type empty;
      }
    }
  }

  grouping interface-ospf-priority-grouping {
    leaf priority {
      description
        "Router priority";
      type uint8 {
        range "0..255";
      }
    }
  }

  grouping interface-ospf-retransmit-interval-grouping {
    leaf retransmit-interval {
      description
        "Time between retransmitting lost link state advertisements";
      type uint32 {
        range "1..65535";
      }
    }
  }

  grouping interface-ospf-transmit-delay-grouping {
    leaf transmit-delay {
      description
        "Link state transmit delay";
      type uint32 {
        range "1..65535";
      }
    }
  }

  grouping interface-ospf-bfd-grouping {
    container bfd {
      description
        "Enable BFD on this interface";
      presence "true";
      leaf disable {
        description
          "Disable BFD on this interface";
        type empty;
      }
    }
  }

  grouping interface-ospf-network-grouping {
    container network {
      description
        "Network type";
      leaf broadcast {
        description
          "Specify OSPF broadcast multi-access network";
        type empty;
      }
      leaf manet {
        description
          "Specify MANET OSPF interface type";
        type empty;
      }
      leaf non-broadcast {
        description
          "Specify OSPF NBMA network";
        type empty;
      }
      container point-to-multipoint {
        description
          "Specify OSPF point-to-multipoint network";
        presence "true";
        leaf non-broadcast {
          description
            "Specify non-broadcast point-to-mpoint network";
          type empty;
        }
      }
      leaf point-to-point {
        description
          "Specify OSPF point-to-point network";
        type empty;
      }
    }
  }


  // interface * / ip ospf
  grouping config-interface-ip-ospf-grouping {
    container ospf {
      description
        "OSPF interface commands";
      list process-id {
        key "id";
        leaf id {
          type uint16;
        }
        leaf area {
          type ios-types:ospf-area-type;
        }
        leaf secondaries {
          description
            "Include or exclude secondary IP addresses";
          type empty;
        }
        leaf none {
          description
            "Do not include secondary IP addresses";
          type empty;
        }
      }

      // interface * / ip ospf authentication
      container authentication {
        description
          "Enable authentication";
        presence "Enable authentication";
        container key-chain {
          description
            "Use a key-chain for cryptographic authentication keys";
          leaf name {
            type string;
          }
        }
        leaf message-digest {
          description
            "Use message-digest authentication";
          type empty;
        }
        leaf null {
          description
            "Use no authentication";
          type empty;
        }
      }

      // interface * / ip ospf authentication-key
      uses ospf-authentication-key-grouping;

      // interface * / ip ospf network
      leaf network {
        description
          "Network type";
        type enumeration {
          enum "broadcast";
          enum "non-broadcast";
          enum "point-to-multipoint";
          enum "point-to-point";
        }
      }
      // interface * / ip ospf bfd

      uses interface-ospf-bfd-grouping;
      // interface * / ip ospf cost
      leaf cost {
        description
          "Interface cost";
        type uint16 {
          range "1..65535";
        }
      }

      // interface * / ip ospf database-filter
      container database-filter {
        description
          "Filter OSPF LSA during synchronization and flooding";
        leaf all {
          description
            "Filter all LSA";
          type empty;
        }
        leaf out {
          description
            "Outgoing LSA";
          type empty;
        }
      }

      // interface * / ip ospf dead-interval
      container dead-interval {
        description
          "Interval after which a neighbor is declared dead";
        leaf value {
          type uint32 {
            range "1..65535";
          }
        }
        container minimal {
          description
            "Set to 1 second";
          leaf hello-multiplier {
            description
              "Set multiplier for Hellos";
            type uint8;
          }
        }
      }

      // interface * / ip ospf demand-circuit
      container demand-circuit {
        description
          "OSPF Demand Circuit";
        presence "true";
        leaf ignore {
          description
            "Ignore demand circuit auto-negotiation requests";
          type empty;
        }
      }

      // interface * / ip ospf fast-reroute
      container fast-reroute {
        description
          "LFA FastReroute parameters";
        container per-prefix {
          description
            "Per-prefix LFA FRR parameters";
          container candidate {
            description
              "If interface can be protecting";
            presence "true";
            leaf disable {
              description
                "Disable LFA FRR interface protection";
              type empty;
            }
          }
          container protection {
            description
              "If interface can be protected";
            presence "true";
            leaf disable {
              description
                "Disable LFA FRR interface protection";
              type empty;
            }
          }
        }
      }

      // interface * / ip ospf flood-reduction
      leaf flood-reduction {
        description
          "OSPF Flood Reduction";
        type empty;
      }

      // interface * / ip ospf hello-interval
      uses interface-ospf-hello-interval-grouping;

      // interface * / ip ospf lls
      container lls {
        description
          "Link-local Signaling (LLS) support";
        presence "true";
        leaf disable {
          description
            "disable LLS";
          type empty;
        }
      }

      // interface * / ip ospf message-digest-key
      list message-digest-key {
        description
          "Set message digest key";
        key "id";
        leaf id {
          type uint8 {
            range "1 .. 255";
          }
        }
        container md5 {
          description
            "Use MD5 algorithm";
          leaf auth-type {
            type uint8 {
              range "0 .. 7";
            }
          }
          leaf auth-key {
            type string;
          }
        }
      }

      // interface * / ip ospf mtu-ignore
      leaf mtu-ignore {
        description
          "Ignores the MTU in DBD packets";
        type empty;
      }

      // interface * / ip ospf multi-area
      container multi-area {
        description
          "Set the OSPF multi-area ID";
        leaf id {
          type union {
            type uint32 {
              range "0..4294967295";
            }
            type inet:ipv4-address;
          }
        }
        leaf cost {
          description
            "Interface cost";
          type uint32 {
            range "1..65535";
          }
        }
      }

      // interface * / ip ospf prefix-suppression
      uses interface-ospf-prefix-suppression-grouping;

      // interface * / ip ospf priority
      uses interface-ospf-priority-grouping;

      // interface * / ip ospf resync-timeout
      leaf resync-timeout {
        description
          "Interval after which adjacency is reset if oob-resync is not started";
        type uint32 {
          range "1..65535";
        }
      }

      // interface * / ip ospf retransmit-interval
      uses interface-ospf-retransmit-interval-grouping;
      // interface * / ip ospf shutdown
      leaf shutdown {
        description
          "Set OSPF protocol's state to disable under current interface";
        type empty;
      }
      // interface * / ip ospf transmit-delay
      uses interface-ospf-transmit-delay-grouping;
      // interface * / ip ospf ttl-security
      container ttl-security {
        description
          "TTL security check";
        presence "true";
        leaf diable {
          description
            "disable TTL security check";
          type empty;
        }
        leaf hops {
          description
            "IP hops";
          type uint8 {
            range "1..254";
          }
        }
      }
    }
  }

  // interface * ipv6 ospf
  grouping config-interface-ipv6-ospf-grouping {
    container ospf {
      description
        "OSPF interface commands";
      list process {
        key "id";
        leaf id {
          type uint16 {
            range "1..65535";
          }
        }
        leaf area {
          description
            "Set the OSPF area ID";
          type union {
            type uint32 {
              range "0..4294967295";
            }
            type inet:ipv4-address;
          }
        }
        leaf instance {
          description
            "Set the OSPF instance";
          type union {
            type uint8 {
              range "0..31";
            }
            type uint8 {
              range "32..255";
            }
          }
        }
      }

      // interface * / ipv6 ospf authentication
      container authentication {
        description
          "Enable authentication";
        leaf null {
          description
            "Use no authentication";
          type empty;
        }
        uses authentication-ipsec-grouping;
      }

      // interface * / ipv6 ospf bfd
      uses interface-ospf-bfd-grouping;

      // interface * / ipv6 ospf cost
      leaf cost {
        description
          "Route cost of this interface";
        type uint16 {
          range "1..65535";
        }
      }

      // interface * / ipv6 ospf database-filter
      container database-filter {
        description
          "Filter OSPF LSA during synchronization and flooding";
        choice database {
          leaf all {
            description
              "Filter all LSA";
            type enumeration {
              enum "out";
            }
          }
          leaf disable {
            description
              "Disable LSA Filter on this interface";
            type empty;
          }
        }
      }
      // interface * / ipv6 ospf dead-interval
      uses interface-ospf-dead-interval-grouping;

      // interface * / ipv6 ospf demand-circuit
      container demand-circuit {
        description
          "OSPF demand circuit";
        presence "true";
        leaf disable {
          description
            "Disable demand circuit on this interface";
          type empty;
        }
        leaf ignore {
          description
            "Ignore demand circuit auto-negotiation requests";
          type empty;
        }
      }

      // interface * / ipv6 ospf encryption
      uses interface-ospf-encryption-grouping;

      // interface * / ipv6 ospf flood-reduction
      container flood-reduction {
        description
          "OSPF Flood Reduction";
        presence "true";
        leaf disable {
          description
            "Disable Flood Reduction on this interface";
          type empty;
        }
      }

      // interface * / ipv6 ospf hello-interval
      uses interface-ospf-hello-interval-grouping;

      // interface * / ipv6 ospf mtu-ignore
      container mtu-ignore {
        description
          "Ignores the MTU in DBD packets";
        presence "true";
        leaf disable {
          description
            "Disable Ingore MTU on this interface";
          type empty;
        }
      }

      // interface * / ipv6 ospf neighbor
      uses interface-ospf-neighbor-grouping;

      //  interface * / ipv6 ospf network
      uses interface-ospf-network-grouping;

      // interface * / ipv6 ospf priority
      uses interface-ospf-priority-grouping;
      // interface * / ipv6 ospf retransmit-interval

      uses interface-ospf-retransmit-interval-grouping;

      // interface * / ipv6 ospf shutdown
      container shutdown {
        description
          "Shut down the interface in OSPFv3";
        presence "true";
        leaf disable {
          description
            "Disable inherited shutdown";
          type empty;
        }
      }

      // interface * / ipv6 ospf transmit-delay
      uses interface-ospf-transmit-delay-grouping;
    }
  }

  grouping ospf-ospfv3-common-address-family-grouping {
    container capability {
      description
        "Enable specific OSPF feature";
      leaf capability-type {
        type enumeration {
          enum "lls";
          enum "opaque";
          enum "transit";
          enum "vrf-lite";
        }
      }
    }
    container compatible {
      description
        "OSPF compatibility list";
      leaf rfc1583 {
        description
          "Compatible with RFC 1583";
        type empty;
      }
      leaf rfc1587 {
        description
          "Compatible with RFC 1587";
        type empty;
      }
      leaf rfc5243 {
        description
          "Compatible with RFC 5243";
        type empty;
      }
    }
    container default-information {
      description
        "Control distribution of default information";
      container originate {
        description
          "Distribute a default route";
        presence "Distribute a default route";
        leaf always {
          description
            "Always advertise default route";
          type empty;
        }
        leaf metric {
          description
            "OSPF default metric";
          type uint32 {
            range "0 .. 16777214";
          }
        }
        leaf metric-type {
          description
            "OSPF metric type for default routes";
          type ios-types:ospf-metric-type;
        }
        leaf route-map {
          description
            "Route map reference";
          type string;
        }
      }
    }
    leaf default-metric {
      description
        "Set metric of redistributed routes";
      type uint32 {
        range "1 .. 16777214";
      }
    }
    container discard-route {
      description
        "Enable or disable discard-route installation";
      presence "Enable or disable discard-route installation";
      leaf external {
        description
          "Discard route for redistributed summarised routes";
        type empty;
      }
      leaf internal {
        description
          "Discard route for summarised internal routes";
        type empty;
      }
      leaf metric {
        type uint32 {
          range "1 .. 255";
        }
      }
    }
    container distance {
      description
        "Define an administrative distance";
      container ospf-distance {
        leaf distance {
          type uint32 {
            range "1 .. 255";
          }
        }
        leaf ip {
          type inet:ipv4-address;
        }
        leaf wildcard {
          type inet:ipv4-address;
        }
        leaf acl-name {
          type ios-types:access-list-standard-id-type;
        }
      }
      container ospf {
        description
          "OSPF routes Administrative distance";
        leaf external {
          description
            "External routes";
          type uint32 {
            range "1 .. 255";
          }
        }
        leaf inter-area {
          description
            "Inter-area routes";
          type uint32 {
            range "1 .. 255";
          }
        }
        leaf intra-area {
          description
            "Intra-area routes";
          type uint32 {
            range "1 .. 255";
          }
        }
      }
    }
    leaf maximum-paths {
      description
        "Forward packets over multiple paths";
      type uint32 {
        range "1 .. 32";
      }
    }
    container redistribute {
      description
        "Redistribute information from another routing protocol";
      uses ospf-redistribute-top-grouping;
      container maximum-prefix {
        description
          "Maximum number of prefixes redistributed to protocol";
        leaf number {
          type uint32 {
            range "1 .. 4294967295";
          }
        }
        container threshold-warning-only-container {
          leaf threshold {
            type uint32 {
              range "1 .. 100";
            }
          }
          leaf warning-only {
            description
              "Only give warning message when limit is exceeded";
            type empty;
          }
        }
      }
      container vrf {
        description
          "Specify a source VRF";
        list non-global-vrf {
          key "name";
          leaf name {
            type string;
          }
          uses ospf-redistribute-top-grouping;
        }
        container global {
          description
            "global VRF";
          uses ospf-redistribute-top-grouping;
        }
      }
    }
  }

  grouping ospf-ospfv3-common-grouping {
    list area {
      description
        "OSPF area parameters";
      key "id";
      leaf id {
        type ios-types:ospf-area-type;
      }
      container authentication {
        description
          "Enable authentication";
        presence "true";
        leaf message-digest {
          description
            "Use message-digest authentication";
          type empty;
        }
      }
      container capability {
        description
          "Enable area specific capability";
        leaf default-exclusion {
          description
            "Enable exclusion of links from base topology";
          type empty;
        }
      }
      leaf default-cost {
        description
          "Set the summary default-cost of a NSSA/stub area";
        type uint32 {
          range "0 .. 16777215";
        }
      }
      list filter-list {
        description
          "Filter networks between OSPF areas";
        key "in-out";
        leaf in-out {
          type enumeration {
            enum "in";
            enum "out";
          }
        }
        leaf prefix {
          mandatory true;
          description
            "Filter prefixes between OSPF areas";
          type string;
        }
      }
      container nssa {
        description
          "Specify a NSSA area";
        presence "Specify a NSSA area";
        container default-information-originate {
          description
            "Originate Type 7 default into NSSA area";
          presence "Originate Type 7 default into NSSA area";
          leaf metric {
            description
              "OSPF default metric";
            type int32 {
              range "0 .. 16777214";
            }
          }
          leaf metric-type {
            description
              "OSPF metric type for default routes";
            type ios-types:ospf-metric-type;
          }
          leaf no-ext-capability {
            description
              "Do not send domain specific capabilities into NSSA";
            type empty;
          }
          leaf no-redistribution {
            description
              "No redistribution into this NSSA area";
            type empty;
          }
          leaf no-summary {
            description
              "Do not send summary LSA into NSSA";
            type empty;
          }
          leaf nssa-only {
            description
              "Limit default advertisement to this NSSA area";
            type empty;
          }
          container translate {
            description
              "Translate LSA";
            container type7 {
              description
                "From Type 7 to Type 5";
              leaf always {
                description
                  "Always translate LSAs on this ABR";
                type empty;
              }
              leaf suppress-fa {
                description
                  "Suppress forwarding address in translated LSAs";
                type empty;
              }
            }
          }
        }
        leaf no-ext-capability {
          description
            "Do not send domain specific capabilities into NSSA";
          type empty;
        }
        leaf no-redistribution {
          description
            "No redistribution into this NSSA area";
          type empty;
        }
        leaf no-summary {
          description
            "Do not send summary LSA into NSSA";
          type empty;
        }
        leaf nssa-only {
          description
            "Limit default advertisement to this NSSA area";
          type empty;
        }
        container translate {
          description
            "Translate LSA";
          container type7 {
            description
              "From Type 7 to Type 5";
            leaf always {
              description
                "Always translate LSAs on this ABR";
              type empty;
            }
            leaf suppress-fa {
              description
                "Suppress forwarding address in translated LSAs";
              type empty;
            }
          }
        }
      }
      container ipv4-range {
        list range {
          description 
            "Summarize routes matching address/mask (border routers only)";
          key "ip mask";
          leaf ip {
            type inet:ipv4-address;
          }
          leaf mask {
            type inet:ipv4-address;
          }
          choice advertise-choice {
            leaf advertise {
              description 
                "Advertise this range (default)";
              type empty;
            }
            leaf not-advertise {
              description 
                "DoNotAdvertise this range";
              type empty;
            }
          }
          leaf cost {
            description 
              "User specified metric for this range";
            type uint32 {
              range "0 .. 16777215";
            }
          }
        }
      } 
      container ipv6-range {
        list range {
          description 
            "Summarize routes matching address/mask (border routers only)";
          key "ip";
          leaf ip {
            type ios-types:ipv6-prefix;
          }
          choice advertise-choice {
            leaf advertise {
              description 
                "Advertise this range (default)";
              type empty;
            }
            leaf not-advertise {
              description 
                "DoNotAdvertise this range";
              type empty;
            }
          }
          leaf cost {
            description 
              "User specified metric for this range";
            type uint32 {
              range "0 .. 16777215";
            }
          }
        }
      } 
      list sham-link {
        description
          "Define a sham link and its parameters";
        key "source dest";
        leaf source {
          type inet:ip-address;
        }
        leaf dest {
          type inet:ip-address;
        }
        leaf cost {
          description
            "Associate a cost with the sham-link";
          type uint16 {
            range "0 .. 65535";
          }
        }
        container ttl-security {
          description
            "TTL security check";
          leaf hops {
            description
              "IP hops";
            type uint8;
          }
        }
      }
      container stub {
        description
          "Specify a stub area";
        presence "Specify a stub area";
        leaf no-ext-capability {
          description
            "Do not send domain specific capabilities into stub area";
          type empty;
        }
        leaf no-summary {
          description
            "Do not send summary LSA into stub area";
          type empty;
        }
      }
      list virtual-link {
        description
          "Define a virtual link and its parameters";
        key "id";
        leaf id {
          type inet:ip-address;
        }
        container authentication {
          description
            "Set authentication type";
          uses ospf-area-virtual-link-grouping;
          container key-chain {
            description
              "Use a key-chain for cryptographic authentication keys";
            leaf name {
              type string;
            }
            uses ospf-area-virtual-link-grouping;
          }
          container message-digest {
            description
              "Message-digest authentication";
            uses ospf-area-virtual-link-grouping;
          }
          leaf null {
            description
              "No authentication";
            type empty;
          }
        }
        container hello-interval {
          description
            "Hello packet interval";
          leaf hello-interval-value {
            type int32 {
              range "1 .. 8192";
            }
          }
        }
        container dead-interval {
          description
            "Dead router detection time";
          leaf dead-interval-value {
            type uint16 {
              range "1 .. 8192";
            }
          }
        }
        container retransmit-interval {
          description
            "LSA retransmit interval";
          leaf retransmit-interval-value {
            type uint16 {
              range "1 .. 8192";
            }
          }
        }
        container transmit-delay {
          description
            "LSA transmission delay";
          leaf transmit-delay-value {
            type uint16 {
              range "1 .. 8192";
            }
          }
        }
        container topology {
          description
            "Disable virtual link on topology";
          leaf disable {
            description
              "Disable virtual link";
            type empty;
          }
        }
        container ttl-security {
          description
            "TTL security check";
          leaf hops {
            description
              "IP hops";
            type uint8 {
              range "1..254";
            }
          }
        }
        uses ospf-area-virtual-link-grouping;
      }
    }
    container auto-cost {
      description
        "Calculate OSPF interface cost according to bandwidth";
      presence "Calculate OSPF interface cost according to bandwidth";
      leaf reference-bandwidth {
        description
          "Use reference bandwidth method to assign OSPF cost";
        type uint32 {
          range "1 .. 4294967";
        }
      }
    }
    container event-log {
      description
        "OSPF Event Logging";
      presence "true";
      leaf one-shot {
        description
          "Disable Logging When Log Buffer Becomes Full";
        type empty;
      }
      leaf pause {
        description
          "Pause Event Logging";
        type empty;
      }
      leaf size {
        description
          "Maximum Number of Events Stored in the Event Log";
        type uint32 {
          range "1..65534";
        }
      }
    }
    container bfd {
      description
        "BFD configuration commands";
      leaf all-interfaces {
        description
          "Enable BFD on all interfaces";
        type empty;
      }
    }
    container interface-id {
      description
        "Source of the interface ID";
      leaf snmp-if-index {
        description
          "SNMP MIB ifIndex";
        type empty;
      }
    }
    container log-adjacency-changes {
      description
        "Log changes in adjacency state";
      presence "true";
      leaf detail {
        description
          "Log all state changes";
        type empty;
      }
    }
    container max-lsa {
      description
        "maximum number of LSAs OSPF process will receive";
      leaf number {
        type uint32 {
          range "1 .. 4294967294";
        }
      }
      leaf threshold-value {
        type uint32 {
          range "1 .. 100";
        }
      }
      leaf ignore-count {
        description
          "maximum number of times adjacencies can be suppressed";
        type uint32 {
          range "1 .. 65534";
        }
      }
      leaf ignore-time {
        description
          "time during which all adjacencies are suppressed";
        type uint32 {
          range "1 .. 17895";
        }
      }
      leaf reset-time {
        description
          "time after which ignore-count is reset to zero";
        type uint32 {
          range "2 .. 35791";
        }
      }
      leaf warning-only {
        description
          "Only give warning message when limit is exceeded";
        type empty;
      }
    }
    container max-metric {
      description
        "Set maximum metric";
      container router-lsa {
        description
          "Maximum metric in self-originated router-LSAs";
        presence "Maximum metric in self-originated router-LSAs";
        container external-lsa {
          presence "Override external-lsa metric with max-metric value";
          description
            "Override external-lsa metric with max-metric value";
          leaf metric {
            type uint32 {
              range "1 .. 16777215";
            }
          }
        }
        leaf include-stub {
          description
            "Set maximum metric for stub links in router-LSAs";
          type empty;
        }
        container on-startup {
          description
            "Set maximum metric temporarily after reboot";
          presence "Set maximum metric temporarily after reboot";
          choice time-wait-for-bgp-choice {
            leaf time {
              type uint32 {
                range "5 .. 86400";
              }
            }
            leaf wait-for-bgp {
              description
                "Let BGP decide when to originate router-LSA with normal metric";
              type empty;
            }
          }
        }
        container summary-lsa {
          description
            "Override summary-lsa metric with max-metric value";
          presence "Override summary-lsa metric with max-metric value";
          leaf metric {
            type uint32 {
              range "1 .. 16777215";
            }
          }
        }
      }
    }
    uses ios-ifc:passive-interface-grouping;
    container queue-depth {
      description
        "OSPF Hello/Router process queue depth";
      container hello {
        description
          "OSPF Hello process queue depth";
        uses queue-depth-grouping;
      }
      container update {
        description
          "OSPF Router process queue depth";
        uses queue-depth-grouping;
      }
    }
    container timers {
      description
        "Adjust routing timers";
      container lsa {
        description
          "OSPF LSA timers";
        leaf arrival {
          description
            "OSPF LSA arrival timer";
          type uint32 {
            range "0 .. 600000";
          }
        }
      }
      container pacing {
        description
          "OSPF pacing timers";
        leaf flood {
          description
            "OSPF flood pacing timer";
          type uint32 {
            range "5 .. 100";
          }
        }
        leaf lsa-group {
          description
            "OSPF LSA group pacing timer";
          type uint32 {
            range "10 .. 1800";
          }
        }
        leaf retransmission {
          description
            "OSPF retransmission pacing timer";
          type uint32 {
            range "5 .. 200";
          }
        }
      }
      container throttle {
        description
          "OSPF throttle timers";
        container lsa {
          description
            "OSPF LSA throttle timers";
          container all {
            description
              "For all type of OSPF LSAs";
            leaf delay {
              type uint32 {
                range "0 .. 600000";
              }
            }
            leaf min-delay {
              type uint32 {
                range "0 .. 600000";
              }
            }
            leaf max-delay {
              type uint32 {
                range "0 .. 600000";
              }
            }
          }
        }
        container spf {
          description
            "OSPF SPF throttle timers";
          leaf delay {
            type uint32 {
              range "0 .. 600000";
            }
          }
          leaf min-delay {
            type uint32 {
              range "0 .. 600000";
            }
          }
          leaf max-delay {
            type uint32 {
              range "0 .. 600000";
            }
          }
        }
      }
    }
    leaf router-id {
      description
        "Override configured router identifier (peers will reset)";
      type inet:ipv4-address;
    }
    leaf nsr {
      description
        "Enable non-stop routing";
      type empty;
    }
    container traffic-share {
      description
        "How to compute traffic share over alternate paths";
      leaf min {
        description
          "All traffic shared among min metric paths";
        type empty;
      }
      leaf across-interfaces {
        description
          "Use different interfaces for equal-cost paths";
        type empty;
      }
    }
    container ttl-security {
      description
        "TTL security check";
      leaf all-interfaces {
        description
          "Enable TTL Security on all interfaces";
        type empty;
      }
      leaf hops {
        description
          "IP hops";
        type uint8 {
          range "1..254";
        }
      }
    }
  }

  grouping distribute-list-grouping {
    container distribute-list {
      description
        "Filter networks in routing updates";
      list accesslist {
        key "in-out";
        leaf in-out {
          type ios-types:access-list-in-out-type;
        }
      }
      list accesslist-ifname {
        key "in-out interface";
        leaf in-out {
          type ios-types:access-list-in-out-type;
        }
        leaf interface {
          // Note: interface name must be type string since part of key
          type string;
        }
        leaf interface-routing-id {
          type uint8;
        }
        leaf isis-tag {
          type string;
        }
        leaf vrf {
          description
            "VPN Routing/Forwarding Instance";
          type string;
        }
      }
      list accesslist-prefix-gateway {
        key "in-out";
        leaf in-out {
          type ios-types:access-list-in-out-type;
        }
        leaf prefix-gateway {
          mandatory true;
          type enumeration {
            enum "prefix";
            enum "gateway";
            enum "route-map";
          }
        }
        leaf name {
          mandatory true;
          type string;
        }
      }
      list accesslist-prefix-gateway-ifname {
        key "in-out interface";
        leaf in-out {
          type ios-types:access-list-in-out-type;
        }
        leaf interface {
          type string;
        }
        leaf prefix-gateway {
          mandatory true;
          type enumeration {
            enum "prefix";
            enum "gateway";
            enum "route-map";
          }
        }
        leaf name {
          mandatory true;
          type string;
        }
        leaf interface-routing-id {
          type uint8;
        }
        leaf isis-tag {
          type string;
        }
        leaf vrf {
          description
            "VPN Routing/Forwarding Instance";
          type string;
        }
      }
    }
  }

  grouping ospf-authentication-key-grouping {
    container authentication-key {
      description
        "Set authentication key";
      leaf auth-type {
        type uint8 {
          range "0 .. 7";
        }
      }
      leaf auth-key {
        type string;
      }
    }
  }

  grouping ospf-area-virtual-link-grouping {
    uses ospf-authentication-key-grouping;
    list message-digest-key {
      description
        "Set message digest key";
      key "id";
      leaf id {
        type uint8 {
          range "1 .. 255";
        }
      }
      container md5 {
        description
          "Use MD5 algorithm";
        leaf auth-type {
          type uint8 {
            range "0 .. 7";
          }
        }
        leaf auth-key {
          type string {
            length "1 .. 16";
          }
        }
      }
    }
  }

  //ospf ast-reroute per-prefix tie-break index
  grouping tie-break-index {
    leaf required {
      description
        "Mandatory repair path attribute";
      type empty;
    }
    leaf index {
      description
        "Tiebreak attribute priority";
      type uint8 {
        range "1..255";
      }
    }
  }

  grouping queue-depth-grouping {
    leaf options {
      type union {
        type uint32 {
          range "1 .. 2147483647";
        }
        type enumeration {
          enum "unlimited";
        }
      }
    }
  }

  grouping router-eigrp-redistribute-grouping {
    container metric {
      description
        "Metric for redistributed routes";
      leaf bandwith {
        description
          "Bandwidth metric in Kbits per second";
        type uint32 {
          range "1..4294967295";
        }
      }
      leaf delay {
        description
          "EIGRP delay metric, in 10 microsecond units";
        type uint32 {
          range "0..4294967295";
        }
      }
      leaf reliability {
        description
          "EIGRP reliability metric where 255 is 100% reliable";
        type uint8 {
          range "0..255";
        }
      }
      leaf Effective {
        description
          "EIGRP Effective bandwidth metric (Loading) where 255 is 100% loaded";
        type uint8 {
          range "1..255";
        }
      }
      leaf mtu {
        description
          "EIGRP MTU of the path";
        type uint16 {
          range "1..65535";
        }
      }
    }
    leaf route-map {
      description
        "Route map reference";
      type string;
    }
  }

  grouping ospf-redistribute-match-grouping {
    leaf metric {
      description
        "Metric for redistributed routes";
      type uint32;
    }
    leaf metric-type {
      description
        "OSPF/IS-IS exterior metric type for redistributed routes";
      type enumeration {
        enum "1" {
        }
        enum "2" {
        }
      }
    }
    leaf nssa-only {
      description
        "Limit redistributed routes to NSSA areas";
      type empty;
    }
    leaf subnets {
      description
        "Consider subnets for redistribution into OSPF";
      type empty;
    }
    leaf route-map {
      description
        "Route map reference";
      type string;
    }
    leaf tag {
      description
        "Set tag for routes redistributed into OSPF";
      type uint32 {
        range "0 .. 4294967295";
      }
    }
  }

  grouping ospf-redistribute-top-match-grouping {
    container match {
      description
        "Redistribution of OSPF routes";
      container internal {
        presence "Redistribute OSPF internal routes";
        description
          "Redistribute OSPF internal routes";
        uses ospf-redistribute-match-grouping;
      }
      container external {
        description
          "Redistribute OSPF external routes";
        presence "Redistribute OSPF external routes";
        leaf external-routes {
          type redist-ospf-external-type;
        }
        uses ospf-redistribute-match-grouping;
      }
      container nssa-external {
        description
          "Redistribute OSPF NSSA external routes";
        presence "Redistribute OSPF NSSA external routes";
        leaf nssa-external-routes {
          type redist-ospf-external-type;
        }
        uses ospf-redistribute-match-grouping;
      }
    }
  }

  grouping ospf-iso-igrp-redistribute-grouping {
    leaf metric {
      description
        "Metric for redistributed routes";
      type uint32;
    }
    leaf metric-type {
      description
        "OSPF/IS-IS exterior metric type for redistributed routes";
      type enumeration {
        enum "1" {
        }
        enum "2" {
        }
      }
    }
    leaf tag {
      description
        "Set tag for routes redistributed into OSPF";
      type uint32 {
        range "0 .. 4294967295";
      }
    }
    leaf subnets {
      description
        "Consider subnets for redistribution into OSPF";
      type empty;
    }
  }

  grouping ospf-redistribute-grouping {
    container redist-options {
      uses ospf-iso-igrp-redistribute-grouping;
      leaf route-map {
        description
          "Route map reference";
        type string;
      }
      leaf nssa-only {
        description
          "Limit redistributed routes to NSSA areas";
        type empty;
      }
    }
  }

  grouping ospf-redistribute-top-grouping {
    list application {
      description
        "Application";
      key "name";
      leaf name {
        type string;
      }
      uses ospf-redistribute-grouping;
    }
    list bgp {
      description
        "Border Gateway Protocol (BGP)";
      key "as-number";
      uses ospf-redistribute-bgp-grouping;
    }
    container connected {
      description
        "Connected";
      presence "Connected";
      uses ospf-redistribute-grouping;
    }
    list eigrp {
      description
        "Enhanced Interior Gateway Routing Protocol (EIGRP)";
      key "as-number";
      uses ospf-redistribute-bgp-grouping;
    }
    container isis {
      presence "ISO IS-IS";
      description
        "ISO IS-IS";
      choice isis-level-routes-isis-area-choice {
        leaf isis-level-routes {
          type enumeration {
            enum "level-1";
            enum "level-2";
            enum "level-1-2";
          }
        }
        list isis-area {
          key "name";
          leaf name {
            type string;
          }
          leaf isis-level-routes {
            type enumeration {
              enum "level-1";
              enum "level-2";
              enum "level-1-2";
            }
          }
          uses ospf-redistribute-grouping;
        }
      }
      uses ospf-redistribute-grouping;
    }
    container iso-igrp {
      description
        "IGRP for OSI networks";
      presence "IGRP for OSI networks";
      choice area-tag-route-map-choice {
        container area-tag-route-map-container {
          leaf area-tag {
            type string;
          }
          leaf route-map {
            description
              "Route map reference";
            type string;
          }
        }
        leaf route-map {
          description
            "Route map reference";
          type string;
        }
      }
      container iso-igrp-container {
        uses ospf-iso-igrp-redistribute-grouping;
      }
    }
    container lisp {
      description
        "Locator ID Separation Protocol (LISP)";
      uses ospf-redistribute-grouping;
    }
    container mobile {
      description
        "Mobile routes";
      presence "Mobile routes";
      uses ospf-redistribute-grouping;
    }
    container odr {
      description
        "On Demand stub Routes";
      presence "On Demand stub Routes";
      uses ospf-redistribute-grouping;
    }
    list ospf {
      description
        "Open Shortest Path First (OSPF)";
      key "id";
      leaf id {
        type uint32 {
          range "1 .. 65535";
        }
      }
      uses ospf-redistribute-top-match-grouping;
      uses ospf-redistribute-match-grouping;
      leaf vrf {
        description
          "VPN Routing/Forwarding Instance";
        type string;
      }
    }
    list ospfv3 {
      description
        "OSPFv3";
      key "id";
      leaf id {
        type uint32 {
          range "1 .. 65535";
        }
      }
      uses ospf-redistribute-top-match-grouping;
      uses ospf-redistribute-match-grouping;
    }
    list rip {
      description
        "Routing Information Protocol (RIP)";
      key "id";
      leaf id {
        description
          "User selected string identifying this rip process";
        type string;
      }
      uses ospf-redistribute-grouping;
    }
    container static {
      description
        "Static routes";
      presence "Static routes";
      uses ospf-redistribute-grouping;
    }
  }

  grouping ospf-redistribute-bgp-grouping {
    leaf as-number {
      type ios-types:bgp-as-number-type;
    }
    uses ospf-redistribute-grouping;
  }

  grouping router-snmp-grouping {
    container snmp {
      description
        "Modify snmp parameters";
      list context {
        description
          "Configure a SNMP context";
        key "name";
        leaf name {
          description
            "Context Name";
          type string;
        }
        container community {
          description
            "Configure a SNMP v2c Community string and access privs";
          leaf community-string {
            type string;
          }
          container access {
            leaf standard-acl {
              type uint32 {
                range "1..99";
              }
            }
            leaf expanded-acl {
              type uint32 {
                range "1300..1999";
              }
            }
            leaf acl-name {
              type string;
            }
            leaf ipv6 {
              description
                "Specify IPv6 Named Access-List";
              type string;
            }
            leaf ro {
              description
                "Read-only access with this community string";
              type empty;
            }
            leaf rw {
              description
                "Read-write access with this community string";
              type empty;
            }
          }
        }
        container user {
          description
            "Configure a SNMP v3 user";
          leaf name {
            type string;
          }
          container permisssion {
            container access {
              description
                "specify an access-list associated with this group";
              leaf standard-acl {
                type uint32;
              }
              leaf acl-name {
                type string;
              }
              leaf ipv6 {
                type string;
              }
            }
            container auth {
              description
                "authentication parameters for the user";
              leaf md5 {
                description
                  "Use HMAC MD5 algorithm for authentication";
                type string;
              }
              leaf sha {
                description
                  "Use HMAC SHA algorithm for authentication";
                type string;
              }
            }
            leaf credential {
              description
                "If the user password is already configured and saved";
              type empty;
            }
            leaf encrypted {
              description
                "specifying passwords as MD5 or SHA digests";
              type empty;
            }
          }
        }
      }
    }
  }

  grouping ospf-address-family-grouping {
    uses router-snmp-grouping;
    container topology {
      description
        "Associate the routing protocol to a topology instance";
      leaf name {
        type string;
      }
      leaf tid {
        description
          "Configuring the routing protocol topology tid";
        type uint32 {
          range "32..127";
        }
      }
    }
  }

  grouping config-router-ospf-grouping {
    list ospf { //69000
      description
        "Open Shortest Path First (OSPF)";
      key "id";
      leaf id {
        type uint16 {
          range "1..65535";
        }
      }

      // router ospf * / vrf *
      leaf vrf {
        description
          "VPN Routing/Forwarding Instance";
        type string;
      }

      // router ospf * / address-family
      container address-family {
        description
          "Enter Address Family command mode";
        container ipv4_1 {
          container ipv4 {
            description
              "Address family";
            uses ospf-address-family-grouping;
          }
        }

        container ipv4 {
          description
            "Address family";
          container unicast {
            description
              "Address Family Modifier";
            uses ospf-address-family-grouping;
          }
          container multicast {
            description
              "Address Family Modifier";
            uses ospf-address-family-grouping;
          }
        }
      }

      uses ospf-ospfv3-common-grouping;
      uses ospf-ospfv3-common-address-family-grouping;
      uses distribute-list-grouping;
      container domain-id {
        description
          "OSPF domain-id";
        choice domain-id-choice {
          leaf ip-format {
            type inet:ipv4-address;
          }
          container ip-format-secondary {
            leaf ip {
              type inet:ipv4-address;
            }
            leaf secondary {
              description
                "Secondary Domain-ID";
              type empty;
            }
          }
          leaf Null {
            description
              "Null Domain-ID";
            type empty;
          }
          container type {
            description
              "OSPF domain ID type in Hex format";
            leaf type-leaf {
              type enumeration {
                enum "0005";
                enum "0105";
                enum "0205";
                enum "8005";
              }
            }
            leaf value {
              description
                "OSPF domain ID value in Hex format";
              type string {
                pattern "[0-9a-fA-F]{12}";
              }
            }
          }
        }
      }
      leaf domain-tag {
        description
          "OSPF domain-tag";
        type uint32 {
          range "1 .. 4294967295";
        }
      }
      container fast-reroute {
        description
          "LFA FastReroute parameters";
        leaf keep-all-paths {
          description
            "Keep LFA FRR audit trail";
          type empty;
        }
        container per-prefix {
          description
            "Per-prefix LFA FRR parameters";
          container enable {
            description
              "Enable LFA Fast Reroute";
            leaf area {
              description
                "Area to enable LFA FRR in";
              type ios-types:ospf-area-type;
            }
            leaf prefix-priority {
              description
                "Priority of prefixes to be protected";
              type enumeration {
                enum "high";
                enum "low";
              }
            }
          }
          container remote-lfa {
            description
              "Remote LFA FastReroute parameters";
            container area-cost {
              leaf area {
                description
                  "Area for remote LFA command";
                type ios-types:ospf-area-type;
              }
              leaf maximum-cost {
                description
                  "Maximum distance to tunnel endpoint";
                type uint32 {
                  range "1..16777214";
                }
              }  
            }
            container area-tunnel {
              leaf area {
                description
                  "Area for remote LFA command";
                type ios-types:ospf-area-type;
              }
              leaf tunnel {
                description
                  "Remote LFA tunnel type";
                type enumeration {
                  enum "mpls-ldp";
                }
              }
            }
            leaf maximum-cost {
              description
                "Maximum distance to tunnel endpoint";
              type uint32 {
                range "1..16777214";
              }
            }
            leaf tunnel {
              description
                "Remote LFA tunnel type";
              type enumeration {
                enum "mpls-ldp";
              }
            }
          }
          container tie-break {
            description
              "LFA FRR repair path selection policy tiebreaks";
            container broadcast-interface-disjoint {
              description
                "Interface protection attribute";
              uses tie-break-index;
            }
            container downstream {
              description
                "Downstream repair path attribute";
              uses tie-break-index;
            }
            container linecard-disjoint {
              description
                "Line card protection attribute";
              uses tie-break-index;
            }
            container lowest-metric {
              description
                "Lowest metric repair path attribute";
              uses tie-break-index;
            }
            container node-protecting {
              description
                "Node protecting repair path attribute";
              uses tie-break-index;
            }
            container primary-path {
              description
                "Equal cost multipath attribute";
              uses tie-break-index;
            }
            container secondary-path {
              description
                "Not-equal cost multipath attribute";
              uses tie-break-index;
            }
            container srlg {
              description
                "Shared risk link group attribute";
              uses tie-break-index;
            }
          }
        }
      }
      container graceful-restart {
        presence "true";
        description
          "Graceful-restart options";
        leaf disable {
          description
            "Graceful restart disable";
          type empty;
        }
        container helper {
          description
            "helper support";
          presence "true";
          leaf disable {
            description
              "disable helper support";
            type empty;
          }
          leaf strict-lsa-checking {
            description
              "enable helper strict LSA checking";
            type empty;
          }
        }
        leaf restart-interval {
          description
            "Graceful restart interval";
          type uint16;
        }
      }
      container ignore {
        description
          "Do not complain about specific event";
        container lsa {
          description
            "Do not complain upon receiving LSA of the specified type";
          leaf mospf {
            description
              "MOSPF Type 6 LSA";
            type empty;
          }
        }
      }
      leaf ispf {
        description
          "Enable incremental SPF computation";
        type empty;
      }
      container limit {
        description
          "Limit a specific OSPF feature";
        container retransmissions {
          description
            "LS update, DBD, and LS request retransmissions";
          leaf non-dc {
            description
              "Non-demand-circuit retransmissions";
            type ios-types:limit-dc-non-dc-type;
          }
          leaf dc {
            description
              "Demand circuit retransmissions";
            type ios-types:limit-dc-non-dc-type;
          }
        }
      }
      container local-rib-criteria {
        description
          "Enable or disable usage of local RIB as route criteria";
        leaf forwarding-address {
          description
            "Local RIB used to validate external/NSSA forwarding addresses";
          type empty;
        }
        leaf inter-area-summary {
          description
            "Local RIB used as criteria for inter-area summaries";
          type empty;
        }
        leaf nssa-translation {
          description
            "Local RIB used as criteria for NSSA translation";
          type empty;
        }
      }
      container microloop {
        description
          "Traffic microloop control parameters";
        container avoidance {
          description
            "Traffic microloop avoidance parameters";
          presence "true";
          leaf disable {
            description
              "Microloop avoidance auto-enable prohibited";
            type empty;
          }
          leaf protected {
            description
              "Microloop avoidance for protected prefixes only";
            type empty;
          }
          leaf rib-update-delay {
            description
              "Delay before updating the RIB";
            type uint32 {
              range "1..600000";
            }
          }
        }
      }

      container mpls {
        description
          "Configure MPLS routing protocol parameters";
        container ldp {
          description
            "routing protocol commands for MPLS LDP";
          container autoconfig {
            description
              "Configure LDP automatic configuration";
            presence "Configure LDP automatic configuration";
            leaf area {
              description
                "Configure an OSPF area to run MPLS LDP";
              type ios-types:ospf-area-type;
            }
          }
          container sync {
            description
              "Configure LDP-IGP Synchronization";
            presence "Configure LDP-IGP Synchronization";
          }
        }
        container traffic-eng {
          description
            "routing protocol commands for MPLS Traffic Engineering";
          leaf multicast-intact {
            description
              "MPLS TE and PIM interaction";
            type empty;
          }
          list area {
            description
              "configure an ospf area to run MPLS Traffic Engineering";
            key "id";
            leaf id {
              description
                "OSPF area ID";
              type ios-types:ospf-area-type;
            }
          }
          container autoroute-exclude {
            description
              "MPLS TE autoroute exclude";
            leaf prefix-list {
              description
                "Filter prefixes";
              type string;
            }
          }
          list interface {
            description
              "MPLS TE interface configuration for this OSPF process";
            key "name-id";
            leaf name-id {
              description
                "Interface name and ID";
              type string;
            }
            leaf area {
              description
                "Advertise MPLS TE information for this interface into area";
              type uint32;
            }
          }
          list mesh-group {
            description
              "Traffic Engineering Mesh-Group advertisement";
            key "id area";
            leaf id {
              description
                "Mesh Group ID: <0..4294967295>";
              type uint32;
            }
            leaf area {
              description
                "configure flooding scope as area";
              type ios-types:ospf-area-type;
            }
            leaf interface {
              description
                "Interface name and ID";
              type string;
            }
          }
          container router-id {
            description
              "Traffic Engineering stable IP address for system";
            uses ios-ifc:interface-grouping;
          }
        }
      }

      list neighbor {
        description
          "Specify a neighbor router";
        key "ip";
        leaf ip {
          type inet:ipv4-address;
        }
        leaf cost {
          description
            "OSPF cost for point-to-multipoint neighbor";
          type uint32 {
            range "1 .. 65535";
          }
        }
        container database-filter {
          description
            "Filter OSPF LSA during synchronization and flooding for point-to-multipoint neighbor";
          container all {
            description
              "Filter all LSA";
            leaf out {
              description
                "Outgoing LSA";
              type empty;
            }
          }
        }
        leaf poll-interval {
          description
            "OSPF dead-router polling interval";
          type uint32 {
            range "0 .. 65535";
          }
        }
        leaf priority {
          description
            "OSPF priority of non-broadcast neighbor";
          type uint32 {
            range "0 .. 255";
          }
        }
      }
      list network {
        description
          "Enable routing on an IP network";
        key "ip mask";
        leaf ip {
          type inet:ipv4-address;
        }
        leaf mask {
          type inet:ipv4-address;
        }
        leaf area {
          description
            "Set the OSPF area ID";
          type ios-types:ospf-area-type;
        }
      }
      container nsf {
        description
          "Non-stop forwarding";
        presence "true";
        container cisco {
          description
            "Cisco Non-stop forwarding";
          presence "true";
          container enforce {
            description
              "Cancel NSF restart when non-NSF-aware neighbors detected";
            leaf global {
              description
                "For the whole OSPF process";
              type empty;
            }
          }
          container helper {
            description
              "helper support";
            presence "helper support";
            leaf disable {
              description
                "disable helper support";
              type empty;
            }
          }
        }
        container ietf {
          description
            "IETF graceful restart";
          presence "true";
          container helper {
            description
              "helper support";
            presence "helper support";
            leaf disable {
              description
                "disable helper support";
              type empty;
            }
            leaf strict-lsa-checking {
              description
                "enable helper strict LSA checking";
              type empty;
            }
          }
          leaf restart-interval {
            description
              "Graceful restart interval";
            type uint16 {
              range "1..1800";
            }
          }
        }
      }
      container prefix-priority {
        description
          "OSPF prefix priority";
        leaf high {
          description
            "High prefix priority";
          type empty;
        }
        leaf route-map {
          description
            "Prefix priority selection by route-map";
          type string;
        }
      }
      leaf prefix-suppression {
        description
          "OSPF prefix suppression";
        type empty;
      }
      leaf priority {
        description
          "OSPF topology priority";
        type uint8 {
          range "0..127";
        }
      }
      container process-min-time {
        description
          "Percentage of quantum to be used before releasing CPU";
        leaf percent {
          description
            "percent";
          type uint32 {
            range "1 .. 100";
          }
        }
      }
      leaf shutdown {
        description
          "Shutdown the OSPF protocol under the current instance";
        type boolean;
      }
      uses router-snmp-grouping;
      list summary-address {
        description
          "Configure IP address summaries";
        key "ip wildcard";
        leaf ip {
          type inet:ipv4-address;
        }
        leaf wildcard {
          type inet:ipv4-address;
        }
        choice tag-no-advertise-choice {
          leaf nssa-only {
            description
              "Limit summary to NSSA areas";
            type empty;
          }
          leaf tag {
            description
              "Set tag";
            type uint32 {
              range "0 .. 4294967295";
            }
          }
          leaf not-advertise {
            description
              "Do not advertise when translating OSPF type-7 LSA";
            type empty;
          }
        }
      }
    }
  }

  /////////////////////////////////////////////////////////
  // native / router / ospf
  /////////////////////////////////////////////////////////
  augment "/ios:native/ios:router" {
    uses config-router-ospf-grouping;
  }

  /////////////////////////////////////////////////////////
  // native / interface * / ip
  /////////////////////////////////////////////////////////
  augment "/ios:native/ios:interface/ios:FastEthernet/ios:ip" {
    uses config-interface-ip-ospf-grouping;
  }

  augment "/ios:native/ios:interface/ios:GigabitEthernet/ios:ip" {
    uses config-interface-ip-ospf-grouping;
  }

  augment "/ios:native/ios:interface/ios:TenGigabitEthernet/ios:ip" {
    uses config-interface-ip-ospf-grouping;
  }

  augment "/ios:native/ios:interface/ios:FiveGigabitEthernet/ios:ip" {
    uses config-interface-ip-ospf-grouping;
  }

  augment "/ios:native/ios:interface/ios:TwentyFiveGigabitEthernet/ios:ip" {
    uses config-interface-ip-ospf-grouping;
  }

  augment "/ios:native/ios:interface/ios:Port-channel/ios:ip" {
    uses config-interface-ip-ospf-grouping;
  }

  augment "/ios:native/ios:interface/ios:Loopback/ios:ip" {
    uses config-interface-ip-ospf-grouping;
  }

  augment "/ios:native/ios:interface/ios:Tunnel/ios:ip" {
    uses config-interface-ip-ospf-grouping;
  }

  augment "/ios:native/ios:interface/ios:BDI/ios:ip" {
    uses config-interface-ip-ospf-grouping;
  }

  /////////////////////////////////////////////////////////
  // native / interface * / ipv6
  /////////////////////////////////////////////////////////
  augment "/ios:native/ios:interface/ios:FastEthernet/ios:ipv6" {
    uses config-interface-ipv6-ospf-grouping;
  }

  augment "/ios:native/ios:interface/ios:GigabitEthernet/ios:ipv6" {
    uses config-interface-ipv6-ospf-grouping;
  }

  augment "/ios:native/ios:interface/ios:TenGigabitEthernet/ios:ipv6" {
    uses config-interface-ipv6-ospf-grouping;
  }

  augment "/ios:native/ios:interface/ios:FiveGigabitEthernet/ios:ipv6" {
    uses config-interface-ipv6-ospf-grouping;
  }

  augment "/ios:native/ios:interface/ios:TwentyFiveGigabitEthernet/ios:ipv6" {
    uses config-interface-ipv6-ospf-grouping;
  }

  augment "/ios:native/ios:interface/ios:Port-channel/ios:ipv6" {
    uses config-interface-ipv6-ospf-grouping;
  }

  augment "/ios:native/ios:interface/ios:Loopback/ios:ipv6" {
    uses config-interface-ipv6-ospf-grouping;
  }

  augment "/ios:native/ios:interface/ios:Tunnel/ios:ipv6" {
    uses config-interface-ipv6-ospf-grouping;
  }
}
