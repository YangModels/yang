module tailf-yang-patch {
  yang-version 1.1;
  namespace "http://tail-f.com/ns/tailf-yang-patch";
  prefix tfypatch;

  // Export to the same interfaces as tailf-rollback, since it is
  // imported there. This is for get-schema to work on all imports
  // by all exported modules.
  tailf:export rest;
  tailf:export netconf;
  tailf:export maapi;

  import tailf-common {
    prefix tailf;
  }

  import ietf-yang-patch {
    prefix ypatch;
  }

  description
    "This module uses the ypatch:yang-patch-status grouping in order to
     populate the yang-patch-status payload. When the payload is emitted
     the internal namespace is replaced with the standard namespace.

     This is done because ietf-yang-patch has no data nodes, and thus
     can't hold any data. This has worked historically because
     conformance was implement. Changing conformance to import (which is
     correct since the model doesn't have any data nodes) breaks the
     historic implementation.

     Copyright 2022-2023 Cisco Systems, Inc.
     All rights reserved.
     Permission is hereby granted to redistribute this file without
     modification.";

  revision 2023-01-17 {
    description
      "Released as part of ConfD-8.0.2 / NCS-6.0.2.

       Initial release.";
  }

  tailf:structure ypstatus {
    uses ypatch:yang-patch-status;
  }
}
