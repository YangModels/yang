module cisco-evpn-service {
  yang-version 1.1;
  namespace "http://cisco.com/yang/evpn/cisco-evpn-service";
  prefix cisco-evpn-service;

  import ietf-inet-types {
    prefix inet;
  }
  import Cisco-IOS-XE-types {
    prefix ios-types;
  }

  organization
    "Cisco Systems, Inc.";
  contact
    "Cisco Systems, Inc.
     Customer Service
     Postal: 170 W Tasman Drive
     San Jose, CA 95134
     Tel: +1 1800 553-NETS
     E-mail: cs-yang@cisco.com";
  description
    "This module defines the top level model for evpn service deployment.
     Copyright (c) 2021 by Cisco Systems, Inc.
     All rights reserved.";

  revision 2022-03-01 {
    description
      "Added containers for all lists that were not in containers.
       Added mapping of all BGP AF l2vpn evpn neighbors as DIY model peers.
       Changed mapping for DAG and CGW modes.
       Added evi-id leaf for returning the evi id which may be different from vlan number.
       Added dhcp relay configurations per l2-instance";
  }

  grouping evpn-global {
    description
      "Configuration properties for evpn Fabric";
    container global-configs {
      container peer-config {
        list bgp {
          key "bgp-local-as";
          leaf bgp-local-as {
            type uint32;
            description
              "bgp as number";
          }
          leaf router-id {
            type inet:ipv4-address;
            description
              "bgp router-id";
          }
          leaf enable-evpn {
            type boolean;
            description
              "Enable EVPN BGP";
          }
          leaf enable-trm {
            type boolean;
            description
              "Enable BGP multicast control plane";
          }
          leaf control-node {
            type boolean;
            description
              "node acts as a control plane node";
          }
          container peers {
            description
              "List of peer border and/or control plane node loopback addresses";
            list peer {
              key "loopback-id";
              leaf loopback-id {
                type inet:ip-address;
                description
                  "IP address of the peer loopback address";
              }
              leaf loopback-source {
                type uint32;
                description
                  "Loopback interface identifier";
              }
              leaf control-node {
                type boolean;
                description
                  "node acts as a control plane node";
              }
              leaf border-node {
                type boolean;
                description
                  "node acts as a border node";
              }
              leaf edge-node {
                type boolean;
                description
                  "node acts as an edge node";
              }
            }
          }
          container l3-vpn-neighbors {
            container vpnv4-neighbors {
              list l3-vpnv4-neighbor {
                description
                  "l3 VPN neighbors";
                key "ipv4-neighbor";
                leaf ipv4-neighbor {
                  type inet:ipv4-address;
                  description
                    "IP address of the connected router interface (neighbor)";
                }
                leaf remote-as {
                  type uint32;
                  description
                    "as number for remote connected network";
                }
                leaf loopback-source {
                  type uint32;
                  description
                    "Loopback interface identifier";
                }
              }
            }
            container vpnv6-neighbors {
              list l3-vpnv6-neighbor {
                description
                  "l3 VPN neighbors";
                key "ipv6-neighbor";
                leaf ipv6-neighbor {
                  type inet:ipv4-address;
                  description
                    "IP address of the connected router interface (neighbor)";
                }
                leaf remote-as {
                  type uint32;
                  description
                    "as number for remote connected network";
                }
                leaf loopback-source {
                  type uint32;
                  description
                    "Loopback interface identifier";
                }
              }
            }
          }
        }
      }
      leaf loopback-id {
        type uint32;
        description
          "Loopback interface identifier";
      }
      leaf loopback-ip {
        type inet:ipv4-address;
        description
          "Loopback interface address";
      }
      container dot1x-interfaces {
        list interface {
          key "id";
          leaf id {
            type string;
            description
              "Name of the interface, e.g. GigabitEthernet1/0/1";
          }
          leaf auth-mode {
            type enumeration {
              enum closed1XMAB {
                value 0;
                description
                  "closed auth";
              }
              enum closedMAB1X {
                value 1;
                description
                  "closed auth";
              }
              enum open1XMAB {
                value 2;
                description
                  "open auth";
              }
              enum openMAB1X {
                value 3;
                description
                  "open auth";
              }
              enum easy1XMAB {
                value 4;
                description
                  "easy-connect auth";
              }
              enum easyMAB1X {
                value 5;
                description
                  "easy-connect auth";
              }
            }
            mandatory true;
          }
          leaf wake-on-lan {
            type boolean;
            description
              "true if packet should be sent to wake up hosts";
          }
          leaf multi-host {
            description
              "Set the Host mode for authentication on this interface - true multiple hosts, false single host";
            type boolean;
          }
          leaf timeout {
            type uint16;
            description
              "multiplier (times 3) for time in seconds to wait before falling back to alternate configuration mode";
          }
        }
      }
      container acl-configurations {
        description
          "ACL configurations for AUTH filtering in IPV4 and IPV6";
        list acls {
          key "acl-name";
          leaf acl-name {
            type string;
            description
              "ACL Name passed by DNAC used as the ACL native model ACL name";
          }
          list contract {
            key "sequence";
            leaf sequence {
              type uint64;
              description
                "ACE sequence number controlling the order of ACE application";
            }
            leaf id {
              type string;
              description
                "ACL ACE entry name string saved in the remark filed in the ACE configuration";
            }
            leaf action {
              type enumeration {
                enum DENY;
                enum PERMIT;
              }
              description
                "ACE rule action";
              mandatory true;
            }
            leaf port {
              type enumeration {
                enum bgp {
                  value 179;
                }
                enum chargen {
                  value 19;
                }
                enum daytime {
                  value 13;
                }
                enum discard {
                  value 9;
                }
                enum domain {
                  value 53;
                }
                enum echo {
                  value 7;
                }
                enum finger {
                  value 79;
                }
                enum ftp {
                  value 21;
                }
                enum ftp-data {
                  value 20;
                }
                enum gopher {
                  value 70;
                }
                enum hostname {
                  value 101;
                }
                enum ident {
                  value 113;
                }
                enum irc {
                  value 194;
                }
                enum klogin {
                  value 543;
                }
                enum kshell {
                  value 544;
                }
                enum lpd {
                  value 515;
                }
                enum msrpc {
                  value 135;
                }
                enum nntp {
                  value 119;
                }
                enum pim-auto-rp {
                  value 496;
                }
                enum pop2 {
                  value 109;
                }
                enum pop3 {
                  value 110;
                }
                enum smtp {
                  value 25;
                }
                enum sunrpc {
                  value 111;
                }
                enum tacacs {
                  value 49;
                }
                enum talk {
                  value 517;
                }
                enum telnet {
                  value 23;
                }
                enum time {
                  value 37;
                }
                enum uucp {
                  value 540;
                }
                enum whois {
                  value 43;
                }
                enum www {
                  value 80;
                }
                enum biff {
                  value 512;
                }
                enum bootpc {
                  value 68;
                }
                enum bootps {
                  value 67;
                }
                enum dnsix {
                  value 195;
                }
                enum isakmp {
                  value 500;
                }
                enum mobile-ip {
                  value 434;
                }
                enum nameserver {
                  value 42;
                }
                enum netbios-dgm {
                  value 138;
                }
                enum netbios-ns {
                  value 137;
                }
                enum netbios-ss {
                  value 139;
                }
                enum non500-isakmp {
                  value 4500;
                }
                enum ntp {
                  value 123;
                }
                enum rip {
                  value 520;
                }
                enum ripv6 {
                  value 521;
                }
                enum snmp {
                  value 161;
                }
                enum snmptrap {
                  value 162;
                }
                enum syslog {
                  value 514;
                }
                enum tftp {
                  value 69;
                }
                enum who {
                  value 513;
                }
                enum xdmcp {
                  value 177;
                }
              }
              description
                "traffic type standard port";
              mandatory true;
            }
            leaf protocol {
              type enumeration {
                enum ahp;
                enum eigrp;
                enum esp;
                enum gre;
                enum icmp;
                enum igmp;
                enum ip;
                enum ipinip;
                enum nos;
                enum object-group;
                enum ospf;
                enum pcp;
                enum pim;
                enum tcp;
                enum udp;
                enum hbh;
                enum ipv6;
                enum sctp;
              }
              description
                "protocol type";
              mandatory true;
            }
          }
        }
      }
      container dns-configuration {
        container name-server {
          list server {
            key "server-id";
            leaf server-id {
              type union {
                type inet:ipv4-address;
                type inet:ipv6-address;
              }
            }
          }
        }
        leaf domain-name {
          type string;
          description
            "default domain name";
        }
      }
      container dhcp-relay {
        description
          "global dhcp relay configurations";
        leaf source-interface {
          type uint32;
          description
            "Loopback interface identifier";
        }
        leaf vrf-name {
          type string;
          description
            "vrf forwarding name";
        }
        leaf ipv4-dhcp-helper {
          type inet:ipv4-address;
          description
            "V4 dhcp helper address";
        }
        leaf ipv6-dhcp-relay {
          type inet:ipv6-prefix;
          description
            "V6 dhcp relay address";
        }
      }
    }
  }

  grouping evpn-l3-instances {
    container l3-instances {
      list l3-instance {
        description
          "evpn instance identifier";
        key "id";
        leaf id {
          type uint32;
          description
            "Number used for l3 instance identifier";
        }
        leaf vrf-name {
          type string;
          mandatory true;
          description
            "The vrf name provided by user.";
        }
        leaf evpn-extension {
          type boolean;
          description
            "True if bgp address-family ipv4 vrf 'vrf-name' includes advertise l2vpn evpn";
        }
        leaf enable-trm {
          type enumeration {
            enum trm-none {
              value 0;
              description
                "disable tenant multicast";
            }
            enum trm-dist-anycast {
              value 1;
              description
                "distributed-anycast rp placement";
            }
            enum trm-external-rp {
              value 2;
              description
                "external rp placement";
            }
          }
        }
        leaf core-vlan-id {
          type uint16;
          description
            "VLAN ID l3vni core SVI";
        }
        leaf mcast-group {
          type inet:ipv4-address;
          description
            "multicast group address";
        }
        leaf rp-address {
          type inet:ipv4-address;
          description
            "RP ip address";
        }
        leaf rp-is-local {
          type boolean;
          description
            "rp is local";
        }
        leaf route-distinquisher {
          type ios-types:asn-ip-type;
          mandatory true;
          description
            "RD for this l3-instance";
        }
        container rt-imports {
          list rt-import {
            description
              "list of rt-imports for this l3-instance";
            key "id";
            leaf id {
              type ios-types:asn-ip-type;
              description
                "rt import e.g. route-target import 300:5555 stitching where 300:5555 is the id";
            }
          }
        }
        container rt-exports {
          list rt-export {
            description
              "list of rt-exports for this l3-instance";
            key "id";
            leaf id {
              type ios-types:asn-ip-type;
              description
                "rt export e.g. route-target export 300:5555 stitching where 300:5555 is the id";
            }
          }
        }
        container rt-imports-v6 {
          list rt-import {
            description
              "list of rt-imports for this l3-instance";
            key "id";
            leaf id {
              type ios-types:asn-ip-type;
              description
                "rt import e.g. route-target import 300:5555 stitching where 300:5555 is the id";
            }
          }
        }
        container rt-exports-v6 {
          list rt-export {
            description
              "list of rt-exports for this l3-instance";
            key "id";
            leaf id {
              type ios-types:asn-ip-type;
              description
                "rt export e.g. route-target export 300:5555 stitching where 300:5555 is the id";
            }
          }
        }
        container l3-vpn-ics {
          container l3-vpn-rt-imports {
            container import-ipv4 {
              description
                "ipv4 rt-imports for l3-instance";
              list l3-vpn-rt-import-ipv4 {
                description
                  "list of rt-imports for this l3-instance";
                key "id";
                leaf id {
                  type ios-types:asn-ip-type;
                  description
                    "rt import e.g. route-target import 300:5555 where 300:5555 is the id";
                }
              }
            }
            container import-ipv6 {
              description
                "ipv6 rt-imports for l3-instance";
              list l3-vpn-rt-import-ipv6 {
                description
                  "list of rt-imports for this l3-instance";
                key "id";
                leaf id {
                  type ios-types:asn-ip-type;
                  description
                    "rt import e.g. route-target import 300:5555 where 300:5555 is the id";
                }
              }
            }
          }
          container l3-vpn-rt-exports {
            container export-ipv4 {
              description
                "ipv4 rt-exports for l3-instance";
              list l3-vpn-rt-export-ipv4 {
                description
                  "list of rt-exports for this l3-instance";
                key "id";
                leaf id {
                  type ios-types:asn-ip-type;
                  description
                    "rt import e.g. route-target export 300:5555 where 300:5555 is the id";
                }
              }
            }
            container export-ipv6 {
              description
                "ipv6 rt-exports for l3-instance";
              list l3-vpn-rt-export-ipv6 {
                description
                  "list of rt-exports for this l3-instance";
                key "id";
                leaf id {
                  type ios-types:asn-ip-type;
                  description
                    "rt import e.g. route-target export 300:5555 where 300:5555 is the id";
                }
              }
            }
          }
        }
        container vrf-lite-ics {
          list vrf-lite-ic {
            description
              "vrf-lite ic interconnect";
            key "handoff-interface";
            leaf handoff-interface {
              type string;
              description
                "Main interface name for border handoff";
            }
            leaf handoff-dot1qtag {
              type string;
              description
                "dot1q tag to use to tag traffic to peering devices";
              mandatory true;
            }
            leaf local-ipv4-address {
              type inet:ipv4-address;
              description
                "ipv4 address for local interface";
            }
            leaf local-ipv4-mask {
              type inet:ipv4-address;
              description
                "ipv4 mask for local interface";
            }
            leaf local-ipv6 {
              type inet:ipv6-prefix;
              description
                "IPv6 prefix";
            }
            leaf remote-as {
              type uint32;
              description
                "as number for remote connected network";
            }
            leaf remote-ipv4 {
              type inet:ipv4-address;
              description
                "IP address of the connected router interface (neighbor)";
            }
            leaf remote-ipv6 {
              type inet:ipv6-address;
              description
                "IPv6 address of the connected router interface (neighbor) 10::2";
            }
          }
        }
        container networks {
          description
            "list of network definitions to include in bgp address-family";
          container ipv4 {
            description
              "ipv4 networks for l3-instance";
            list ipv4-network {
              description
                "list of network definitions";
              key "network mask";
              leaf network {
                type inet:ipv4-address;
                description
                  "ipv4 address for statically defined network";
              }
              leaf mask {
                type inet:ipv4-address;
                description
                  "ipv4 mask for statically defined network";
              }
            }
          }
          container ipv6 {
            description
              "ipv6 networks for l3-instance";
            list ipv6-network {
              description
                "list of network definitions";
              key "prefix";
              leaf prefix {
                type ios-types:ipv6-prefix;
                description
                  "ipv6 prefix for statically defined network";
              }
            }
          }
        }
        container default-routes {
          description
            "optional default route for vrf";
          list default-route {
            description
              "list of default routes for l3-instance";
            key "prefix mask";
            leaf prefix {
              type inet:ipv4-address;
              description
                "IPv4 address";
            }
            leaf mask {
              type inet:ipv4-address;
              description
                "IPv4 mask";
            }
            list destination {
              description
                "default route destination";
              key "address";
              leaf address {
                type inet:ipv4-address;
                description
                  "IPv4 default route";
              }
            }
          }
        }
      }
    }
  }

  grouping evpn-l2-instances {
    container l2-instances {
      list l2-instance {
        description
          "evpn instance identifier";
        key "id";
        leaf id {
          type uint32;
          description
            "Number used for the evpn instance and vlan";
        }
        leaf evi-id {
          type uint32;
          description
            "If evpn instance id is different from id (vlan number) in DIY configurations";
        }
        leaf vrf-name {
          type string;
          description
            "The vrf name provided by user.";
          mandatory true;
        }
        leaf vlan-name {
          type string;
          description
            "The vlan name provided by user.";
          default "none";
        }
        leaf vni-id {
          type uint32;
          description
            "VNI number used for l2 instance";
          mandatory true;
        }
        leaf evpn-extension {
          type boolean;
          description
            "True if evpn configuration extensions applied to l2-instances";
        }
        leaf irb-gw-mode {
          type enumeration {
            enum DAG {
              value 0;
              description
                "Distributed anycast gateway";
            }
            enum CGW {
              value 1;
              description
                "Centralized gateway";
            }
          }
          description
            "DAG for distributed anycast gateway, CGW for centralized gateway";
        }
        leaf suppression {
          type boolean;
          description
            "suppress flooding for address resolution state";
        }
        leaf mac-address {
          type string;
          description
            "mac-address for the vlan defined for the l2-instance";
        }
        leaf ipv4-address {
          type inet:ipv4-address;
          description
            "IPv4 address subnet for L2 VNI use";
        }
        leaf ipv4-mask {
          type inet:ipv4-address;
          description
            "IPv4 address subnet mask for L2 VNI use";
        }
        leaf ipv6-prefix {
          type inet:ipv6-prefix;
          description
            "IPv6 address subnet for L2 VNI use";
        }
        leaf route-distinguisher {
          type ios-types:asn-ip-type;
          description
            "rt import";
        }
        container route-target {
          container import {
            description
              "rt-import for this l2-instance";
            leaf rt-value {
              type ios-types:asn-ip-type;
              description
                "rt import";
            }
          }
          container export {
            description
              "rt-export for this l2-instance";
            leaf rt-value {
              type ios-types:asn-ip-type;
              description
                "rt export";
            }
          }
        }
        leaf unicast-replication {
          type boolean;
          description
            "True enables unicast replication for the evpn control plane";
        }
        leaf mcast-group {
          type inet:ipv4-address;
          description
            "Multicast group address for replication";
        }
        container dhcp-relay {
          description
            "l2-instance dhcp relay configurations";
          leaf ipv4-dhcp-helper {
            type inet:ipv4-address;
            description
              "V4 dhcp helper address";
          }
          leaf ipv6-dhcp-relay {
            type inet:ipv6-address;
            description
              "V6 dhcp relay address";
          }
          leaf ipv4-dhcp-global {
            type inet:ipv4-address;
            description
              "V4 dhcp helper global address";
          }
          leaf ipv6-dhcp-global {
            type inet:ipv6-address;
            description
              "V6 dhcp relay global address";
          }
        }
        container access-interfaces {
          list access-interface {
            key "id";
            leaf id {
              type string;
              description
                "Name of the access interface, e.g. GigabitEthernet1/0/1";
            }
            leaf ap-access-node {
              type boolean;
              description
                "true if AP is connected to access-node";
            }
          }
        }
        container trunk-interfaces {
          list trunk-interface {
            key "id";
            leaf id {
              type string;
              description
                "Name of trunk interface, e.g. GigabitEthernet1/0/1";
            }
          }
        }
      }
    }
  }

  grouping evpn-config {
    description
      "Top-level grouping for evpn configuration.";
    container evpn-config {
      description
        "Top container for evpn configuration.";
      uses evpn-global;
      uses evpn-l3-instances;
      uses evpn-l2-instances;
    }
  }

  grouping evpn-top {
    description
      "Top-level grouping for evpn model.";
    container evpn-service {
      description
        "Top most container for evpn management.";
      uses evpn-config;
    }
  }

  uses evpn-top;
}
