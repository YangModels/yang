module Cisco-IOS-XE-wireless-client-global-oper {
  yang-version 1.1;
  namespace "http://cisco.com/ns/yang/Cisco-IOS-XE-wireless-client-global-oper";
  prefix wireless-client-global-oper;

  import Cisco-IOS-XE-common-types {
    prefix common-types-ios-xe;
  }
  import Cisco-IOS-XE-wireless-client-types {
    prefix wireless-client-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains client operational data aggregated across wireless processes.
     Copyright (c) 2022-2023 by Cisco Systems, Inc.
     All rights reserved.";

  revision 2024-03-01 {
    description
      "- Added client list details per AP";
    reference
      "1.6.0";
    cisco-semver:module-version "1.6.0";
  }
  revision 2023-11-01 {
    description
      "- Added total layer 3 access client counts
       - Added information for WLAN-VRF mappings";
    reference
      "1.5.0";
    cisco-semver:module-version "1.5.0";
  }
  revision 2023-03-01 {
    description
      "- Deprecated most-ms-entries, total-ms-entries, total-ipv4-ms-entries and cur-wgb-entries leaves
       - Deprecating the number of sleeping clients from webauth stats
       - Deprecated container identity PSK tagged clients, since this data is present in client oper yang model";
    reference
      "1.4.0";
    cisco-semver:module-version "1.4.0";
  }
  revision 2022-11-01 {
    description
      "- Update yang-version to 1.1
       - Added device classification and its statistics";
    reference
      "1.3.0";
    cisco-semver:module-version "1.3.0";
  }
  revision 2022-03-01 {
    description
      "- Added clients 802.11 statistics
       - Added statistics information for client latency, web authentication session management, wlan sort, AP sort and Identity PSK tag clients";
    reference
      "1.2.0";
    cisco-semver:module-version "1.2.0";
  }
  revision 2021-11-01 {
    description
      "- Added statistics information for clients 802.1x,
         clients exclusion and wireless trace statistics";
    reference
      "1.1.0";
    cisco-semver:module-version "1.1.0";
  }
  revision 2021-07-01 {
    description
      "Initial revision";
    reference
      "1.0.0";
    cisco-semver:module-version "1.0.0";
  }

  grouping client-statistics {
    description
      "Client statistics";
    container co-client-del-reason {
      description
        "Client delete reason statistics";
      uses wireless-client-types:co-delete-reason;
    }
  }

  grouping st-client-assoc-stats {
    description
      "Clients association statistics";
    leaf total-attempt {
      type uint32;
      description
        "Total association attempts";
    }
    leaf total-fail {
      type uint32;
      description
        "Total association failures";
    }
    leaf total-resp-accept {
      type uint32;
      description
        "Total association response accepts";
    }
    leaf total-resp-reject {
      type uint32;
      description
        "Total association response rejects";
    }
    leaf total-resp-error {
      type uint32;
      description
        "Total association response errors";
    }
  }

  grouping st-client-dms-stats {
    description
      "Client DMS statistics";
    leaf action-frame-req {
      type uint32;
      description
        "Total DMS requests received in action frame";
    }
    leaf action-frame-resp {
      type uint32;
      description
        "Total DMS responses sent in action frame";
    }
    leaf reassoc-req {
      type uint32;
      description
        "Total DMS requests received in Re-assoc Request";
    }
  }

  grouping st-client-roaming-stats {
    description
      "Client roaming attempt statistics";
    leaf total-roam {
      type uint32;
      description
        "Total roam attempts";
    }
    leaf cckm-roam {
      type uint32;
      description
        "Total CCKM roam attempts";
    }
    leaf dot11r-roam {
      type uint32;
      description
        "Total 802.11r roam attempts";
    }
    leaf dot11i-fast-roam {
      type uint32;
      description
        "Total 802.11i fast roam attempts";
    }
    leaf dot11i-slow-roam {
      type uint32;
      description
        "Total 802.11i slow roam attempts";
    }
    leaf roam-fail {
      type uint32;
      description
        "Total roam failures in 802.11";
    }
    leaf ap-auth-roams {
      type uint32;
      description
        "Total Flexconnect AP authentication roaming attempts";
    }
    leaf ap-auth-dot11i-fast-roam {
      type uint32;
      description
        "Total number of 802.11i fast roam attempts at AP authentication";
    }
    leaf ap-auth-dot11i-slow-roam {
      type uint32;
      description
        "Total number of 802.11i slow roam attempts at AP authentication";
    }
    leaf flex-11r-roam {
      type uint32;
      description
        "Total 802.11r Flex roaming attempts";
    }
    leaf dot11r-slow-roam {
      type uint32;
      description
        "Total 802.11r slow roaming attempts";
    }
    leaf pmkr0-name-mismatch {
      type uint32;
      description
        "Total 802.11r pairwise master key R0 name mismatch";
    }
    leaf pmkr1-name-mismatch {
      type uint32;
      description
        "Total 802.11r pairwise master key R1 name mismatch";
    }
  }

  grouping st-load-balance-stats {
    description
      "Load balance statistics";
    leaf total-denied {
      type uint32;
      description
        "Load balancing total denied counts";
    }
    leaf total-denied-sent {
      type uint32;
      description
        "Load balancing total denial sent (messages)";
    }
    leaf total-ex-max-denial {
      type uint32;
      description
        "Load balancing exceeded denial maximum limit counts";
    }
    leaf cand-5g {
      type uint32;
      description
        "APs that are not 5GHz candidates for service set transition";
    }
    leaf cand-24g {
      type uint32;
      description
        "APs that are not 2.4GHz candidates for service set transition";
    }
  }

  grouping st-client-dot11r-ft-stats {
    description
      "Clients 802.11r FT statistics";
    leaf total-auth-req-rx {
      type uint32;
      description
        "Total 802.11r FT authentication requests received";
    }
    leaf total-auth-resp-success {
      type uint32;
      description
        "Total 802.11r FT authentication response success";
    }
    leaf total-auth-resp-fail {
      type uint32;
      description
        "Total 802.11r FT authentication response failures";
    }
    leaf total-action-req-rx {
      type uint32;
      description
        "Total 802.11r FT action requests received";
    }
    leaf total-action-resp-success {
      type uint32;
      description
        "Total 802.11r FT action response success";
    }
    leaf total-action-resp-fail {
      type uint32;
      description
        "Total 802.11r FT action response failures";
    }
  }

  grouping st-wpa3-sae-stats {
    description
      "WPA3 SAE statistics";
    leaf attempts {
      type uint32;
      description
        "Total WPA3 SAE attempts";
    }
    leaf protocol-incomplete {
      type uint32;
      description
        "Total WPA3 SAE incomplete protocol failures";
    }
    leaf commit-rx {
      type uint32;
      description
        "Total WPA3 SAE commit messages received";
    }
    leaf commit-rejected {
      type uint32;
      description
        "Total WPA3 SAE commit messages rejected";
    }
    leaf commit-unsupported-group {
      type uint32;
      description
        "Total WPA3 SAE commit unsupported group rejections";
    }
    leaf commit-sent {
      type uint32;
      description
        "Total WPA3 SAE commit messages sent";
    }
    leaf confirm-rx {
      type uint32;
      description
        "Total WPA3 SAE confirm messages received";
    }
    leaf confirm-rejected {
      type uint32;
      description
        "Total WPA3 SAE confirm messages rejected";
    }
    leaf confirm-field-mismatch {
      type uint32;
      description
        "Total WPA3 SAE message confirm field mismatch";
    }
    leaf confirm-msg-invalid-length {
      type uint32;
      description
        "Total WPA3 SAE confirm message invalid length";
    }
    leaf confirm-sent {
      type uint32;
      description
        "Total WPA3 SAE confirm messages sent";
    }
    leaf open-sessions {
      type uint32;
      description
        "Total WPA3 SAE open sessions";
    }
    leaf accepted {
      type uint32;
      description
        "Total WPA3 SAE successful authentications";
    }
    leaf h2e-commit-rx {
      type uint32;
      description
        "Total WPA3 SAE Hash to Element commit received";
    }
    leaf hnp-commit-rx {
      type uint32;
      description
        "Total WPA3 SAE Hunting and Pecking commit received";
    }
    leaf h2e-commit-pwe-mismatch {
      type uint32;
      description
        "Total password element method mismatch for SAE Hash to Element commit received";
    }
    leaf hnp-commit-pwe-mismatch {
      type uint32;
      description
        "Total password element method mismatch for SAE Hunting And Pecking commit received";
    }
  }

  grouping st-client-dot11-statistics {
    description
      "Clients 802.11 statistics";
    container client-assoc-stats {
      description
        "Client association statistics";
      uses wireless-client-global-oper:st-client-assoc-stats;
    }
    container client-dms-stats {
      description
        "Client DMS statistics";
      uses wireless-client-global-oper:st-client-dms-stats;
    }
    container client-roaming-stats {
      description
        "Client roaming attempt statistics";
      uses wireless-client-global-oper:st-client-roaming-stats;
    }
    container load-balance-stats {
      description
        "Load balance statistics";
      uses wireless-client-global-oper:st-load-balance-stats;
    }
    leaf other-roam-attempts {
      type uint32;
      description
        "Total other roam type attempts";
    }
    leaf aid-allocation-fail {
      type uint32;
      description
        "Total AID allocation failures";
    }
    leaf aid-free-fail {
      type uint32;
      description
        "Total AID free failures";
    }
    container client-dot11r-ft-stats {
      description
        "Clients 802.11r FT statistics";
      uses wireless-client-global-oper:st-client-dot11r-ft-stats;
    }
    leaf num-clients-on-24ghz-radio {
      type uint32;
      description
        "Total number of clients on 2.4Ghz";
    }
    leaf num-clients-on-5ghz-radio {
      type uint32;
      description
        "Total number of clients on 5Ghz";
    }
    container wpa3-sae-stats {
      description
        "WPA3 SAE statistics";
      uses wireless-client-global-oper:st-wpa3-sae-stats;
    }
    leaf mdid-mismatch {
      type uint32;
      description
        "Total 802.11r mobility domain identifier mismatch";
    }
    leaf wifi-direct-assoc-fail {
      type uint32;
      description
        "Total WiFi direct association rejects";
    }
    leaf wifi-direct-assoc-success {
      type uint32;
      description
        "Total WiFi direct association success";
    }
    leaf num-6ghz-clients {
      type uint32;
      description
        "Total number of clients in 6GHz";
    }
  }

  grouping st-client-state-stats-data {
    description
      "Statistics of number of clients in each state";
    leaf avg-client-state-duration {
      type uint64;
      description
        "Average duration in the state";
    }
    leaf total-sessions {
      type uint64;
      description
        "Total number of sessions in the state";
    }
  }

  grouping st-client-state-stats {
    description
      "All states client statistics";
    list client-state-stats-value {
      max-elements 14;
      description
        "All states client statistics";
      uses wireless-client-global-oper:st-client-state-stats-data;
    }
  }

  grouping client-avg-run-state-latency {
    description
      "Average run state latency statistics";
    leaf run-state {
      type uint32;
      description
        "Average run state latency";
    }
    leaf run-state-sans-user-delay {
      type uint32;
      description
        "Average run state latency without user delay";
    }
  }

  grouping client-latency-stats {
    description
      "Client run state latency statistics";
    container client-states-stats {
      description
        "Client states statistics";
      uses wireless-client-global-oper:st-client-state-stats;
    }
    container avg-run-state-latency {
      description
        "Average run state latency statistics";
      uses wireless-client-global-oper:client-avg-run-state-latency;
    }
  }

  grouping client-live-stats {
    description
      "Statistics of clients/mobile stations current state";
    leaf auth-state-clients {
      type uint32;
      description
        "Number of clients in authenticating state";
    }
    leaf mobility-state-clients {
      type uint32;
      description
        "Number of clients in mobility state";
    }
    leaf iplearn-state-clients {
      type uint32;
      description
        "Number of clients in IP learn state";
    }
    leaf webauth-state-clients {
      type uint32;
      description
        "Number of clients in web authenticating state";
    }
    leaf run-state-clients {
      type uint32;
      description
        "Number of clients in run state";
    }
    leaf delete-state-clients {
      type uint32;
      description
        "Number of clients in deletion state";
    }
    leaf random-mac-clients {
      type uint32;
      description
        "Number of clients using random MAC address";
    }
    leaf l3-access-clients {
      type uint32;
      description
        "Number of Layer 3 access clients";
    }
  }

  grouping ewlc-client-session-stats {
    description
      "Client session statistics";
    leaf most-ms-entries {
      type uint32;
      status deprecated;
      description
        "Most clients entries";
    }
    leaf cur-ms-entries {
      type uint32;
      description
        "Current clients entries";
    }
    leaf total-ms-entries {
      type uint32;
      status deprecated;
      description
        "Total clients entries";
    }
    leaf total-ipv4-ms-entries {
      type uint32;
      status deprecated;
      description
        "Total ipv4 clients entries";
    }
    leaf cur-wgb-entries {
      type uint32;
      status deprecated;
      description
        "Current WGB entries";
    }
    leaf cur-foreign-entries {
      type uint32;
      description
        "Foreign clients entries";
    }
    leaf cur-anchor-entries {
      type uint32;
      description
        "Anchor clients entries";
    }
    leaf cur-local-entries {
      type uint32;
      description
        "Local clients entries";
    }
    leaf cur-idle-state-entries {
      type uint32;
      description
        "Idle state clients entries";
    }
  }

  grouping ewlc-client-global-stats-op {
    description
      "Client global statistics";
    container session-stats {
      description
        "Session statistics";
      uses wireless-client-global-oper:ewlc-client-session-stats;
    }
  }

  grouping rssi-sample {
    description
      "Received signal indicator stats";
    leaf rssi-value-a {
      type int8;
      description
        "RSSI value a";
    }
    leaf rssi-value-b {
      type int8;
      description
        "RSSI value b";
    }
  }

  grouping sm-dot1x-global-stats {
    description
      "Session manager 802.1x global statistics";
    leaf eapol-rx {
      type uint32;
      description
        "Total EAPoL frames received";
    }
    leaf eapol-rx-start {
      type uint32;
      description
        "Total EAPoL Start frames received";
    }
    leaf eapol-rx-logoff {
      type uint32;
      description
        "Total EAPoL Logoff frames received";
    }
    leaf eapol-rx-resp {
      type uint32;
      description
        "Total EAPoL Response frames received";
    }
    leaf eapol-rx-resp-id {
      type uint32;
      description
        "Total EAPoL Response identifier frames received";
    }
    leaf eapol-rx-req {
      type uint32;
      description
        "Total EAPoL Request frames received";
    }
    leaf eapol-rx-invalid {
      type uint32;
      description
        "Total Invalid EAPoL frames received";
    }
    leaf eapol-rx-len-error {
      type uint32;
      description
        "Total EAPoL frames with length error received";
    }
    leaf eapol-tx {
      type uint32;
      description
        "Total EAPoL frames transmitted";
    }
    leaf eapol-tx-start {
      type uint32;
      description
        "Total EAPoL Start frames transmitted";
    }
    leaf eapol-tx-logoff {
      type uint32;
      description
        "Total EAPoL Logoff frames transmitted";
    }
    leaf eapol-tx-resp {
      type uint32;
      description
        "Total EAPoL Response frames transmitted";
    }
    leaf eapol-tx-req {
      type uint32;
      description
        "Total EAPoL Request frames transmitted";
    }
    leaf eapol-retx-req {
      type uint32;
      description
        "Total EAPoL Request frames re-transmitted";
    }
    leaf eapol-retx-req-fail {
      type uint32;
      description
        "Total EAPoL Request frames re-transmitted failed";
    }
    leaf eapol-tx-req-id {
      type uint32;
      description
        "Total EAPoL Request identifier frames transmitted";
    }
    leaf eapol-retx-req-id {
      type uint32;
      description
        "Total EAPoL Request identifier frames re-transmitted";
    }
    leaf eapol-retx-req-id-fail {
      type uint32;
      description
        "Total EAPoL Request identifier frames re-transmitted fail";
    }
  }

  grouping http-new-req-stats {
    description
      "HTTP new request statistics";
    leaf new-req-no-session-error {
      type uint32;
      description
        "HTTP socket new request no session error";
    }
    leaf new-req-ctx-exists-error {
      type uint32;
      description
        "HTTP socket new request context exist error";
    }
  }

  grouping st-ssl-stats {
    description
      "SSL event statistics";
    leaf event-read-block-count {
      type uint32;
      description
        "SSL socket event read block count";
    }
    leaf event-write-block-count {
      type uint32;
      description
        "SSL socket event write block count";
    }
    leaf event-ok-count {
      type uint32;
      description
        "SSL socket event OK count";
    }
  }

  grouping st-sm-webauth-http-stats {
    description
      "Web-authentication HTTP statistics";
    leaf http-request-count {
      type uint32;
      description
        "HTTP request count";
    }
    leaf read-event-count {
      type uint32;
      description
        "Socket read event count";
    }
    leaf read-complete-count {
      type uint32;
      description
        "Socket read complete count";
    }
    leaf write-event-count {
      type uint32;
      description
        "Socket write event count";
    }
    leaf write-complete-count {
      type uint32;
      description
        "Socket write complete count";
    }
    leaf aaa-message-count {
      type uint32;
      description
        "AAA message count";
    }
    container ssl-event-stats {
      description
        "SSL event statistics";
      uses wireless-client-global-oper:st-ssl-stats;
    }
    container http-new-req-stats {
      description
        "HTTP new request statistics";
      uses wireless-client-global-oper:http-new-req-stats;
    }
    leaf num-of-socket-opened {
      type uint32;
      description
        "Number of sockets opened";
    }
    leaf num-of-socket-closed {
      type uint32;
      description
        "Number of sockets closed";
    }
  }

  grouping sm-webauth-duration-stats {
    description
      "Web-authentication duration statistics";
    leaf total {
      type uint32;
      description
        "Total duration in seconds";
    }
    leaf max {
      type uint32;
      description
        "Maximum duration in seconds";
    }
    leaf min {
      type uint32;
      description
        "Minimum duration in seconds";
    }
    leaf samples {
      type uint32;
      description
        "Sample count";
    }
  }

  grouping st-sm-webauth-backpressure-counters {
    description
      "Web authentication backpressure queue counters";
    leaf ssl-handshake-pending {
      type uint32;
      description
        "Pending SSL handshake count";
    }
    leaf https-new-request-pending {
      type uint32;
      description
        "Pending HTTPS requests";
    }
    leaf aaa-reply-pending {
      type uint32;
      description
        "Pending AAA replies";
    }
  }

  grouping st-sm-webauth-stats {
    description
      "Web-authentication statistics";
    container http-stats {
      description
        "HTTP statistics";
      uses wireless-client-global-oper:st-sm-webauth-http-stats;
    }
    container iom-reading {
      description
        "IOM socket reading statistics";
      uses wireless-client-global-oper:sm-webauth-duration-stats;
    }
    container method-reading {
      description
        "Method reading statistics";
      uses wireless-client-global-oper:sm-webauth-duration-stats;
    }
    container iom-writing {
      description
        "IOM socket writing statistics";
      uses wireless-client-global-oper:sm-webauth-duration-stats;
    }
    container method-writing {
      description
        "Method writing statistics";
      uses wireless-client-global-oper:sm-webauth-duration-stats;
    }
    container iom-aaa {
      description
        "IOM AAA response statistics";
      uses wireless-client-global-oper:sm-webauth-duration-stats;
    }
    container method-aaa {
      description
        "Method AAA response statistics";
      uses wireless-client-global-oper:sm-webauth-duration-stats;
    }
    leaf num-of-sleeping-clients {
      type uint32;
      status deprecated;
      description
        "Number of sleeping clients";
    }
    leaf session-count {
      type uint32;
      description
        "Session count";
    }
    leaf half-open-count {
      type uint32;
      description
        "Half open socket count";
    }
    container backpressure-counters {
      description
        "Web authentication backpressure counters";
      uses wireless-client-global-oper:st-sm-webauth-backpressure-counters;
    }
  }

  grouping st-tof {
    description
      "Wireless trace statistics";
    leaf-list tof-tag {
      type uint64;
      ordered-by user;
      description
        "Wireless trace on failure statistics";
    }
  }

  grouping st-client-exclusion-stats {
    description
      "Clients exclusion statistics";
    leaf excluded-clients {
      type uint32;
      description
        "Total excluded clients";
    }
    leaf disabled-clients {
      type uint32;
      description
        "Total disabled clients";
    }
  }

  grouping sm-device-list-node {
    description
      "Device stats";
    leaf device-type {
      type string;
      description
        "Type of device";
    }
    leaf device-count {
      type uint32;
      description
        "Number of devices";
    }
  }

  grouping sm-device-count-list {
    description
      "Devices statistics";
    list sm-device-list {
      description
        "List of devices and their statistics";
      uses wireless-client-global-oper:sm-device-list-node;
    }
  }

  grouping ap-emltd-by-list {
    description
      "AP details";
    leaf ap-mac {
      type yang:mac-address;
      description
        "AP MAC address";
    }
    leaf wtp-name {
      type string;
      description
        "AP name";
    }
    leaf num-client {
      type uint32;
      description
        "Number of client joined on AP";
    }
    leaf data-usage {
      type uint64;
      description
        "Data usage";
    }
    leaf through-put {
      type uint64;
      description
        "Throughput";
    }
    leaf ap-admin-state {
      type boolean;
      description
        "AP administrative state";
    }
  }

  grouping ap-emltd {
    description
      "List of AP and joined clients informations";
    list ap-list {
      description
        "Lists of AP";
      uses wireless-client-global-oper:ap-emltd-by-list;
    }
  }

  grouping sort-emltd-ap {
    description
      "APs in sorted order";
    leaf mapping {
      type wireless-types:enm-ap-sort;
      description
        "Method to sort the AP list";
    }
    container sort-ap {
      description
        "APs in sorted order";
      uses wireless-client-global-oper:ap-emltd;
    }
  }

  grouping wlan-emltd-by-list {
    description
      "Lists of WLAN and clients informations";
    leaf wlan-id {
      type uint16;
      description
        "WLAN identifier";
    }
    leaf wlan-profile-name {
      type string;
      description
        "WLAN profile name";
    }
    leaf num-client {
      type uint32;
      description
        "Number of client on WLAN";
    }
    leaf data-usage {
      type uint64;
      description
        "Data usage";
    }
  }

  grouping wlan-emltd {
    description
      "List of WLAN in sorted order";
    list wlan-list {
      description
        "List of WLAN in sorted order";
      uses wireless-client-global-oper:wlan-emltd-by-list;
    }
  }

  grouping sort-emltd-wlan {
    description
      "List of WLAN in sorted order";
    leaf mapping {
      type wireless-types:enm-wlan-sort;
      description
        "Method to sort the WLAN list";
    }
    container sort-wlan {
      description
        "Lists of WLAN in sorted order";
      uses wireless-client-global-oper:wlan-emltd;
    }
  }

  grouping st-nearby-ap {
    description
      "Near by AP statistics";
    leaf ap-name {
      type string;
      description
        "AP name";
    }
    list rssi-samples {
      max-elements 4;
      description
        "RSSI of APs";
      uses wireless-client-global-oper:rssi-sample;
    }
  }

  grouping st-nearby-aps {
    description
      "Near by AP statistics";
    leaf client-mac {
      type yang:mac-address;
      description
        "Client MAC address";
    }
    list nearby-ap {
      max-elements 6;
      description
        "List of near by AP";
      uses wireless-client-global-oper:st-nearby-ap;
    }
  }

  grouping emltd-ipsk-tag-data {
    description
      "Identity PSK tagged clients details";
    leaf client-mac {
      type yang:mac-address;
      description
        "Client MAC address";
    }
    leaf ap-mac {
      type yang:mac-address;
      description
        "AP MAC address";
    }
    leaf ap-name {
      type string;
      description
        "AP name";
    }
    leaf wlan-id {
      type uint16;
      description
        "WLAN identifier";
    }
    leaf slot {
      type uint16;
      description
        "AP slot identifier";
    }
  }

  grouping emltd-ipsk-tag-clients {
    description
      "Identity PSK tag clients details";
    list ipsk-client {
      description
        "List of Identity PSK tag client";
      uses wireless-client-global-oper:emltd-ipsk-tag-data;
    }
  }

  grouping emltd-ipsk-clients {
    description
      "List of Identity PSK tag client";
    leaf ipsk-tag-str {
      type string;
      description
        "Identity PSK tag";
    }
    container clients {
      description
        "Identity PSK tag clients";
      uses wireless-client-global-oper:emltd-ipsk-tag-clients;
    }
  }

  grouping st-wlan-vrf-map-detail {
    description
      "WLAN Details";
    leaf policy-profile-name {
      type string;
      description
        "Policy Profile Name";
    }
    leaf vlan-id {
      type uint16;
      description
        "VLAN ID";
    }
    leaf ni-name {
      type string;
      description
        "Network instance name. If the Network instance type is net-inst-default, then name is not meaningful";
    }
    leaf ni-type {
      type common-types-ios-xe:net-inst-type;
      description
        "Network instance type. Differentiates between the default routing instance and VRFs";
    }
  }

  grouping st-wlan-vrf-map-info {
    description
      "List of WLAN-VRF mapping information";
    leaf wlan-id {
      type uint16;
      description
        "WLAN ID";
    }
    leaf profile-name {
      type string;
      description
        "WLAN Profile Name";
    }
    list wlan-vrf-maps {
      description
        "List of VRFs mapped to this WLAN";
      uses wireless-client-global-oper:st-wlan-vrf-map-detail;
    }
  }

  grouping wtp-mac-client-mac-key {
    description
      "AP MAC and client MAC key";
    leaf wtp-mac {
      type yang:mac-address;
      description
        "AP MAC";
    }
    leaf client-mac {
      type yang:mac-address;
      description
        "Client MAC";
    }
  }

  grouping st-emltd-client-list-per-ap {
    description
      "Details of client";
    leaf wlan-id {
      type uint32;
      description
        "Wlan Id to which the client is associated";
    }
    leaf vap-ssid {
      type string;
      description
        "SSID to which the client is associated";
    }
    leaf ms-assoc-time {
      type yang:date-and-time;
      description
        "Absolute time at which the client associated";
    }
    leaf current-channel {
      type uint8;
      description
        "Channel number on which the client associated";
    }
    leaf width {
      type wireless-client-types:ewlc-dot11-width;
      units "MHz";
      description
        "Channel width on which the client associated";
    }
    leaf vlan-id {
      type uint16;
      description
        "VLAN assigned to the client";
    }
    leaf model-number {
      type string;
      description
        "Model number of the client device";
    }
    leaf ip-address {
      type inet:ip-address;
      description
        "IP Address of the client";
    }
    leaf bytes-tx {
      type uint64;
      units "bytes";
      description
        "Bytes transmitted by the client";
    }
    leaf bytes-rx {
      type uint64;
      units "bytes";
      description
        "Bytes received by the client";
    }
    leaf most-recent-snr {
      type uint8;
      units "dB";
      description
        "Recent SNR of the client";
    }
    leaf active {
      type empty;
      description
        "Active state of client";
    }
  }

  container client-global-oper-data {
    config false;
    description
      "Root container for client operational data aggregated across wireless processes";
    list wlan-vrf-map-info {
      key "wlan-id";
      unique "profile-name";
      description
        "WLAN-VRF mapping information";
      uses wireless-client-global-oper:st-wlan-vrf-map-info {
        refine "profile-name" {
          mandatory true;
        }
      }
    }
    list client-list-details-per-ap {
      key "wtp-mac client-mac";
      description
        "Client list details per AP";
      uses wireless-client-global-oper:wtp-mac-client-mac-key;
      uses wireless-client-global-oper:st-emltd-client-list-per-ap;
    }
    list nearby-aps {
      key "client-mac";
      description
        "Near by APs";
      uses wireless-client-global-oper:st-nearby-aps;
    }
    container client-live-stats {
      presence "client-live-stats";
      description
        "Snapshot of statistics of current state of wireless clients";
      uses wireless-client-global-oper:client-live-stats;
    }
    container client-global-stats-data {
      presence "client-global-stats-data";
      description
        "Client global statistics data";
      uses wireless-client-global-oper:ewlc-client-global-stats-op;
    }
    container client-stats {
      presence "client-stats";
      description
        "Summary of client statistics";
      uses wireless-client-global-oper:client-statistics;
    }
    container client-dot11-stats {
      presence "client-dot11-stats";
      description
        "Clients 802.11 statistics";
      uses wireless-client-global-oper:st-client-dot11-statistics;
    }
    container client-latency-stats {
      presence "client-latency-stats";
      description
        "Client run state latency statistics";
      uses wireless-client-global-oper:client-latency-stats;
    }
    container sm-webauth-stats {
      presence "sm-webauth-stats";
      description
        "Web-authentication HTTP statistics";
      uses wireless-client-global-oper:st-sm-webauth-stats;
    }
    container dot1x-global-stats {
      presence "dot1x-global-stats";
      description
        "Dot1x global statistics";
      uses wireless-client-global-oper:sm-dot1x-global-stats;
    }
    container client-exclusion-stats {
      presence "client-exclusion-stats";
      description
        "Client exclusion statistics";
      uses wireless-client-global-oper:st-client-exclusion-stats;
    }
    container sm-device-count {
      presence "sm-device-count";
      description
        "Types of devices and their statistics";
      uses wireless-client-global-oper:sm-device-count-list;
    }
    list sort-ap {
      key "mapping";
      description
        "List of AP in sorted order";
      uses wireless-client-global-oper:sort-emltd-ap;
    }
    list sort-wlan {
      key "mapping";
      description
        "List of WLAN in sorted order";
      uses wireless-client-global-oper:sort-emltd-wlan;
    }
    container tof-stats {
      presence "tof-stats";
      description
        "Wireless trace statistics";
      uses wireless-client-global-oper:st-tof;
    }
    list ipsk-tag-client {
      key "ipsk-tag-str";
      status deprecated;
      description
        "Identity PSK tagged clients";
      uses wireless-client-global-oper:emltd-ipsk-clients;
    }
  }
}
