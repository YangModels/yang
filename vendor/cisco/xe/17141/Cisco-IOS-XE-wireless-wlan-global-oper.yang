module Cisco-IOS-XE-wireless-wlan-global-oper {
  yang-version 1.1;
  namespace "http://cisco.com/ns/yang/Cisco-IOS-XE-wireless-wlan-global-oper";
  prefix wireless-wlan-global-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains  operational WLAN data aggregated across wireless processes.
     Copyright (c) 2022 by Cisco Systems, Inc.
     All rights reserved.";

  revision 2023-03-01 {
    description
      "- Marked per-wlan-max-client-syslog leaf deprecated";
    reference
      "1.1.0";
    cisco-semver:module-version "1.1.0";
  }
  revision 2022-11-01 {
    description
      "Initial revision";
    reference
      "1.0.0";
    cisco-semver:module-version "1.0.0";
  }

  grouping wlan-info-entry {
    description
      "WLAN statistics";
    leaf wlan-profile {
      type string;
      description
        "WLAN profile name";
    }
    leaf curr-clients-count {
      type uint32;
      description
        "Number of active clients for this WLAN";
    }
    leaf per-wlan-max-client-syslog {
      type boolean;
      status deprecated;
      description
        "Syslog message enabled when maximum clients are reached on WLAN";
    }
  }

  container wlan-global-oper-data {
    config false;
    description
      "Root container for  WLAN operational data aggregated across wireless processes";
    list wlan-info {
      key "wlan-profile";
      description
        "WLAN client statistics";
      uses wireless-wlan-global-oper:wlan-info-entry;
    }
  }
}
