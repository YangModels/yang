module Cisco-IOS-XE-ethernet {
  yang-version 1.1;
  namespace "http://cisco.com/ns/yang/Cisco-IOS-XE-ethernet";
  prefix ios-eth;

  import cisco-semver {
    prefix cisco-semver;
  }
  import Cisco-IOS-XE-native {
    prefix ios;
  }
  import Cisco-IOS-XE-features {
    prefix ios-features;
  }
  import Cisco-IOS-XE-pppoe {
    prefix ios-pppoe;
  }
  import Cisco-IOS-XE-types {
    prefix ios-types;
  }
  include Cisco-IOS-XE-ethernet-oam;
  include Cisco-IOS-XE-ethernet-cfm-efp;

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Ethernet Interfaces Yang model.
     Copyright (c) 2016-2021 by Cisco Systems, Inc.
     All rights reserved.";

  revision 2024-03-01 {
    description
      "- Added support for enum sdwan in load-balance-hash-algo
       - Obsolete nodes related to synchronous mode";
    cisco-semver:module-version "9.0.0";
  }
  revision 2023-11-01 {
    description
      "- Removing channel-group from unsupported interfaces";
    cisco-semver:module-version "8.0.0";
  }
  revision 2023-07-01 {
    description
      "- Added support for macsec disable-sci/access-control";
    cisco-semver:module-version "7.0.0";
  }
  revision 2023-03-01 {
    description
      "- Update release version";
    cisco-semver:module-version "6.2.1";
  }
  revision 2022-11-01 {
    description
      "- Update yang-version to 1.1";
    cisco-semver:module-version "6.2.0";
  }
  revision 2022-07-01 {
    description
      "- Added support for bpdu, cfm, stp, mrp in ethernet-cfm-efp
       - Added IE protocol MRP support";
    cisco-semver:module-version "6.1.0";
  }
  revision 2021-11-01 {
    description
      "- channel-group CLI usage correction
       - Replace queue with queue new under plim qos";
    cisco-semver:module-version "6.0.0";
  }
  revision 2021-07-01 {
    description
      "- Added cos container
       - Added leaves primary and secondary  to encapsulation dot1q chain
       - under Port-channel sub-interfaces  to support vlan load-balancing on
       - routing platforms
       - Added a 'tailf:cli-remove-before-change' to send no-CLI first and then with
         updated value for 'channel-group mode' CLI";
    cisco-semver:module-version "5.0.0";
  }
  revision 2021-03-01 {
    description
      "- Change range for leaf number of interface * channel-group";
    cisco-semver:module-version "4.0.0";
  }
  revision 2020-11-01 {
    description
      "- Added leafs speed 25000, 40000 and 100000
       - Added must condition for channel-group";
    cisco-semver:module-version "3.0.0";
  }
  revision 2020-07-01 {
    description
      "- Added internal loopback CLIs for an interface
       - Added leafs speed 2500 and speed 5000";
    cisco-semver:module-version "2.1.0";
  }
  revision 2020-03-01 {
    description
      "- Introduced channel-group delete after port-channel modify";
    cisco-semver:module-version "2.0.1";
  }
  revision 2019-11-01 {
    description
      "- Added config under UCSE interface";
    cisco-semver:module-version "2.0.0";
  }
  revision 2019-07-01 {
    description
      "- Establish semantic version baseline
       - Add BD-VIF interface
       - Split the file into 2 submodules comprising
         of components cfm/efp/lmi/loopback";
    cisco-semver:module-version "1.0.0";
  }
  revision 2019-01-22 {
    description
      "Added leaf for App-hosting Gigabit Ethernet interface";
  }
  revision 2018-11-21 {
    description
      "Cleanup spelling errors in description statements";
  }
  revision 2018-11-14 {
    description
      "Added dhcp-border-relay option in Loopback interface";
  }
  revision 2018-07-25 {
    description
      "Remove the must constraints for interface auto-negotiation and speed";
  }
  revision 2018-07-18 {
    description
      "Validate interface auto-negotiation is not enabled when setting speed";
  }
  revision 2018-04-17 {
    description
      "imported pppoe groupings";
  }
  revision 2018-04-09 {
    description
      "Add dependency for bridge-domain";
  }
  revision 2018-03-08 {
    description
      "allow speed change under interface";
  }
  revision 2018-03-06 {
    description
      "add dependency between speed and duplex";
  }
  revision 2018-02-22 {
    description
      "add encapsulation priority-tagged without parameter support";
  }
  revision 2018-02-02 {
    description
      "Add model for port-channel mlacp";
  }
  revision 2018-01-15 {
    description
      "Added dot1ad nni support ";
  }
  revision 2018-01-04 {
    description
      "Change ethernet lmi ce-vlan map vlan range";
  }
  revision 2017-11-27 {
    description
      "Added Change 25GE name";
  }
  revision 2017-09-21 {
    description
      "Added interface macsec without option";
  }
  revision 2017-09-20 {
    description
      "Added interface macsec";
  }
  revision 2017-09-14 {
    description
      "This revision has changes for new 2gig interface addition";
  }
  revision 2017-08-21 {
    description
      "Augment HundredGigE interface with ethernet grouping";
  }
  revision 2017-08-16 {
    description
      "This revision has changes for new 5gig and 25gig interfaces addition";
  }
  revision 2017-08-10 {
    description
      "Add BDI interface";
  }
  revision 2017-07-25 {
    description
      "Modification to fix model under service instance *";
  }
  revision 2017-07-18 {
    description
      "Consolidate modeling for interface lacp";
  }
  revision 2017-02-07 {
    description
      "Initial revision";
  }

  grouping config-interface-mrp-grouping {
    container mrp {
      description
        "enable mrp for this interface";
      leaf ring {
        description
          "denotes ring number";
        type uint8 {
          range "1..3";
        }
      }
    }
  }

  grouping interface-ethernet-carrier-delay-grouping {
    choice delay-choice {
      leaf seconds {
        type uint8 {
          range "0..60";
        }
      }
      leaf msec {
        description
          "delay specified in milliseconds";
        type uint16 {
          range "0..1000";
        }
      }
    }
  }

  grouping config-interface-ethernet-member-link-lacp-grouping {
    container lacp {
      description
        "LACP interface subcommands";
      leaf port-priority {
        description
          "LACP priority on this interface ";
        type uint32 {
          range "0..65535";
        }
      }
      leaf rate {
        description
          "Rate at which the LACP packets are requested on ingress to this interface";
        type enumeration {
          enum fast;
          enum normal;
        }
      }
    }
  }

  grouping config-interface-port-channel-lacp-grouping {
    container lacp {
      description
        "LACP Port Channel interface subcommands";
      leaf failover {
        description
          "Link failover options";
        type enumeration {
          enum brute-force;
          enum non-revertive;
        }
      }
      leaf fast-switchover {
        description
          "Enable LACP fast switchover on this port channel";
        type empty;
      }
      leaf max-bundle {
        description
          "LACP maximum number of ports to bundle in this port channel";
        type uint8 {
          range "1..16";
        }
      }
      leaf min-bundle {
        description
          "LACP minimum number of ports to bundle in this port channel";
        type uint8 {
          range "1..16";
        }
      }
    }
  }

  grouping config-interface-port-channel-mlacp-grouping {
    container mlacp {
      description
        "mLACP Port Channel interface subcommands";
      container interchassis {
        description
          "mLACP Interchassis commands";
        leaf group {
          description
            "Interchassis Group";
          type uint32 {
            range "1..4294967295";
          }
        }
      }
    }
  }

  grouping config-interface-channel-group-obsolete-grouping {
    container channel-group {
      description
        "OBSOLETE - Add this interface to an Etherchannel group";
      status obsolete;
      leaf number {
        status obsolete;
        must '/ios:native/ios:interface/ios:Port-channel/ios:name = current()' {
          error-message "Channel-group should be created after Port-channel and deleted before";
        }
        type uint16 {
          range "1..512";
        }
      }
      leaf mode {
        description
          "OBSOLETE - Etherchannel Mode of the interface";
        status obsolete;
        when '(../number)';
        type enumeration {
          enum active;
          enum auto;
          enum desirable;
          enum on;
          enum passive;
        }
      }
      leaf non-silent {
        description
          "OBSOLETE - Start negotiation only after data packets received";
        status obsolete;
        type empty;
      }
      leaf link {
        description
          "OBSOLETE - Assign a link identifier used for load-balancing";
        status obsolete;
        type uint8 {
          range "1..4";
        }
      }
      leaf auto {
        description
          "OBSOLETE - LACP auto";
        status obsolete;
        type empty;
      }
    }
  }

  grouping config-interface-channel-group-grouping {
    container channel-group {
      description
        "Add this interface to an Etherchannel group";
      leaf number {
        must '/ios:native/ios:interface/ios:Port-channel/ios:name = current()' {
          error-message "Channel-group should be created after Port-channel and deleted before";
        }
        type uint16 {
          range "1..512";
        }
      }
      leaf mode {
        description
          "Etherchannel Mode of the interface";
        when '(../number)';
        type enumeration {
          enum active;
          enum auto;
          enum desirable;
          enum on;
          enum passive;
        }
      }
      leaf non-silent {
        description
          "Start negotiation only after data packets received";
        type empty;
      }
      leaf link {
        description
          "Assign a link identifier used for load-balancing";
        type uint8 {
          range "1..4";
        }
      }
      leaf auto {
        description
          "LACP auto";
        type empty;
      }
    }
  }

  grouping config-interface-ethernet-grouping {
    container carrier-delay {
      description
        "Specify delay for interface transitions";
      uses interface-ethernet-carrier-delay-grouping;
      container down {
        description
          "Carrier Down Transitions";
        uses interface-ethernet-carrier-delay-grouping;
      }
      container up {
        description
          "Carrier Up Transitions";
        uses interface-ethernet-carrier-delay-grouping;
      }
    }
    leaf channel-protocol {
      description
        "Select the channel protocol (LACP, PAgP)";
      type enumeration {
        enum lacp;
        enum pagp;
      }
    }
    container eapol {
      description
        "eapol";
      leaf announcement {
        description
          "EAPOL announcement";
        type empty;
      }
      container destination-address {
        description
          "Configure destination MAC address";
        choice address-option {
          leaf mac-address {
            description
              "MAC address";
            type ios-types:cisco-mac-address-type;
          }
          leaf bridge-group-address {
            description
              "Configure bridge group address";
            type empty;
          }
          leaf broadcast-addr {
            description
              "Configure broadcast MAC address";
            type empty;
          }
          leaf lldp-multicast-address {
            description
              "Configure lldp multicast address";
            type empty;
          }
        }
        leaf broadcast-address {
          status deprecated;
          description
            "Deprecated, Use node broadcast-addr";
          type empty;
        }
      }
      leaf eth-type {
        description
          "Ethernet Type for EAPOL Frame";
        type enumeration {
          enum 876F;
        }
      }
    }
    container synchronous {
      description
        "Synchronous (OBSOLETE)
         Please use config-interface-synchronous-grouping in synce yang model";
      status obsolete;
      leaf mode {
        description
          "Mode (OBSOLETE)
           Please use config-interface-synchronous-grouping in synce yang model";
        status obsolete;
        type empty;
      }
    }
    container speed {
      description
        "Configure speed operation";
      choice speed-choice {
        leaf auto {
          description
            "Enable AUTO speed configuration";
          type empty;
        }
        leaf value-10 {
          description
            "10 Mbps operation";
          type empty;
        }
        leaf value-100 {
          description
            "100 Mbps operation";
          type empty;
        }
        leaf value-1000 {
          description
            "1000 Mbps operation";
          type empty;
        }
        leaf value-2500 {
          description
            "2500 Mbps operation";
          type empty;
        }
        leaf value-5000 {
          description
            "5000 Mbps operation";
          type empty;
        }
        leaf value-10000 {
          description
            "10000 Mbps operation";
          type empty;
        }
        leaf value-25000 {
          description
            "25000 Mbps operation";
          type empty;
        }
        leaf value-40000 {
          description
            "40000 Mbps operation";
          type empty;
        }
        leaf value-100000 {
          description
            "100000 Mbps operation";
          type empty;
        }
        leaf nonegotiate {
          type empty;
        }
      }
    }
    leaf duplex {
      description
        "Configure duplex operation.";
      type enumeration {
        enum auto;
        enum full;
        enum half;
      }
    }
    container loopback {
      description
        "Configure internal loopback on an interface";
      choice loopback-mode {
        case external {
          leaf external {
            description
              "Loopback towards line at the transceiver level";
            type empty;
          }
        }
        case mac {
          leaf mac {
            description
              "Loopback towards system at the MAC controller level";
            type empty;
          }
        }
        case phy {
          container phy {
            description
              "Loopback at Phy level";
            choice phy-mode {
              case external {
                leaf external {
                  description
                    "Loopback towards line";
                  type enumeration {
                    enum deep;
                    enum shallow;
                  }
                }
              }
              case internal {
                leaf internal {
                  description
                    "Loopback towards system";
                  type enumeration {
                    enum deep;
                    enum shallow;
                  }
                }
              }
            }
          }
        }
        case xpt {
          leaf xpt {
            description
              "Loopback at cross-point level";
            type enumeration {
              enum External;
              enum Internal;
            }
          }
        }
      }
    }
    container negotiation {
      description
        "Select autonegotiation mode";
      leaf auto {
        description
          "Enable link autonegotiation";
        type boolean;
      }
    }
    container plim {
      description
        "Configure features on the PLIM";
      container ethernet {
        description
          "Configure features on the ethernet interface";
        container vlan {
          description
            "vlan specific features";
          container filter {
            description
              "Configure VLAN filtering";
            leaf disable {
              description
                "Configure the interface to accept all VLAN traffic";
              type empty;
            }
          }
        }
      }
      container qos {
        description
          "QoS on the PLIM";
        container input {
          description
            "Configure PLIM QoS at the input of an interface";
          container queue_new {
            description
              "Queue number";
            container zero {
              description
                "Low priority queue";
              container pause {
                description
                  "Pause Frame generation and threshold";
                leaf enable {
                  description
                    "Enable pause-frame generation";
                  type boolean;
                }
                leaf threshold {
                  description
                    "Threshold as a percent of queue limit for pause frame generation";
                  type uint8 {
                    range "0..99";
                  }
                }
              }
            }
            container strict-priority {
              description
                "High priority queue";
              container pause {
                description
                  "Pause Frame generation and threshold";
                leaf enable {
                  description
                    "Enable pause-frame generation";
                  type boolean;
                }
                leaf threshold {
                  description
                    "Threshold as a percent of queue limit for pause frame generation";
                  type uint8 {
                    range "0..99";
                  }
                }
              }
            }
          }
          container queue {
            status deprecated;
            description
              "Queue number";
            choice priority {
              case low {
                container zero {
                  status deprecated;
                  description
                    "Low priority queue";
                  container pause {
                    status deprecated;
                    description
                      "Pause Frame generation and threshold";
                    leaf enable {
                      status deprecated;
                      description
                        "Enable pause-frame generation";
                      type boolean;
                    }
                    leaf threshold {
                      status deprecated;
                      description
                        "Threshold as a percent of queue limit for pause frame generation";
                      type uint8 {
                        range "0..99";
                      }
                    }
                  }
                }
              }
              case high {
                container strict-priority {
                  status deprecated;
                  description
                    "High priority queue";
                  container pause {
                    status deprecated;
                    description
                      "Pause Frame generation and threshold";
                    leaf enable {
                      status deprecated;
                      description
                        "Enable pause-frame generation";
                      type boolean;
                    }
                    leaf threshold {
                      status deprecated;
                      description
                        "Threshold as a percent of queue limit for pause frame generation";
                      type uint8 {
                        range "0..99";
                      }
                    }
                  }
                }
              }
            }
          }
          container map {
            container cos {
              description
                "VLAN COS mapping";
              leaf enable {
                description
                  "Enable VLAN cos mapping";
                type empty;
              }
              container cos-range {
                description
                  "Specify a range of cos values to classify in the format of 'X - X'";
                leaf start-range-val {
                  description
                    "The starting cos value of the range";
                  type ios-types:cos-type;
                }
                leaf range-val {
                  description
                    "Used to indicate a range should be specified";
                  type enumeration {
                    enum -;
                  }
                }
                leaf end-range-val {
                  description
                    "The ending cos value of the range";
                  type ios-types:cos-type;
                }
                leaf queue {
                  description
                    "Queue to map the entered COS values to";
                  type enumeration {
                    enum 0;
                    enum low-priority;
                    enum strict-priority;
                  }
                }
              }
              container cos-list {
                description
                  "Specify a list of cos values to classify";
                leaf cos-value1 {
                  description
                    "First cos value in the list, must be specified";
                  type ios-types:cos-type;
                }
                leaf cos-value2 {
                  description
                    "Second cos value in the list, optional";
                  type ios-types:cos-type;
                }
                leaf cos-value3 {
                  description
                    "Third cos value in the list, optional";
                  type ios-types:cos-type;
                }
                leaf cos-value4 {
                  description
                    "Fourth cos value in the list, optional";
                  type ios-types:cos-type;
                }
                leaf cos-value5 {
                  description
                    "Fifth cos value in the list, optional";
                  type ios-types:cos-type;
                }
                leaf cos-value6 {
                  description
                    "Sixth cos value in the list, optional";
                  type ios-types:cos-type;
                }
                leaf cos-value7 {
                  description
                    "Seventh cos value in the list, optional";
                  type ios-types:cos-type;
                }
                leaf cos-value8 {
                  description
                    "Eighth cos value in the list, optional";
                  type ios-types:cos-type;
                }
                leaf queue {
                  description
                    "Queue to map the entered COS values to";
                  type enumeration {
                    enum 0;
                    enum low-priority;
                    enum strict-priority;
                  }
                }
              }
            }
            description
              "ip mapping";
            container ip {
              container all {
                leaf queue {
                  type enumeration {
                    enum 0;
                    enum low-priority;
                    enum strict-priority;
                  }
                }
              }
              leaf dscp-based {
                type empty;
              }
              container dscp {
                choice dscp-value {
                  case value-case {
                    leaf dscp-value1 {
                      type ios-types:dscp-type;
                    }
                    leaf dscp-value2 {
                      type ios-types:dscp-type;
                    }
                    leaf dscp-value3 {
                      type ios-types:dscp-type;
                    }
                    leaf dscp-value4 {
                      type ios-types:dscp-type;
                    }
                    leaf dscp-value5 {
                      type ios-types:dscp-type;
                    }
                    leaf dscp-value6 {
                      type ios-types:dscp-type;
                    }
                    leaf dscp-value7 {
                      type ios-types:dscp-type;
                    }
                    leaf dscp-value8 {
                      type ios-types:dscp-type;
                    }
                  }
                }
                leaf queue {
                  type enumeration {
                    enum low-latency;
                    enum strict-priority;
                    enum 0;
                  }
                }
              }
              leaf precedence-based {
                type empty;
              }
              container precedence {
                choice precedence-value {
                  case precedence-value {
                    leaf precedence-value1 {
                      type uint8 {
                        range "0..7";
                      }
                    }
                    leaf precedence-value2 {
                      type uint8 {
                        range "0..7";
                      }
                    }
                    leaf precedence-value3 {
                      type uint8 {
                        range "0..7";
                      }
                    }
                    leaf precedence-value4 {
                      type uint8 {
                        range "0..7";
                      }
                    }
                    leaf precedence-value5 {
                      type uint8 {
                        range "0..7";
                      }
                    }
                    leaf precedence-value6 {
                      type uint8 {
                        range "0..7";
                      }
                    }
                    leaf precedence-value7 {
                      type uint8 {
                        range "0..7";
                      }
                    }
                    leaf precedence-value8 {
                      type uint8 {
                        range "0..7";
                      }
                    }
                  }
                }
                leaf queue {
                  type enumeration {
                    enum 0;
                    enum low-priority;
                    enum strict-priority;
                  }
                }
              }
            }
            container ipv6 {
              container all {
                leaf queue {
                  type enumeration {
                    enum 0;
                    enum low-priority;
                    enum strict-priority;
                  }
                }
              }
            }
            container ipv4v6 {
              leaf qos-value-based {
                type empty;
              }
              container qos-value {
                choice qos-value {
                  case value-case {
                    leaf dscp-value1 {
                      type ios-types:dscp-type;
                    }
                    leaf dscp-value2 {
                      type ios-types:dscp-type;
                    }
                    leaf dscp-value3 {
                      type ios-types:dscp-type;
                    }
                    leaf dscp-value4 {
                      type ios-types:dscp-type;
                    }
                    leaf dscp-value5 {
                      type ios-types:dscp-type;
                    }
                    leaf dscp-value6 {
                      type ios-types:dscp-type;
                    }
                    leaf dscp-value7 {
                      type ios-types:dscp-type;
                    }
                    leaf dscp-value8 {
                      type ios-types:dscp-type;
                    }
                  }
                }
                leaf queue {
                  type enumeration {
                    enum low-latency;
                    enum strict-priority;
                    enum 0;
                  }
                }
              }
            }
            container mpls {
              container all {
                leaf queue {
                  type enumeration {
                    enum 0;
                    enum low-priority;
                    enum strict-priority;
                  }
                }
              }
              container exp {
                choice exp-value {
                  case exp-case {
                    leaf exp {
                      type ios-types:exp-type;
                    }
                  }
                }
                leaf queue {
                  type enumeration {
                    enum 0;
                    enum low-priority;
                    enum strict-priority;
                  }
                }
              }
            }
          }
          container policer {
            container bandwidth {
              leaf bandwidth-value {
                type uint32 {
                  range "150000..10000000";
                }
              }
              leaf strict-priority {
                type empty;
              }
            }
          }
          leaf weight {
            type uint16 {
              range "40..10000";
            }
          }
        }
      }
    }
    uses ios-pppoe:config-pppoe-grouping;
    uses ios-pppoe:config-pppoe-client-grouping;
    uses ios-pppoe:config-pppoe-session-grouping;
  }

  grouping config-port-channel-grouping {
    leaf auto {
      description
        "LACP auto for the system";
      type empty;
    }
    container load-balance-hash-algo {
      description
        "Load Balance hash algorithms";
      leaf load-balance-hash-algo {
        default "src-dst-ip";
        type enumeration {
          enum dst-ip;
          enum dst-mac;
          enum src-dst-ip;
          enum src-dst-mac;
          enum src-dst-mixed-ip-port;
          enum src-ip;
          enum src-mac;
          enum sdwan;
        }
      }
      if-feature "ios-features:router-poch-lb";
    }
    container load-balance {
      description
        "Load Balancing method";
      leaf load-balance {
        type enumeration {
          enum dst-ip;
          enum dst-mac;
          enum dst-mixed-ip-port;
          enum dst-port;
          enum mpls;
          enum src-dst-ip;
          enum src-dst-mac;
          enum src-dst-mixed-ip-port;
          enum src-dst-port;
          enum src-ip;
          enum src-mac;
          enum src-mixed-ip-port;
          enum src-port;
          enum vlan-dst-ip;
          enum vlan-dst-mixed-ip-port;
          enum vlan-src-dst-ip;
          enum vlan-src-dst-mixed-ip-port;
          enum vlan-src-ip;
          enum vlan-src-mixed-ip-port;
        }
      }
      container extended {
        description
          "Extended Load Balance Methods";
        presence "true";
        leaf-list extended {
          type enumeration {
            enum dst-ip;
            enum dst-mac;
            enum dst-port;
            enum ipv6-label;
            enum l3-proto;
            enum src-ip;
            enum src-mac;
            enum src-port;
          }
        }
      }
    }
    container load-balancing {
      description
        "Load Balance method";
      leaf vlan-manual {
        description
          "Manual Traffic Distribution based on VLAN id";
        type empty;
      }
    }
  }

  grouping config-interface-macsec-grouping {
    leaf macsec {
      status obsolete;
      description
        "Enable macsec on the interface";
      type boolean;
      default "false";
    }
    container macsec-option {
      description
        "Enable macsec on the interface";
      container macsec {
        leaf dot1q-in-clear {
          description
            "Dot1q in Clear option";
          type enumeration {
            enum 1;
          }
        }
        container replay-protection {
          status obsolete;
          description
            "Set replay-protection";
          leaf window-size {
            status obsolete;
            description
              "Set replay window-size";
            type uint32;
          }
        }
        leaf access-control {
          status obsolete;
          description
            "Access Control Policy";
          type enumeration {
            enum must-secure;
            enum should-secure;
          }
        }
        leaf disable-sci-v2 {
          description
            "Disable SCI filed in MACsec header";
          type empty;
        }
        leaf disable-sci {
          status obsolete;
          description
            "Disable SCI filed in MACsec header";
          type boolean;
          default "false";
        }
      }
    }
  }

  grouping config-interface-Loopback-dbr-grouping {
    leaf dhcp-border-relay {
      description
        "Config dhcp-border-relay on an interface";
      type empty;
    }
  }

  grouping config-esmc-grouping {
    container esmc {
      description
        "Ethernet Synchronization Messaging Channel (OBSOLETE)
         Please use config-esmc-grouping defined in synce yang model";
      status obsolete;
      leaf process {
        description
          "process";
        status obsolete;
        type empty;
      }
    }
  }

  augment "/ios:native" {
    uses config-esmc-grouping {
      if-feature "ios-features:esmc";
    }
  }

  augment "/ios:native/ios:ethernet" {
    uses config-ethernet-lmi-grouping;
    uses config-ethernet-cfm-efp-grouping;
    uses config-ethernet-oam-grouping;
  }

  augment "/ios:native/ios:port-channel" {
    uses config-port-channel-grouping;
  }

  augment "/ios:native/ios:interface/ios:Ethernet" {
    uses config-interface-ethernet-oam-grouping;
  }

  augment "/ios:native/ios:interface/ios:FastEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:GigabitEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
    uses config-interface-mrp-grouping {
      if-feature "ios-features:mrp";
    }
  }

  augment "/ios:native/ios:interface/ios:TwoGigabitEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:FiveGigabitEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:AppGigabitEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:TenGigabitEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:TwentyFiveGigE" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:FortyGigabitEthernet" {
    uses config-interface-ethernet-grouping;
    uses config-interface-channel-group-grouping;
    uses config-interface-ethernet-oam-grouping;
    uses config-interface-ethernet-cfm-efp-grouping;
    uses config-interface-ethernet-member-link-lacp-grouping;
    uses config-interface-macsec-grouping {
      if-feature "ios-features:macsec";
    }
  }

  augment "/ios:native/ios:interface/ios:HundredGigE" {
    uses config-interface-ethernet-grouping;
    uses config-interface-channel-group-grouping;
    uses config-interface-ethernet-oam-grouping;
    uses config-interface-ethernet-cfm-efp-grouping;
    uses config-interface-macsec-grouping {
      if-feature "ios-features:macsec";
    }
  }

  augment "/ios:native/ios:interface/ios:Port-channel" {
    uses config-interface-ethernet-grouping;
    uses config-interface-channel-group-obsolete-grouping;
    uses config-interface-ethernet-oam-grouping;
    uses config-interface-ethernet-cfm-efp-grouping;
    uses config-interface-port-channel-lacp-grouping;
    uses config-interface-port-channel-mlacp-grouping;
  }

  augment "/ios:native/ios:interface/ios:Port-channel-subinterface/ios:Port-channel" {
    uses config-interface-ethernet-grouping;
    uses config-interface-channel-group-obsolete-grouping;
    uses config-interface-ethernet-oam-grouping;
    uses config-interface-ethernet-cfm-efp-grouping;
  }

  augment "/ios:native/ios:interface/ios:VirtualPortGroup" {
    uses config-interface-ethernet-grouping;
    uses config-interface-channel-group-obsolete-grouping;
    uses config-interface-ethernet-oam-grouping;
    uses config-interface-ethernet-cfm-efp-grouping;
    uses config-interface-ethernet-member-link-lacp-grouping;
  }

  augment "/ios:native/ios:interface/ios:Virtual-Template" {
    uses config-interface-ethernet-grouping;
    uses config-interface-channel-group-obsolete-grouping;
    uses config-interface-ethernet-oam-grouping;
    uses config-interface-ethernet-cfm-efp-grouping;
    uses config-interface-ethernet-member-link-lacp-grouping;
  }

  augment "/ios:native/ios:interface/ios:BDI" {
    uses config-interface-ethernet-grouping;
    uses config-interface-channel-group-obsolete-grouping;
    uses config-interface-ethernet-oam-grouping;
    uses config-interface-ethernet-cfm-efp-grouping;
  }

  augment "/ios:native/ios:interface/ios:Vlan" {
    uses config-interface-ethernet-grouping;
    uses config-interface-channel-group-obsolete-grouping;
    uses config-interface-ethernet-oam-grouping;
    uses config-interface-ethernet-cfm-efp-grouping;
  }

  augment "/ios:native/ios:interface/ios:Loopback" {
    uses config-interface-Loopback-dbr-grouping {
      if-feature "ios-features:dhcp-border-relay";
    }
  }

  augment "/ios:native/ios:interface/ios:BD-VIF" {
    uses config-interface-ethernet-grouping;
    uses config-interface-channel-group-obsolete-grouping;
  }

  augment "/ios:native/ios:interface/ios:ucse" {
    uses config-interface-ethernet-grouping;
    uses config-interface-channel-group-obsolete-grouping;
    uses config-interface-ethernet-cfm-efp-grouping;
  }

  grouping config-encapsulation-dot1q-grouping {
    leaf primary {
      type string;
    }
    leaf secondary {
      when '(../primary)';
      type string;
    }
  }

  augment "/ios:native/ios:interface/ios:Port-channel-subinterface/ios:Port-channel/ios:encapsulation/ios:encap-choice/ios:dot1Q/ios:dot1Q" {
    uses config-encapsulation-dot1q-grouping {
      if-feature "ios-features:router-poch-lb";
    }
  }
}
