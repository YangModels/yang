module Cisco-IOS-XE-mpls {
  yang-version 1.1;
  namespace "http://cisco.com/ns/yang/Cisco-IOS-XE-mpls";
  prefix ios-mpls;

  import cisco-semver {
    prefix cisco-semver;
  }
  import ietf-inet-types {
    prefix inet;
  }
  import Cisco-IOS-XE-types {
    prefix ios-types;
  }
  import Cisco-IOS-XE-native {
    prefix ios;
  }
  import Cisco-IOS-XE-interface-common {
    prefix ios-ifc;
  }
  import Cisco-IOS-XE-isis {
    prefix ios-isis;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Multiprotocol Label Switching (MPLS) Yang model.
     Copyright (c) 2016-2019 by Cisco Systems, Inc.
     All rights reserved.";

  revision 2024-03-01 {
    description
      "- Added support for mpls discovery vpn and next-hop";
    cisco-semver:module-version "2.2.0";
  }
  revision 2022-11-01 {
    description
      "- Update yang-version to 1.1";
    cisco-semver:module-version "2.1.0";
  }
  revision 2020-07-01 {
    description
      "Fix for pyang xpath evaluation errors";
    cisco-semver:module-version "2.0.0";
  }
  revision 2020-03-01 {
    description
      "- Added container MPLS NHRP under interface Tunnel";
    cisco-semver:module-version "1.1.0";
  }
  revision 2019-11-01 {
    description
      "Removed suppress annotation from affinity block";
    cisco-semver:module-version "1.0.1";
  }
  revision 2019-07-01 {
    description
      "- Establish semantic version baseline
       - Added mldp leaf at interface mpls
       - Add interface BD-VIF mpls";
    cisco-semver:module-version "1.0.0";
  }
  revision 2019-01-22 {
    description
      "Added leaf for App-hosting Gigabit Ethernet interface";
  }
  revision 2018-11-07 {
    description
      "Cleanup spelling errors in description statements";
  }
  revision 2018-08-14 {
    description
      "Added support for multiple backup tunnel & confd sync issue";
  }
  revision 2018-06-28 {
    description
      "Added must constraints for deleting vrf";
  }
  revision 2017-11-27 {
    description
      "Added Change 25GE name";
  }
  revision 2017-11-14 {
    description
      "This revison has changes for new 40 and 100GE interface addition";
  }
  revision 2017-09-15 {
    description
      "This revison has changes for new 2gig interface addition";
  }
  revision 2017-08-16 {
    description
      "This revision has changes for new 5gig and 25gig interfaces addition";
  }
  revision 2017-07-20 {
    description
      "Add interface BDI mpls";
  }
  revision 2017-06-30 {
    description
      "This revision removes compile warning for mpls ldp router-id vrf";
  }
  revision 2017-02-23 {
    description
      "This revision adds support for MPLS-TE (global and interface mode)";
  }
  revision 2017-02-07 {
    description
      "Initial revision";
  }

  typedef ldp-discovery-address-type {
    type union {
      type enumeration {
        enum interface;
      }
      type inet:ipv4-address;
    }
  }

  typedef mpls-te-tiebreaker-type {
    type enumeration {
      enum max-fill {
        description
          "Use max-fill tiebreaker";
      }
      enum min-fill {
        description
          "Use min-fill tiebreaker";
      }
      enum random {
        description
          "Use random tiebreaker";
      }
    }
  }

  typedef mpls-te-attribute-flags {
    description
      "<0x0-0xFFFFFFFF>";
    type string {
      pattern '0[xX][0-9a-fA-F]{1,8}';
    }
  }

  grouping mpls-static-binding-ipv4-grouping {
    leaf label {
      type uint32;
    }
    container input {
      description
        "Incoming (local) label";
      leaf label {
        type uint32;
      }
    }
    container output {
      description
        "Outgoing (remote) label";
      leaf dst-next-hop {
        type inet:ipv4-address;
      }
      leaf label {
        type union {
          type uint32;
          type enumeration {
            enum explicit-null;
            enum implicit-null;
          }
        }
      }
    }
  }

  grouping mpls-for-to-grouping {
    container for {
      description
        "Access-list specifying controls on destination prefixes";
      leaf from {
        type string;
      }
      leaf to {
        description
          "Access-list specifying controls on LDP peers";
        type string;
      }
    }
  }

  grouping neighbor-vrf-grouping {
    list neighbor-content {
      description
        "Configure neighbor parameters";
      key "address";
      leaf address {
        type inet:ipv4-address;
      }
      leaf implicit-withdraw {
        description
          "Enable LDP Implicit Withdraw Label";
        type empty;
      }
      container labels {
        description
          "Configure label binding exchange controls";
        leaf accept {
          description
            "Specify label bindings to accept";
          type string;
        }
      }
      container password {
        description
          "Set a password";
        leaf enctype {
          type uint8 {
            range "0..7";
          }
        }
        leaf text {
          type string {
            pattern '[a-zA-Z].*';
          }
        }
      }
      container targeted {
        description
          "Establish targeted session";
        presence "Establish targeted session";
        leaf protocol {
          type enumeration {
            enum ldp;
            enum tdp;
          }
        }
      }
    }
  }

  grouping duration-grouping {
    container duration {
      description
        "Period to sustain session protection after loss of link discovery";
      choice duration-choice {
        leaf holdup-time {
          description
            "Holdup time in seconds";
          type uint32 {
            range "30..2147483";
          }
        }
        leaf infinite {
          description
            "Protect session forever after loss of link discovery";
          type empty;
        }
      }
    }
  }

  grouping mpls-ldp-password-grouping {
    container password {
      description
        "Configure LDP MD5 password";
      container fallback {
        description
          "Specifies a fallback password will follow";
        leaf encryption-type {
          type uint8 {
            range "0..7";
          }
        }
        leaf LINE {
          description
            "The UNENCRYPTED (cleartext) password";
          type string;
        }
        container key-chain {
          description
            "Specifies a key-chain name will follow";
          presence "true";
          leaf LINE {
            description
              "help";
            type string;
          }
        }
      }
      container option {
        description
          "LDP password options";
        list seq-num {
          key "seq-num";
          leaf seq-num {
            description
              "Sequence number of the LDP password option";
            type uint16 {
              range "1..32767";
            }
          }
          container for {
            description
              "IP access-list specifying control on LDP peers";
            list LINE {
              key "acl-name";
              leaf acl-name {
                description
                  "IP standard access-list for LDP peers; name or number (1-99)";
                type string;
              }
              leaf encryption-type {
                type uint8 {
                  range "0..7";
                }
              }
              leaf LINE {
                description
                  "The UNENCRYPTED (cleartext) password";
                type string;
              }
              container key-chain {
                description
                  "Specifies a key-chain name will follow";
                presence "true";
                leaf LINE {
                  description
                    "help";
                  type string;
                }
              }
              leaf tcp-ao {
                description
                  "Specifies a key-chain name will follow for LDP tcp-ao";
                type string;
              }
            }
          }
        }
      }
      container required {
        description
          "MD5 password is required for the peer";
        presence "true";
        leaf for {
          description
            "IP access-list specifying control on LDP peers";
          type string;
        }
      }
      container rollover {
        description
          "LDP password rollover parameters";
        leaf duration {
          description
            "Configure LDP password rollover duration in minutes";
          type uint16 {
            range "1..65535";
          }
        }
      }
    }
  }

  grouping label-mode-grouping {
    choice label-mode-choice {
      leaf per-ce {
        description
          "Per CE label";
        type empty;
      }
      leaf per-prefix {
        description
          "Per prefix label (default)";
        type empty;
      }
      leaf per-vrf {
        description
          "Per VRF label for entire VRF";
        type empty;
      }
      leaf vrf-conn-aggr {
        description
          "Per VRF label for connected and BGP aggregates in VRF";
        type empty;
      }
    }
  }

  grouping mpls-te-path-selection-common {
    leaf metric {
      description
        "Metric Type Configuration: < te | igp >";
      type enumeration {
        enum igp;
        enum te;
      }
    }
    container invalidation {
      description
        "Path invalidation configuration";
      leaf value {
        description
          "Path invalidation timer value: <0..60000> milliseconds, (default 10000)";
        type int32 {
          range "0 .. 60000";
        }
      }
      leaf drop {
        description
          "Drop Tunnel Traffic";
        type empty;
      }
    }
  }

  grouping mpls-te-path-selection-grouping {
    container path-selection {
      description
        "Path Selection Configuration";
      uses mpls-te-path-selection-common;
      container segment-routing {
        description
          "Segment-routing path-selection options";
        leaf adjacency {
          description
            "Segment-routing adjacency path-selection type";
          type enumeration {
            enum protected;
            enum unprotected;
          }
        }
      }
    }
  }

  grouping mpls-te-tunnel-num-range-grouping {
    container min-max {
      description
        "Configure the starting id-range";
      leaf min {
        description
          "starting tunnel number range";
        type uint16 {
          range "0..65535";
        }
      }
      leaf max {
        must '. >= ../min' {
          error-message "Max value must be >= min value";
        }
        description
          "Configure the ending id-range: <0..65535>";
        type uint16 {
          range "0..65535";
        }
      }
    }
  }

  grouping mpls-te-affinity-mask-grouping {
    container affinity-mask {
      description
        "desired link affinity attributes";
      leaf affinity {
        description
          "desired link affinity attributes: <0x0-0xFFFFFFFF>";
        type mpls-te-attribute-flags;
      }
      leaf mask {
        description
          "Mask on desired link attributes: <0x0-0xFFFFFFFF>";
        type mpls-te-attribute-flags;
      }
    }
  }

  grouping mpls-te-auto-bw-grouping {
    container auto-bw {
      description
        "Specify automatic bandwidth configuration";
      presence "true";
      leaf frequency {
        description
          "Seconds between applying auto-bw: <300..604800>";
        type uint32 {
          range "300..604800";
        }
      }
      leaf collect-bw {
        description
          "Just collect bandwidth info";
        type empty;
      }
      leaf adjustment-threshold {
        description
          "Percent bandwidth change to trigger adjustment: <1..99>";
        type uint8 {
          range "1..99";
        }
      }
      container overflow-limit {
        description
          "Number of consecutive samples exceeding threshold: <1..10>";
        leaf limit {
          type uint8 {
            range "1..10";
          }
        }
        leaf overflow-threshold {
          description
            "Set the bandwidth change threshold to trigger overflow adjustment: <1..99> %";
          type uint8 {
            range "1..99";
          }
        }
      }
      leaf max-bw {
        description
          "Maximum bandwidth to apply: <0..4294967295> (kbps)";
        type uint32 {
          range "0..4294967295";
        }
      }
      leaf min-bw {
        description
          "Minimum bandwidth to apply: <0..4294967294> (kbps)";
        type uint32 {
          range "0..4294967294";
        }
      }
    }
  }

  grouping mpls-te-backup-bw-choice-grouping {
    choice bandwidth-option {
      leaf bandwidth {
        description
          "Amount of allocatable backup bw: <1..4294967295> kbps";
        type uint32 {
          range "1..4294967295";
        }
      }
      leaf unlimited {
        description
          "Unlimited amount of allocatable bw";
        type empty;
      }
    }
  }

  grouping mpls-te-class-global-pool-grouping {
    choice class-global-pool-choice {
      case class-type-choice {
        container class-type {
          leaf class-type-num {
            description
              "Enter the Class-type: <0..1>";
            type uint8 {
              range "0..1";
            }
          }
          uses mpls-te-backup-bw-choice-grouping;
        }
      }
      case global-pool-choice {
        container global-pool {
          uses mpls-te-backup-bw-choice-grouping;
        }
      }
    }
  }

  grouping mpls-te-mode-cfg-pathoption-list {
    list path-option {
      description
        "Specify the path-option to add, edit (or delete)";
      key "po-num";
      leaf po-num {
        description
          "Entry path-option number";
        type uint16 {
          range "1..65535";
        }
      }
      container explicit {
        description
          "setup based on preconfigured path";
        container identifier {
          description
            "Specify path by number";
          leaf pnum {
            description
              "Path number: <1..65535>";
            type uint16 {
              range "1..65535";
            }
          }
          leaf verbatim {
            description
              "Send out path as is, with no checking";
            type empty;
          }
        }
        container name {
          description
            "Specify path by name";
          leaf pname {
            description
              "Path name";
            type string;
          }
          leaf verbatim {
            description
              "Send out path as is, with no checking";
            type empty;
          }
        }
      }
    }
  }

  grouping mpls-te-popt-attributes-grouping {
    leaf attributes {
      description
        "Specify name of LSP attribute list";
      type string;
    }
  }

  grouping mpls-te-popt-segment-routing-grouping {
    leaf segment-routing {
      description
        "Specify segment-routing for this pathoption";
      type empty;
    }
  }

  grouping mpls-te-popt-verbatim-grouping {
    leaf verbatim {
      description
        "Send out path as is, with no checking";
      type empty;
    }
  }

  grouping mpls-te-popt-lockdown-grouping {
    leaf lockdown {
      description
        "Not a candidate for reoptimization";
      type empty;
    }
    leaf sticky {
      description
        "Stay on the same path after change in required resources";
      when '../lockdown';
      type empty;
    }
  }

  grouping mpls-te-popt-bandwidth-grouping {
    container bandwidth {
      description
        "Override the bandwidth configured on the tunnel";
      choice bandwidth-choice {
        case bandwidth-option {
          leaf bandwidth {
            description
              "Bandwidth requirement: <0..4294967295> kbps";
            type uint32;
          }
        }
        case sub-pool-option {
          leaf sub-pool {
            description
              "Tunnel uses sub-pool bandwidth: <1..4294967295> kbps";
            type uint32 {
              range "1..4294967295";
            }
          }
        }
      }
    }
  }

  grouping mpls-te-popt-pce-verbatim-grouping {
    leaf pce {
      description
        "Use PCE for path computation";
      type empty;
    }
    leaf address {
      description
        "PCE IPv4 address";
      when '../pce';
      type inet:ipv4-address;
    }
    leaf verbatim {
      description
        "Do not validate links from the ERO object";
      when '../pce';
      type empty;
    }
  }

  grouping mpls-te-popt-attributes-bw-grouping {
    choice popt-choice {
      case attributes-option {
        uses mpls-te-popt-attributes-grouping;
      }
      case bandwidth-option {
        uses mpls-te-popt-bandwidth-grouping;
      }
    }
  }

  grouping mpls-te-popt-attributes-bw-pce-grouping {
    choice popt-choice {
      case attributes-option {
        uses mpls-te-popt-attributes-grouping;
      }
      case bandwidth-option {
        uses mpls-te-popt-bandwidth-grouping;
      }
      case pce-option {
        uses mpls-te-popt-pce-verbatim-grouping;
      }
    }
  }

  grouping mpls-te-popt-id-grouping {
    choice id-choice {
      mandatory true;
      case identifier-option {
        leaf identifier {
          description
            "Specify an IP explicit path by number: <1..65535>";
          type uint16 {
            range "1..65535";
          }
        }
      }
      case name-option {
        leaf name {
          description
            "Specify an IP explicit path by name";
          type string;
        }
      }
    }
  }

  grouping mpls-te-setup-hold-priority-grouping {
    container priority {
      description
        "Setup & hold priority";
      presence "true";
      leaf setup-priority {
        description
          "Setup priority: <0..7>";
        mandatory true;
        type uint8 {
          range "0..7";
        }
      }
      leaf hold-priority {
        description
          "Hold priority: <0..7>";
        type uint8 {
          range "0..7";
        }
      }
    }
  }

  grouping config-mpls-grouping {
    container atm {
      description
        "Configure ATM options";
      leaf disable-headend-vc {
        description
          "Dedicated lsc capability: In this mode headend Tag VCs are disabled.";
        type empty;
      }
    }
    leaf cos-map {
      description
        "Configure MPLS CoS ATM Multi-VC CoS Map";
      type uint8 {
        range "1..255";
      }
    }
    container ip {
      description
        "Dynamic MPLS forwarding for IP";
      leaf default-route {
        description
          "Allow MPLS forwarding for ip default route";
        type empty;
      }
      container conf {
        leaf propagate-ttl {
          type boolean;
        }
      }
      container conf-arg {
        container propagate-ttl {
          leaf forwarded {
            type boolean;
          }
        }
      }
      container ttl-expiration {
        description
          "Control MPLS TTL expiration behavior";
        leaf pop {
          description
            "Popping labels on TTL expiration";
          type uint8 {
            range "1..6";
          }
        }
      }
    }
    container label {
      description
        "Label properties";
      container atm {
        description
          "Configure ATM options";
        leaf disable-headend-vc {
          description
            "Dedicated lsc capability: In this mode headend Tag VCs are disabled.";
          type empty;
        }
      }
      container mode {
        description
          "MPLS Label allocation mode";
        choice mode-choice {
          container all-vrfs {
            description
              "MPLS Label allocation mode for all VRFs";
            container protocol {
              description
                "MPLS Label allocation protocol";
              container all-afs {
                description
                  "All VRF (IPv4 and IPv6) address families";
                uses label-mode-grouping;
              }
              container bgp-vpnv4 {
                description
                  "VRF IPv4 address family";
                uses label-mode-grouping;
              }
              container bgp-vpnv6 {
                description
                  "VRF IPv6 address family";
                uses label-mode-grouping;
              }
            }
          }
          container vrf {
            description
              "MPLS Label allocation mode for a specific VRF";
            list vrf {
              key "vrf-name";
              leaf vrf-name {
                description
                  "VPN Routing/Forwarding instance name";
                type string;
              }
              container protocol {
                description
                  "MPLS Label allocation protocol";
                container all-afs {
                  description
                    "All VRF (IPv4 and IPv6) address families";
                  uses label-mode-grouping;
                }
                container bgp-vpnv4 {
                  description
                    "VRF IPv4 address family";
                  uses label-mode-grouping;
                }
                container bgp-vpnv6 {
                  description
                    "VRF IPv6 address family";
                  uses label-mode-grouping;
                }
              }
            }
          }
        }
      }
      leaf protocol {
        description
          "Set platform default label distribution protocol";
        type enumeration {
          enum ldp;
          enum tdp;
        }
      }
      container range {
        description
          "Label range";
        leaf min {
          type uint32 {
            range "16..1048575";
          }
        }
        leaf max {
          must '. > ../min' {
            error-message "Max label value must be > min label value";
          }
          type uint32 {
            range "16..1048575";
          }
        }
        container static {
          description
            "Specify block of labels for static bindings";
          leaf min {
            type uint32 {
              range "16..1048575";
            }
          }
          leaf max {
            must '. > ../min' {
              error-message "Max label value must be > min label value";
            }
            type uint32 {
              range "16..1048575";
            }
          }
        }
      }
    }
    container ldp {
      description
        "Label Distribution Protocol";
      container enable {
        leaf advertise-labels {
          type boolean;
        }
      }
      container enable2 {
        container advertise-labels {
          description
            "Label advertisements";
          uses mpls-for-to-grouping;
          list interface {
            description
              "Advertise /32 interface address";
            key "name";
            leaf name {
              type string;
            }
          }
          leaf oldstyle {
            description
              "Use old style (TDP) method for matching prefix acl";
            type empty;
          }
          container vrf {
            list vrf {
              key "vrf-name";
              leaf vrf-name {
                description
                  "VPN Routing/Forwarding instance name";
                type string;
              }
              uses mpls-for-to-grouping;
              container interface {
                uses ios-ifc:interface-grouping;
              }
              leaf oldstyle {
                description
                  "Use old style (TDP) method for matching prefix acl";
                type empty;
              }
            }
          }
        }
        container atm {
          description
            "Configure ATM MPLS options";
          leaf control-mode {
            description
              "Select LSP setup control mode for MPLS VCs";
            type enumeration {
              enum independent;
              enum ordered;
            }
          }
          leaf vc-merge {
            description
              "Select VC merge capability";
            type boolean;
          }
        }
        container backoff {
          description
            "Set LDP session backoff parameters";
          leaf initial {
            type uint32 {
              range "5..2147483";
            }
          }
          leaf max {
            must '. > ../initial' {
              error-message "Max value must be > initial value";
            }
            type uint32 {
              range "5..2147483";
            }
          }
        }
        container discovery {
          description
            "LDP discovery";
          container hello {
            description
              "LDP discovery Hello";
            leaf holdtime {
              description
                "LDP discovery Hello holdtime";
              type uint16 {
                range "1..65535";
              }
            }
            leaf interval {
              description
                "LDP discovery Hello interval";
              type uint16 {
                range "1..65535";
              }
            }
          }
          container targeted-hello {
            description
              "LDP discovery Targeted Hello";
            container accept {
              description
                "Accept targeted hellos";
              presence "Accept targeted hellos";
              leaf from {
                description
                  "Access list to specify acceptable targeted hello sources";
                type string;
              }
            }
            leaf holdtime {
              description
                "LDP discovery Hello holdtime";
              type uint16 {
                range "1..65535";
              }
            }
            leaf interval {
              description
                "LDP discovery Hello interval";
              type uint16 {
                range "1..65535";
              }
            }
          }
        }
        leaf entropy-label {
          description
            "Enable Entropy Label for LDP";
          type empty;
        }
        container explicit-null {
          description
            "Advertise Explicit Null label in place of Implicit Null";
          presence "Advertise Explicit Null label in place of Implicit Null";
          leaf for {
            description
              "Access-list specifying controls on destination prefixes";
            type string;
          }
          leaf to {
            description
              "Access-list specifying controls on LDP peers";
            type string;
          }
        }
        container graceful-restart {
          description
            "Configure Graceful Restart timers";
          presence "Configure Graceful Restart timers";
          container timers {
            description
              "Configure Graceful Restart timers";
            leaf forwarding-holding {
              description
                "Forwarding State Holding time";
              type uint16 {
                range "30..600";
              }
            }
            leaf max-recovery {
              description
                "Max-Recovery time";
              type uint16 {
                range "15..600";
              }
            }
            leaf neighbor-liveness {
              description
                "Neighbor-Liveness time";
              type uint16 {
                range "5..600";
              }
            }
          }
        }
        leaf holdtime {
          description
            "LDP session holdtime";
          type uint32 {
            range "15..2147483";
          }
        }
        container igp {
          description
            "Configure IGP-related LDP parameters";
          container sync {
            description
              "Configure LDP-IGP Synchronization parameters";
            leaf holddown {
              description
                "Hold down time in milliseconds";
              type uint32 {
                range "1..2147483647";
              }
            }
          }
        }
        container label {
          description
            "LDP label mode";
          presence "true";
          container label-Mode__config-ldp-lbl {
            container allocate {
              description
                "Allocate local labels for specified destination prefixes";
              container global {
                description
                  "Specify global Routing/Forwarding instance";
                presence "true";
                choice global-choice {
                  leaf host-routes {
                    description
                      "allocate local label for host routes only";
                    type empty;
                  }
                  leaf prefix-list {
                    description
                      "IP prefix-list for destination prefixes.";
                    type string;
                  }
                }
              }
            }
          }
        }
        container logging {
          description
            "Enable LDP logging";
          leaf neighbor-changes {
            description
              "Log LDP neighbor state changes";
            type boolean;
          }
          container password {
            description
              "Log LDP password events";
            container configuration-conf {
              leaf configuration {
                type boolean;
              }
            }
            container rollover-conf {
              leaf rollover {
                type boolean;
              }
            }
            choice ldp-pwd-choice {
              container configuration {
                description
                  "Log LDP password configuration changes";
                presence "true";
                leaf rate-limit {
                  description
                    "Messages per minute";
                  type uint8 {
                    range "1..60";
                  }
                }
              }
              container rollover {
                description
                  "Log LDP password rollover events";
                presence "true";
                leaf rate-limit {
                  description
                    "Messages per minute";
                  type uint8 {
                    range "1..60";
                  }
                }
              }
            }
          }
        }
        leaf loop-detection {
          description
            "Enable LDP Loop Detection";
          type empty;
        }
        leaf maxhops {
          description
            "Limit hop count for LDP LSP setup";
          type uint8 {
            range "0..255";
          }
        }
        container neighbor {
          uses neighbor-vrf-grouping;
          container vrf {
            list vrf {
              key "vrf-name";
              leaf vrf-name {
                description
                  "VPN Routing/Forwarding instance name";
                type string;
              }
              uses neighbor-vrf-grouping;
            }
          }
        }
        leaf nsr {
          description
            "Enable Non Stop Routing for LDP";
          type empty;
        }
        uses mpls-ldp-password-grouping;
        container request-labels {
          description
            "Access list to specify valid downstream on demand destinations.";
          leaf for {
            description
              "Access list to specify acceptable downstream on demand destinations";
            type string;
          }
        }
        container router-id {
          description
            "Select interface to prefer for LDP identifier address";
          container interface {
            uses ios-ifc:interface-grouping;
            leaf force {
              description
                "Forcibly change the LDP router id";
              type empty;
            }
          }
          list vrf {
            key "vrf-name";
            leaf vrf-name {
              description
                "VPN Routing/Forwarding instance name";
              type string;
            }
            container interface {
              uses ios-ifc:interface-grouping;
              leaf force {
                description
                  "Forcibly change the LDP router id";
                type empty;
              }
            }
          }
        }
        container tcp {
          description
            "Set TCP parameters for LDP";
          leaf pak-priority {
            description
              "Set (local) priority for LDP session TCP connection";
            type empty;
          }
        }
        container vrf {
          list vrf {
            key "vrf-name";
            leaf vrf-name {
              description
                "VPN Routing/Forwarding instance name";
              type string;
            }
            uses mpls-ldp-password-grouping;
          }
        }
      }
      container session {
        description
          "Configure session parameters";
        container protection {
          description
            "Configure session protection parameters";
          presence "true";
          uses duration-grouping;
          container for {
            description
              "Access-list to specify LDP peers";
            leaf acl-name {
              description
                "IP access-list for LDP peers; name or number (1-99)";
              type string;
            }
            uses duration-grouping;
          }
          container vrf {
            description
              "VPN Routing/Forwarding instance name";
            list vrf {
              key "vrf-name";
              leaf vrf-name {
                description
                  "VPN Routing/Forwarding instance name";
                type string;
              }
              container for {
                description
                  "Access-list to specify LDP peers";
                leaf acl-name {
                  description
                    "IP access-list for LDP peers; name or number (1-99)";
                  type string;
                }
                uses duration-grouping;
              }
              uses duration-grouping;
            }
          }
        }
      }
    }
    container prefix-map {
      description
        "Configure MPLS CoS Tag-VC Multi-VC Prefix Map";
      leaf nr {
        type uint8 {
          range "1..255";
        }
      }
      leaf access-list {
        description
          "Configure access-list for this prefix-map";
        type uint8 {
          range "1..255";
        }
      }
      leaf cos-map {
        description
          "Configure cos-map for this prefix-map";
        type uint8 {
          range "1..255";
        }
      }
    }
    container static {
      description
        "MPLS static application";
      presence "true";
      container binding {
        description
          "Establish static label bindings";
        container ipv4 {
          description
            "Bind IPv4 destination with label";
          list global {
            key "address mask";
            leaf address {
              type inet:ipv4-address;
            }
            leaf mask {
              type inet:ipv4-address;
            }
            uses mpls-static-binding-ipv4-grouping;
          }
          list vrf {
            key "name address mask";
            leaf name {
              must '/ios:native/ios:vrf/ios:definition[ios:name=current()] or /ios:native/ios:ip/ios:vrf[ios:name=current()]' {
                error-message "VRF must be created 1st, deleted last";
              }
              type string;
            }
            leaf address {
              type inet:ipv4-address;
            }
            leaf mask {
              type inet:ipv4-address;
            }
            uses mpls-static-binding-ipv4-grouping;
          }
        }
      }
    }
    container traffic-eng {
      description
        "Configure Traffic Engineering parameters";
      container auto-bw {
        description
          "auto-bw parameters";
        container timers {
          description
            "Enable auto-bw Timers Collection and Application";
          presence "Enable auto-bw Timers Collection and Application";
          leaf frequency {
            description
              "Interval between auto-bw data collection: <1..604800> seconds";
            type uint32 {
              range "1..604800";
            }
          }
        }
      }
      container auto-tunnel {
        description
          "Configure automatic TE tunnels";
        container backup {
          description
            "Configure auto-tunnel backup tunnel";
          presence "true";
          container config {
            description
              "Config commands to apply to all backup auto-tunnels";
            uses mpls-te-affinity-mask-grouping {
              refine "affinity-mask/affinity" {
                description
                  "Desired link attributes for links comprising tunnel: <0x0-0xFFFFFFFF>";
              }
            }
            container unnumbered-interface {
              description
                "Configure the interface to use for unnumbered";
              uses ios-ifc:interface-grouping;
            }
          }
          leaf nhop-only {
            description
              "Automatically create n-hop backup tunnels only";
            type empty;
          }
          container srlg {
            description
              "Shared Risk Link Groups influence backup tunnel path selection";
            leaf exclude {
              description
                "Backup tunnels avoid SRLGs of protected interfaces: < force | preferred >";
              type enumeration {
                enum force {
                  description
                    "Backup tunnels MUST not use SRLGs of protected interfaces";
                }
                enum preferred {
                  description
                    "Backup tunnels try to avoid using SRLGs of protected interfaces";
                }
              }
            }
          }
          container timers {
            description
              "Configure timers for backup auto-tunnels";
            container removal {
              description
                "Configure timer for removal of backup tunnel";
              container unused {
                description
                  "seconds between scanning to remove not in use tunnels";
                leaf interval {
                  description
                    "Seconds between scanning to remove not in use tunnels: <0..604800> seconds";
                  type uint32 {
                    range "0..604800";
                  }
                }
                leaf duration {
                  description
                    " How long auto backup is unused before removal: <0..604800> seconds, 0 = never remove";
                  type uint32 {
                    range "0..604800";
                  }
                }
              }
            }
          }
          container tunnel-num {
            description
              "Configure tunnel I/F numbers for backup auto-tunnels";
            uses mpls-te-tunnel-num-range-grouping;
          }
        }
        container mesh {
          description
            "Automatically create mesh tunnels";
          presence "true";
          container tunnel-num {
            description
              "Configure tunnel I/F numbers for mesh auto-tunnels";
            uses mpls-te-tunnel-num-range-grouping;
          }
        }
        container p2p {
          description
            "Enable and configure TE service P2P auto tunnels";
          presence "true";
          container config {
            description
              "Config commands to apply to all TE service P2P auto-tunnels";
            container unnumbered-interface {
              description
                "Configure the interface to use for unnumbered";
              uses ios-ifc:interface-grouping;
            }
          }
          container tunnel-num {
            description
              "Configure tunnel I/F numbers for TE service P2P auto-tunnels";
            uses mpls-te-tunnel-num-range-grouping;
          }
        }
        container primary {
          description
            "Automatically create one-hop primary tunnels";
          container config {
            description
              "Config commands to apply to all primary auto-tunnels";
            container mpls {
              description
                "Configure dynamic MPLS forwarding";
              leaf ip {
                description
                  "Configure dynamic MPLS forwarding for ip";
                type empty;
              }
            }
            container unnumbered-interface {
              description
                "Configure the interface to use for unnumbered";
              uses ios-ifc:interface-grouping;
            }
          }
          leaf onehop {
            description
              "Automatically create tunnel to all next-hops";
            type empty;
          }
          container timers {
            description
              "Configure timers for primary auto-tunnels";
            container removal {
              description
                "Configure removal of primary tunnels";
              leaf rerouted {
                description
                  "How long auto-tunnel primary can stay frr active: <30..604800> seconds";
                type uint32 {
                  range "30..604800";
                }
              }
            }
          }
          container tunnel-num {
            description
              "Configure tunnel I/F numbers for primary auto-tunnels";
            uses mpls-te-tunnel-num-range-grouping;
          }
        }
      }
      container ds-te {
        description
          "Configure standard DS-TE parameters";
        leaf bc-model {
          description
            "Configure BC model: < mam >";
          type enumeration {
            enum mam {
              description
                "BC Maximum allocation model";
            }
          }
        }
        leaf mode {
          description
            "Configure DS-TE mode: < ietf | migration >";
          type enumeration {
            enum ietf {
              description
                "Configure DS-TE standard mode";
            }
            enum migration {
              description
                "Configure DS-TE migration mode";
            }
          }
        }
        container te-classes {
          description
            "Specify TE-Class parameters";
          presence "true";
          list te-class {
            description
              "Configure a TE-Class";
            key "te-idx";
            leaf te-idx {
              description
                "Specify the TE-Class index: <0..7>";
              type uint8 {
                range "0..7";
              }
            }
            container class-type {
              description
                "Specify the Class-Type for this TE-Class";
              leaf type {
                description
                  "Specify Class-Type value (0 for Global and 1 for Sub-Pool)";
                type uint8 {
                  range "0..1";
                }
              }
              leaf priority {
                description
                  "Specify preemption priority value for this TE Class-Type: <0..7>";
                type uint8 {
                  range "0..7";
                }
              }
            }
            leaf unused {
              description
                "Specify that this TE-Class index is unused";
              type empty;
            }
          }
        }
      }
      leaf fault-oam {
        description
          "Node level fault OAM configuration";
        type empty;
      }
      container fast-reroute {
        description
          "fast-reroute parameters";
        container backup-prot-preempt {
          description
            "Preemption algorithm for backup tunnels";
          leaf optimize-bw {
            description
              "Reduce bandwidth wastage (default: minimize LSPs preempted)";
            type empty;
          }
        }
        container timers {
          description
            "configure fast-reroute timer";
          leaf promotion {
            description
              "Time between promotions: <0..604800> seconds, (0 disables promotion)";
            type uint32 {
              range "0..604800";
            }
          }
        }
      }
      container link-management {
        description
          "Link Management configuration";
        container timers {
          description
            "Link Management timers configuration";
          leaf bandwidth-hold {
            description
              "Link Management bandwidth hold timer: <1..300> seconds";
            type uint16 {
              range "1..300";
            }
          }
          leaf periodic-flooding {
            description
              "Link Management periodic flooding interval: <0..3600> seconds";
            type uint16 {
              range "0..3600";
            }
          }
        }
      }
      container logging {
        description
          "Trap logging configuration";
        container lsp {
          description
            "LSP-specific traps logging configuration";
          container path-errors {
            description
              "Log LSP Path Error traps";
            presence "Log LSP Path Error traps";
            leaf access-list {
              type ios-types:access-list-type;
            }
          }
          container preemption {
            description
              "Log LSP Preemption traps";
            presence "Log LSP Preemption traps";
            leaf access-list {
              type ios-types:access-list-type;
            }
          }
          container reservation-errors {
            description
              "Log LSP Reservation Error traps";
            presence "Log LSP Reservation Error traps";
            leaf access-list {
              type ios-types:access-list-type;
            }
          }
          container setups {
            description
              "Log LSP Establishment Traps";
            presence "Log LSP Establishment Traps";
            leaf access-list {
              type ios-types:access-list-type;
            }
          }
          container teardowns {
            description
              "Log LSP Teardown Traps";
            presence "Log LSP Teardown Traps";
            leaf access-list {
              type ios-types:access-list-type;
            }
          }
        }
        container tunnel {
          description
            "Tunnel-specific traps logging configuration";
          container lsp-selection {
            description
              "Log Tunnel LSP Selection traps";
            presence "Log Tunnel LSP Selection traps";
            leaf access-list {
              type ios-types:access-list-type;
            }
          }
          container lsp-switchover {
            description
              "Log Tunnel LSP Switchover traps";
            presence "Log Tunnel LSP Switchover traps";
            leaf access-list {
              type ios-types:access-list-type;
            }
          }
          container path {
            description
              "Log Tunnel Path-related traps";
            container change {
              description
                "Log Tunnel Path change traps";
              presence "Log Tunnel Path change traps";
              leaf access-list {
                type ios-types:access-list-type;
              }
            }
          }
        }
      }
      container lsp {
        description
          "Configure LSP parameters";
        list attributes {
          description
            "Configure LSP attributes";
          key "name";
          leaf name {
            description
              "Name of LSP attribute list";
            type string;
          }
          container mpls-te-mode-config-lsp-attr {
            uses mpls-te-affinity-mask-grouping {
              refine "affinity-mask/affinity" {
                description
                  "Specify attribute flags for links comprising LSP: <0x0-0xFFFFFFFF>";
              }
            }
            uses mpls-te-auto-bw-grouping;
            container autoroute {
              description
                "parameters for routing over tunnel";
              leaf destination {
                description
                  "announce tunnel destination to IP static route";
                type empty;
              }
            }
            container bandwidth {
              description
                "Specify LSP bandwidth";
              choice bandwidth-choice {
                leaf bw {
                  description
                    "Bandwidth requirement: <0..4294967295> (kbps)";
                  type uint32 {
                    range "0..4294967295";
                  }
                }
                leaf sub-pool {
                  description
                    "Sub-pool Bandwidth requirement: <1..4294967295> (kbps)";
                  type uint32 {
                    range "1..4294967295";
                  }
                }
              }
            }
            container bfd-reverse-path {
              description
                "Specify bfd reverse path";
              leaf binding-label {
                description
                  "MPLS binding-label value: <16..1048575>";
                type uint32 {
                  range "16..1048575";
                }
              }
            }
            container lockdown {
              description
                "Lockdown the LSP--disable reoptimization";
              presence "true";
              leaf sticky {
                description
                  "stay on the same path after change in required resources";
                type empty;
              }
            }
            uses mpls-te-path-selection-grouping;
            container pce {
              presence "true";
              description
                "Specify PCE Configuration";
              container disjoint-path {
                description
                  "Disjoint Path Configuration";
                leaf source {
                  description
                    "Source IPv4 address";
                  type inet:ipv4-address;
                }
                leaf type {
                  description
                    "Disjointness type: <link | node | srlg>";
                  type enumeration {
                    enum link {
                      description
                        "Link Disjointness";
                    }
                    enum node {
                      description
                        "Node Disjointness";
                    }
                    enum srlg {
                      description
                        "SRLG Disjointness";
                    }
                  }
                }
                leaf group-id {
                  description
                    "Group ID: <1..4294967295>";
                  type uint32 {
                    range "1..4294967295";
                  }
                }
              }
            }
            uses mpls-te-setup-hold-priority-grouping {
              refine "priority" {
                description
                  "Specify LSP priority";
              }
            }
            container protection {
              description
                "Enable failure protection";
              presence "true";
              container fast-reroute {
                description
                  "Enable fast-reroute failure protection";
                presence "true";
                leaf bw-protect {
                  description
                    "Enable BW protection";
                  type empty;
                }
              }
            }
            leaf record-route {
              description
                "Record the route used by the LSP";
              type empty;
            }
          }
        }
      }
      leaf nsr {
        description
          "TE NSR configuration";
        type empty;
      }
      container path-option {
        description
          "Configure path-option";
        container list {
          description
            "Configure path-option list";
          list identifier {
            description
              "Specify path-option list by number";
            key "pol-num";
            leaf pol-num {
              description
                "Path option list identifier: <1..65535>";
              type uint16 {
                range "1..65535";
              }
            }
            uses mpls-te-mode-cfg-pathoption-list;
          }
          list name {
            description
              "Specify path-option list by name";
            key "pol-name";
            leaf pol-name {
              description
                "Path option list name";
              type string;
            }
            uses mpls-te-mode-cfg-pathoption-list;
          }
        }
      }
      container path-selection {
        description
          "Path Selection Configuration";
        uses mpls-te-path-selection-common;
        container overload {
          description
            "Overload Node Configuration";
          container allow {
            description
              "Allow overloaded nodes in CSPFs";
            leaf head {
              description
                "Allow overloaded head node in TE CSPF";
              type empty;
            }
            leaf middle {
              description
                "Allow overloaded middle node in TE CSPF";
              type empty;
            }
            leaf tail {
              description
                "Allow overloaded tail node in TE CSPF";
              type empty;
            }
          }
        }
        leaf tiebreaker {
          description
            "Tiebreaker Configuration: < max-fill | min-fill | random >";
          type mpls-te-tiebreaker-type;
        }
      }
      container pcc {
        description
          "Path Computation Client form MPLS-TE";
        leaf report-all {
          description
            "Force reporting of all MPLS-TE LSPs";
          type empty;
        }
        container peer {
          description
            "Specify a PCEP peer";
          list ipv4 {
            key "ipv4";
            leaf ipv4 {
              description
                "PCE server IPv4 address";
              type inet:ipv4-address;
            }
            leaf source {
              description
                "Source IPv4 address to use";
              type inet:ipv4-address;
            }
            leaf precedence {
              description
                "Specify Precedence for this PCE: <0..255>, (default is 0)";
              type uint8 {
                range "0..255";
              }
            }
            leaf force-autoroute {
              description
                "Force autoroute for all pce initiated lsp";
              type empty;
            }
            leaf delegate-only {
              description
                "PCE server does not support requests if stateful";
              type empty;
            }
            choice keychain-password-choice {
              leaf keychain {
                description
                  "Use key-chain: <password text> | <keychain name>";
                type string;
              }
              container password {
                description
                  "Configure PCE MD5 password";
                choice password-type-choice {
                  leaf clear {
                    description
                      "Unencrypted password: <password text> | <keychain name>";
                    type string;
                  }
                  leaf encrypted {
                    description
                      "Hidden password: <password text> | <keychain name>";
                    type string;
                  }
                }
              }
            }
          }
        }
      }
      container reoptimize {
        description
          "Reoptimization parameters";
        container events {
          description
            "Reoptimization triggers";
          leaf link-up {
            description
              "Reoptimize tunnels on link up events";
            type empty;
          }
        }
        container timers {
          description
            "Reoptimization timers";
          container delay {
            description
              "Delay reoptimization action";
            leaf after-frr {
              description
                "Delay LSP reoptimization in the event of FRR: <0..120> seconds";
              type uint8 {
                range "0..120";
              }
            }
            leaf cleanup {
              description
                "Delay cleanup of reoptimized LSP: <0..60> seconds";
              type uint8 {
                range "0..60";
              }
            }
            leaf installation {
              description
                "Delay replacement of current LSP by reoptimized LSP: <0..3600> seconds";
              type uint16 {
                range "0..3600";
              }
            }
          }
          leaf frequency {
            description
              "Interval between reoptimization scans: <0..604800> seconds";
            type uint32 {
              range "0..604800";
            }
          }
        }
      }
      container signalling {
        description
          "Traffic Engineering Signalling Parameters";
        container advertise {
          description
            "Signalling advertisement parameters";
          container explicit-null {
            description
              "Use MPLS encoding for Explicit-Null Label in signalling messages";
            presence "true";
            leaf access-list {
              description
                "IP access-list to determine applicable signalling peers. Either a string or number: <1..99>";
              type union {
                type uint8 {
                  range "1..99";
                }
                type string;
              }
            }
          }
        }
        container forwarding {
          description
            "Control interaction of LSP signalling and LFIB maintenance";
          leaf sync {
            description
              "Program linecard LFIBs before signalling LSP label upstream";
            type empty;
          }
        }
      }
      container topology {
        description
          "Topology Database Configuration";
        container holddown {
          description
            "Topology Database hold down timers";
          leaf sigerr {
            description
              "Link hold down time for signalling errors: <0..300> seconds";
            type uint16 {
              range "0..300";
            }
          }
        }
        container mesh-group {
          description
            "mesh-group commands";
          leaf accept-domain {
            description
              "accept receipt of Domain Scope";
            type empty;
          }
        }
      }
      container trace {
        description
          "Trace configuration";
        container buffer-size {
          description
            "Trace buffer size configuration";
          leaf error {
            description
              "Trace error buffer size: <1..500> kB, (default 32kB)";
            type uint16 {
              range "1..500";
            }
          }
          leaf event {
            description
              "Trace event buffer size: <1..2500> kB, (default 1% of system memory)";
            type uint16 {
              range "1..2500";
            }
          }
          leaf warning {
            description
              "Trace warning buffer size: <1..250> kB (default 32kB)";
            type uint8 {
              range "1..250";
            }
          }
        }
      }
      leaf tunnels {
        description
          "Traffic Engineering tunnels";
        type empty;
      }
    }
    container tp {
      description
        "Configure MPLS Transport Profile parameters";
      presence "true";
    }
    container discovery {
      description
        "Configure discovery parameters";
      container vpn {
        description
          "Configure discovery vpn parameters";
        leaf interval {
          description
            "vpn interval (1-86400)";
          type uint32 {
            range "1..86400";
          }
        }
        leaf next-hop {
          description
            "vpn next hop parameters";
          type empty;
        }
      }
    }
  }

  grouping config-interface-mpls-grouping {
    description
      "Configure MPLS interface parameters";
    container accounting {
      description
        "Enable MPLS accounting on this interface";
      container experimental {
        description
          "Count packets by MPLS experimental value on this interface";
        leaf input {
          description
            "received packets";
          type empty;
        }
        leaf output {
          description
            "transmitted packets";
          type empty;
        }
      }
    }
    container bgp {
      description
        "MPLS BGP";
      leaf forwarding {
        description
          "Configure MPLS forwarding for directly connected BGP peers";
        type empty;
      }
    }
    leaf ip {
      description
        "Configure dynamic MPLS forwarding for IP";
      type empty;
    }
    container label {
      description
        "Label properties";
      leaf protocol {
        description
          "Configure label/tag distribution protocol (LDP/TDP)";
        type enumeration {
          enum both;
          enum ldp;
          enum tdp;
        }
      }
    }
    container ldp {
      description
        "Configure Label Distribution Protocol (LDP) parameters";
      container discovery {
        description
          "Configure interface LDP Discovery parameters";
        leaf transport-address {
          description
            "Specify interface LDP transport address";
          type ldp-discovery-address-type;
        }
      }
      container igp {
        description
          "Configure IGP-related parameters";
        container sync {
          description
            "Allow LDP-IGP Synchronization on this interface";
          presence "true";
          leaf delay {
            description
              "Configure LDP to IGP sync achieved notification delay time (seconds)";
            type uint8 {
              range "5..60";
            }
          }
        }
      }
    }
    leaf mtu {
      description
        "Set MPLS Maximum Transmission Unit";
      type union {
        type uint16 {
          range "1501..1524";
        }
        type uint16 {
          range "64..1500";
        }
        type uint16 {
          range "64..9216";
        }
      }
    }
    container nhrp {
      description
        "MPLS NHRP commands";
      presence "true";
      leaf inspect {
        description
          "NHRP MPLS inspect command";
        type empty;
      }
    }
    container traffic-eng {
      description
        "Configure Traffic Engineering parameters";
      leaf administrative-weight {
        description
          "Set the administrative weight for the interface: <0..4294967295>";
        type uint32 {
          range "0..4294967295";
        }
      }
      leaf attribute-flags {
        description
          "Set user-defined interface attribute flags:  <0x0-0xFFFFFFFF>";
        type mpls-te-attribute-flags;
      }
      container backup-path {
        description
          "Configure an MPLS TE backup for this interface";
        list Tunnel {
          description
            "Tunnel interface number: <0..2147483647>";
          key "name";
          leaf name {
            type uint32 {
              range "0..2147483647";
            }
          }
        }
      }
      container flooding {
        description
          "Set flooding parameters";
        container thresholds {
          description
            "Set flooding thresholds";
          leaf-list down {
            description
              "Set the thresholds for decreased resource availability in percentage: <0..100>";
            max-elements 16;
            type uint8 {
              range "0..100";
            }
          }
          leaf-list up {
            description
              "Set the thresholds for increased resource availability in percentage: <0..100>";
            max-elements 16;
            type uint8 {
              range "0..100";
            }
          }
        }
      }
      container passive-interface {
        description
          "Force a flood of non-IGP link";
        leaf nbr-te-id {
          description
            "Set the neighbor TE ID (router-id)";
          type inet:ipv4-address;
        }
        leaf nbr-if-addr {
          description
            "Set the Neighbor IP interface address";
          type inet:ipv4-address;
        }
        container nbr-igp-id {
          description
            "Set the Neighbor IGP ID (system-id)";
          choice igp-id-choice {
            leaf isis {
              description
                "Set the neighbor ISIS node ID";
              type ios-isis:isis-net;
            }
            leaf ospf {
              description
                "Set the neighbor OSPF node ID";
              type inet:ipv4-address;
            }
          }
        }
      }
      leaf tunnels {
        description
          "enable MPLS Traffic Engineering tunnels";
        type empty;
      }
    }
    leaf mldp {
      description
        "Configure interface MLDP routing protocol";
      default "true";
      type boolean;
    }
  }

  grouping config-tunnel-mpls-grouping {
    description
      "Configure MPLS tunnel parameters";
    container traffic-eng {
      uses mpls-te-affinity-mask-grouping {
        refine "affinity-mask/affinity" {
          description
            "Desired link attributes for links comprising tunnel: <0x0-0xFFFFFFFF>";
        }
      }
      uses mpls-te-auto-bw-grouping {
        refine "auto-bw" {
          description
            "Specify mpls tunnel should automatically change BW";
        }
        refine "auto-bw/adjustment-threshold" {
          description
            "Set the bandwidth change threshold to trigger adjustment";
        }
        refine "auto-bw/collect-bw" {
          description
            "Just collect bandwidth info on this tunnel";
        }
        refine "auto-bw/frequency" {
          description
            "Frequency to change tunnel BW: <300..604800>";
        }
        refine "auto-bw/max-bw" {
          description
            "Set the maximum bandwidth for auto-bw on this tunnel: <0..4294967295> (kbps)";
        }
        refine "auto-bw/min-bw" {
          description
            "Set the minimum bandwidth for auto-bw on this tunnel: <0..4294967294> (kbps)";
        }
        refine "auto-bw/overflow-limit" {
          description
            "Set consecutive samples exceeding threshold which trigger adjustment: <1..10>";
        }
      }
      container autoroute {
        description
          "parameters for routing over tunnel";
        leaf announce {
          type empty;
        }
        container metric {
          description
            "Specify mpls tunnel metric";
          choice metric-choice {
            leaf range {
              description
                "Set tunnel metric for autoroutes: <1..4294967295>";
              type uint32 {
                range "1..4294967295";
              }
            }
            leaf absolute {
              description
                "Set absolute metric for all autoroutes over tunnel: <1..4294967295>";
              type uint32 {
                range "1..4294967295";
              }
            }
            leaf relative {
              description
                "Adjust tunnel metric for autoroutes relative to IGP: <-10..10>";
              type int8 {
                range "-10..10";
              }
            }
          }
        }
        leaf destination {
          description
            "announce tunnel destination to IP static route";
          type empty;
        }
      }
      container backup-bw {
        choice backup-bw-choice {
          case bw-option {
            leaf bandwidth {
              description
                "Amount of allocatable backup bw, any lsp may use: <1..4294967295> kbps";
              type uint32 {
                range "1..4294967295";
              }
            }
          }
          case sub-pool-option {
            container sub-pool {
              description
                "Enter Allocatable amount for Sub-Pool bw";
              choice sub-pool-choice {
                leaf unlimited {
                  description
                    "Unlimited amount for Sub-Pool bw";
                  type empty;
                }
                container sub-pool-config {
                  leaf bandwidth {
                    description
                      "Amount of allocatable backup bw, only sub-pool may use: <1..4294967295> kbps";
                    type uint32 {
                      range "1..4294967295";
                    }
                  }
                  uses mpls-te-class-global-pool-grouping {
                    refine "class-global-pool-choice/class-type-choice/class-type/class-type-num" {
                      description
                        "Enter the Class-type: <0..0>";
                      must '. = 0';
                    }
                  }
                }
              }
            }
          }
          case class-global-pool-option {
            uses mpls-te-class-global-pool-grouping;
          }
        }
      }
      container bandwidth {
        description
          "tunnel bandwidth requirement";
        choice bandwidth-choice {
          case bandwidth-option {
            leaf bw {
              description
                "bandwidth requirement: <0..4294967295> kbps";
              type uint32;
            }
            leaf class-type {
              description
                "classtype value";
              type uint8 {
                range "0..1";
              }
            }
          }
          case sub-pool-option {
            leaf sub-pool {
              description
                "tunnel uses sub-pool bandwidth: <1..4294967295> kbps";
              type uint32 {
                range "1..4294967295";
              }
            }
          }
        }
      }
      container bfd {
        description
          "Bidirectional Forwarding Detection (BFD) configuration";
        leaf sbfd {
          description
            " Seamless BFD";
          type string;
        }
      }
      container binding-sid {
        description
          "Binding Segment Identifier";
        leaf label {
          description
            "MPLS label (depends on the configured static label range)";
          must '. >= /ios:native/ios:mpls/ios-mpls:label/ios-mpls:range/ios-mpls:static/ios-mpls:min and . <= /ios:native/ios:mpls/ios-mpls:label/ios-mpls:range/ios-mpls:static/ios-mpls:max';
          type uint32 {
            range "16..1048575";
          }
        }
      }
      container exp {
        description
          "Set the experimental values allowed for this interface";
        leaf-list exp-value {
          description
            "Enter up to 8 experimental values separated by white-spaces: <0..7>";
          max-elements 8;
          type uint8 {
            range "0..7";
          }
        }
        leaf default {
          description
            "Default all unconfigured exp to this interface";
          type empty;
        }
      }
      container exp-bundle {
        description
          "Configure the tunnel as a bundle";
        leaf master {
          description
            "Master tunnel for the bundle";
          type empty;
        }
        container member {
          description
            "Member tunnel for the bundle";
          leaf Tunnel {
            description
              "Tunnel interface number: <0..2147483647>";
            type uint32 {
              range "0..2147483647";
            }
          }
        }
      }
      container fast-reroute {
        description
          "Specify mpls tunnel can be fast-rerouted";
        presence "true";
        leaf bw-protect {
          description
            "bandwidth protection desired";
          type empty;
        }
        leaf node-protect {
          description
            "node protection desired";
          type empty;
        }
      }
      container forwarding-adjacency {
        description
          "Treat this tunnel as a Forwarding Adjacency";
        presence "true";
        leaf holdtime {
          description
            "How long to wait upon flooding a down Forwarding Adjacency: <0..4294967295> msec";
          type uint32;
        }
      }
      container interface {
        description
          "Add tunnel interface config";
        container down {
          description
            " Tunnel interface down config";
          leaf delay {
            description
              "Tunnel interface down delay config: <0..0>";
            type uint32;
            must '. = 0';
          }
        }
      }
      leaf load-share {
        description
          "Specify tunnel load-sharing metric: <0..1000000>";
        type uint32 {
          range "0..1000000";
        }
      }
      leaf name {
        description
          "specify a name describing the TE tunnel";
        type string {
          length "1..63";
        }
      }
      container path-option {
        list working {
          key "id";
          leaf id {
            type uint32;
          }
          choice path-option-choice {
            mandatory true;
            case dynamic-option {
              container dynamic {
                description
                  "Setup based on dynamically calculated path";
                presence "true";
                choice popt-choice {
                  case option-segment-routing {
                    container segment-routing {
                      description
                        "Specify segment-routing for this pathoption";
                      presence "true";
                      choice popt-sr-choice {
                        case option-attributes {
                          uses mpls-te-popt-attributes-grouping;
                        }
                        case option-lockdown {
                          uses mpls-te-popt-lockdown-grouping;
                        }
                        case option-pce {
                          uses mpls-te-popt-pce-verbatim-grouping;
                        }
                      }
                    }
                  }
                  case option-pce {
                    uses mpls-te-popt-pce-verbatim-grouping;
                  }
                  case option-lockdown {
                    uses mpls-te-popt-lockdown-grouping;
                    uses mpls-te-popt-bandwidth-grouping;
                  }
                  case option-attibutes {
                    uses mpls-te-popt-attributes-grouping;
                  }
                }
              }
            }
            case explicit-option {
              container explicit {
                description
                  "Setup based on preconfigured path";
                uses mpls-te-popt-id-grouping;
                uses mpls-te-popt-segment-routing-grouping;
                uses mpls-te-popt-verbatim-grouping;
                choice popt-choice {
                  case attributes-option {
                    uses mpls-te-popt-attributes-grouping;
                  }
                  case lockdown-option {
                    uses mpls-te-popt-lockdown-grouping;
                    uses mpls-te-popt-bandwidth-grouping {
                      when '(count(segment-routing) = 0)';
                    }
                  }
                }
              }
            }
            case segment-routing-option {
              container segment-routing {
                description
                  "Specify segment-routing for this pathoption";
                presence "true";
                uses mpls-te-popt-lockdown-grouping;
              }
            }
          }
        }
        list protect {
          key "id";
          leaf id {
            type leafref {
              path "../../working/id";
            }
          }
          choice protect-choice {
            mandatory true;
            case diverse-option {
              container diverse {
                description
                  "Setup based on dynamically calculated diverse path";
                leaf node {
                  description
                    "Use at least node diverse path";
                  type empty;
                }
                leaf srlg {
                  description
                    "Use at least srlg diverse path";
                  type empty;
                }
                uses mpls-te-popt-segment-routing-grouping;
                leaf non-revertive {
                  description
                    "Diverse non-revertive";
                  type empty;
                }
                uses mpls-te-popt-pce-verbatim-grouping;
                leaf lockdown {
                  description
                    "Not a candidate for reoptimization";
                  type empty;
                }
                uses mpls-te-popt-attributes-bw-grouping {
                  when '(count(./pce) = 1) or (count(./lockdown) = 1)';
                }
                must '(count(.) = 0) or (count(./pce) = 1) or (count(./lockdown) = 1)' {
                  error-message "Diverse protect path-option must have either pce of lockdown if any other option is configured.";
                }
              }
            }
            case explicit-option {
              container explicit {
                description
                  "Setup based on preconfigured path";
                uses mpls-te-popt-id-grouping;
                uses mpls-te-popt-segment-routing-grouping;
                leaf non-revertive {
                  description
                    "Diverse non-revertive";
                  type empty;
                }
                uses mpls-te-popt-verbatim-grouping;
                uses mpls-te-popt-attributes-bw-grouping;
              }
            }
            case list-option {
              container list {
                description
                  "A list of backup paths";
                uses mpls-te-popt-id-grouping;
                uses mpls-te-popt-segment-routing-grouping;
                leaf non-revertive {
                  description
                    "Make the protect path non-revertive";
                  type empty;
                }
                uses mpls-te-popt-attributes-bw-pce-grouping;
              }
            }
          }
        }
      }
      uses mpls-te-path-selection-grouping {
        augment "path-selection" {
          leaf cost-limit {
            description
              "Cost Limit Configuration: <1..4294967295>";
            type uint32 {
              range "1..4294967295";
            }
          }
          leaf hop-limit {
            description
              "Cost Limit Configuration: <1..255>";
            type uint8 {
              range "1..255";
            }
          }
          leaf tiebreaker {
            description
              "Tiebreaker Configuration: < max-fill | min-fill | random >";
            type mpls-te-tiebreaker-type;
          }
        }
      }
      uses mpls-te-setup-hold-priority-grouping {
        refine "priority" {
          description
            "Tunnel priority";
        }
        refine "priority/hold-priority" {
          must '../setup-priority >= .';
        }
      }
      container record-route {
        description
          "record the route used by the tunnel";
        presence "true";
      }
    }
  }

  augment "/ios:native/ios:mpls" {
    uses config-mpls-grouping;
  }

  augment "/ios:native/ios:interface/ios:FastEthernet/ios:mpls" {
    uses config-interface-mpls-grouping;
  }

  augment "/ios:native/ios:interface/ios:GigabitEthernet/ios:mpls" {
    uses config-interface-mpls-grouping;
  }

  augment "/ios:native/ios:interface/ios:TenGigabitEthernet/ios:mpls" {
    uses config-interface-mpls-grouping;
  }

  augment "/ios:native/ios:interface/ios:FiveGigabitEthernet/ios:mpls" {
    uses config-interface-mpls-grouping;
  }

  augment "/ios:native/ios:interface/ios:AppGigabitEthernet/ios:mpls" {
    uses config-interface-mpls-grouping;
  }

  augment "/ios:native/ios:interface/ios:TwentyFiveGigE/ios:mpls" {
    uses config-interface-mpls-grouping;
  }

  augment "/ios:native/ios:interface/ios:TwoGigabitEthernet/ios:mpls" {
    uses config-interface-mpls-grouping;
  }

  augment "/ios:native/ios:interface/ios:FortyGigabitEthernet/ios:mpls" {
    uses config-interface-mpls-grouping;
  }

  augment "/ios:native/ios:interface/ios:HundredGigE/ios:mpls" {
    uses config-interface-mpls-grouping;
  }

  augment "/ios:native/ios:interface/ios:Vlan/ios:mpls" {
    uses config-interface-mpls-grouping;
  }

  augment "/ios:native/ios:interface/ios:Port-channel/ios:mpls" {
    uses config-interface-mpls-grouping;
  }

  augment "/ios:native/ios:interface/ios:Loopback/ios:mpls" {
    uses config-interface-mpls-grouping;
  }

  augment "/ios:native/ios:interface/ios:Tunnel/ios:mpls" {
    uses config-interface-mpls-grouping;
  }

  augment "/ios:native/ios:interface/ios:BDI/ios:mpls" {
    uses config-interface-mpls-grouping;
  }

  augment "/ios:native/ios:interface/ios:BD-VIF/ios:mpls" {
    uses config-interface-mpls-grouping;
  }
}
