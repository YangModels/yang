module Cisco-IOS-XE-cloud-services-cfg {
  yang-version 1.1;
  namespace "http://cisco.com/ns/yang/Cisco-IOS-XE-cloud-services-cfg";
  prefix cloudm;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for configuration of cloud services
     parameters.
     Copyright (c) 2022 by Cisco Systems, Inc.
     All rights reserved.";

  revision 2023-07-01 {
    description
      "- Add HTTP validation for cloud proxy type";
    reference
      "2.0.0";
    cisco-semver:module-version "2.0.0";
  }
  revision 2023-03-01 {
    description
      "Initial revision";
    reference
      "1.0.0";
    cisco-semver:module-version "1.0.0";
  }

  typedef cloudm-config-db-proxy-type {
    type enumeration {
      enum cloud-services-proxy-type-https {
        value 0;
        description
          "HTTPS proxy type";
      }
      enum cloud-services-proxy-type-unknown {
        value 1;
        description
          "Unknown proxy type";
      }
      enum cloud-services-proxy-type-http {
        value 2;
        description
          "HTTP proxy";
      }
    }
    description
      "Type of proxy transport";
  }

  grouping cloudm-config-db-proxy {
    description
      "Proxy for cloud services access";
    leaf host {
      type string {
        length "0..230";
        pattern '(([A-Za-z0-9]+[A-Za-z0-9.\-]*|([0-9]{1,3}\.){3}[0-9]{1,3}|\[[a-fA-F0-9:]+\])(:[0-9]{1,5})?)?';
      }
      default "";
      description
        "Proxy URL without scheme";
    }
    leaf proxy-type {
      type cloudm:cloudm-config-db-proxy-type;
      must "((../proxy-type = 'cloud-services-proxy-type-http') and (../host != '')) or ((../proxy-type = 'cloud-services-proxy-type-unknown') and (../host = ''))" {
        error-message "proxy type can only be HTTP, or empty and unknown";
        error-app-tag "must-violation";
      }
      default "cloud-services-proxy-type-unknown";
      description
        "Proxy transport";
    }
  }

  grouping st-cloudm-global-config {
    description
      "Parameters for cloud services access";
    container proxy {
      description
        "Configures cloud services proxy";
      uses cloudm:cloudm-config-db-proxy;
    }
  }

  container cloud-services-cfg-data {
    description
      "Cloud services configuration data";
    container cloudm-config {
      presence "cloudm-config";
      description
        "Cloud services configuration parameters";
      uses cloudm:st-cloudm-global-config;
    }
  }
}
