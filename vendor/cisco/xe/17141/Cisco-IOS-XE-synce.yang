module Cisco-IOS-XE-synce {
  yang-version 1.1;
  namespace "http://cisco.com/ns/yang/Cisco-IOS-XE-synce";
  prefix ios-synce;

  import cisco-semver {
    prefix cisco-semver;
  }
  import Cisco-IOS-XE-interface-common {
    prefix ios-ifc;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Synchronous Ethernet Yang Model.
     Copyright (c) 2016-2020 by Cisco Systems, Inc.
     All rights reserved.";

  revision 2024-03-01 {
    description
      "- Added support to enforce interface clock source to various Quality Level values";
    cisco-semver:module-version "3.2.0";
  }
  revision 2022-11-01 {
    description
      "- Update yang-version to 1.1";
    cisco-semver:module-version "3.1.0";
  }
  revision 2020-07-01 {
    description
      "- Changed quality-level from a list to a container
       - Obsolete old model and remodelled the network-clock input-source priority <> controller";
    cisco-semver:module-version "3.0.0";
  }
  revision 2020-03-01 {
    description
      "- Added the option revertive in tod-clock container
       - Added the option of displaying <slot>/<card>/<port> in all external nodes
       - Added the t1 option in the external container
       - Added the option <slot>/<card>/<port> in network-clock external
       - Corrected the issues with quality-level container
       - Corrected the issues with input-source container
       - Corrected the issues with participate container";
    cisco-semver:module-version "2.0.0";
  }
  revision 2019-11-01 {
    description
      "Initial revision";
    cisco-semver:module-version "1.0.0";
  }

  typedef synce-external-intf {
    type union {
      type enumeration {
        enum R0;
        enum R1;
      }
      type string {
        pattern '([0-9]/)([0-9]|1[0-5])(/([0-9]|1[0-5]))';
      }
    }
  }

  grouping config-synce-ext-port-grouping {
    leaf port {
      type synce-external-intf;
    }
  }

  grouping config-synce-ext-t1-option-grouping {
    container t1-options {
      description
        "Various options for t1";
      when "/ios:native/ios:network-clock/ios-synce:synchronization-synce/ios-synce:ssm/ios-synce:option/ios-synce:option-2/ios-synce:generation = 'GEN2'";
      choice opt {
        leaf d4 {
          type empty;
        }
        leaf esf {
          type empty;
        }
        leaf sf {
          type empty;
        }
      }
      leaf hold-off {
        type union {
          type enumeration {
            enum 0;
          }
          type uint16 {
            range "50..10000";
          }
        }
      }
    }
  }

  grouping config-synce-ext-common-t1-option-grouping {
    choice opt {
      leaf d4 {
        description
          "D4 Super Frame Signal Mode";
        type empty;
      }
      leaf esf {
        description
          "Extended Super Frame Signal Mode";
        type empty;
      }
      leaf sf {
        description
          "Super Frame Signal Mode";
        type empty;
      }
      leaf word {
        description
          "Input source description";
        type string;
      }
    }
    leaf linecode {
      description
        "Linecode option";
      type enumeration {
        enum ami;
        enum b8zs;
      }
    }
    leaf line-build-out {
      description
        "Line build out option";
      type enumeration {
        enum 0-133ft;
        enum 133-266ft;
        enum 266-399ft;
        enum 399-533ft;
        enum 533-655ft;
      }
    }
  }

  grouping config-synce-ext2-t1-option-grouping {
    container t1-options {
      description
        "Various options for t1";
      when "/ios:native/ios:network-clock/ios-synce:synchronization-synce/ios-synce:ssm/ios-synce:option/ios-synce:option-2/ios-synce:generation = 'GEN2'";
      uses config-synce-ext-common-t1-option-grouping;
      leaf Word {
        description
          "Input source description";
        type string;
      }
    }
  }

  grouping config-synce-ext3-t1-option-grouping {
    container t1-options {
      description
        "Various options for t1";
      when "/ios:native/ios:network-clock/ios-synce:synchronization-synce/ios-synce:ssm/ios-synce:option/ios-synce:option-2/ios-synce:generation = 'GEN2'";
      uses config-synce-ext-common-t1-option-grouping;
    }
  }

  grouping config-synce-grouping {
    leaf eec {
      type uint8 {
        range "1..2";
      }
      default "1";
    }
    container external {
      list slot-port {
        key "slot-card-name";
        leaf slot-card-name {
          description
            "<slot>/<card>/<port>";
          type string {
            pattern '([0-9]/)([0-9]|1[0-5])(/([0-9]|1[0-5]))';
          }
        }
        leaf signal {
          type enumeration {
            enum 10m;
            enum 2048k;
            enum 2m;
            enum e1;
            enum t1;
          }
        }
        leaf cas {
          type empty;
        }
        leaf crc4 {
          type empty;
        }
        leaf fas {
          type empty;
        }
        uses config-synce-ext-t1-option-grouping;
        leaf hold-off {
          type union {
            type enumeration {
              enum 0;
            }
            type uint16 {
              range "50..10000";
            }
          }
        }
      }
      list R0 {
        key "signal";
        leaf signal {
          type enumeration {
            enum 10m;
            enum 2048k;
            enum 2m;
            enum e1;
            enum t1;
          }
        }
        leaf cas {
          type empty;
        }
        leaf crc4 {
          type empty;
        }
        leaf fas {
          type empty;
        }
        uses config-synce-ext-t1-option-grouping;
        leaf hold-off {
          type union {
            type enumeration {
              enum 0;
            }
            type uint16 {
              range "50..10000";
            }
          }
        }
      }
      list R1 {
        key "signal";
        leaf signal {
          type enumeration {
            enum 10m;
            enum 2048k;
            enum 2m;
            enum e1;
            enum t1;
          }
        }
        leaf cas {
          type empty;
        }
        leaf crc4 {
          type empty;
        }
        leaf fas {
          type empty;
        }
        uses config-synce-ext-t1-option-grouping;
        leaf hold-off {
          type union {
            type enumeration {
              enum 0;
            }
            type uint16 {
              range "50..10000";
            }
          }
        }
      }
    }
    container hold-off {
      leaf value {
        type union {
          type enumeration {
            enum 0;
          }
          type uint16 {
            range "50..10000";
          }
        }
        default "300";
      }
      leaf global {
        description
          "Global";
        type boolean;
        default "true";
      }
    }
    container input-source-ctrl {
      description
        "Synchronization Input Source";
      when 'not (../input-source-synce)';
      list input-source-ctrl {
        description
          "Synchronization Input Source";
        key "controller number";
        leaf priority {
          type uint8 {
            range "1..250";
          }
        }
        leaf controller {
          description
            "T1/E1 controller";
          type enumeration {
            enum T1;
            enum E1;
            enum t1;
            enum e1;
            enum wanphy;
            enum dwdm;
          }
        }
        leaf number {
          type string {
            pattern '([0-3]/)([0-9]|1[0-5])(/([0-9]|1[0-5]))';
          }
        }
        leaf word {
          type string;
        }
      }
    }
    list input-source-synce {
      description
        "Synchronization Input Source";
      key "priority";
      leaf priority {
        type uint8 {
          range "1..250";
        }
      }
      choice ext-source-opts {
        list External {
          key "port";
          uses config-synce-ext-port-grouping;
          list signal-list {
            key "signal";
            leaf signal {
              type enumeration {
                enum 10m;
                enum 2048k;
                enum 2m;
                enum e1;
                enum t1;
              }
            }
            uses config-synce-ext2-t1-option-grouping;
            leaf cas {
              type empty;
            }
            leaf crc4 {
              type empty;
            }
            leaf fas {
              type empty;
            }
            leaf sig-ohms-choice {
              type enumeration {
                enum 120ohms;
                enum 75ohms;
              }
            }
            leaf linecode {
              type enumeration {
                enum ami;
                enum hdb3;
              }
            }
            leaf source-description {
              type string;
            }
          }
        }
        container interface {
          uses ios-ifc:interface-grouping;
          leaf ip-source {
            type string;
          }
        }
        container ptp {
          leaf domain {
            type uint8 {
              range "0..127";
            }
          }
          leaf ip-source {
            type string;
          }
        }
        container controller {
          description
            "T1/E1 controller";
          status obsolete;
          leaf name {
            status obsolete;
            type enumeration {
              enum T1;
              enum E1;
              enum t1;
              enum e1;
              enum wanphy;
              enum dwdm;
            }
          }
          leaf number {
            status obsolete;
            type string {
              pattern '([0-1]/)([0-9]|1[0-5])(/([0-9]|1[0-5]))';
            }
          }
          leaf word {
            status obsolete;
            type string;
          }
        }
      }
    }
    container log {
      leaf ql-changes {
        type empty;
      }
    }
    container output-source {
      list line {
        key "priority";
        leaf priority {
          type uint8 {
            range "1..250";
          }
        }
        choice out-source-opts {
          container interface {
            list interface-list {
              key "interface-name";
              leaf interface-name {
                type string;
              }
              list External {
                key "port";
                uses config-synce-ext-port-grouping;
                list signal-list {
                  key "signal";
                  leaf signal {
                    type enumeration {
                      enum 10m;
                      enum 2048k;
                      enum 2m;
                      enum e1;
                      enum t1;
                    }
                  }
                  uses config-synce-ext3-t1-option-grouping;
                  leaf cas {
                    type empty;
                  }
                  leaf crc4 {
                    type empty;
                  }
                  leaf fas {
                    type empty;
                  }
                  leaf sig-ohms-choice {
                    type enumeration {
                      enum 120ohms;
                      enum 75ohms;
                    }
                  }
                  leaf linecode {
                    type enumeration {
                      enum ami;
                      enum hdb3;
                    }
                  }
                }
              }
            }
          }
          container ptp {
            list domain {
              key "domain-num";
              leaf domain-num {
                type uint8 {
                  range "0..127";
                }
              }
              list External {
                key "port";
                uses config-synce-ext-port-grouping;
                list signal-list {
                  key "signal";
                  leaf signal {
                    type enumeration {
                      enum 10m;
                      enum 2048k;
                      enum 2m;
                      enum e1;
                      enum t1;
                    }
                  }
                  uses config-synce-ext3-t1-option-grouping;
                  leaf cas {
                    type empty;
                  }
                  leaf crc4 {
                    type empty;
                  }
                  leaf fas {
                    type empty;
                  }
                  leaf sig-ohms-choice {
                    type enumeration {
                      enum 120ohms;
                      enum 75ohms;
                    }
                  }
                  leaf linecode {
                    type enumeration {
                      enum ami;
                      enum hdb3;
                    }
                  }
                }
              }
            }
          }
        }
      }
      list system {
        max-elements 1;
        key "priority";
        leaf priority {
          type uint8 {
            range "1..250";
          }
        }
        list External {
          key "port";
          uses config-synce-ext-port-grouping;
          list signal-list {
            key "signal";
            leaf signal {
              type enumeration {
                enum 10m;
                enum 2048k;
                enum 2m;
                enum e1;
                enum t1;
              }
            }
            uses config-synce-ext3-t1-option-grouping;
            leaf cas {
              type empty;
            }
            leaf crc4 {
              type empty;
            }
            leaf fas {
              type empty;
            }
            leaf sig-ohms-choice {
              type enumeration {
                enum 120ohms;
                enum 75ohms;
              }
            }
            leaf linecode {
              type enumeration {
                enum ami;
                enum hdb3;
              }
            }
          }
        }
      }
    }
    leaf participate {
      description
        "Enable/Disable a slot from participating in network-clocking";
      type string;
    }
    list quality-level {
      key "direction";
      leaf direction {
        type enumeration {
          enum rx;
          enum tx;
        }
      }
      list ql-val-list {
        key "ql-value";
        leaf ql-value {
          type enumeration {
            enum QL-DNU;
            enum QL-PRC;
            enum QL-SEC;
            enum QL-SSU-A;
            enum QL-SSU-B;
            enum QL-DUS;
            enum QL-PRS;
            enum QL-SMC;
            enum QL-ST2;
            enum QL-ST3;
            enum QL-ST3E;
            enum QL-ST4;
            enum QL-STU;
            enum QL-TNC;
          }
        }
        choice ext-source-opts {
          list External {
            key "port";
            uses config-synce-ext-port-grouping;
            list signal-list {
              key "signal";
              leaf signal {
                type enumeration {
                  enum 10m;
                  enum 2048k;
                  enum 2m;
                  enum e1;
                  enum t1;
                }
              }
              uses config-synce-ext3-t1-option-grouping;
              leaf cas {
                type empty;
              }
              leaf crc4 {
                type empty;
              }
              leaf fas {
                type empty;
              }
              leaf sig-ohms-choice {
                type enumeration {
                  enum 120ohms;
                  enum 75ohms;
                }
              }
            }
          }
          container interface {
            uses ios-ifc:interface-grouping;
          }
          container ptp {
            leaf-list domain {
              type uint8 {
                range "0..127";
              }
            }
          }
          container controller {
            description
              "T1/E1 controller";
            leaf name {
              type enumeration {
                enum wanphy;
                enum dwdm;
                enum T1;
                enum E1;
                enum t1;
                enum e1;
              }
            }
            leaf number {
              type string {
                pattern '([0-1]/)([0-9]|1[0-5])(/([0-9]|1[0-5]))';
              }
            }
          }
        }
      }
    }
    container ref-ql-val-trap-clear {
      leaf ql-value {
        type enumeration {
          enum QL-DNU;
          enum QL-PRC;
          enum QL-SEC;
          enum QL-SSU-A;
          enum QL-SSU-B;
        }
        default "QL-PRC";
      }
    }
    leaf revertive-synce {
      description
        "Network clock revertive mode";
      type empty;
    }
    container synchronization-synce {
      description
        "Network clock synchronization selection process";
      leaf automatic {
        description
          "ITU-T G.781/Telcordia standard based";
        type empty;
      }
      leaf input-threshold {
        type enumeration {
          enum QL-DNU;
          enum QL-PRC;
          enum QL-SEC;
          enum QL-SSU-A;
          enum QL-SSU-B;
        }
        default "QL-DNU";
      }
      leaf mode {
        description
          "synchronization networking mode";
        type enumeration {
          enum QL-enabled;
        }
      }
      leaf-list participate {
        description
          "network clock participate, input line card slot number";
        type string;
      }
      leaf squelch-threshold {
        type enumeration {
          enum QL-DNU;
          enum QL-PRC;
          enum QL-SEC;
          enum QL-SSU-A;
          enum QL-SSU-B;
        }
        default "QL-SEC";
      }
      container ssm {
        container option {
          leaf option1 {
            type enumeration {
              enum 1;
            }
            default "1";
          }
          container option-2 {
            leaf option2 {
              type enumeration {
                enum 2;
              }
            }
            leaf generation {
              type enumeration {
                enum GEN1;
                enum GEN2;
              }
            }
          }
        }
      }
    }
    container wait-to-restore-synce {
      description
        "Wait-to-Restore timer";
      leaf time {
        description
          "Wait-to-Restore time";
        type uint32 {
          range "0..86400";
        }
        default "300";
      }
      leaf global {
        description
          "Global";
        type boolean;
        default "true";
      }
    }
  }

  grouping config-tod-grouping {
    list input-source-synce {
      description
        "Synchronization Input Source";
      key "priority";
      leaf priority {
        description
          "Priority";
        type uint8 {
          range "1..251";
        }
      }
      choice source-opts {
        container ptp {
          leaf domain {
            type uint8 {
              range "0..127";
            }
          }
        }
        leaf gps {
          type synce-external-intf;
        }
        leaf internal {
          type empty;
        }
      }
    }
    leaf hold-off {
      type uint16 {
        range "0..60001";
      }
      default "12000";
    }
    leaf wait-to-restore {
      type uint16 {
        range "0..361";
      }
      default "20";
    }
    leaf revertive {
      description
        "Reference clock reverts to the highest priority after fail";
      type boolean;
      default "true";
    }
  }

  grouping config-esmc-grouping {
    container esmc-synce {
      description
        "Ethernet Synchronization Messaging Channel";
      leaf process {
        description
          "process";
        type empty;
      }
    }
  }

  grouping config-interface-synchronous-grouping {
    container synchronous-synce {
      description
        "Synchronous";
      leaf mode {
        description
          "Mode";
        type empty;
      }
    }
  }

  grouping config-interface-synchronous-esmc-grouping {
    container esmc {
      description
        "ESMC Settings";
      container mode {
        description
          "ESMC mode";
        leaf ql-disabled {
          type empty;
        }
        choice mode-choice {
          leaf none {
            type empty;
          }
          leaf rx {
            description
              "ESMC receive-only mode";
            type empty;
          }
          leaf tx {
            description
              "ESMC transmit-only mode";
            type empty;
          }
        }
      }
    }
  }

  grouping config-interface-synchronous-netclk-grouping {
    container network-clock {
      leaf hold-off {
        type union {
          type enumeration {
            enum 0;
          }
          type uint16 {
            range "50..10000";
          }
        }
        default "300";
      }
      container source {
        container quality-level {
          leaf ql {
            type enumeration {
              enum QL-DNU;
              enum QL-PRC;
              enum QL-SEC;
              enum QL-SSU-A;
              enum QL-SSU-B;
              enum QL-PRS;
              enum QL-STU;
              enum QL-ST2;
              enum QL-TNC;
              enum QL-ST3;
              enum QL-ST3E;
              enum QL-SMC;
              enum QL-DUS;
            }
          }
          choice direction-choice {
            leaf rx {
              type empty;
            }
            leaf tx {
              type empty;
            }
          }
        }
      }
      leaf wait-to-restore {
        type uint32 {
          range "0..86400";
        }
        default "300";
      }
    }
  }

  augment "/ios:native/ios:network-clock" {
    uses config-synce-grouping;
  }

  augment "/ios:native" {
    uses config-esmc-grouping;
  }

  augment "/ios:native/ios:tod-clock" {
    uses config-tod-grouping;
  }

  augment "/ios:native/ios:interface/ios:Ethernet" {
    uses config-interface-synchronous-grouping;
    uses config-interface-synchronous-esmc-grouping;
    uses config-interface-synchronous-netclk-grouping;
  }

  augment "/ios:native/ios:interface/ios:TenGigabitEthernet" {
    uses config-interface-synchronous-grouping;
    uses config-interface-synchronous-esmc-grouping;
    uses config-interface-synchronous-netclk-grouping;
  }

  augment "/ios:native/ios:interface/ios:GigabitEthernet" {
    uses config-interface-synchronous-grouping;
    uses config-interface-synchronous-esmc-grouping;
    uses config-interface-synchronous-netclk-grouping;
  }

  augment "/ios:native/ios:interface/ios:FastEthernet" {
    uses config-interface-synchronous-grouping;
    uses config-interface-synchronous-esmc-grouping;
    uses config-interface-synchronous-netclk-grouping;
  }

  augment "/ios:native/ios:interface/ios:FiveGigabitEthernet" {
    uses config-interface-synchronous-grouping;
    uses config-interface-synchronous-esmc-grouping;
    uses config-interface-synchronous-netclk-grouping;
  }

  augment "/ios:native/ios:interface/ios:AppGigabitEthernet" {
    uses config-interface-synchronous-grouping;
    uses config-interface-synchronous-esmc-grouping;
    uses config-interface-synchronous-netclk-grouping;
  }

  augment "/ios:native/ios:interface/ios:TwentyFiveGigE" {
    uses config-interface-synchronous-grouping;
    uses config-interface-synchronous-esmc-grouping;
    uses config-interface-synchronous-netclk-grouping;
  }

  augment "/ios:native/ios:interface/ios:TwoGigabitEthernet" {
    uses config-interface-synchronous-grouping;
    uses config-interface-synchronous-esmc-grouping;
    uses config-interface-synchronous-netclk-grouping;
  }

  augment "/ios:native/ios:interface/ios:FortyGigabitEthernet" {
    uses config-interface-synchronous-grouping;
    uses config-interface-synchronous-esmc-grouping;
    uses config-interface-synchronous-netclk-grouping;
  }

  augment "/ios:native/ios:interface/ios:HundredGigE" {
    uses config-interface-synchronous-grouping;
    uses config-interface-synchronous-esmc-grouping;
    uses config-interface-synchronous-netclk-grouping;
  }
}
