module Cisco-IOS-XE-l2nat {
  yang-version 1.1;
  namespace "http://cisco.com/ns/yang/Cisco-IOS-XE-l2nat";
  prefix l2nat;

  import ietf-inet-types {
    prefix inet;
  }
  import Cisco-IOS-XE-native {
    prefix ios;
  }
  import Cisco-IOS-XE-features {
    prefix ios-features;
  }

  organization
    "Cisco Systems, Inc.";
  contact
    "Cisco Systems, Inc.
     Customer Service
     Postal: 170 W Tasman Drive
     San Jose, CA 95134
     Tel: +1 1800 553-NETS
     E-mail: cs-yang@cisco.com";
  description
    "Cisco XE Layer 2 NAT model";

  revision 2024-03-01 {
    description
      "Initial revision";
  }

  grouping config-l2nat-grouping {
    container l2nat {
      description
        "L2NAT Configuration";
      list instance {
        description
          "L2NAT instance name";
        key "name";
        leaf name {
          description
            "Name of the instance";
          type string {
            length "1..80";
          }
        }
        container fixup {
          description
            "Protocols to be fixed for NAT";
          leaf all {
            description
              "Fix all protocols";
            type empty;
          }
          leaf arp {
            description
              "Fix ARP";
            type empty;
          }
          leaf icmp {
            description
              "Fix ICMP";
            type empty;
          }
        }
        container permit {
          description
            "Protocols to permit";
          choice permit-choice {
            case permit-all {
              leaf all {
                description
                  "Permit all traffic";
                type empty;
              }
            }
            case permit-protocols {
              leaf igmp {
                description
                  "Permit IGMP traffic";
                type empty;
              }
              leaf multicast {
                description
                  "Permit multicast traffic";
                type empty;
              }
              leaf unmatched {
                description
                  "Permit unmatched traffic";
                type empty;
              }
            }
          }
        }
        container inside {
          description
            "L2NAT translation from inside to outside direction";
          container from {
            description
              "Translate from";
            list host {
              description
                "host format";
              key "from_ip to_ip";
              unique "from_ip";
              unique "to_ip";
              leaf from_ip {
                description
                  "Original Host Source IP of packets sourced from inside network";
                type inet:ipv4-address;
              }
              leaf to_ip {
                description
                  "Translated Host Source IP of packets sourced from inside network";
                type inet:ipv4-address;
              }
            }
            list network {
              description
                "network format";
              key "from_ip to_ip mask";
              unique "from_ip";
              unique "to_ip";
              leaf from_ip {
                description
                  "Original Network of Source IP of packets sourced from inside network-last byte ignored";
                type inet:ipv4-address;
              }
              leaf to_ip {
                description
                  "Translated Network of Source IP of packets sourced from inside network-last byte ignored";
                type inet:ipv4-address;
              }
              leaf mask {
                description
                  "The network mask for both network IP addresses";
                type inet:ipv4-address;
              }
            }
            list range {
              description
                "range format";
              key "from_ip to_ip number";
              unique "from_ip";
              unique "to_ip";
              leaf from_ip {
                description
                  "Original Starting Source IP of packets sourced from inside network";
                type inet:ipv4-address;
              }
              leaf to_ip {
                description
                  "Translated Starting Source IP of packets sourced from inside network";
                type inet:ipv4-address;
              }
              leaf number {
                description
                  "Number of ip addresses in range";
                type uint8 {
                  range "2..128";
                }
              }
            }
          }
        }
        container outside {
          description
            "L2NAT translations from outside to inside direction";
          container from {
            description
              "Translate from";
            list host {
              description
                "host format";
              key "from_ip to_ip";
              unique "from_ip";
              unique "to_ip";
              leaf from_ip {
                description
                  "Original Host Source IP of packets sourced from outside network";
                type inet:ipv4-address;
              }
              leaf to_ip {
                description
                  "Translated Host Source IP of packets sourced from outside network";
                type inet:ipv4-address;
              }
            }
            list network {
              if-feature "ios-features:l2nat-outside-network";
              description
                "network format";
              key "from_ip to_ip mask";
              unique "from_ip";
              unique "to_ip";
              leaf from_ip {
                description
                  "Original Network of Source IP of packets sourced from outside network-last byte ignored";
                type inet:ipv4-address;
              }
              leaf to_ip {
                description
                  "Translated Network of Source IP of packets sourced from outside network-last byte ignored";
                type inet:ipv4-address;
              }
              leaf mask {
                description
                  "The network mask for both network IP addresses";
                type inet:ipv4-address;
              }
            }
            list range {
              description
                "range format";
              key "from_ip to_ip number";
              unique "from_ip";
              unique "to_ip";
              leaf from_ip {
                description
                  "Original Starting Source IP of packets sourced from outside network";
                type inet:ipv4-address;
              }
              leaf to_ip {
                description
                  "Translated Starting Source IP of packets sourced from outside network";
                type inet:ipv4-address;
              }
              leaf number {
                description
                  "Number of ip addresses in range";
                type uint8 {
                  range "2..128";
                }
              }
            }
          }
        }
      }
    }
  }

  grouping config-interface-l2nat-grouping {
    container l2nat {
      description
        "L2NAT instance to be attached to interface";
      leaf instance_name {
        description
          "Name of L2NAT instance";
        type leafref {
          path "/ios:native/l2nat/instance/name";
        }
      }
      list instance_name_with_vlan {
        description
          "L2NAT instance name";
        key "name vlan";
        leaf name {
          description
            "Name of L2NAT instance";
          type leafref {
            path "/ios:native/l2nat/instance/name";
          }
        }
        leaf vlan {
          description
            "VLAN ID";
          type uint16 {
            range "1..1024";
          }
        }
      }
    }
  }

  augment "/ios:native" {
    uses config-l2nat-grouping;
  }

  augment "/ios:native/ios:interface/ios:GigabitEthernet" {
    uses config-interface-l2nat-grouping;
  }

  augment "/ios:native/ios:interface/ios:TenGigabitEthernet" {
    uses config-interface-l2nat-grouping;
  }

  augment "/ios:native/ios:interface/ios:Port-channel" {
    uses config-interface-l2nat-grouping;
  }
}
