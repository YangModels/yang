module Cisco-IOS-XE-dhcp-security-track-server-oper {
  yang-version 1.1;
  namespace "http://cisco.com/ns/yang/Cisco-IOS-XE-dhcp-security-track-server-oper";
  prefix dhcp-ios-xe-security-track-server-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for tracking DHCP
     servers as part of DHCP security infrastructure.
     Copyright (c) 2018-2019, 2022 by Cisco Systems, Inc.
     All rights reserved.";

  revision 2023-03-01 {
    description
      "Added subnet-mask in dhcp-security-track-server-entry";
    reference
      "1.3.0";
    cisco-semver:module-version "1.3.0";
  }
  revision 2022-11-01 {
    description
      "Update yang-version to 1.1";
    reference
      "1.2.0";
    cisco-semver:module-version "1.2.0";
  }
  revision 2019-05-01 {
    description
      "Added semantic version";
    reference
      "1.1.0";
    cisco-semver:module-version "1.1.0";
  }
  revision 2018-07-05 {
    description
      "Initial revision";
    reference
      "1.0.0";
    cisco-semver:module-version "1.0.0";
  }

  grouping dhcp-security-track-server-key {
    description
      "Key to track a DHCP server within server tracking table.";
    leaf vlan {
      type uint16;
      description
        "VLAN the DHCP server was discovered on.";
    }
    leaf ip {
      type inet:ip-address;
      description
        "IP Address of the DHCP server, it is (a) the server identifier in
         the DHCP option of the packet or if that is empty it is (b) the server
         IP address field in the packet or if that is also empty it is (c) the
         source IP in the packet.";
    }
    leaf hwaddr {
      type yang:mac-address;
      description
        "MAC Address of the DHCP server. This is really the
         source MAC of L2 adjacent endpoint, and it might not be actual server.
         It might happen that the same DHCP server is responding via different
         adjacent endpoints.";
    }
    leaf subnet-ip {
      type inet:ip-address;
      description
        "Subnet IP based on offered/acknowledged client IP address and Subnet Mask";
    }
  }

  grouping dhcp-security-track-server-ack-key {
    description
      "Key to track a DHCP ACK within ack table on a given server.";
    leaf ip-address {
      type inet:ip-address;
      description
        "The client IP Address as specified in the YIADDR (your IP address) field
         of DHCPACK/DHCPOFFER message.";
    }
  }

  grouping dhcp-security-track-server-ack-entry {
    description
      "Information about a DHCP ACK entry in the tracking database.";
    leaf ack-time {
      type yang:date-and-time;
      description
        "Represents the time when this DHCP ACK was received.";
    }
  }

  grouping dhcp-security-track-server-entry {
    description
      "Information about a DHCP server entry in the tracking database.";
    leaf srv-id {
      type uint32;
      description
        "DHCP Server Identifier, this is assigned internally and remains
         unique within the network-element.";
    }
    leaf last-updated-time {
      type yang:date-and-time;
      description
        "Represents the time when device received last DHCPACK or DHCPOFFER message
         from this server.";
    }
    leaf num-of-acks {
      type uint32;
      description
        "Total number of DHCPACK messages received from this server.";
    }
    leaf num-of-offers {
      type uint32;
      description
        "Total number of DHCPOFFER messages received from this server.";
    }
    leaf if-name {
      type string;
      description
        "Represents the name of the interface this server was discovered on.";
    }
    leaf-list dhcp-msg {
      type uint8;
      max-elements 576;
      ordered-by user;
      description
        "Last DHCP message in network byte order as received over the wire.";
    }
    list dhcp-security-track-server-ack-entry {
      key "ip-address";
      description
        "DHCP ACK tracking table associated with this server.";
      uses dhcp-ios-xe-security-track-server-oper:dhcp-security-track-server-ack-entry;
      uses dhcp-ios-xe-security-track-server-oper:dhcp-security-track-server-ack-key;
    }
    leaf subnet-mask {
      type inet:ip-address;
      description
        "DHCP Server subnet mask.";
    }
  }

  container dhcp-security-track-server-oper-data {
    config false;
    description
      "DHCP security server tracking operational data.";
    list dhcp-security-track-server-entry {
      key "vlan ip hwaddr subnet-ip";
      description
        "DHCP snooping server tracking information specific to a server.";
      uses dhcp-ios-xe-security-track-server-oper:dhcp-security-track-server-entry;
      uses dhcp-ios-xe-security-track-server-oper:dhcp-security-track-server-key;
    }
  }
}
