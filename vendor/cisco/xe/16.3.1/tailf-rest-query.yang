module tailf-rest-query {
  namespace "http://tail-f.com/ns/tailf-rest-query";
  prefix "tfrestq";

  tailf:export none;

  import tailf-common {
    prefix tailf;
  }
  import tailf-common-query {
    prefix tfcq;
  }

  organization "Tail-f Systems";

  description
    "This module defines the structure of the query interface for REST.

     It is an internal module, not exported over any other northbound
     interface.";

  revision 2014-11-13 {
    description
      "Moved common parameters to 'tailf-common-query'.

       Removed the output leaf 'no-more-data', so that when
       there are no more results available, the 'query-result'
       container is empty.";
  }
  revision 2014-06-30 {
    description
      "Initial revision.";
  }

  /*
   * Start an XPath Query
   */
  tailf:structure start-query {
    container start-query {
      presence "request";
      description
        "Start an XPath Query by POSTing to /api/query, where the
         body contains the 'start-query' container.  On success,
         a 'start-query-result' will be returned with a handle to
         the query.";

      uses tfcq:start-query-parameters;
    }
  }

  /*
   * Format of the result from a start-query request
   */
  tailf:structure start-query-result {
    container start-query-result {
      presence "reply";
      description
        "REPLY: to start-query

         Format of the returned answer from a start-query request.
         The returned query-handle is used in any succeeding
         use of the fetch-query-result request.";

      uses tfcq:query-handle;
    }
  }


  /*
   * Fetch the resulting data from a query
   */
  tailf:structure fetch-query-result {
    container fetch-query-result {
      presence "request";
      description
        "Request return data from an XPath Query by POSTing to /api/query,
         where the body contains the 'fetch-query-result' container.  On
         success, a 'query-result' will be returned.";

      uses tfcq:query-handle;
   }
  }

  /*
   * Format of the result from a fetch-query-result request
   */
  tailf:structure query-result {
    container query-result {
      presence "reply";
      description
        "REPLY: to fetch-query-result

         Fetch (more) data, resulting from the query.";

      uses tfcq:query-result;
    }
  }


  /*
   * Reset a Query
   */
  tailf:structure reset-query {
    container reset-query {
      presence "request";
      description
        "Reset an existing query by POSTing to /api/query, where the body
         contains a 'reset-query' container.

         The next fetch-query-result will retrieve the given chunk of
         data again.";

      uses tfcq:reset-query-parameters;
    }
  }

  /*
   * Stop a Query
   */
  tailf:structure stop-query {
    container stop-query {
      presence "request";
      description
        "Stop the query.";

      uses tfcq:query-handle;
    }
  }
}
