module cisco-xe-native-router-deviation {
  namespace "http://cisco.com/ns/cisco-xe-native-router-deviation";

  prefix nd;

  import ned {
    prefix ios;
  }

  organization
    "Cisco Systems, Inc.";

  contact
    "Cisco Systems, Inc.

     Customer Service

     Postal: 170 W Tasman Drive
     San Jose, CA 95134

     Tel: +1 1800 553-NETS

     E-mail: cs-yang@cisco.com";

  description
    "This module defines deviation statements for Cisco IOS ned
     module.";

  revision 2016-07-20 {
    description
      "Initial Revision";

    reference
      "RFC 6020: YANG - A Data Modeling Language for the
       Network Configuration Protocol (NETCONF)";
  }

  // G.8032
  deviation /ios:native/ios:ethernet/ios:ring {
    deviate not-supported;
    description "Not supported in this release";
  }

  deviation /ios:native/ios:vtp {
    deviate not-supported;
    description "Not supported in this release";
  }

  deviation /ios:native/ios:module {
    deviate not-supported;
    description "Not supported in this release";
  }

  deviation /ios:native/ios:vmps {
    deviate not-supported;
    description "Not supported in this release";
  }

  deviation /ios:native/ios:policer {
    deviate not-supported;
    description "Not supported in this release";
  }

  deviation /ios:native/ios:gatekeeper {
    deviate not-supported;
    description "Not supported in this release";
  }

  deviation /ios:native/ios:mgcp {
    deviate not-supported;
    description "Not supported in this release";
  }

  deviation /ios:native/ios:setup {
    deviate not-supported;
    description "Not supported in this release";
  }

  deviation /ios:native/ios:tod-clock {
    deviate not-supported;
    description "Not supported in this release";
  }

  deviation /ios:native/ios:dot11 {
    deviate not-supported;
    description "Not supported in this release";
  }

  deviation /ios:native/ios:memory-size {
    deviate not-supported;
    description "Not supported in this release";
  }

  deviation /ios:native/ios:onep {
    deviate not-supported;
    description "Not supported in this release";
  }

  deviation /ios:native/ios:transceiver {
    deviate not-supported;
    description "Not supported in this release";
  }
}
