module cisco-cfm-stats {

    yang-version 1;

    namespace "urn:cisco:params:xml:ns:yang:cisco-cfm-stats";
    prefix cfmstats;

    import ietf-yang-types {
        prefix yang;
    }

    organization
        "Cisco Systems, Inc.";

   contact
        " Cisco Systems, Inc.
          Customer Service

          Postal: 170 W Tasman Drive
          San Jose, CA 95134

          Tel: +1 1800 553-NETS

          E-mail: cs-yang@cisco.com";
    
    description
       " This module contains a collection of YANG definitions for
         monitoring memory usage of processes in a Network Element.";
    
    reference "TODO";

    revision 2015-04-09 {
        description "Proposed";
    }


    container cfm-statistics {
        config false;
        description
          "Data nodes for CFM Statistics.";

        list mep {
            key "domain-name ma-name mpid";

            description
              "The list of MEP entries in the system.";

            leaf domain-name {
                type string;
                description
                  "The name of the Domain corresponding the the MEP.";
            }

            leaf ma-name {
                type string;
                description
                  "The name of the MA corresponding the the MEP.";
            }

            leaf mpid {
                type uint32;
                description
                  "ID of the MEP";
            }

            leaf last-cleared {
                type union {
                    type yang:date-and-time;
                    type enumeration {
                        enum never;
                    }
                }
                description
                    "The last time when the counters were cleared.";
            }

            leaf ccm-transmitted {
                type uint64;
                description "The number of CCMs transmitted from the local MEP.";
            }

            leaf ccm-seq-errors {
                type uint64;
                description "The number of CCM sequence number errors detected.";
            }

            leaf ltr-unexpected {
                type uint64;
                description "The number of unexpected linktrace reply packets 
                            received at this MEP.";
            }
            
            leaf lbr-transmitted {
                type uint64;
                description "The number of loopback reply packets transmitted
                            from the local MEP.";
            }

            leaf lbr-seq-errors {
                type uint64;
                description "The number of loopback reply packets received 
                            with sequence number errors.";
            }

            leaf lbr-received-ok {
                type uint64;
                description "The number of valid loopback reply packets received.";
            }

            leaf lbr-received-bad {
                type uint64;
                description "The number of loopback reply packets received 
                            with corrupted data pattern";
            }
        }
    }

}
