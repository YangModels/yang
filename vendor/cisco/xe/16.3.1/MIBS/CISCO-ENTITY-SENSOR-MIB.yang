/*
 * Generated by confdc --mib2yang-std
 * Source: mgmt/dmi/model/common/mib-source/CISCO-ENTITY-SENSOR-MIB.mib
 */
/*
 * This YANG module has been generated by smidump 0.5.0:
 *
 *      smidump -f yang CISCO-ENTITY-SENSOR-MIB
 *
 * Do not edit. Edit the source file instead!
 */

module CISCO-ENTITY-SENSOR-MIB {

  namespace "urn:ietf:params:xml:ns:yang:smiv2:CISCO-ENTITY-SENSOR-MIB";
  prefix CISCO-ENTITY-SENSOR-MIB;

  import CISCO-TC {
    prefix "cisco-tc";
  }

  import ENTITY-MIB {
    prefix "entity-mib";
  }

  import ietf-yang-smiv2 {
    prefix "smiv2";
  }

  import ietf-yang-types {
    prefix "yang";
  }

  organization
   "Cisco Systems, Inc.";

  contact
   "Postal: Cisco Systems, Inc.
    170 West Tasman Drive
    San Jose, CA 95134-1706
    USA
    
    Tel: +1 408 526 4000
    
    E-mail: cs-snmp@cisco.com";

  description
   "The CISCO-ENTITY-SENSOR-MIB is used to monitor
    the values of sensors in the Entity-MIB (RFC 2037) 
    entPhysicalTable.";

  revision 2015-01-15 {
    description
     "Corrected the definition of entSensorPrecision.";
  }

  revision 2013-09-21 {
    description
     "Added entSensorThresholdRecoveryNotification to
      entitySensorMIBNotifications.
      Added entSensorThresholdSeverity as a varbind
      object to entSensorThresholdNotification.
      Added entitySensorNotificationGroup 
      and deprecated 
      entitySensorThresholdNotificationGroup.
      Added entSensorThresholdNotification and
      entSensorThresholdRecoveryNotification to
      entitySensorNotificationGroup.
      Added entitySensorMIBComplianceV05 and 
      deprecated entitySensorMIBComplianceV04.";
  }

  revision 2007-11-12 {
    description
     "Added entitySensorNotifCtrlGlobalGroup.";
  }

  revision 2006-01-01 {
    description
     "Add new object entSensorMeasuredEntity to
      entSensorValueTable.";
  }

  revision 2005-09-08 {
    description
     "Change the module descriptor name from entitySensorMIB
      to ciscoEntitySensorMIB since ENTITY-SENSOR-MIB also
      uses the same name and there is a conflict.";
  }

  revision 2003-01-07 {
    description
     "[1] Add dBm(14) in SensorDataType.";
  }

  revision 2002-10-16 {
    description
     "[1] Add critical(30) in CSensorThresholdSeverity.
      [2] Change to MAX-ACCESS read-write for 3 objects.
      [3] Add entitySensorMIBComplianceV02.";
  }

  revision 2000-06-20 {
    description
     "Initial version of this MIB module.";
  }

  typedef SensorDataType {
    type enumeration {
      enum "other" {
        value "1";
      }
      enum "unknown" {
        value "2";
      }
      enum "voltsAC" {
        value "3";
      }
      enum "voltsDC" {
        value "4";
      }
      enum "amperes" {
        value "5";
      }
      enum "watts" {
        value "6";
      }
      enum "hertz" {
        value "7";
      }
      enum "celsius" {
        value "8";
      }
      enum "percentRH" {
        value "9";
      }
      enum "rpm" {
        value "10";
      }
      enum "cmm" {
        value "11";
      }
      enum "truthvalue" {
        value "12";
      }
      enum "specialEnum" {
        value "13";
      }
      enum "dBm" {
        value "14";
      }
    }
    description
     "sensor measurement data types.  valid values are:
      other(1):        a measure other than those listed below
      unknown(2):      unknown measurement, or 
                       arbitrary, relative numbers    
      voltsAC(3):      electric potential
      voltsDC(4):      electric potential
      amperes(5):      electric current
      watts(6):        power
      hertz(7):        frequency
      celsius(8):      temperature
      percentRH(9):    percent relative humidity
      rpm(10):         shaft revolutions per minute
      cmm(11),:        cubic meters per minute (airflow)
      truthvalue(12):  value takes { true(1), false(2) }
      specialEnum(13): value takes user defined enumerated values
      dBm(14):         dB relative to 1mW of power";
  }

  typedef SensorDataScale {
    type enumeration {
      enum "yocto" {
        value "1";
      }
      enum "zepto" {
        value "2";
      }
      enum "atto" {
        value "3";
      }
      enum "femto" {
        value "4";
      }
      enum "pico" {
        value "5";
      }
      enum "nano" {
        value "6";
      }
      enum "micro" {
        value "7";
      }
      enum "milli" {
        value "8";
      }
      enum "units" {
        value "9";
      }
      enum "kilo" {
        value "10";
      }
      enum "mega" {
        value "11";
      }
      enum "giga" {
        value "12";
      }
      enum "tera" {
        value "13";
      }
      enum "exa" {
        value "14";
      }
      enum "peta" {
        value "15";
      }
      enum "zetta" {
        value "16";
      }
      enum "yotta" {
        value "17";
      }
    }
    description
     "International System of Units (SI) prefixes.";
  }

  typedef SensorPrecision {
    type int32 {
      range "-8..9";
    }
    description
     "When in the range 1 to 9, SensorPrecision is the number
      of decimal places in the fractional part of 
      a SensorValue fixed-point number.  When in the range -8 to
      -1, SensorPrecision is the number of accurate digits in 
      a SensorValue fixed-point number.
      
      SensorPrecision is 0 for non-fixed-point numbers.
      
      Agent implementors must choose a value for SensorPrecision 
      so that the precision and accuracy of a SensorValue is 
      correctly indicated.
      
      For example, a temperature sensor that can measure 0o to 
      100o C in 0.1o increments, +/- 0.05o, would have a 
      SensorPrecision of 1, a SensorDataScale of units(0), and a 
      SensorValue ranging from 0 to 1000.  
      The SensorValue would be interpreted as (degrees C * 10).
      
      If that temperature sensor's precision were 0.1o but its 
      accuracy were only +/- 0.5o, then the SensorPrecision would 
      be 0. The SensorValue would be interpreted as degrees C.
      
      Another example: a fan rotation speed sensor that measures RPM 
      from 0 to 10,000 in 100 RPM increments, with an accuracy of 
      +50/-37 RPM, would have a SensorPrecision of -2, a 
      SensorDataScale of units(9), and a SensorValue ranging from 0 
      to 10000. The 10s and 1s digits of SensorValue would always 
      be 0.";
  }

  typedef SensorValue {
    type int32 {
      range "-1000000000..1000000000";
    }
    description
     "For sensors that measure voltsAC, voltsDC,
      amperes, watts, hertz, celsius, cmm
      this item is a fixed point number ranging from 
      -999,999,999 to +999,999,999.  Use the value 
      -1000000000 to indicate underflow. Use the value 
      +1000000000 to indicate overflow.  Use SensorPrecision
      to indicate how many fractional digits the SensorValue
      has.
      
      
      For sensors that measure percentRH, this item
      is a number ranging from 0 to 100.
      
      For sensors that measure rpm, this item
      can take only nonnegative values, 0..999999999.
      
      For sensors of type truthvalue, this item 
      can take only two values: true(1), false(2).
      
      For sensors of type specialEnum, this item
      can take any value in the range (-1000000000..1000000000),
      but the meaning of each value is specific to the 
      sensor.
      
      For sensors of type other and unknown, 
      this item can take any value in the range 
      (-1000000000..1000000000), but the meaning of the values 
      are specific to the sensor.
      
      Use Entity-MIB entPhysicalTable.entPhysicalVendorType
      to learn about the sensor type.";
  }

  typedef SensorStatus {
    type enumeration {
      enum "ok" {
        value "1";
      }
      enum "unavailable" {
        value "2";
      }
      enum "nonoperational" {
        value "3";
      }
    }
    description
     "Indicates the operational status of the sensor.
      
      ok(1) means the agent can read the sensor 
      value.
      
      unavailable(2) means that the agent presently 
      can not report the sensor value.
      
      nonoperational(3) means that the agent believes
      the sensor is broken.  The sensor could have a 
      hard failure (disconnected wire), or a soft failure
      such as out-of-range, jittery, or wildly fluctuating
      readings.";
  }

  typedef SensorValueUpdateRate {
    type int32 {
      range "0..999999999";
    }
    description
     "Indicates the interval in seconds between updates to the
      sensor's value.  
      
      The value zero indicates:
      - the sensor value is updated on demand (when polled by the 
        agent for a get-request), 
      - or when the sensor value changes (event-driven), 
      - or the agent does not know the rate";
  }

  typedef SensorThresholdSeverity {
    type enumeration {
      enum "other" {
        value "1";
      }
      enum "minor" {
        value "10";
      }
      enum "major" {
        value "20";
      }
      enum "critical" {
        value "30";
      }
    }
    description
     "sensor threshold severity.  Valid values are:
      
      other(1)    : a severity other than those listed below.
      minor(10)   : Minor Problem threshold.
      major(20)   : Major Problem threshold.
      critical(30): Critical problem threshold. A system might shut
                    down the sensor associated FRU automatically if
                    the sensor value reach the critical problem
                    threshold.";
  }

  typedef SensorThresholdRelation {
    type enumeration {
      enum "lessThan" {
        value "1";
      }
      enum "lessOrEqual" {
        value "2";
      }
      enum "greaterThan" {
        value "3";
      }
      enum "greaterOrEqual" {
        value "4";
      }
      enum "equalTo" {
        value "5";
      }
      enum "notEqualTo" {
        value "6";
      }
    }
    description
     "sensor threshold relational operator types.  valid values are:
      
      lessThan(1):        if the sensor value is less than
                          the threshold value
      lessOrEqual(2):     if the sensor value is less than or equal to
                          the threshold value
      greaterThan(3):     if the sensor value is greater than 
                          the threshold value
      greaterOrEqual(4):  if the sensor value is greater than or equal
                          to the threshold value
      equalTo(5):         if the sensor value is equal to
                          the threshold value
      notEqualTo(6):      if the sensor value is not equal to
                          the threshold value";
  }


  container CISCO-ENTITY-SENSOR-MIB {
    config false;

    container entSensorGlobalObjects {
      smiv2:oid "1.3.6.1.4.1.9.9.91.1.3";

      leaf entSensorThreshNotifGlobalEnable {
        type boolean;
        description
         "This variable enables the generation of
          entSensorThresholdNotification globally
          on the device. If this object value is
          'false', then no entSensorThresholdNotification
          will be generated on this device. If this object
          value is 'true', then whether a 
          entSensorThresholdNotification for a threshold will
          be generated or not depends on the instance value of
          entSensorThresholdNotificationEnable for that
          threshold.";
        smiv2:max-access "read-write";
        smiv2:oid "1.3.6.1.4.1.9.9.91.1.3.1";
      }
    }

    container entSensorValueTable {
      description
       "This table lists the type, scale, and present value
        of a sensor listed in the Entity-MIB entPhysicalTable.";
      smiv2:oid "1.3.6.1.4.1.9.9.91.1.1.1";

      list entSensorValueEntry {
        key "entPhysicalIndex";
        description
         "An entSensorValueTable entry describes the
          present reading of a sensor, the measurement units
          and scale, and sensor operational status.";
        smiv2:oid "1.3.6.1.4.1.9.9.91.1.1.1.1";

        leaf entPhysicalIndex {
          type leafref {
            path "/entity-mib:ENTITY-MIB/entity-mib:entPhysicalTable/entity-mib:entPhysicalEntry/entity-mib:entPhysicalIndex";
          }
        }

        leaf entSensorType {
          type CISCO-ENTITY-SENSOR-MIB:SensorDataType;
          description
           "This variable indicates the type of data
            reported by the entSensorValue.
            
            This variable is set by the agent at start-up
            and the value does not change during operation.";
          smiv2:max-access "read-only";
          smiv2:oid "1.3.6.1.4.1.9.9.91.1.1.1.1.1";
        }

        leaf entSensorScale {
          type CISCO-ENTITY-SENSOR-MIB:SensorDataScale;
          description
           "This variable indicates the exponent to apply
            to sensor values reported by entSensorValue.
            
            This variable is set by the agent at start-up
            and the value does not change during operation.";
          smiv2:max-access "read-only";
          smiv2:oid "1.3.6.1.4.1.9.9.91.1.1.1.1.2";
        }

        leaf entSensorPrecision {
          type CISCO-ENTITY-SENSOR-MIB:SensorPrecision;
          description
           "This variable indicates the number of decimal
            places of precision in fixed-point
            sensor values reported by entSensorValue.
            
            This variable is set to 0 when entSensorType
            is not a fixed-point type: e.g.'percentRH(9)', 
            'rpm(10)', 'cmm(11)', or 'truthvalue(12)'.
            
            This variable is set by the agent at start-up
            and the value does not change during operation.";
          smiv2:max-access "read-only";
          smiv2:oid "1.3.6.1.4.1.9.9.91.1.1.1.1.3";
        }

        leaf entSensorValue {
          type CISCO-ENTITY-SENSOR-MIB:SensorValue;
          description
           "This variable reports the most recent measurement seen
            by the sensor.
            
            To correctly display or interpret this variable's value, 
            you must also know entSensorType, entSensorScale, and 
            entSensorPrecision.
            
            However, you can compare entSensorValue with the threshold
            values given in entSensorThresholdTable without any semantic
            knowledge.";
          smiv2:max-access "read-only";
          smiv2:oid "1.3.6.1.4.1.9.9.91.1.1.1.1.4";
        }

        leaf entSensorStatus {
          type CISCO-ENTITY-SENSOR-MIB:SensorStatus;
          description
           "This variable indicates the present operational status
            of the sensor.";
          smiv2:max-access "read-only";
          smiv2:oid "1.3.6.1.4.1.9.9.91.1.1.1.1.5";
        }

        leaf entSensorValueTimeStamp {
          type yang:timestamp;
          description
           "This variable indicates the age of the value reported by
            entSensorValue";
          smiv2:max-access "read-only";
          smiv2:oid "1.3.6.1.4.1.9.9.91.1.1.1.1.6";
        }

        leaf entSensorValueUpdateRate {
          type CISCO-ENTITY-SENSOR-MIB:SensorValueUpdateRate;
          units "seconds";
          description
           "This variable indicates the rate that the agent
            updates entSensorValue.";
          smiv2:max-access "read-only";
          smiv2:oid "1.3.6.1.4.1.9.9.91.1.1.1.1.7";
        }

        leaf entSensorMeasuredEntity {
          type cisco-tc:EntPhysicalIndexOrZero;
          description
           "This object identifies the physical entity for which the
            sensor is taking measurements.  For example, for a sensor
            measuring the voltage output of a power-supply, this object
            would be the entPhysicalIndex of that power-supply; for a sensor
            measuring the temperature inside one chassis of a multi-chassis
            system, this object would be the enPhysicalIndex of that
            chassis.
            
            This object has a value of zero when the physical entity
            for which the sensor is taking measurements can not be
            represented by any one row in the entPhysicalTable, or that
            there is no such physical entity.";
          smiv2:max-access "read-only";
          smiv2:oid "1.3.6.1.4.1.9.9.91.1.1.1.1.8";
        }
      }
    }

    container entSensorThresholdTable {
      description
       "This table lists the threshold severity, relation, and
        comparison value, for a sensor listed in the Entity-MIB 
        entPhysicalTable.";
      smiv2:oid "1.3.6.1.4.1.9.9.91.1.2.1";

      list entSensorThresholdEntry {
        key "entPhysicalIndex entSensorThresholdIndex";
        description
         "An entSensorThresholdTable entry describes the
          thresholds for a sensor: the threshold severity,
          the threshold value, the relation, and the 
          evaluation of the threshold.
          
          Only entities of type sensor(8) are listed in this table.
          Only pre-configured thresholds are listed in this table.
          
          Users can create sensor-value monitoring instruments
          in different ways, such as RMON alarms, Expression-MIB, etc.
          
          Entries are created by the agent at system startup and
          FRU insertion.  Entries are deleted by the agent at
          FRU removal.";
        smiv2:oid "1.3.6.1.4.1.9.9.91.1.2.1.1";

        leaf entPhysicalIndex {
          type leafref {
            path "/entity-mib:ENTITY-MIB/entity-mib:entPhysicalTable/entity-mib:entPhysicalEntry/entity-mib:entPhysicalIndex";
          }
        }

        leaf entSensorThresholdIndex {
          type int32 {
            range "1..99999999";
          }
          description
           "An index that uniquely identifies an entry
            in the entSensorThresholdTable. This index
            permits the same sensor to have several 
            different thresholds.";
          smiv2:max-access "not-accessible";
          smiv2:oid "1.3.6.1.4.1.9.9.91.1.2.1.1.1";
        }

        leaf entSensorThresholdSeverity {
          type CISCO-ENTITY-SENSOR-MIB:SensorThresholdSeverity;
          description
           "This variable indicates the severity of this threshold.";
          smiv2:max-access "read-write";
          smiv2:oid "1.3.6.1.4.1.9.9.91.1.2.1.1.2";
        }

        leaf entSensorThresholdRelation {
          type CISCO-ENTITY-SENSOR-MIB:SensorThresholdRelation;
          description
           "This variable indicates the relation between sensor value
            (entSensorValue) and threshold value (entSensorThresholdValue), 
            required to trigger the alarm.  when evaluating the relation, 
            entSensorValue is on the left of entSensorThresholdRelation, 
            entSensorThresholdValue is on the right. 
            
            in pseudo-code, the evaluation-alarm mechanism is:
            
            ...
            if (entSensorStatus == ok) then
                if (evaluate(entSensorValue, entSensorThresholdRelation,  
                    entSensorThresholdValue)) 
                then
                    if (entSensorThresholdNotificationEnable == true)) 
                    then
                        raise_alarm(sensor's entPhysicalIndex);
                    endif
                endif
            endif
            ...";
          smiv2:max-access "read-write";
          smiv2:oid "1.3.6.1.4.1.9.9.91.1.2.1.1.3";
        }

        leaf entSensorThresholdValue {
          type CISCO-ENTITY-SENSOR-MIB:SensorValue;
          description
           "This variable indicates the value of the threshold.
            
            To correctly display or interpret this variable's value, 
            you must also know entSensorType, entSensorScale, and 
            entSensorPrecision.
            
            However, you can directly compare entSensorValue 
            with the threshold values given in entSensorThresholdTable 
            without any semantic knowledge.";
          smiv2:max-access "read-write";
          smiv2:oid "1.3.6.1.4.1.9.9.91.1.2.1.1.4";
        }

        leaf entSensorThresholdEvaluation {
          type boolean;
          description
           "This variable indicates the result of the most
            recent evaluation of the threshold.  If the threshold
            condition is true, entSensorThresholdEvaluation 
            is true(1).  If the threshold condition is false, 
            entSensorThresholdEvaluation is false(2).
            
            Thresholds are evaluated at the rate indicated by 
            entSensorValueUpdateRate.";
          smiv2:max-access "read-only";
          smiv2:oid "1.3.6.1.4.1.9.9.91.1.2.1.1.5";
        }

        leaf entSensorThresholdNotificationEnable {
          type boolean;
          description
           "This variable controls generation of
            entSensorThresholdNotification for this threshold.
            
            When this variable is 'true', generation of 
            entSensorThresholdNotification is enabled for this
            threshold. When this variable is 'false', 
            generation of entSensorThresholdNotification is
            disabled for this threshold.";
          smiv2:max-access "read-write";
          smiv2:oid "1.3.6.1.4.1.9.9.91.1.2.1.1.6";
        }
      }
    }
  }

  notification entSensorThresholdNotification {
    description
     "The notification is generated when
      the sensor value entSensorValue crosses 
      the threshold value entSensorThresholdValue and
      the value of entSensorThreshNotifGlobalEnable is true.
      
      entSensorThresholdSeverity indicates the severity 
      of this threshold.
      
      The agent implementation guarantees prompt, timely
      evaluation of threshold and generation of this
      notification.";
    smiv2:oid "1.3.6.1.4.1.9.9.91.2.0.1";

    container object-1 {

      leaf entPhysicalIndex {
        type leafref {
          path "/entity-mib:ENTITY-MIB/entity-mib:entPhysicalTable/entity-mib:entPhysicalEntry/entity-mib:entPhysicalIndex";
        }
      }

      leaf entSensorThresholdIndex {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdIndex";
        }
      }

      leaf entSensorThresholdValue {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdValue";
        }
      }
    }

    container object-2 {

      leaf entPhysicalIndex {
        type leafref {
          path "/entity-mib:ENTITY-MIB/entity-mib:entPhysicalTable/entity-mib:entPhysicalEntry/entity-mib:entPhysicalIndex";
        }
      }

      leaf entSensorValue {
        type leafref {
          path "/CISCO-ENTITY-SENSOR-MIB:CISCO-ENTITY-SENSOR-MIB/CISCO-ENTITY-SENSOR-MIB:entSensorValueTable/CISCO-ENTITY-SENSOR-MIB:entSensorValueEntry/CISCO-ENTITY-SENSOR-MIB:entSensorValue";
        }
      }
    }

    container object-3 {

      leaf entPhysicalIndex {
        type leafref {
          path "/entity-mib:ENTITY-MIB/entity-mib:entPhysicalTable/entity-mib:entPhysicalEntry/entity-mib:entPhysicalIndex";
        }
      }

      leaf entSensorThresholdIndex {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdIndex";
        }
      }

      leaf entSensorThresholdSeverity {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdSeverity";
        }
      }
    }
  }

  notification entSensorThresholdRecoveryNotification {
    description
     "This notification is generated
      as a recovery notification when 
      the sensor value entSensorValue goes below 
      the threshold value entSensorThresholdValue
      once it has generated entSensorThresholdNotification.
      The value of entSensorThreshNotifGlobalEnable needs
      to be true.
      
      entSensorThresholdSeverity indicates the severity 
      of this threshold.
      
      The agent implementation guarantees prompt, timely
      evaluation of threshold and generation of this
      notification.";
    smiv2:oid "1.3.6.1.4.1.9.9.91.2.0.2";

    container object-1 {

      leaf entPhysicalIndex {
        type leafref {
          path "/entity-mib:ENTITY-MIB/entity-mib:entPhysicalTable/entity-mib:entPhysicalEntry/entity-mib:entPhysicalIndex";
        }
      }

      leaf entSensorValue {
        type leafref {
          path "/CISCO-ENTITY-SENSOR-MIB:CISCO-ENTITY-SENSOR-MIB/CISCO-ENTITY-SENSOR-MIB:entSensorValueTable/CISCO-ENTITY-SENSOR-MIB:entSensorValueEntry/CISCO-ENTITY-SENSOR-MIB:entSensorValue";
        }
      }
    }

    container object-2 {

      leaf entPhysicalIndex {
        type leafref {
          path "/entity-mib:ENTITY-MIB/entity-mib:entPhysicalTable/entity-mib:entPhysicalEntry/entity-mib:entPhysicalIndex";
        }
      }

      leaf entSensorThresholdIndex {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdIndex";
        }
      }

      leaf entSensorThresholdSeverity {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdSeverity";
        }
      }
    }

    container object-3 {

      leaf entPhysicalIndex {
        type leafref {
          path "/entity-mib:ENTITY-MIB/entity-mib:entPhysicalTable/entity-mib:entPhysicalEntry/entity-mib:entPhysicalIndex";
        }
      }

      leaf entSensorThresholdIndex {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdIndex";
        }
      }

      leaf entSensorThresholdValue {
        type leafref {
          path "/CISCO-ENTITY-SENSOR-MIB:CISCO-ENTITY-SENSOR-MIB/CISCO-ENTITY-SENSOR-MIB:entSensorThresholdTable/CISCO-ENTITY-SENSOR-MIB:entSensorThresholdEntry/CISCO-ENTITY-SENSOR-MIB:entSensorThresholdValue";
        }
      }
    }
  }

  smiv2:alias "ciscoEntitySensorMIB" {
    smiv2:oid "1.3.6.1.4.1.9.9.91";
  }

  smiv2:alias "entitySensorMIBObjects" {
    smiv2:oid "1.3.6.1.4.1.9.9.91.1";
  }

  smiv2:alias "entSensorValues" {
    smiv2:oid "1.3.6.1.4.1.9.9.91.1.1";
  }

  smiv2:alias "entSensorThresholds" {
    smiv2:oid "1.3.6.1.4.1.9.9.91.1.2";
  }

  smiv2:alias "entSensorGlobalObjects" {
    smiv2:oid "1.3.6.1.4.1.9.9.91.1.3";
  }

  smiv2:alias "entitySensorMIBNotificationPrefix" {
    smiv2:oid "1.3.6.1.4.1.9.9.91.2";
  }

  smiv2:alias "entitySensorMIBNotifications" {
    smiv2:oid "1.3.6.1.4.1.9.9.91.2.0";
  }

  smiv2:alias "entitySensorMIBConformance" {
    smiv2:oid "1.3.6.1.4.1.9.9.91.3";
  }

  smiv2:alias "entitySensorMIBCompliances" {
    smiv2:oid "1.3.6.1.4.1.9.9.91.3.1";
  }

  smiv2:alias "entitySensorMIBGroups" {
    smiv2:oid "1.3.6.1.4.1.9.9.91.3.2";
  }

}
