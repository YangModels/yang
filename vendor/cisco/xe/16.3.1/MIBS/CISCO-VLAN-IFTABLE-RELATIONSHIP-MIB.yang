/*
 * Generated by confdc --mib2yang-std
 * Source: mgmt/dmi/model/common/mib-source/CISCO-VLAN-IFTABLE-RELATIONSHIP-MIB.mib
 */
/*
 * This YANG module has been generated by smidump 0.5.0:
 *
 *      smidump -f yang CISCO-VLAN-IFTABLE-RELATIONSHIP-MIB
 *
 * Do not edit. Edit the source file instead!
 */

module CISCO-VLAN-IFTABLE-RELATIONSHIP-MIB {

  namespace "urn:ietf:params:xml:ns:yang:smiv2:CISCO-VLAN-IFTABLE-RELATIONSHIP-MIB";
  prefix CISCO-VLAN-IFTABLE-RELATIONSHIP-MIB;

  import CISCO-TC {
    prefix "cisco-tc";
  }

  import CISCO-VTP-MIB {
    prefix "cisco-vtp";
  }

  import IF-MIB {
    prefix "if-mib";
  }

  import ietf-yang-smiv2 {
    prefix "smiv2";
  }

  organization
   "Cisco Systems, Inc.";

  contact
   "Cisco Systems
    Customer Service
    
    Postal: 170 W Tasman Drive
            San Jose, CA  95134
            USA
    
    Tel: +1 800 553-NETS
    
    E-mail: cs-snmp@cisco.com";

  description
   "Cisco VLAN ifTable Relationship MIB lists VLAN-id and ifIndex
    information for routed VLAN interfaces.  
    
    A routed VLAN interface is the router interface or sub-interface 
    to which the router's IP address on the VLAN is attached.  
    For example, an ISL, SDE, or 802.1Q encapsulated
    subinterface, or Switched Virtual Interface (SVI).";

  revision 2013-07-15 {
    description
     "Initial version of this MIB module.";
  }

  revision 1999-04-01 {
    description
     "[Revision added by libsmi due to a LAST-UPDATED clause.]";
  }


  container CISCO-VLAN-IFTABLE-RELATIONSHIP-MIB {
    config false;

    container cviVlanInterfaceIndexTable {
      description
       "The cviVlanInterfaceIndexTable provides a way to
        translate a VLAN-id in to an ifIndex, so that 
        the routed VLAN interface's routing configuration 
        can be obtained from interface entry in ipRouteTable.
        
        Note that some routers can have interfaces to multiple
        VLAN management domains, and therefore can have multiple 
        routed VLAN interfaces which connect to different VLANs 
        having the same VLAN-id.  Thus, it is possible to have 
        multiple rows in this table for the same VLAN-id.
        
        The cviVlanInterfaceIndexTable also provides a way
        to find the VLAN-id from an ifTable VLAN's ifIndex.";
      smiv2:oid "1.3.6.1.4.1.9.9.128.1.1.1";

      list cviVlanInterfaceIndexEntry {
        key "cviVlanId cviPhysicalIfIndex";
        description
         "Each entry represents a routed VLAN interface, its
          corresponding physical port if any, and the ifTable entry
          for the routed VLAN interface.
          
          Entries are created by the agent when the routed VLAN interface
          is created.  Operational status of routing does not affect
          the entries listed here.  For routing configuration please refer
          to ipRouteTable.
          
          Entries are deleted by the agent when the routed VLAN interface
          is removed from the system configuration.";
        smiv2:oid "1.3.6.1.4.1.9.9.128.1.1.1.1";

        leaf cviVlanId {
          type cisco-vtp:VlanIndex;
          description
           "The VLAN-id number of the routed VLAN interface.";
          smiv2:max-access "not-accessible";
          smiv2:oid "1.3.6.1.4.1.9.9.128.1.1.1.1.1";
        }

        leaf cviPhysicalIfIndex {
          type cisco-tc:InterfaceIndexOrZero;
          description
           "For subinterfaces, this object is the ifIndex of the
            physical interface for the subinterface.
            
            For Switch Virtual Interfaces (SVIs), this object is zero.";
          smiv2:max-access "not-accessible";
          smiv2:oid "1.3.6.1.4.1.9.9.128.1.1.1.1.2";
        }

        leaf cviRoutedVlanIfIndex {
          type if-mib:InterfaceIndex;
          description
           "The index for the ifTable entry associated with
            this routed VLAN interface.";
          smiv2:max-access "read-only";
          smiv2:oid "1.3.6.1.4.1.9.9.128.1.1.1.1.3";
        }
      }
    }
  }

  smiv2:alias "ciscoVlanIfTableRelationshipMIB" {
    smiv2:oid "1.3.6.1.4.1.9.9.128";
  }

  smiv2:alias "cviMIBObjects" {
    smiv2:oid "1.3.6.1.4.1.9.9.128.1";
  }

  smiv2:alias "cviGlobals" {
    smiv2:oid "1.3.6.1.4.1.9.9.128.1.1";
  }

  smiv2:alias "cviMIBConformance" {
    smiv2:oid "1.3.6.1.4.1.9.9.128.1.3";
  }

  smiv2:alias "cviMIBCompliances" {
    smiv2:oid "1.3.6.1.4.1.9.9.128.1.3.1";
  }

  smiv2:alias "cviMIBGroups" {
    smiv2:oid "1.3.6.1.4.1.9.9.128.1.3.2";
  }

}
