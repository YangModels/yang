module TRANSPORT-ADDRESS-MIB {
  namespace "http://tail-f.com/ns/mibs/TRANSPORT-ADDRESS-MIB/200211010000Z";
  prefix TRANSPORT_ADDRESS_MIB;
  tailf:id "";
  tailf:snmp-mib-module-name "TRANSPORT-ADDRESS-MIB";

  import ietf-yang-types {
    prefix yang;
  }
  import tailf-common {
    prefix tailf;
  }

  revision 2002-11-01 {
    description
      "";
  }

  typedef TransportDomain {
    type yang:object-identifier;
  }

  typedef TransportAddressType {
    type enumeration {
      enum "unknown" {
        value 0;
      }
      enum "udpIpv4" {
        value 1;
      }
      enum "udpIpv6" {
        value 2;
      }
      enum "udpIpv4z" {
        value 3;
      }
      enum "udpIpv6z" {
        value 4;
      }
      enum "tcpIpv4" {
        value 5;
      }
      enum "tcpIpv6" {
        value 6;
      }
      enum "tcpIpv4z" {
        value 7;
      }
      enum "tcpIpv6z" {
        value 8;
      }
      enum "sctpIpv4" {
        value 9;
      }
      enum "sctpIpv6" {
        value 10;
      }
      enum "sctpIpv4z" {
        value 11;
      }
      enum "sctpIpv6z" {
        value 12;
      }
      enum "local" {
        value 13;
      }
      enum "udpDns" {
        value 14;
      }
      enum "tcpDns" {
        value 15;
      }
      enum "sctpDns" {
        value 16;
      }
    }
  }

  typedef TransportAddress {
    type tailf:hex-list {
      tailf:value-length "min .. 255";
    }
  }

  typedef TransportAddressIPv4 {
    type tailf:hex-list {
      tailf:value-length "6";
    }
  }

  typedef TransportAddressIPv6 {
    type tailf:hex-list {
      tailf:value-length "18";
    }
  }

  typedef TransportAddressIPv4z {
    type tailf:hex-list {
      tailf:value-length "10";
    }
  }

  typedef TransportAddressIPv6z {
    type tailf:hex-list {
      tailf:value-length "22";
    }
  }

  typedef TransportAddressLocal {
    type string {
      length "1 .. 255";
    }
  }

  typedef TransportAddressDns {
    type string {
      length "1 .. 255";
    }
  }
}
