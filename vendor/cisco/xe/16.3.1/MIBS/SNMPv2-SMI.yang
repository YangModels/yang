module SNMPv2-SMI {
  namespace "http://tail-f.com/ns/mibs/SNMPv2-SMI/1.0";
  prefix SNMPv2_SMI;
  tailf:id "";
  tailf:snmp-mib-module-name "SNMPv2-SMI";

  import ietf-yang-types {
    prefix yang;
  }
  import tailf-common {
    prefix tailf;
  }

  typedef ExtUTCTime {
    type tailf:hex-list {
      tailf:value-length "11 .. 13";
    }
  }

  typedef ObjectName {
    type yang:object-identifier;
  }

  typedef NotificationName {
    type yang:object-identifier;
  }

  typedef Integer32 {
    type int32 {
      range "-2147483648 .. 2147483647";
    }
  }

  typedef IpAddress {
    type string {
      pattern "(0|[1-9](([0-9]){0,2})).(0|[1-9](([0-9]){0,2})).(0|[1-9](([0-9]){0,2})).(0|[1-9](([0-9]){0,2}))";
    }
  }

  typedef Counter32 {
    type uint32 {
      range "0 .. 4294967295";
    }
  }

  typedef Gauge32 {
    type uint32 {
      range "0 .. 4294967295";
    }
  }

  typedef Unsigned32 {
    type uint32 {
      range "0 .. 4294967295";
    }
  }

  typedef TimeTicks {
    type uint32 {
      range "0 .. 4294967295";
    }
  }

  typedef Opaque {
    type tailf:hex-list;
  }

  typedef Counter64 {
    type yang:counter64 {
      range "0 .. 18446744073709551615";
    }
  }
}
