/*
 * Generated by confdc --mib2yang-std
 * Source: mgmt/dmi/model/common/mib-source/UDP-MIB.mib
 */
/*
 * This YANG module has been generated by smidump 0.5.0:
 *
 *      smidump -f yang UDP-MIB
 *
 * Do not edit. Edit the source file instead!
 */

module UDP-MIB {

  namespace "urn:ietf:params:xml:ns:yang:smiv2:UDP-MIB";
  prefix UDP-MIB;

  import INET-ADDRESS-MIB {
    prefix "inet-address";
  }

  import ietf-inet-types {
    prefix "inet";
  }

  import ietf-yang-smiv2 {
    prefix "smiv2";
  }

  import ietf-yang-types {
    prefix "yang";
  }

  organization
   "IETF IPv6 Working Group
    http://www.ietf.org/html.charters/ipv6-charter.html";

  contact
   "Bill Fenner (editor)
    
    AT&T Labs -- Research
    75 Willow Rd.
    Menlo Park, CA 94025
    
    Phone: +1 650 330-7893
    Email: <fenner@research.att.com>
    
    John Flick (editor)
    
    Hewlett-Packard Company
    8000 Foothills Blvd. M/S 5557
    Roseville, CA 95747
    
    Phone: +1 916 785 4018
    Email: <john.flick@hp.com>
    
    Send comments to <ipv6@ietf.org>";

  description
   "The MIB module for managing UDP implementations.
    Copyright (C) The Internet Society (2005).  This
    version of this MIB module is part of RFC 4113;
    see the RFC itself for full legal notices.";

  revision 2005-05-20 {
    description
     "IP version neutral revision, incorporating the
      following revisions:
      
      - Added udpHCInDatagrams and udpHCOutDatagrams in order
        to provide high-capacity counters for fast networks.
      - Added text to the descriptions of all counter objects
        to indicate how discontinuities are detected.
      - Deprecated the IPv4-specific udpTable and replaced it
        with the version neutral udpEndpointTable.  This
        table includes support for connected UDP endpoints
        and support for identification of the operating
        system process associated with a UDP endpoint.
      - Deprecated the udpGroup and replaced it with object
        groups representing the current set of objects.
      - Deprecated udpMIBCompliance and replaced it with
        udpMIBCompliance2, which includes the compliance
        information for the new object groups.
      
      This version published as RFC 4113.";
  }

  revision 1994-11-01 {
    description
     "Initial SMIv2 version, published as RFC 2013.";
  }

  revision 1991-03-31 {
    description
     "The initial revision of this MIB module was part of
      MIB-II, published as RFC 1213.";
  }


  container UDP-MIB {
    config false;

    container udp {
      smiv2:oid "1.3.6.1.2.1.7";

      leaf udpInDatagrams {
        type yang:counter32;
        description
         "The total number of UDP datagrams delivered to UDP
          users.
          
          Discontinuities in the value of this counter can occur
          at re-initialization of the management system, and at
          other times as indicated by discontinuities in the
          value of sysUpTime.";
        smiv2:max-access "read-only";
        smiv2:oid "1.3.6.1.2.1.7.1";
      }

      leaf udpNoPorts {
        type yang:counter32;
        description
         "The total number of received UDP datagrams for which
          there was no application at the destination port.
          
          Discontinuities in the value of this counter can occur
          at re-initialization of the management system, and at
          other times as indicated by discontinuities in the
          value of sysUpTime.";
        smiv2:max-access "read-only";
        smiv2:oid "1.3.6.1.2.1.7.2";
      }

      leaf udpInErrors {
        type yang:counter32;
        description
         "The number of received UDP datagrams that could not be
          delivered for reasons other than the lack of an
          application at the destination port.
          
          Discontinuities in the value of this counter can occur
          at re-initialization of the management system, and at
          other times as indicated by discontinuities in the
          value of sysUpTime.";
        smiv2:max-access "read-only";
        smiv2:oid "1.3.6.1.2.1.7.3";
      }

      leaf udpOutDatagrams {
        type yang:counter32;
        description
         "The total number of UDP datagrams sent from this
          entity.
          
          Discontinuities in the value of this counter can occur
          at re-initialization of the management system, and at
          other times as indicated by discontinuities in the
          value of sysUpTime.";
        smiv2:max-access "read-only";
        smiv2:oid "1.3.6.1.2.1.7.4";
      }

      leaf udpHCInDatagrams {
        type yang:counter64;
        description
         "The total number of UDP datagrams delivered to UDP
          users, for devices that can receive more than 1
          million UDP datagrams per second.
          
          Discontinuities in the value of this counter can occur
          at re-initialization of the management system, and at
          other times as indicated by discontinuities in the
          value of sysUpTime.";
        smiv2:max-access "read-only";
        smiv2:oid "1.3.6.1.2.1.7.8";
      }

      leaf udpHCOutDatagrams {
        type yang:counter64;
        description
         "The total number of UDP datagrams sent from this
          entity, for devices that can transmit more than 1
          million UDP datagrams per second.
          
          Discontinuities in the value of this counter can occur
          at re-initialization of the management system, and at
          other times as indicated by discontinuities in the
          value of sysUpTime.";
        smiv2:max-access "read-only";
        smiv2:oid "1.3.6.1.2.1.7.9";
      }
    }

    container udpTable {
      status deprecated;
      description
       "A table containing IPv4-specific UDP listener
        information.  It contains information about all local
        IPv4 UDP end-points on which an application is
        currently accepting datagrams.  This table has been
        deprecated in favor of the version neutral
        udpEndpointTable.";
      smiv2:oid "1.3.6.1.2.1.7.5";

      list udpEntry {
        key "udpLocalAddress udpLocalPort";
        status deprecated;
        description
         "Information about a particular current UDP listener.";
        smiv2:oid "1.3.6.1.2.1.7.5.1";

        leaf udpLocalAddress {
          type inet:ipv4-address;
          status deprecated;
          description
           "The local IP address for this UDP listener.  In the
            case of a UDP listener that is willing to accept
            datagrams for any IP interface associated with the
            node, the value 0.0.0.0 is used.";
          smiv2:max-access "read-only";
          smiv2:oid "1.3.6.1.2.1.7.5.1.1";
        }

        leaf udpLocalPort {
          type int32 {
            range "0..65535";
          }
          status deprecated;
          description
           "The local port number for this UDP listener.";
          smiv2:max-access "read-only";
          smiv2:oid "1.3.6.1.2.1.7.5.1.2";
        }
      }
    }

    container udpEndpointTable {
      description
       "A table containing information about this entity's UDP
        endpoints on which a local application is currently
        accepting or sending datagrams.
        
        The address type in this table represents the address
        type used for the communication, irrespective of the
        higher-layer abstraction.  For example, an application
        using IPv6 'sockets' to communicate via IPv4 between
        ::ffff:10.0.0.1 and ::ffff:10.0.0.2 would use
        InetAddressType ipv4(1).
        
        Unlike the udpTable in RFC 2013, this table also allows
        the representation of an application that completely
        specifies both local and remote addresses and ports.  A
        listening application is represented in three possible
        ways:
        
        1) An application that is willing to accept both IPv4
           and IPv6 datagrams is represented by a
           udpEndpointLocalAddressType of unknown(0) and a
           udpEndpointLocalAddress of ''h (a zero-length
           octet-string).
        
        2) An application that is willing to accept only IPv4
           or only IPv6 datagrams is represented by a
           udpEndpointLocalAddressType of the appropriate
           address type and a udpEndpointLocalAddress of
           '0.0.0.0' or '::' respectively.
        
        3) An application that is listening for datagrams only
           for a specific IP address but from any remote
           system is represented by a
           udpEndpointLocalAddressType of the appropriate
           address type, with udpEndpointLocalAddress
           specifying the local address.
        
        In all cases where the remote is a wildcard, the
        udpEndpointRemoteAddressType is unknown(0), the
        udpEndpointRemoteAddress is ''h (a zero-length
        octet-string), and the udpEndpointRemotePort is 0.
        
        If the operating system is demultiplexing UDP packets
        by remote address and port, or if the application has
        'connected' the socket specifying a default remote
        address and port, the udpEndpointRemote* values should
        be used to reflect this.";
      smiv2:oid "1.3.6.1.2.1.7.7";

      list udpEndpointEntry {
        key "udpEndpointLocalAddressType udpEndpointLocalAddress udpEndpointLocalPort udpEndpointRemoteAddressType udpEndpointRemoteAddress udpEndpointRemotePort udpEndpointInstance";
        description
         "Information about a particular current UDP endpoint.
          
          Implementers need to be aware that if the total number
          of elements (octets or sub-identifiers) in
          udpEndpointLocalAddress and udpEndpointRemoteAddress
          exceeds 111, then OIDs of column instances in this table
          will have more than 128 sub-identifiers and cannot be
          accessed using SNMPv1, SNMPv2c, or SNMPv3.";
        smiv2:oid "1.3.6.1.2.1.7.7.1";

        leaf udpEndpointLocalAddressType {
          type inet-address:InetAddressType;
          description
           "The address type of udpEndpointLocalAddress.  Only
            IPv4, IPv4z, IPv6, and IPv6z addresses are expected, or
            unknown(0) if datagrams for all local IP addresses are
            accepted.";
          smiv2:max-access "not-accessible";
          smiv2:oid "1.3.6.1.2.1.7.7.1.1";
        }

        leaf udpEndpointLocalAddress {
          type inet-address:InetAddress;
          description
           "The local IP address for this UDP endpoint.
            
            The value of this object can be represented in three
            
            possible ways, depending on the characteristics of the
            listening application:
            
            1. For an application that is willing to accept both
               IPv4 and IPv6 datagrams, the value of this object
               must be ''h (a zero-length octet-string), with
               the value of the corresponding instance of the
               udpEndpointLocalAddressType object being unknown(0).
            
            2. For an application that is willing to accept only IPv4
               or only IPv6 datagrams, the value of this object
               must be '0.0.0.0' or '::', respectively, while the
               corresponding instance of the
               udpEndpointLocalAddressType object represents the
               appropriate address type.
            
            3. For an application that is listening for data
               destined only to a specific IP address, the value
               of this object is the specific IP address for which
               this node is receiving packets, with the
               corresponding instance of the
               udpEndpointLocalAddressType object representing the
               appropriate address type.
            
            As this object is used in the index for the
            udpEndpointTable, implementors of this table should be
            careful not to create entries that would result in OIDs
            with more than 128 subidentifiers; else the information
            cannot be accessed using SNMPv1, SNMPv2c, or SNMPv3.";
          smiv2:max-access "not-accessible";
          smiv2:oid "1.3.6.1.2.1.7.7.1.2";
        }

        leaf udpEndpointLocalPort {
          type inet:port-number;
          description
           "The local port number for this UDP endpoint.";
          smiv2:max-access "not-accessible";
          smiv2:oid "1.3.6.1.2.1.7.7.1.3";
        }

        leaf udpEndpointRemoteAddressType {
          type inet-address:InetAddressType;
          description
           "The address type of udpEndpointRemoteAddress.  Only
            IPv4, IPv4z, IPv6, and IPv6z addresses are expected, or
            unknown(0) if datagrams for all remote IP addresses are
            accepted.  Also, note that some combinations of
            
            udpEndpointLocalAdressType and
            udpEndpointRemoteAddressType are not supported.  In
            particular, if the value of this object is not
            unknown(0), it is expected to always refer to the
            same IP version as udpEndpointLocalAddressType.";
          smiv2:max-access "not-accessible";
          smiv2:oid "1.3.6.1.2.1.7.7.1.4";
        }

        leaf udpEndpointRemoteAddress {
          type inet-address:InetAddress;
          description
           "The remote IP address for this UDP endpoint.  If
            datagrams from any remote system are to be accepted,
            this value is ''h (a zero-length octet-string).
            Otherwise, it has the type described by
            udpEndpointRemoteAddressType and is the address of the
            remote system from which datagrams are to be accepted
            (or to which all datagrams will be sent).
            
            As this object is used in the index for the
            udpEndpointTable, implementors of this table should be
            careful not to create entries that would result in OIDs
            with more than 128 subidentifiers; else the information
            cannot be accessed using SNMPv1, SNMPv2c, or SNMPv3.";
          smiv2:max-access "not-accessible";
          smiv2:oid "1.3.6.1.2.1.7.7.1.5";
        }

        leaf udpEndpointRemotePort {
          type inet:port-number;
          description
           "The remote port number for this UDP endpoint.  If
            datagrams from any remote system are to be accepted,
            this value is zero.";
          smiv2:max-access "not-accessible";
          smiv2:oid "1.3.6.1.2.1.7.7.1.6";
        }

        leaf udpEndpointInstance {
          type uint32 {
            range "1..4294967295";
          }
          description
           "The instance of this tuple.  This object is used to
            distinguish among multiple processes 'connected' to
            the same UDP endpoint.  For example, on a system
            implementing the BSD sockets interface, this would be
            used to support the SO_REUSEADDR and SO_REUSEPORT
            socket options.";
          smiv2:max-access "not-accessible";
          smiv2:oid "1.3.6.1.2.1.7.7.1.7";
        }

        leaf udpEndpointProcess {
          type uint32;
          description
           "The system's process ID for the process associated with
            this endpoint, or zero if there is no such process.
            This value is expected to be the same as
            HOST-RESOURCES-MIB::hrSWRunIndex or SYSAPPL-MIB::
            sysApplElmtRunIndex for some row in the appropriate
            tables.";
          smiv2:max-access "read-only";
          smiv2:oid "1.3.6.1.2.1.7.7.1.8";
        }
      }
    }
  }

  smiv2:alias "udp" {
    smiv2:oid "1.3.6.1.2.1.7";
  }

  smiv2:alias "udpMIB" {
    smiv2:oid "1.3.6.1.2.1.50";
  }

  smiv2:alias "udpMIBConformance" {
    smiv2:oid "1.3.6.1.2.1.50.2";
  }

  smiv2:alias "udpMIBCompliances" {
    smiv2:oid "1.3.6.1.2.1.50.2.1";
  }

  smiv2:alias "udpMIBGroups" {
    smiv2:oid "1.3.6.1.2.1.50.2.2";
  }

}
