module SNMPv2-MIB-ann {
  namespace "urn:dummy";
  prefix dummy;

  import tailf-common {
    prefix tailf;
  }
  import SNMPv2-MIB {
    prefix x;
  }

  tailf:annotate "/x:SNMPv2-MIB/x:system/x:sysDescr" {
    tailf:callpoint "snmpagent" {
      tailf:internal;
    }
  }
  tailf:annotate "/x:SNMPv2-MIB/x:system/x:sysObjectID" {
    tailf:callpoint "snmpagent" {
      tailf:internal;
    }
  }
  tailf:annotate "/x:SNMPv2-MIB/x:system/x:sysUpTime" {
    tailf:callpoint "snmpagent" {
      tailf:internal;
    }
  }
  tailf:annotate "/x:SNMPv2-MIB/x:system/x:sysServices" {
    tailf:callpoint "snmpagent" {
      tailf:internal;
    }
  }
  tailf:annotate "/x:SNMPv2-MIB/x:system/x:sysORLastChange" {
    tailf:callpoint "snmpagent" {
      tailf:internal;
    }
  }
  tailf:annotate "/x:SNMPv2-MIB/x:snmp/x:snmpInPkts" {
    tailf:callpoint "snmpagent" {
      tailf:internal;
    }
  }
  tailf:annotate "/x:SNMPv2-MIB/x:snmp/x:snmpInBadVersions" {
    tailf:callpoint "snmpagent" {
      tailf:internal;
    }
  }
  tailf:annotate "/x:SNMPv2-MIB/x:snmp/x:snmpInBadCommunityNames" {
    tailf:callpoint "snmpagent" {
      tailf:internal;
    }
  }
  tailf:annotate "/x:SNMPv2-MIB/x:snmp/x:snmpInBadCommunityUses" {
    tailf:callpoint "snmpagent" {
      tailf:internal;
    }
  }
  tailf:annotate "/x:SNMPv2-MIB/x:snmp/x:snmpInASNParseErrs" {
    tailf:callpoint "snmpagent" {
      tailf:internal;
    }
  }
  tailf:annotate "/x:SNMPv2-MIB/x:snmp/x:snmpSilentDrops" {
    tailf:callpoint "snmpagent" {
      tailf:internal;
    }
  }
  tailf:annotate "/x:SNMPv2-MIB/x:snmp/x:snmpProxyDrops" {
    tailf:callpoint "snmpagent" {
      tailf:internal;
    }
  }
  tailf:annotate "/x:SNMPv2-MIB/x:snmpSet/x:snmpSetSerialNo" {
    tailf:callpoint "snmpagent" {
      tailf:internal;
    }
  }
  tailf:annotate "/x:SNMPv2-MIB/x:sysORTable" {
    tailf:callpoint "snmpagent" {
      tailf:internal;
    }
  }
}
