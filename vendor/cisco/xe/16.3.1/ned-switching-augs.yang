module ned-switching-augs {
    namespace "http://cisco.com/ns/yang/ned/ios/switching/augs";
    prefix ned-sw-a;

    import tailf-common {
       prefix tailf;
    }
    import ietf-inet-types {
      prefix inet;
    }
    import ned {
       prefix ned;
    }

    organization "Cisco Systems";

    description
       "NED YANG module for IOS
        Copyright (c) 2016 by Cisco Systems, Inc.
        All rights reserved.";

    ////////////////////////////////////////////////////////////////////////////
    // REVISION
    ///////////////////////////////////////////////////////////////////////////
    revision 2016-04-21 {
       description "Removed policy table-map actions";
    }
    revision 2016-04-20 {
       description "Added type string in vlan-list";
    }
    revision 2016-04-07 {
       description "Added vlan augment";
    }
    revision 2016-04-07 {
       description "Added Copyright";
    }
    revision 2016-02-26 {
       description "Added interface auto-qos and policy table-map actions";
    }

    ////////////////////////////////////////////////////////////////////////////////
    // GROUPING
    ///////////////////////////////////////////////////////////////////////////////
    
    // auto qos {trust|video|voip} groupings
    grouping auto-qos-grouping {
      container auto {
        tailf:info "Configure Automation";
        description "Configure Automation";
        container qos {
            tailf:info "Configure AutoQoS";
            description "Configure AutoQoS";
            container classify {
                tailf:info "Configure classification for untrusted devices";
                description "Configure classification for untrusted devices";
                presence true;
                leaf police {
                    tailf:info "Configure QoS policing for untrusted devices";
                    description "Configure QoS policing for untrusted devices";
                    type empty;
                }
            }
            container trust {
                tailf:info "Trust the DSCP/CoS marking";
                description "Trust the DSCP/CoS marking";
                presence true;
                leaf cos {
                    tailf:info "Trust the CoS marking";
                    description "Trust the CoS marking";
                    tailf:cli-full-command;
                    type empty;
                }
                leaf dscp {
                    tailf:info "Trust the DSCP marking";
                    description "Trust the DSCP marking";
                    tailf:cli-full-command;
                    type empty;
                }
            }
            container video {
                tailf:info "Configure AutoQoS for video devices";
                description "Configure AutoQoS for video devices";
                leaf cts {
                    tailf:info "Trust the QoS marking of the Cisco Telepresence System";
                    description "Trust the QoS marking of the Cisco Telepresence System";
                    tailf:cli-full-command;
                    type empty;
                }
                leaf ip-camera {
                    tailf:info "Trust the QoS marking of the Ip Video Surveillance camera";
                    description "Trust the QoS marking of the Ip Video Surveillance camera";
                    tailf:cli-full-command;
                    type empty;
                }
                leaf media-player {
                    tailf:info "Trust the Qos marking of the Cisco Media Player";
                    description "Trust the Qos marking of the Cisco Media Player";
                    tailf:cli-full-command;
                    type empty;
                }
            }
            container voip {
                tailf:info "Configure AutoQoS for VoIP";
                description "Configure AutoQoS for VoIP";
                presence true;
                leaf cisco-phone {
                    tailf:info "Trust the QoS marking of Cisco IP Phone";
                    description "Trust the QoS marking of Cisco IP Phone";
                    tailf:cli-full-command;
                    type empty;
                }
                leaf cisco-softphone {
                    tailf:info "Trust the QoS marking of Cisco IP SoftPhone";
                    description "Trust the QoS marking of Cisco IP SoftPhone";
                    tailf:cli-full-command;
                    type empty;
                }
                leaf trust {
                    tailf:info "Trust the DSCP/CoS marking";
                    description "Trust the DSCP/CoS marking";
                    tailf:cli-full-command;
                    type empty;
                }
            }
        }
      }
    }

    ////////////////////////////////////////////////////////////////////////////////
    // AUGMENT
    ///////////////////////////////////////////////////////////////////////////////

    augment /ned:native/ned:interface/ned:FastEthernet {
      uses auto-qos-grouping;
    }
    augment /ned:native/ned:interface/ned:GigabitEthernet {
      uses auto-qos-grouping;
    }
    augment /ned:native/ned:interface/ned:TenGigabitEthernet {
      uses auto-qos-grouping;
    }
    augment /ned:native/ned:interface/ned:Port-channel {
      uses auto-qos-grouping;
    }
    augment /ned:native/ned:interface/ned:Port-channel-subinterface/ned:Port-channel {
      uses auto-qos-grouping;
    }
    augment /ned:native/ned:ip/ned:igmp/ned:snooping {
      container vlan {
        tailf:info "IGMP Snooping enable for Catalyst VLAN";
        description "IGMP Snooping enable for Catalyst VLAN";
        list range {
          tailf:cli-drop-node-name;
          tailf:cli-suppress-mode;
          key "range";
          leaf range {
            tailf:info "Vlan number";
            description "Vlan number";
            type uint16 {
              range "1..1001 | 1006..4094";
            }
          }
          leaf immediate-leave {
            tailf:info "Enable IGMPv2 immediate leave processing";
            description "Enable IGMPv2 immediate leave processing";
            type empty;
          }
          leaf last-member-query-count {
            tailf:info "Last member query count";
            description "Interval (milliseconds)";
            type uint8 {
              range "1..7";
            }
          }
          leaf last-member-query-interval {
            tailf:info "Last member query interval";
            description "Interval (milliseconds)";
            type uint16 {
              range "100..32767";
            }
          }
          container mrouter {
            tailf:info "Configure an L2 port as a multicast router port";
            description "Configure an L2 port as a multicast router port";
            leaf interface {
              tailf:info "next-hop interface to mrouter";
              description "GigabitEthernet IEEE 802.3z";
              type string;
            }
            container learn {
              tailf:info "Set the multicast router learning method";
              description "Set the multicast router learning method";
              leaf cgmp {
                tailf:info "Learn the multicast router snooping CGMP packets";
                description "Learn the multicast router snooping CGMP packets";
                type empty;
              }
              leaf pim-dvmrp {
                tailf:info "Learn the multicast router snooping PIM-DVMRP packets";
                description "Learn the multicast router snooping PIM-DVMRP packets";
                type empty;
              }
            }
          }
          container querier {
            tailf:info "Enable IGMP querier for this Vlan";
            description "Enable IGMP querier for this Vlan";
            presence true;
            leaf address {
              tailf:info "IGMP querier source IP address";
              description "IGMP querier source IP address";
              type inet:ipv4-address;
            }
            leaf max-response-time {
              tailf:info "IGMP querier maximum response time (sec)";
              description "IGMP querier maximum response time (sec)";
              type uint8 {
                range "1..25";
              }
            }
            leaf query-interval {
              tailf:info "IGMP querier query interval (sec)";
              description "IGMP querier query interval (sec)";
              type uint16 {
                range "1..18000";
              }
            }
            container tcn {
              tailf:info "IGMP querier TCN related parameters";
              description "IGMP querier TCN related parameters";
              container query {
                tailf:info "IGMP querier TCN query related parameters";
                description "IGMP querier TCN query related parameters";
                leaf count {
                  tailf:info "IGMP querier TCN query count";
                  description "IGMP querier TCN query count";
                  type uint8 {
                    range "1..10";
                  }
                }
                leaf interval {
                  tailf:info "IGMP querier TCN query interval (sec)";
                  description "IGMP querier TCN query interval (sec)";
                  type uint8 {
                    range "1..255";
                  }
                }
              }
            }
            container timer {
              tailf:info "IGMP other querier timer";
              description "IGMP other querier timer";
              leaf expiry {
                tailf:info "IGMP querier other querier time out (sec)";
                description "IGMP querier other querier time out (sec)";
                type uint16 {
                  range "60..300";
                }
              }
            }
            leaf version {
              tailf:info "IGMP version";
              description "IGMP version";
              type uint8 {
                range "1..2";
              }
            }
          }
          leaf robustness-variable {
            tailf:info "IGMP snooping vlan robustness variable";
            description "Robustness variable";
            type uint8 {
              range "1..3";
            }
          }
          container static {
            tailf:info "Configure an L2 port as a member of a group";
            description "Configure an L2 port as a member of a group";
            list ipv4 {
              tailf:cli-drop-node-name;
              tailf:cli-suppress-mode;
              key "ipv4";
              leaf ipv4 {
                tailf:info "IP address of the group";
                description "IP address of the group";
                type inet:ipv4-address;
              }
              leaf interface {
                tailf:info "Specify an interface statically configured";
                description "GigabitEthernet IEEE 802.3z";
                type string;
              }
            }
          }
        }
      }
    }
    augment /ned:native/ned:vlan {
      leaf vlan-id {
        description "ISL VLAN IDs 1-4094";
        tailf:cli-drop-node-name;
        type string;
      }
      //vlan configuration
      leaf configuration {
        tailf:info "vlan feature configuration mode";
        description "VLAN ID List Eg. 1-10,15";
        type string {
	  pattern "([0-9]{1,4}(-[0-9]{1,4})?(,[0-9]{1,4}(-[0-9]{1,4})?)*)";
	}
      }
      // vlan access-map
      list access-map {
        tailf:info "Create vlan access-map or enter vlan access-map command mode";
        description "Create vlan access-map or enter vlan access-map command mode";
        tailf:cli-mode-name "config-access-map";
        key "map_tag";
        leaf map_tag {
          tailf:info "Vlan access map tag";
          description "Vlan access map tag";
          type string;
        }
        container action {
          tailf:info "Take the action";
          description "Take the action";
          leaf drop {
            tailf:info "Drop packets";
            description "Drop packets";
            type empty;
          }
          leaf forward {
            tailf:info "Forward packets";
            description "Forward packets";
            type empty;
          }
        }
        container match {
          tailf:info "Match values.";
          description "Match values.";
          container ip {
            tailf:info "IP based match";
            description "IP based match";
            leaf-list address {
              tailf:info "Match IP address to access control.";
              description "Match IP address to access control.";
              tailf:cli-flat-list-syntax;
              type ned:exp-acl-type;
            }
          }
          container ipv6 {
            tailf:info "IPv6 based match";
            description "IPv6 based match";
            leaf-list address {
              tailf:info "Match IPv6 address to access control.";
              description "Match IPv6 address to access control.";
              tailf:cli-flat-list-syntax;
              type string;
            }
          }
          container mac {
            tailf:info "MAC based match";
            description "MAC based match";
            leaf-list address {
              tailf:info "Match MAC address to access control.";
              description "Match MAC address to access control.";
              tailf:cli-flat-list-syntax;
              type string;
            }
          }
        } 
      }
      //vlan filter
      container filter {
        tailf:info "Apply a VLAN Map";
        description  "Apply a VLAN Map";
        tailf:cli-compact-syntax;
        tailf:cli-sequence-commands;
        leaf map-name {
          tailf:cli-drop-node-name;
          tailf:info "VLAN map name";
          description "VLAN map name";
          type string {
            tailf:info "WORD;;VLAN map name";
          }
        }
        leaf-list vlan-list {
          tailf:info "VLANs to apply filter to";
          description "VLANs to apply filter to";
          tailf:cli-range-list-syntax;
          type union {
            type uint16 {
              tailf:info "<1-4094>;;VLAN id";
              range "1..4094";
            }
            type string;
            type enumeration {
              enum all {
                tailf:info "Add this filter to all VLANs";
              }
            } 
          }
        }
      }

      // vlan group
      list group {
        tailf:info "Create a vlan group";
        description "Create a vlan group";
        tailf:cli-suppress-mode;
        key "group_name";
        leaf group_name {
          tailf:info "Group name starts with alphabet";
          description "Group name starts with alphabet";
          type string;
        }
        leaf-list vlan-list {
          tailf:info "List of vlans in this group";
          description "List of vlans in this group";
          tailf:cli-range-list-syntax;
          type union {
            type uint16 {
              tailf:info "<1-4094>;;VLAN id";
              range "1..4094";
            }
            type string;
          }
        }
      }
    }
}
