module cisco-lldp-state {

    yang-version 1;

    namespace "urn:cisco:params:xml:ns:yang:cisco-lldp-state";
    prefix lldp;

    organization
        "Cisco Systems, Inc.";

    contact
        " Cisco Systems, Inc.
          Customer Service

          Postal: 170 W Tasman Drive
          San Jose, CA 95134

          Tel: +1 1800 553-NETS

          E-mail: cs-yang@cisco.com";
    
    description
        " This module contains a collection of YANG definitions for
          monitoring LLDP state information.";
    
    reference "TODO";

    revision 2015-04-09 {
        description "Proposed";
    }


    container lldp-state {
        config false;

        description
            "Data nodes for LLDP entries.";

        list lldp-entry {
            key "device-id local-interface connecting-interface";

            description
                "The list of LLDP entries.";

            leaf device-id {
                type string;
                description
                    "The device ID of the link.";
            }

            leaf local-interface {
                type string;
                description
                    "The name of the local interface on the current device.";
            }
	    leaf connecting-interface {
                type string;
                description
                    "The name of the connected interface to 'local-interface'.";
            }

            leaf ttl {
                type uint32;
                description
                    "TTL denoting hold-time of this link entry.";
            }

            container capabilities {
		leaf repeater {
		    type empty;
		}

		leaf bridge {
		    type empty;
		}

		leaf access-point {
		    type empty;
	        }

		leaf router {
		    type empty;
		}

		leaf telephone {
		    type empty;
		}

		leaf docsis {
		    type empty;
		}

		leaf station {
		    type empty;
		}

		leaf other {
		    type empty;
		}

                description
                    "The LLDP device type";
            }

        }
    }

}
