module cisco-ia {
  namespace "http://cisco.com/yang/cisco-ia";
  prefix cisco-ia;

  import cisco-self-mgmt {
    prefix cisco-sfm;
  }
    
  import tailf-common {
    prefix tailf;
  }

  import ietf-yang-types {
    prefix "yang";
  }

  description
    "Copyright (c) 2016 by Cisco Systems, Inc."+
    "All rights reserved.";

  revision "2016-05-20" {
    description "Fix intelligent-sync default and convert leaf-lists into lists";
  }

  revision "2016-05-16" {
    description "Add augment statement";
  }

  revision 2016-05-13 {
    description "Change confd-cfg-blocking-enabled default and odm-log-level type";
  }

  revision 2016-05-09 {
    description "Add leaf for persistence checking";
  }

  revision 2016-05-04 {
    description "Add tail-f annotations to boolean leaves";
  }

  revision 2016-04-24 {
    description "Add dynamic PRC messages list, cleanup";
  }

  revision 2016-04-22 {
    description "Increase parser msg ignore max elements";
  }

  revision 2016-04-17 {
    description
      "Add container for snmp trap control, replacing"+
      "booleans for individual traps.";
  }

  revision 2016-04-07 {
    description
      "Update description with copyright notice.";
  }
    
  revision 2016-03-15 {
    description "Add intelligent sync control";
  }
    
  grouping cisco-ia-output {
    leaf result {
      type string;
    }
  }
    
  typedef cia-sync-type {
    type enumeration {
      enum "disabled" {
        value 0;
        description "Do no synchronize the CIA
                     database from the Network Element";
      }
      enum "without-defaults" {
        value 1;
        description "Collect \"show running\" from 
                      the Network Element";
      }
      enum "include-defaults" {
        value 2;
        description "Collect \"show running all\" from 
                      the Network Element";
      }
    }
    description "Controls the elements sent to the CIA 
                     database from the Network Element";
  }           
    
  typedef cia-log-level {
    type enumeration {
      enum "none" {
        value 0;
        description "No logging";
      }
      enum "error" {
        value 1;
        description "Log errors only";
      }
      enum "warning" {
        value 2;
        description "Log errors and warnings only";
      }
      enum "information" {
        value 3;
        description "Log errors, warnings, and information only";
      }
      enum "debug" {
        value 4;
        description "Log errors, warnings, information, and debug messages";
      }
    }
    description "Logging levels for CIA";
  }    
      
  typedef onep-log-level {
    type enumeration {
      enum "none" {
        value 0;
        description "No logging";
      }
      enum "fatal" {
        value 1;
        description "Log fatal events only";
      }
      enum "error" {
        value 2;
        description "Log fatal events and errors only";
      }
      enum "warning" {
        value 3;
        description "Log fatal events, errors, and warnings only";
      }
      enum "information" {
        value 4;
        description "Log fatal events, errors, warnings, 
                           and information only";
      }
      enum "debug" {
        value 5;
        description "Log fatal events, errors, warnings, information, and debug messages";
      }
      enum "trace" {
        value 6;
        description "Log all messages";
      }
    }
    description "Logging levels for Onep";
  }    
      
  typedef syslog-severity {
    type enumeration {
      enum "none" {
        value 8;
        description
          "No logging";
      }
      enum "emergency" {
        value 0;
        description
          "Emergency Level Msg";
      }
      enum "alert" {
        value 1;
        description
          "Alert Level Msg";
      }
      enum "critical" {
        value 2;
        description
          "Critical Level Msg";
      }
      enum "error" {
        value 3;
        description
          "Error Level Msg";
      }
      enum "warning" {
        value 4;
        description
          "Warning Level Msg";
      }
      enum "notice" {
        value 5;
        description
          "Notification Level Msg";
      }
      enum "info" {
        value 6;
        description
          "Informational Level Msg";
      }
      enum "debug" {
        value 7;
        description
          "Debugging Level Msg";
      }
    }
    description "Standard Syslog logging levels)";
  }
    
  rpc sync-from {
    tailf:actionpoint sync-from-network-element;
    description "Synchronize the network element's running-configuration
                     to ConfD.";
    input {
      leaf sync-defaults {
        type empty;
        description "Sends the output of \"show running all\" line
        	       by line to Confd.";
      }
    }
    output {
      uses cisco-ia-output;
    }
  }
     
  rpc save-config {
    tailf:actionpoint save-running-config;
    description "Copy the running-config to startup-config on the Network
                     Element.";
    output {
      uses cisco-ia-output;
    }
  }
    
  rpc checkpoint {
    tailf:actionpoint checkpoint-network-element;
    description "Create a configuration rollback checkpoint.
            Equivalent to the \"archive config\" CLI";
    output {
      uses cisco-ia-output;
    }
  }
    
  rpc revert {
    tailf:actionpoint revert-network-element;
    description "Cancel the timed rollback and trigger the
	     rollback immediately, or to reset parameters for the 
	     timed rollback";
    input {
      leaf now {
        type empty;
        description "To cancel the timed rollback and 
            	    trigger the rollback immediately";
      }
      leaf timer {
        type int16 {
          range 1..120;
        }
        description "Reset parameters for the timed rollback";
      }
      leaf idle {
        type int16 {
          range 1..120;
        }
        description "Maximum allowable time period of no activity
            				 before reverting to the saved configuration.";
      }
    }
    output {
      uses cisco-ia-output;
    }
  }
    
  rpc rollback {
    tailf:actionpoint rollback-network-element;
    description "Replaces the current running configuration file with 
        			a saved Cisco IOS XE configuration file.";
    input {
      leaf target-url {
        mandatory true;
        type string;
        description "Cisco IOS XE configuration file that is to replace the current running configuration";
      }
      leaf verbose {
        type boolean;
        default false;
        description "Display a list of the command lines applied by 
        			the Cisco IOS XE software parser during each pass of the 
        			configuration replace operation. The total number of passes
        			performed is also displayed.";
      }
      leaf nolock {
        type boolean;
        default false;
        description "Disables the locking of the running configuration
        		 file that prevents other users from changing the running 
        		 configuration during a configuration replace operation.";
      }
            	
      leaf revert-on-error {
        type empty;
        description "Reverts to the original configuration upon error.";	
      }
            
      leaf revert-timer {
        type int16 {
          range 1..120;
        }
        description "Reverts to the original configuration if 
            			specified time elapses.";
      }
    }
    output {
      uses cisco-ia-output;
    }
  }
    
  rpc reset {
    tailf:actionpoint reset-cia;
    description "Restart all daemons in the CIA container";
    input {
      leaf reinitialize {
        type boolean;
        default false;
        description "Deletes the entire Confd CDB to recover from 
            a corrupted database. USE WITH CAUTION!";
      }
    }
    output {
      uses cisco-ia-output;
    }
  }

  augment "/cisco-sfm:netconf-yang" {     
  container cisco-ia {
    leaf auto-sync {
      type cia-sync-type;
      default "without-defaults";
      description
        "Enables automatic synchronization of the network element's
    			 running configuration with the CIA database.";
    }
    leaf init-sync {
      type cia-sync-type;
      default "without-defaults";
      description
        "Enables synchronization of the network element's
    			 running configuration with the CIA database when CIA initializes.";
    }
    leaf intelligent-sync {
        tailf:cli-boolean-no;
        type boolean;
        default false;
        description "When enabled, intelligent-sync monitors all ttys for
                 configuration changes and replays these changes to the
                 CIA database once the tty exits configuration mode.  When
                 disabled, the complete running-configuration is used to
                 synchronize the CIA database whenever a CLI configuration
                 change is detected";
    }       	        
    container snmp-trap-control {
      description
        "This container describes the configuration parameters for SNMP
         Trap to NetConf notification processing.";
      leaf global-forwarding {
        tailf:cli-boolean-no;
        type boolean;
        default true;
        description
          "This leaf enables or disables forwarding for all SNMP traps.";
      }
      list trap-list {
        key trap-oid;
        max-elements 10;
        min-elements 0;
        description
          "This list describes SNMP Traps that are supported for automatic
           translation to NetConf notifications.";
        leaf trap-oid {
        type yang:object-identifier-128;
          description
            "This leaf contains the OID for the SNMP trap to be forwarded.";
        }
        leaf description {
          type string;
          description
            "This leaf contains the name of the SNMP trap to be forwarded.";
          }
        leaf forward {
          tailf:cli-boolean-no;
          type boolean;
          default true;
          description
            "This leaf enables or disables forwarding for this SNMP trap.";
        }
      }
    }
    leaf message-diag-level {
      type int16 {
        range "0..3";
      }
      default 0;
      description
        "0 = Disabled, 
    			 1 = Save input message, CIA debugs, and response, 
    			 2 = Level 1 + Save \"before\" and \"after\" running-config,
    			 3 = Level 2 + rollback file and configuration diff";
    }	       
    leaf max-diag-messages-saved {
      type int16 {
        range "0..199";
      }
      default 30;
      description
        "The maximum number of messages whose diagnostic data in kept in persistent storage.";
    }	 
    leaf post-sync-acl-process {
        tailf:cli-boolean-no;
        type boolean;
     	default true;
     	description
         "Run \"show ip access-list\" and send to ConfD";
    }
    leaf config-change-delay {
        type int16;
        default 0;
        description
        "Delay in ms before applying CDB change to NE";
   }
    leaf process-missing-prc {
        tailf:cli-boolean-no;
        type boolean;
     	default true;
     	description
         "Process any parser output from configuration changes as a possible error.";
    }

    list parser-msg-ignore {
        config false;
        key message;
        max-elements 200;
        description "Parser output from configuration change that is informational
        	            only, not an error. This is a read only list containing known
                        informational messages";
        leaf message {
            type string {
                length "1..255";
            }
        }
    }

    list conf-parser-msg-ignore {
        key message;
        max-elements 50;
        description "Parser output from configuration change that is informational
        	            only, not an error";
        leaf message {
            type string {
                length "1..255";
            }
        }
    }

    leaf nes-ttynum {
        tailf:hidden full;
        config false;
        type int16;
        description "TTY number used by NetworkElementSynchronizer";
    }
    leaf restored {
        tailf:hidden full;
        type boolean;
        default false;
        description "Indicates if CDB restored from NES running-config";
    }
    container logging {
      leaf confd-log-level {
        type syslog-severity;
        default "error";
        description "Logging level for Confd";
      }    
      leaf ciaauthd-log-level {
        type cia-log-level;
        default "error";
        description "Logging level for CiaAuthDaemon";
      }
      leaf nes-log-level {
        type cia-log-level;
        default "error";
        description "Logging level for 
        	                    Network Element Synchronizer";
      }    	  
      leaf onep-log-level {
        type onep-log-level;
        default "error";
        description "Logging level for ONEP";
      }
      leaf odm-log-level {
        type cia-log-level;
        default "error";
        description "Logging level for 
        	                    Operational Data Manager";
      }
      leaf sync-log-level {
        type cia-log-level;
        default "error";
        description "Logging level for 
        	                    Sync-From Daemon";
      }
    }
    container blocking {
      leaf cli-blocking-enabled {
        tailf:cli-boolean-no;
        type boolean;
        default false;
        description
          "Enables blocking of designated command lines via the 
    			      network element's CLI";
      }
      must "boolean(network-element-command)" {
        error-message
          "Command list must not be empty once initialized";
      }	

      list network-element-command {
        key command;
        max-elements 30;
        description "Command line pattern to disallow via the
        	            network element's CLI";
        leaf command {
            type string {
                length "1..255";
            }
        }
      }

      leaf confd-cfg-blocking-enabled {
        tailf:cli-boolean-no;
        type boolean;
        default true;
        description
          "Enables blocking of designated command lines via the 
    			      network element's CLI";
      }
      must "boolean(confd-cfg-command)" {
        error-message
          "Command list must not be empty once initialized";
      }	

      list confd-cfg-command {
        key command;
        max-elements 50;
        description "Command line pattern to omit syncing to Confd CDB";
        leaf command {
            type string;
        }
      }
    }
  }
  }
}
