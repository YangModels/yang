module enable {
  namespace "http://cisco.com/ns/example/enable";
  prefix enable;

  import tailf-common {
    prefix tailf;
  }

  container enable {
    leaf password {
      type tailf:des3-cbc-encrypted-string;
    }
  }
}
