module Cisco-IOS-XE-bgp-oper {
 
    yang-version 1;
 
    namespace "http://cisco.com/ns/yang/Cisco-IOS-XE-bgp-oper";
    prefix bgp-ios-xe-oper;
 
    import ietf-inet-types {
        prefix inet;
    }


    organization
        "Cisco Systems, Inc.";
 
    contact
       "Cisco Systems, Inc. Customer Service Postal: 170 W Tasman Drive
        San Jose, CA 95134 Tel: +1 1800 553-NETS E-mail: cs-yang@cisco.com";
    
    description
       "This module contains a collection of YANG definitions for
        monitoring BGP information."+
       "Copyright (c) 2016-2017 by Cisco Systems, Inc."+
       "All rights reserved."; 

  // =========================================================================
  // REVISION 
  // =========================================================================

  revision 2017-02-07 {
    description
      "Initial revision";
  }

    grouping bgp-status-code {
        leaf suppressed {
            type empty;
        }
                    
        leaf damped {
            type empty;
        }
                    
        leaf history {
            type empty;
        }
                    
        leaf valid {
            type empty;
        }
                    
        leaf best {
            type empty;
        }
                    
        leaf internal {
            type empty;
        }
                    
        leaf rib-failure {
            type empty;
        }
                    
        leaf stale {
            type empty;
        }
                    
        leaf multipath {
            type empty;
        }
                
        leaf backup-path {
            type empty;
        }
                    
        leaf rt-filter {
            type empty;
        }
                    
        leaf best-external {
            type empty;
        }
                    
        leaf additional-path {
           type empty;
        }
                    
        leaf rib-compressed {
            type empty;
        }
                    
        leaf status {
            type bgp-ios-xe-oper:bgp-rpki-status;
        }
    }

    grouping bgp-message-counters {
        description
            "Information for BGP message counters";

        leaf opens {
            type uint32;
            description
                "OPEN messages";
        }
        leaf updates {
            type uint32;
            description
                "UPDATE messages";
        }
        leaf notifications {
            type uint32;
            description
                "NOTIFICATION messages";
        }
        leaf keepalives {
            type uint32;
            description
                "KEEPALIVE messages";
        }
        leaf route-refreshes {
            type uint32;
            description
               "Route refresh messages";
        }
    }

    grouping bgp-prefix-counters {
        leaf current-prefixes {
            type uint64;
            description
                "Current number of prefixes accepted";
            
        }
        leaf total-prefixes {
            type uint64;
            description
                "Total number of prefixes accepted";
        }
        leaf implicit-withdraw {
            type uint64;
            description
                "number of times that a prefix has been withdrawn 
                and readvertised";
        }
        leaf explicit-withdraw {
            type uint64;
            description
                "Number of times that a prefix has been withdrawn 
                 because it is no longer feasible";
        }
        leaf bestpaths {
            type uint64;
            description
                "Number of received prefixes installed as best paths";
        }
        leaf multipaths {
            type uint64;
            description
                "Number of received prefixes installed as multipaths";
        }
    }

    grouping negotiated-keepalive-timers {
        description
            "Information for neigotiated keepalive timers";
        leaf hold-time {
            type uint16;
            description
                "Hold time";
        }
        leaf keepalive-interval {
            type uint16;
            description
                "keepalive interval";
        }
    }

    grouping neighbor-summary {
        leaf id {
            type string;
        }
        leaf bgp-version {
            type uint32;
        }
        leaf messages-received {
            type uint64;
        }
        leaf messages-sent {
            type uint64;
        }
        leaf table-version {
            type uint64;
        }
        leaf input-queue {
            type uint64;
        }
        leaf output-queue {
            type uint64;
        }
        leaf up-time {
            type string;
        }
        leaf state {
            type bgp-ios-xe-oper:bgp-fsm-state;
        }
        leaf prefixes-received {
            type uint64;
        }
    }

    grouping bgp-connection {
        leaf state {
            type bgp-ios-xe-oper:tcp-fsm-state;
            description
                "TCP FSM state";
        }

        leaf mode {
            type bgp-ios-xe-oper:bgp-mode;
        }
        leaf total-established {
            type uint32;
            description
                "number of times a TCP and BGP connection has been 
                successfully established";
        }
        leaf total-dropped {
            type uint32;
            description
                "number of times that a valid session has failed 
                or been taken down";
        }
        leaf last-reset {
            type string;
            description
                "since the peering session was last reset";
        }
        leaf reset-reason {
            type string;
            description
                "The reason for the last reset";
        }
    }

    grouping bgp-transport {
        leaf path-mtu-discovery {
            type boolean;
        }
        leaf local-port {
            type uint32 ;
            description
                "Local TCP port used for TCP session";
        }
        leaf local-host {
            type inet:ip-address;
            description
                "Local address used for the TCP session";
        }
        leaf foreign-port {
            type uint32;
            description
                "Remote port used by the peer for the TCP session";
        }
        leaf foreign-host {
            type inet:ip-address;
            description
                "Remote address to which the BGP session has
                established";
        }
        leaf mss {
            type uint32;
            description
                "Maximum Data segment size";
        }
    }

    grouping bgp-af-prefix-activity {
        description
            "Prefix statistics for an address family";
        container sent {
            uses bgp-ios-xe-oper:bgp-prefix-counters;
        }
        container received {
            uses bgp-ios-xe-oper:bgp-prefix-counters;
        }
    }

    grouping bgp-neighbor-counters {
        description
            "Information for bgp session counters";

        container sent {
            uses bgp-ios-xe-oper:bgp-message-counters;
        }
        container received {
            uses bgp-ios-xe-oper:bgp-message-counters;
        }

        leaf inq-depth {
            type uint32;
            description "Input Q depth";
        }
        leaf outq-depth {
            type uint32;
            description "Output Q depth";
        }
    }

    grouping neighbor-key { 
        leaf afi-safi {
            type bgp-ios-xe-oper:bgp-afi-safi;
        }
        leaf vrf-name {
            type string;
        }
        leaf neighbor-id {
            type string;
        }
    }

    grouping neighbor {
        leaf description {
            type string;
        }
        leaf bgp-version {
            type uint16;
            description
                "BGP version being used to communicate with the 
                        remote router";
        }
        leaf link {
            type bgp-ios-xe-oper:bgp-link;
        }
        leaf up-time {
            type string;
            description
                "How long the bgp session has been up since
                         the sessioin was established";
        }
        leaf last-write {
            type string;
            description
                "since BGP last sent a message from this neighbor";
        }
        leaf last-read {
            type string;
            description
                "since BGP last received a message to this neighbor";
        }
        leaf installed-prefixes {
            type uint32;
            description
                "number of installed prefixes";
        }
        leaf session-state {
            type bgp-ios-xe-oper:bgp-fsm-state;
        }

        container negotiated-keepalive-timers {
            uses bgp-ios-xe-oper:negotiated-keepalive-timers;
        }

        leaf-list negotiated-cap {
           type string;
            description
                "Information for bgp neighbor session negotiated
                capabilities";
 
        }

        container bgp-neighbor-counters {
            uses bgp-ios-xe-oper:bgp-neighbor-counters;
        }

        container connection {
            uses bgp-ios-xe-oper:bgp-connection;
        }

        container transport {
            uses bgp-ios-xe-oper:bgp-transport;
        }

        container prefix-activity {
            uses bgp-ios-xe-oper:bgp-af-prefix-activity;
        }
    }

    grouping entry-stats {
        leaf total-entries {
            type uint64;
            description
                "total prefix entires";
        }
        leaf memory-usage {
            type uint64;
            description
               "total memory usage in byte";
        }
    }

    grouping activities {
        description
            "BGP activity information";
        leaf prefixes {
            type uint64;
        }
        leaf paths {
            type uint64;
        }
        leaf scan-interval {
            type string;
            description "scan interval in second";
        }
    }

    grouping address-family-key {
        leaf afi-safi {
            type bgp-ios-xe-oper:bgp-afi-safi; 
        }
        leaf vrf-name {
            type string;
        }
    }

    grouping address-family-summary { 
        description
            "Summary of address familiy";

        leaf router-id {
            type inet:ip-address;
        }

        leaf bgp-table-version {
            type uint64;
            description
                 "BGP table version number";
        }

        leaf routing-table-version {
            type uint64;
            description
                "Routing table version number";
        }

        container prefixes {
            uses bgp-ios-xe-oper:entry-stats;
        }

        container path {
            uses bgp-ios-xe-oper:entry-stats;
        }

        container as-path {
            uses bgp-ios-xe-oper:entry-stats;
        }

        container route-map {
            uses bgp-ios-xe-oper:entry-stats;
        }

        container filter-list {
            uses bgp-ios-xe-oper:entry-stats;
        }

        container activities {
            description
                "BGP activity information";
            uses bgp-ios-xe-oper:activities;
        }

        leaf total-memory {
            type uint64;
        }

        container bgp-neighbor-summaries {
            description
                "Summary of neighbor";

            list bgp-neighbor-summary {
                key "id";

                uses bgp-ios-xe-oper:neighbor-summary;
            }
        }
    }

    grouping bgp-state {

        container neighbors {
            list neighbor {
                key "afi-safi vrf-name neighbor-id";

                uses bgp-ios-xe-oper:neighbor-key;
                uses bgp-ios-xe-oper:neighbor;
            }
        }

        container address-families {
            list address-family {
                key "afi-safi vrf-name";

                uses bgp-ios-xe-oper:address-family-key;
                uses bgp-ios-xe-oper:address-family-summary;
            }
        }
    }

    typedef bgp-route-option {
        type enumeration {
            enum bgp-all-routes {
                description
                    "All entries";
            }
            enum bgp-cidr-only-routes {
                description
                    "CIDR ONLY route entries";
            }
            enum bgp-dampened-routes {
                description
                    "Dampened route entries";
            }
            enum bgp-rib-fail-routes {
                description
                    "Rib failure routes";
            }
            enum bgp-injected-routes {
                description
                    "Injected route entries";
            }
            enum bgp-pending-routes {
                description
                    "prefixes pending deletion";
                
            }
            enum bgp-inconsistent-routes {
                description
                    "inconsistency paths";
            }
        }
    }

    typedef bgp-link {
        type enumeration {
            enum internal {
                description "iBGP neighbors";
            }
            enum external {
                description "eBGP neighbors";
            }
        }
    }

    typedef bgp-fsm-state {
        type enumeration {
            enum idle {
                description "neighbor is in Idle state";
            }
            enum connect {
                description "neighbor is in Connect state";
            }
            enum active {
               description "neighbor is in Active state";
            }
            enum opensent {
                description "neighbor is in OpenSent state";
            }
            enum openconfirm {
                description "neighbor is in OpenConfirm state";
            }
            enum established {
                description "neighbor is in Established state";
            }
            enum nonnegotiated {
                description "neighbor is Non Negotiated";
            }
        }
     }

     typedef bgp-afi-safi {
        type enumeration {
            enum ipv4-mdt {
            }
            enum ipv4-multicast {
            }
            enum ipv4-unicast {
            }
            enum ipv4-mvpn {
            }
            enum ipv4-flowspec {
            }
            enum ipv6-multicast {
            }
            enum ipv6-unicast {
            }
            enum ipv6-mvpn {
            }
            enum ipv6-flowspec {
            }
            enum l2vpn-vpls {
            }
            enum l2vpn-e-vpn {
            }
            enum nsap-unicast {
            }
            enum rtfilter-unicast {
            }
            enum vpnv4-multicast {
            }
            enum vpnv4-unicast {
            }
            enum vpnv6-unicast {
            }
            enum vpnv6-multicast {
            }
            enum vpnv4-flowspec {
            }
            enum vpnv6-flowspec {
            }
        }
    }
 
    typedef tcp-fsm-state {
        type enumeration {
            enum closed {
                description
                    "no connection";
            }
            enum listen {
                description
                    "waiting for a connection request from any remote TCP";
            }
            enum synsent {
                description
                    "waiting for a matching connection request
                     after having sent a connection request";
            }
            enum synrcvd {
                description
                    "waiting for a confirming connection request acknowledgment
                     after having both received and sent a connection request";
            }
            enum established {
                description
                    "connection established";
            }
            enum finwait1 {
                description
                    "waiting for a connection termination request
                     from the remote TCP, or an acknowledgment of
                     the connection termination request previously sent";
            }
            enum finwait2 {
                description
                    "waiting for a connection termination request from the
                     remote TCP";
            }
            enum closewait {
                description
                    "waiting for a connection termination request from
                     the local use";
            }
            enum lastack {
                description
                    "waiting for an acknowledgment of the connection termination
                     request previously sent to the remote TCP";
            }
            enum closing {
                description
                    "waiting for a connection termination request acknowledgment
                     from the remote";
            }
            enum timewait {
                description
                    "waiting for enough time to pass to be sure the remote TCP
                     received the acknowledgment of its connection termination
                     request";
            }
        }
    }
     
    typedef bgp-origin-code {
        type enumeration {
            enum origin-igp {
                description "BGP origin code IGP";
            }
            enum origin-egp {
                description "BGP origin code EGP";
            }
            enum origin-incomplete {
                description "BGP origin code incomplete";
            }
        }
    }

    typedef bgp-mode {
        type enumeration {
            enum active {
                description
                    "active connection";
            }
            enum passive {
                description
                    "passive connection";
            }
       }
    }

    typedef bgp-rpki-status {
        type enumeration {
            enum rpki-valid {
            }
            enum rpki-invalid {
            }
            enum rpki-not-found {
            }
        }
    }
 
    container bgp-state {
        config false;
        description
            "Data nodes for BGP entries.";

        uses bgp-ios-xe-oper:bgp-state;
    }
}
