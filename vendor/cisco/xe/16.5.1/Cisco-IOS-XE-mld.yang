module Cisco-IOS-XE-mld {
  namespace "http://cisco.com/ns/yang/Cisco-IOS-XE-mld";
  prefix ios-mld;

  import Cisco-IOS-XE-native {
    prefix ios;
  }


  import ietf-inet-types {
    prefix inet;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Multicast Listener Discovery (MLD) Yang model.
     Copyright (c) 2016 by Cisco Systems, Inc.
     All rights reserved."; 

  // =========================================================================
  // REVISION 
  // =========================================================================

  revision 2017-02-07 {
    description
      "Initial revision";
  }

  

  grouping config-mld-grouping {
    container mld { 
      description
        "Global mld commands";

      container ssm-map {
        description
          "SSM mapping commands";
        leaf enable {
          description
            "Enable SSM mapping";
          type empty;
        }

        container query {
          description
            "Which database should we query for the source";
          leaf dns {
            description
              "Use DNS for source lookup";
            type empty;
          }
        }

        container static {
          description
            "SSM static group to source mapping";
          leaf acl {
            type string;
          }
          leaf source-ip {
            type inet:ipv6-address;
          }
        }
      }
    }
  }

  /////////////////////////////////////////////////////////
  // native / ipv6 / mld
  /////////////////////////////////////////////////////////
  augment "/ios:native/ios:ipv6" {
    uses config-mld-grouping;
  } //augment
} //module
