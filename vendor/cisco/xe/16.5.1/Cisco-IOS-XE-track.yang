module Cisco-IOS-XE-track {
  namespace "http://cisco.com/ns/yang/Cisco-IOS-XE-track";
  prefix ios-track;


  import ietf-inet-types {
    prefix inet;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Object Tracking Yang Model.
     Copyright (c) 2016 by Cisco Systems, Inc.
     All rights reserved."; 

  // =========================================================================
  // REVISION 
  // =========================================================================

  revision 2017-02-07 {
    description
      "Initial revision";
  }

  grouping track-timer-grouping {
    leaf seconds {
      type uint32 {
        range "1..3000";
      }
    }
    leaf ms {
      description
        "Specify polling interval in milliseconds";
      type uint32 {
        range "500..5000";
      }
    }
  }

  grouping track-grouping {
    container delay {
      description
        "Tracking delay";
      leaf down {
        description
          "Delay down change notification";
        type uint32 {
          range "0..180";
        }
      }
      leaf up {
        description
          "Delay up change notification";
        type uint32 {
          range "0..180";
        }
      }
    }
    leaf default-state {
      description
        "default object state";
      type enumeration {
        enum "down";
        enum "up";
      }
    }
    list object {
      description
        "Add a tracked object to list";
      key "number";
      leaf number {
        type uint32 {
          range "1..1000";
        }
      }
      leaf not {
        description
          "Negate the state of object";
        type empty;
      }
    }
    container ipv6-object {
      description
        "Tracking IPv6 object configuration";
      when "../ipv6";
      leaf vrf {
        description
          "VPN Routing/Forwarding table name";
        type string;
      }
    }
    container ip-object {
      description
        "Tracking IP object configuration";
      when "../ip";
      leaf vrf {
        description
          "VPN Routing/Forwarding table name";
        type string;
      }
    }
  }

  grouping default-track-grouping {
    container delay {
      description
        "Tracking delay";
      presence "true";
    }
    leaf default-state {
      description
        "default object state";
      type enumeration {
        enum "down";
        enum "up";
      }
    }
    container ip {
      description
        "Tracking IP object configuration";
      when "../../ip";
      leaf vrf {
        description
          "VPN Routing/Forwarding table";
        type empty;
      }
    }
    container ipv6 {
      description
        "Tracking IPv6 object configuration";
      when "../../ipv6";
      leaf vrf {
        description
          "VPN Routing/Forwarding table";
        type empty;
      }
    }
  }

  grouping config-track-grouping {
    list tracked-object {
      key "object-number";
      leaf object-number {
        type uint32 {
          range "1..1000";
        }
      }
      container interface {
        description
          "Select an interface to track";
        leaf name {
          type string;
        }
        leaf protocol {
          type enumeration {
            enum "ip";
            enum "ipv6";
            enum "line-protocol";
          }
        }
        leaf routing {
          description
            "Track interface IPv6 routing capability";
          when "../protocol = 'ip' or ../protocol = 'ipv6'";
          type empty;
        }
      }
      container ip {
        description
          "IP protocol";
        container route {
          leaf address {
            type inet:ipv4-address;
          }
          leaf mask {
            type inet:ipv4-address;
          }
          leaf reachability {
            description
              "Route reachability state";
            type empty;
          }
          leaf metric {
            description
              "Route metric";
            type enumeration {
              enum "threshold";
            }
          }
        }
        container sla {
          description
            "IP Service Level Agreement";
          leaf number {
            description
              "Entry number";
            type uint32;
          }
          leaf reachability {
            description
              "Reachability";
            type empty;
          }
          leaf state {
            description
              "Return code state";
            type empty;
          }
        }
      }
      container ipv6 {
        description
          "IPv6 protocol";
        container route {
          description
            "IPv6 route";
          leaf address {
            type inet:ipv6-prefix;
          }
          leaf reachability {
            description
              "Route reachability state";
            type empty;
          }
          leaf metric {
            description
              "Route metric";
            type enumeration {
              enum "threshold";
            }
          }
        }
      }
      container list {
        description
          "Group objects in a list";
        leaf boolean {
          description
            "List state based on a boolean calculation on objects";
          type enumeration {
            enum "and";
            enum "or";
          }
        }
        leaf threshold {
          description
            "List state based on a threshold of UP and DOWN objects";
          type enumeration {
            enum "percentage";
            enum "weight";
          }
        }
      }
      leaf stub-object {
        description
          "Stub tracking object";
        type empty;
      }
      container default {
        description
          "Set a command to its defaults";
        uses default-track-grouping;
      }
      uses track-grouping;
    }
    container resolution {
      description
        "Tracking resolution parameters";
      container ip {
        description
          "IP protocol";
        container route {
          description
            "Route metric resolution";
          leaf bgp {
            description
              "BGP route metric resolution";
            type uint32 {
              range "256..40000000";
            }
          }
          leaf eigrp {
            description
              "EIGRP route metric resolution";
            type uint32 {
              range "256..40000000";
            }
          }
          leaf isis {
            description
              "ISIS route metric resolution";
            type uint32 {
              range "1..1000";
            }
          }
          leaf ospf {
            description
              "OSPF route metric resolution";
            type uint32 {
              range "1..1562";
            }
          }
          leaf static {
            description
              "Static route metric resolution";
            type uint32 {
              range "1..100000";
            }
          }
        }
      }
    }
    container timer {
      description
        "Polling interval timers";
      container interface {
        description
          "Interface polling timer";
        uses track-timer-grouping;
      }
      container ip {
        description
          "IP protocol";
        container route {
          description
            "IP route polling timer";
          uses track-timer-grouping;
        }
        container sla {
          description
            "IP SLA polling timer";
          uses track-timer-grouping;
        }
      }
      container ipv6 {
        description
          "IPv6 protocol";
        container route {
          description
            "IPv6 route polling timer";
          uses track-timer-grouping;
        }
      }
      container list {
        description
          "Boolean list polling timer";
        uses track-timer-grouping;
      }
      container stub-object {
        description
          "EEM stub polling timer";
        uses track-timer-grouping;
      }
    }
  }

  /////////////////////////////////////////////////////////
  // native / track *
  /////////////////////////////////////////////////////////
  augment "/ios:native/ios:track" {
    uses config-track-grouping;
  }
}
