module Cisco-IOS-XE-vpdn {
  namespace "http://cisco.com/ns/yang/Cisco-IOS-XE-vpdn";
  prefix ios-vpdn;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Virtual Private Dialup Network (VPDN) Yang model.
     Copyright (c) 2016 by Cisco Systems, Inc.
     All rights reserved."; 

  // =========================================================================
  // REVISION 
  // =========================================================================

  revision 2017-02-07 {
    description
      "Initial revision";
  }

  grouping config-vpdn-grouping {
    container vpdn { //57185
      description
        "Virtual Private Dialup Network";

      leaf authen-before-forward {
        description
          "Authenticate a user locally before tunnelling";
        type empty;
      }

      leaf enable {
        description
          "Enable VPDN";
        type empty;
      }

      leaf-list search-order {
        ordered-by user;
        description
          "Configure the order to search different VPDN tunnel types";
        type enumeration {
          enum "dnis";
          enum "domain";
          enum "multihop-hostname";
        }
      }
    }
  }

  /////////////////////////////////////////////////////////
  // native / vpdn
  /////////////////////////////////////////////////////////
  augment "/ios:native" {
    uses config-vpdn-grouping;
  }
} //module
