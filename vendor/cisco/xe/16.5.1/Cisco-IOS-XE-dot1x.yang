module Cisco-IOS-XE-dot1x {
  namespace "http://cisco.com/ns/yang/Cisco-IOS-XE-dot1x";
  prefix ios-dot1x;


  import Cisco-IOS-XE-native {
    prefix ios;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native dot1x Yang model.
     Copyright (c) 2016 by Cisco Systems, Inc.
     All rights reserved."; 

  // =========================================================================
  // REVISION 
  // =========================================================================

  revision 2017-02-07 {
    description
      "Initial revision";
  }

  

  grouping mode-config-fallback-profile-grouping {
    leaf description {
      description "Any textual description";
      type string;
    }

    container ip {
      description "Internet Protocol configuration commands";
      list access-group {
        description "Specify access control for packets";
        key "name";
        leaf name {
          description "IP expanded access list (standard or extended)";
          type union {
            type uint16 {
              range "1300..2699";
            }
            type string;
          }
        }
        leaf in {
          description "inbound packets";
          type empty;
        }
      }
      leaf admission {
        description "Name of IP admission rule";
        type string;
      }
    }
  }

  grouping config-fallback-grouping {
    container profile {
      description "Create a Fallback profile";
      list fallback-list{
        description "Specify a policy name";
        key "name";
        leaf name {
          type string;
        }
        uses mode-config-fallback-profile-grouping;
      }
    }
  }

  grouping config-dot1x-grouping {
    list credentials {
      description "Configure 802.1X credentials profiles";
      key "profile-name";
      leaf profile-name {
        description "Specify a profile name";
        type string;
      }
      leaf username {
        description
          "Set the authentication userid";
        type string;
      }
      container password {
        description
          "Set the authentication password";
        leaf type {
          type enumeration {
            enum "0";
            enum "7";
          }
        }
        leaf secret {
          type string;
        }
      }
      leaf pki-trustpoint {
        description
          "Set the default pki trustpoint";
        type string;
      }
    }
    // dot1x critical
    container critical {
      description
        "Set 802.1x Critical Authentication parameters";
      leaf eapol {
        description
          "Send EAPOL-Success on successful Critical Authentication";
        type empty;
      }
      container recovery {
        description
          "Set 802.1x Critical Authentication Recovery parameters";
        leaf delay {
          description
            "Set 802.1x Critical Authentication Recovery Delay period";
          type uint16 {
            range "1..10000";
          }
        }
      }
    }
    container test {
      description "Configure dot1x test related parameters";
      leaf timeout {
        description "Seconds";
        type uint16 {
          range "1..65535";
        }
      }
    }
    // dot1x supplicant
    container supplicant {
      description
        "802.1X supplicant configuration";
      leaf force-multicast {
        description
          "Force 802.1X supplicant to send multicast packets";
        type empty;
      }
    }
    // dot1x system-auth-control
    leaf system-auth-control {
      description
        "Enable or Disable SysAuthControl";
      type empty;
    }
  }

  grouping config-interface-dot1x-grouping {
    container dot1x {
      description
        "Interface Config Commands for IEEE 802.1X";
      container authenticator {
        description
          "Configure authenticator parameters";
        container eap {
          description
            "Configure EAP authenticator parameters";
          leaf profile {
            description
              "EAP authenticator profile configuration";
            type string;
          }
        }
      }

      leaf credentials {
        description
          "Credentials profile configuration";
        type string;
      }
      leaf max-reauth-req {
        description
          "Max No. of Reauthentication Attempts";
        type uint8 {
          range "1..10";
        }
      }
      leaf max-req {
        description
          "Max No. of Retries";
        type uint8 {
          range "1..10";
        }
      }
      leaf max-start {
        description
          "Max No. of EAPOL-Start requests";
        type uint8 {
          range "1..10";
        }
      }
      leaf pae {
        description
          "Set 802.1x interface pae type";
        type enumeration {
          enum "authenticator";
          enum "supplicant";
          enum "both";
        }
      }
      container supplicant {
        description
          "Configure supplicant parameters";
        container eap {
          description
            "Configure EAP supplicant parameters";
          leaf profile {
            description
              "EAP supplicant profile configuration";
            type string;
          }
        }
      }
      container timeout {
        description
          "Various Timeouts";
        leaf auth-period {
          description
            "Timeout for authenticator reply";
          type uint16;
        }
        leaf held-period {
          description
            "Timeout for authentication retries";
          type uint16;
        }
        leaf quiet-period {
          description
            "QuietPeriod in Seconds";
          type uint16;
        }
        leaf ratelimit-period {
          description
            "Ratelimit Period in seconds";
          type uint16;
        }
        leaf server-timeout {
          description
            "Timeout for Radius Retries";
          type uint16;
        }
        leaf start-period {
          description
            "Timeout for EAPOL-start retries";
          type uint16;
        }
        leaf supp-timeout {
          description
            "Timeout for supplicant reply";
          type uint16;
        }
        leaf tx-period {
          description
            "Timeout for supplicant retries";
          type uint16;
        }
      }
    }
  }

  /////////////////////////////////////////////////////////
  // native / dot1x
  /////////////////////////////////////////////////////////
  augment "/ios:native/ios:dot1x" {
    uses config-dot1x-grouping;
  }

  /////////////////////////////////////////////////////////
  // native / fallback
  /////////////////////////////////////////////////////////
  augment "/ios:native/ios:fallback" {
    uses config-fallback-grouping;
  }

  /////////////////////////////////////////////////////////
  // native / interface FastEthernet * dot1x
  /////////////////////////////////////////////////////////
  augment "/ios:native/ios:interface/ios:FastEthernet" {
    uses config-interface-dot1x-grouping {
      if-feature ios-features:dot1x;
    }
  }

  /////////////////////////////////////////////////////////
  // native / interface GigabitEthernet * dot1x
  /////////////////////////////////////////////////////////
  augment "/ios:native/ios:interface/ios:GigabitEthernet" {
    uses config-interface-dot1x-grouping {
      if-feature ios-features:dot1x;
    }
  }

  /////////////////////////////////////////////////////////
  // native / interface TenGigabitEthernet * dot1x
  /////////////////////////////////////////////////////////
  augment "/ios:native/ios:interface/ios:TenGigabitEthernet" {
    uses config-interface-dot1x-grouping {
      if-feature ios-features:dot1x;
    } 
  }

  /////////////////////////////////////////////////////////
  // native / interface Port-channel * dot1x
  /////////////////////////////////////////////////////////
  augment "/ios:native/ios:interface/ios:Port-channel" {
    uses config-interface-dot1x-grouping {
      if-feature ios-features:dot1x;
    }
  }
}
