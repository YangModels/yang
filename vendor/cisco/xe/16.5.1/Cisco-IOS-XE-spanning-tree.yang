module Cisco-IOS-XE-spanning-tree {
  namespace "http://cisco.com/ns/yang/Cisco-IOS-XE-spanning-tree";
  prefix ios-stp;


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Spanning Tree (stp) Yang Model.
     Copyright (c) 2016 by Cisco Systems, Inc.
     All rights reserved."; 

  // =========================================================================
  // REVISION 
  // =========================================================================

  revision 2017-02-07 {
    description
      "Initial revision";
  }

  grouping config-spanning-tree-grouping {
    leaf backbonefast {
      description
        "Enable BackboneFast Feature";
      type empty;
    }
    container bridge {
      leaf priority {
        type uint8;
      }
      leaf ID {
        type string;
      }
    }
    // spanning-tree etherchannel
    container etherchannel {
      description
        "Spanning tree etherchannel specific configuration";
      container guard {
        description
          "Configure guard features for etherchannel";
        leaf misconfig {
          description
            "Enable guard to protect against etherchannel misconfiguration";
          type empty;
        }
      }
    }
    // spanning-tree extend
    container extend {
      description
        "Spanning Tree 802.1t extensions";
      leaf system-id {
        description
          "Extend system-id into priority portion of the bridge id (PVST & Rapid PVST only)";
        type empty;
      }
    }
    //  logging       Enable Spanning tree logging
    leaf logging {
      description
        "Enable Spanning tree logging";
      type empty;
    }
    // spanning-tree loopguard
    container loopguard {
      description
        "Spanning tree loopguard options";
      leaf default {
        description
          "Enable loopguard by default on all ports";
        type empty;
      }
    }
    // spanning-tree mst
    container mst {
      description
        "Multiple spanning tree configuration";
      list instance-range {
        key "id";
        leaf id {
          type union {
            type uint16;
            type string;
          }
        }
        leaf priority {
          description
            "Set the bridge priority for the spanning tree";
          type uint16 {
            range "0..61440";
          }
        }
        leaf root {
          description
            "Configure switch as root";
          type enumeration {
            enum "primary";
            enum "secondary";
          }
        }
      }
      // spanning-tree mst configuration
      container configuration {
        description
          "Enter MST configuration submode";
        leaf name {
          description
            "Set configuration name";
          type string;
        }
        list instance {
          description
            "Map vlans to an MST instance";
          key "id";
          leaf id {
            type uint16 {
              range "0..4094";
            }
          }
          leaf-list vlan {
            description
              "Range of vlans to add to the instance mapping";
            type union {
              type uint16;
              type string;
            }
          }
        }
        //  private-vlan  Set private-vlan synchronization
        container private-vlan {
          description
            "Set private-vlan synchronization";
          leaf synchronize {
            description
              "Synchronize vlans";
            type empty;
          }
        }
        //  revision      Set configuration revision number
        leaf revision {
          description
            "Set configuration revision number";
          type uint16;
        }
      }
      //  forward-time   Set the forward delay for the spanning tree
      leaf forward-time {
        description
          "number of seconds for the forward delay timer";
        type uint8 {
          range "4..30";
        }
      }
      //  hello-time     Set the hello interval for the spanning tree
      leaf hello-time {
        description
          "number of seconds between generation of config BPDUs";
        type uint8 {
          range "1..10";
        }
      }
      //  max-age        Set the max age interval for the spanning tree
      leaf max-age {
        description
          "maximum number of seconds the information in a BPDU is valid";
        type uint8 {
          range "6..40";
        }
      }
      //  max-hops       Set the max hops value for the spanning tree
      leaf max-hops {
        description
          "maximum number of hops a BPDU is valid";
        type uint8 {
          range "1..255";
        }
      }
    }
    // spanning-tree optimize
    container optimize {
      container bpdu {
        leaf transmission {
          type boolean;
        }
      }
    }
    //  pathcost      Spanning tree pathcost options
    container pathcost {
      description
        "Spanning tree pathcost options";
      container method {
        description
          "Method to calculate default port path cost";
        leaf long {
          description
            "Use 32 bit based values for default port path costs";
          type empty;
        }
        leaf short {
          type empty;
        }
      }
    }
    // spanning-tree portfast
    container portfast {
      description
        "Spanning tree portfast options";
      leaf bdpu {
        type enumeration {
          enum "bpdufilter";
          enum "bpduguard";
        }
      }
      leaf default {
        description
          "Enable portfast by default on all access ports";
        type empty;
      }
    }
    //  transmit      STP transmit parameters
    container transmit {
      description
        "STP transmit parameters";
      leaf hold-count {
        description
          "Value for txholdcount parameter";
        type uint8 {
          range "1..20";
        }
      }
    }
    //  uplinkfast    Enable UplinkFast Feature
    //  spanning-tree uplinkfast
    container uplinkfast {
      description
        "Enable UplinkFast Feature";
      presence "true";
      leaf max-update-rate {
        description
          "Rate at which station address updates are sent";
        type uint32 {
          range "0..32000";
        }
      }
    }
    // spanning-tree mode
    leaf mode {
      description
        "Spanning tree operating mode";
      type enumeration {
        enum "mst";
        enum "pvst";
        enum "rapid-pvst";
      }
    }
    //  vlan          VLAN Switch Spanning Tree
    // spanning-tree vlans-max-age
    list vlan {
      description
        "VLAN Switch Spanning Tree";
      key "id";
      leaf id {
        type string;
      }
      leaf max-age {
        description
          "Set the max age interval for the spanning tree";
        type uint8 {
          range "6..40";
        }
      }
      leaf forward-time {
        description
          "Set the forward delay for the spanning tree";
        type uint8 {
          range "4..30";
        }
      }
      leaf hello-time {
        description
          "Set the hello interval for the spanning tree";
        type uint8 {
          range "1..10";
        }
      }
      leaf priority {
        description
          "Set the bridge priority for the spanning tree";
        type uint16 {
          range "0..61440";
        }
      }
      container root {
        description
          "Configure switch as root";
        container primary {
          description
            "Configure this switch as primary root for this spanning tree";
          leaf diameter {
            description
              "Network diameter of this spanning tree";
            type uint8 {
              range "2..7";
            }
          }
          leaf hello-time {
            description
              "Hello interval for this spanning tree";
            type uint8 {
              range "1..10";
            }
          }
        }
        container secondary {
          description
            "Configure switch as secondary root";
          leaf diameter {
            description
              "Network diameter of this spanning tree";
            type uint8 {
              range "2..7";
            }
          }
          leaf hello-time {
            description
              "Hello interval for this spanning tree";
            type uint8 {
              range "1..10";
            }
          }
        }
      }
    }
  }

  grouping config-interface-spanning-tree {
    container spanning-tree {
      description
        "Spanning Tree Subsystem";
      leaf bpdufilter {
        description
          "Don't send or receive BPDUs on this interface";
        type enumeration {
          enum "disable";
          enum "enable";
        }
      }
      // interface * / spanning-tree bpduguard
      container bpduguard {
        description
          "Don't accept BPDUs on this interface";
        choice bpduguard-choice {
          leaf disable {
            description
              "Disable BPDU guard for this interface";
            type empty;
          }
          leaf enable {
            type empty;
            description
              "Enable BPDU guard for this interface";
          }
        }
      }
      // interface * / spanning-tree cost
      leaf cost {
        description
          "To set the path cost of the interface";
        type uint32 {
          range "1..200000000";
        }
      }
      // interface * / spanning-tree guard
      leaf guard {
        description
          "Change an interface's spanning tree guard mode";
        type enumeration {
          enum "loop";
          enum "none";
          enum "root";
        }
      }
      // interface * / spanning-tree link-type
      leaf link-type {
        description
          "Specify a link type for spanning tree tree protocol use";
        type enumeration {
          enum "auto" {
          }
          enum "none";
          enum "point-to-point";
          enum "root";
          enum "shared";
        }
      }
      // interface * / spanning-tree portfast
      container portfast {
        description
          "Spanning tree portfast options";
        presence "true";
        leaf disable {
          description
            "Disable portfast for this interface";
          type empty;
        }
        leaf trunk {
          description
            "Enable portfast on the interface even in trunk mode";
          type empty;
        }
        leaf edge {
          description
            "Enable portfast edge on the interface";
          type empty;
        }
      }
      // interface * / spanning-tree port-priority
      leaf port-priority {
        description
          "Spanning tree port-priority options";
        type uint8 {
          range "0..240";
        }
      }
      // interface * / spanning-tree vlan
      container vlan {
        description
          "VLAN Switch Spanning Tree";
        leaf-list vlan-ids {
          description
            "vlan range, example: 1,3-5,7,9-11";
          type union {
            type uint16 {
              range "1..4095";
            }
            type string;
          }
        }
        leaf cost {
          description
            "<1-200000000> Spanning-tree cost";
          type uint32 {
            range "1..200000000";
          }
        }
        leaf port-priority {
          description
            "<0-240> port priority in increments of 16";
          type uint16 {
            range "0..240";
          }
        }
      }
      // interface * / spanning-tree loopguard default
      container loopguard {
        description
          "Spanning tree loopguard options";
        leaf default {
          description
            "Enable loopguard by default on all ports";
          type empty;
        }
      }
      // interface * /spanning-tree mst
      container mst {
        description
          "Per interface MST configurations";
        leaf instance {
          description
            "MST instance list, example 0,2-4,6,8-12";
          type string;
        }
        leaf cost {
          description
            "<1-200000000> Spanning-tree cost";
          type uint32 {
            range "1..200000000";
          }
        }
        leaf port-priority {
          description
            "<0-240> port priority in increments of 16";
          type uint16 {
            range "0..240";
          }
        }
        leaf pre-standard {
          description
            "Force pre-standard MST BPDU transmission on port";
          type empty;
        }
      }
    }
  }

  /////////////////////////////////////////////////////////
  // native / spanning-tree
  /////////////////////////////////////////////////////////
  augment "/ios:native/ios:spanning-tree" {
    uses config-spanning-tree-grouping;
  }

  /////////////////////////////////////////////////////////
  // native / interface FastEthernet * spanning-tree
  /////////////////////////////////////////////////////////
  augment "/ios:native/ios:interface/ios:FastEthernet" {
    uses config-interface-spanning-tree;
  }

  /////////////////////////////////////////////////////////
  // native / interface GigabitEthernet * spanning-tree
  /////////////////////////////////////////////////////////
  augment "/ios:native/ios:interface/ios:GigabitEthernet" {
    uses config-interface-spanning-tree;
  }

  /////////////////////////////////////////////////////////
  // native / interface TenGigabitEthernet * spanning-tree
  /////////////////////////////////////////////////////////
  augment "/ios:native/ios:interface/ios:TenGigabitEthernet" {
    uses config-interface-spanning-tree;
  }

  /////////////////////////////////////////////////////////
  // native / interface Port-channel * spanning-tree
  /////////////////////////////////////////////////////////
  augment "/ios:native/ios:interface/ios:Port-channel" {
    uses config-interface-spanning-tree;
  }
}
