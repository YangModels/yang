module Cisco-IOS-XE-ap {
  namespace "http://cisco.com/ns/yang/Cisco-IOS-XE-ap";
  prefix ios-ap;


  import ietf-inet-types {
      prefix inet;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Access Point (AP) Group Yang model.
     Copyright (c) 2016 by Cisco Systems, Inc.
     All rights reserved."; 

  // =========================================================================
  // REVISION 
  // =========================================================================

  revision 2017-02-07 {
    description
      "Initial revision";
  }

  

  grouping ap-port-grouping {
    leaf poe {
      description
        "Enable/Disable LAN PoE";
      type empty;
    }
    leaf remote-lan {
      description
        "Enter Remote-LAN Name";
      type string;
    }
    leaf shutdown {
      description
        "Enable/Disable port";
      type empty;
    }
  }

  grouping ap-wlan-grouping {
    container airtime-fairness {
      description
        "Configure airtime-fairness to the current AP group";
      container dot11 {
        description
          "Configures airtime-fairness parameters for the AP group";
        container _24GHz {
          description
            "Configures 2.4 GHz airtime-fairness policy";
          leaf policy {
            description
              "Specify name of the airtime-fairness policy to assign";
            type string;
          }
        }
        container _5GHz {
          description
            "Configures 5 GHz airtime-fairness policy";
          leaf policy {
            description
              "Specify name of the airtime-fairness policy to assign";
            type string;
          }
        }
      }
    }
    leaf radio-policy {
      description
        "Configures Radio Policy on given AP-Group";
      type enumeration {
        enum "all";
        enum "dot11a";
        enum "dot11bg";
        enum "dot11g";
      }
    }
    leaf vlan {
      description
        "Specify the vlan name or vlan id";
      type string;
    }
  }

  grouping config-ap-grouping {
    container ap {
      description
        "Configures Cisco APs";
      list group {
        description
          "Manage AP Groups VLAN feature";
        key "name";
        leaf name {
          type string;
        }
        container config {
          container airtime-fairness {
            description
              "airtime-fairness for this AP group";
            container dot11 {
              description
                "Configures airtime-fairness parameters for the AP group";
              container _24GHz {
                description
                  "Configures 2.4 GHz airtime-fairness policy";
                leaf mode {
                  description
                    "Configure airtime-fairness in enforce mode";
                  type enumeration {
                    enum "enforce-policy";
                    enum "monitor";
                  }
                }
                leaf optimization {
                  description
                    "Enable airtime-fairness optimization";
                  type empty;
                }
              }
              container _5GHz {
                description
                  "Configures 5 GHz airtime-fairness policy";
                container mode {
                  description
                    "Configure airtime-fairness in enforce mode";
                  leaf enforce-policy {
                    description
                      "airtime-fairness in enforce policy mode";
                    type empty;
                  }
                  leaf monitor {
                    description
                      "Configure airtime-fairness in monitor mode";
                    type empty;
                  }
                }
                leaf optimization {
                  description
                    "Enable airtime-fairness optimization";
                  type empty;
                }
              }
            }
          }
          leaf description {
            description
              "Enter description";
            type string;
          }
          container hyperlocation {
            description
              "Configures Hyperlocation feature on all supported APs";
            presence true;
            container threshold {
              description
                "Sets Hyperlocation thresholds";
              leaf detection {
                description
                  "RSSI threshold to filter out packets with low RSSI";
                type int8 {
                  range "-100..-50";
                }
              }
              leaf reset {
                description
                  "Enter a value smaller than trigger threshold";
                type uint8 {
                  range "0..99";
                }
              }
              leaf trigger {
                description
                  "Enter number of scan cycles";
                type uint8 {
                  range "1..100";
                }
              }
            }
          }
          container ntp {
            description
              "Sets the NTP server IP address";
            leaf ip {
              description
                "NTP server IPv4 address";
              type inet:ipv4-address;
           }
          }
          list port {
            description
              "Configure LAN port parameters of an AP group";
            key "id";
            leaf id {
              description
                "Enter port ID for LAN";
              type uint8 {
                range "1..3";
              }
            }
            uses ap-port-grouping;
          }
          leaf remote-lan {
            description
              "Enter Remote-LAN name";
            type string;
          }
          container rf-profile {
            description
              "Assign the RF Profile to the current AP Group";
            container dot11 {
              description
                "Configures 802.11 parameters";
              leaf _24ghz {
                description
                  "Specify the name of the RF Profile to assign";
                type string;
              }
              leaf _5ghz {
                description
                  "Specify the name of the RF Profile to assign";
                type string;
              }
            }
          }
          list wlan {
            description
              "Add WLAN to ap group";
            key "name";
            leaf name {
              description
                "Enter WLAN name";
              type string;
            }
            uses ap-wlan-grouping;
          }
        }
      }
      //// ap dot11
      container dot11 {
        description
          "Configures 802.11 parameters";
        container _24ghz {
          description
            "Configures 802.11b parameters.";
          container rate {
            description
              "Configure 802.11b operational rates";
            container RATE_11M {
              description
                "802.11 12M Rate";
              leaf supported {
                description
                  "set a rate to supported";
                type empty;
              }
            }
            container RATE_12M {
              description
                "802.11 12M Rate";
              leaf supported {
                description
                  "set a rate to supported";
                type empty;
              }
            }
            container RATE_18M {
              description
                "802.11 18M Rate";
              leaf supported {
                description
                  "set a rate to supported";
                type empty;
              }
            }
            container RATE_1M {
              description
                "802.11 12M Rate";
              leaf supported {
                description
                  "set a rate to supported";
                type empty;
              }
            }
            container RATE_24M {
              description
                "802.11 24M Rate";
              leaf supported {
                description
                  "set a rate to supported";
                type empty;
              }
            }
            container RATE_2M {
              description
                "802.11 24M Rate";
              leaf supported {
                description
                  "set a rate to supported";
                type empty;
              }
            }
            container RATE_36M {
              description
                "802.11 36M Rate";
              leaf supported {
                description
                  "set a rate to supported";
                type empty;
              }
            }
            container RATE_48M {
              description
                "802.11 48M Rate";
              leaf supported {
                description
                  "set a rate to supported";
                type empty;
              }
            }
            container RATE_54M {
              description
                "802.11 54M Rate";
              leaf supported {
                description
                  "set a rate to supported";
                type empty;
              }
            }
            container RATE_5_5M {
              description
                "802.11 5.5M Rate";
              leaf supported {
                description
                  "set a rate to supported";
                type empty;
              }
            }
            container RATE_6M {
              description
                "802.11 6M Rate";
              leaf supported {
                description
                  "set a rate to supported";
                type empty;
              }
            }
            container RATE_9M {
              description
                "802.11 9M Rate";
              leaf supported {
                description
                  "set a rate to supported";
                type empty;
              }
            }
          }// rate
        } //c 24ghz
        container _49ghz {
              description
           "Configures 802.11a parameters.";
          container rrm {
           description
            "Radio Resource Management";
            container profile {
              description
                "802.11a performance profile";
              leaf foreign {
                description
                  "802.11a foreign interference threshold (0-100)";
                type uint8 {
                  range "0..100";
                }
              }// foreign
            }// profile
          }// c rrm
        }// c 49ghz
        container _5ghz {
          description
            "Configures 802.11a parameters.";
          container rate {
            description
              "Configure 802.11b operational rates";
            container RATE_11M {
              description
                "802.11 12M Rate";
              leaf supported {
                description
                  "set a rate to supported";
                type empty;
              }
            }
            container RATE_12M {
              description
                "802.11 12M Rate";
              leaf supported {
                description
                  "set a rate to supported";
                type empty;
              }
            }
            container RATE_18M {
              description
                "802.11 18M Rate";
              leaf supported {
                description
                  "set a rate to supported";
                type empty;
              }
            }
            container RATE_1M {
              description
                "802.11 12M Rate";
              leaf supported {
                description
                  "set a rate to supported";
                type empty;
              }
            }
            container RATE_24M {
              description
                "802.11 24M Rate";
              leaf supported {
                description
                  "set a rate to supported";
                type empty;
              }
            }
            container RATE_2M {
              description
                "802.11 24M Rate";
              leaf supported {
                description
                  "set a rate to supported";
                type empty;
              }
            }
            container RATE_36M {
              description
                "802.11 36M Rate";
              leaf supported {
                description
                  "set a rate to supported";
                type empty;
              }
            }
            container RATE_48M {
              description
                "802.11 48M Rate";
              leaf supported {
                description
                  "set a rate to supported";
                type empty;
              }
            }
            container RATE_54M {
              description
                "802.11 54M Rate";
              leaf supported {
                description
                  "set a rate to supported";
                type empty;
              }
            }
            container RATE_5_5M {
              description
                "802.11 5.5M Rate";
              leaf supported {
                description
                  "set a rate to supported";
                  type empty;
                }
            }
            container RATE_6M {
              description
                "802.11 6M Rate";
              leaf supported {
                description
                  "set a rate to supported";
                type empty;
              }
            }
            container RATE_9M {
              description
                "802.11 9M Rate";
              leaf supported {
                description
                  "set a rate to supported";
                type empty;
              }
            }
          } // rate
        } // c 5ghz
        container airtime-fairness {
          description
            "Configures airtime-fairness policy";
          list policy-name {
            description
              "Configure airtime-fairness policy";
            key "policy-name";
            leaf policy-name {
              description
                "Enter the airtime-fairness policy name";
              type string;
            }
            leaf policy-id {
              type uint16 {
                range "0..511";
              }
            }
          } // list policy-name
        } // airtime-fairnes
      } // ap dot11
    }
  }

  /////////////////////////////////////////////////////////
  // native
  /////////////////////////////////////////////////////////
  augment "/ios:native" {
    uses config-ap-grouping;
  } //augment
} //module
