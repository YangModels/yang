module Cisco-IOS-XE-vtp {
  namespace "http://cisco.com/ns/yang/Cisco-IOS-XE-vtp";
  prefix ios-vtp;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native VLAN Trunk Protocol (VTP) Yang model.
     Copyright (c) 2016 by Cisco Systems, Inc.
     All rights reserved."; 

  // =========================================================================
  // REVISION 
  // =========================================================================

  revision 2017-02-07 {
    description
      "Initial revision";
  }

  grouping device-modes {
    leaf mst {
      description "Set the mode for MST VTP instance";
      type empty;
    }
    leaf unknown {
      description "Set the mode for unknown VTP instances";
      type empty;
    }
    leaf vlan {
      description "Set the mode for VLAN VTP instance";
      type empty;
    }
  }

  grouping config-vtp-grouping {
    // vtp file
    leaf file {
      description
        "Configure IFS filesystem file where VTP configuration is stored.";
      type string;
    }

    // vtp interface
    container interface {
      description
        "Configure Interface as the preferred source for the VTP IP updater address";
      leaf interface-name {
        description
          "The name of the interface providing the VTP updater ID for this device";
        type string;
      }
      leaf only {
        description
          "Use only this interface's IP address as the VTP IP updater address";
        type empty;
      }
    }

    //vtp password
    container password {
      description
        "Set the password for the VTP administrative domain";
      leaf password {
        description
          "The ascii password for the VTP administrative domain";
        type string;
      }
      leaf hidden {
        description
          "Set the VTP password hidden option";
        type empty;
      }
      leaf secret {
        description
          "Specify the vtp password in encrypted form";
        type empty;
      }
    }
    // vtp pruning
    leaf pruning {
      description
        "Set the adminstrative domain to permit pruning";
      type empty;
    }
    // vtp version
    leaf version {
      description
        "Set the adminstrative domain to VTP version";
      type uint8 {
        range "1..3";
      }
    }
    // vtp domain
    leaf domain {
      description
        "Set the name of the VTP administrative domain.";
      type string;
    }
    //vtp mode
    container mode {
      description "Configure VTP device mode";
      container client {
        description 
          "Set the device to client mode";
        presence true;
        uses device-modes;
      }
      container off {
        description 
          "Set the device to off mode";
        presence true;
        uses device-modes;
      }
      container server {
        description 
          "Set the device to server mode";
        presence true;
        uses device-modes;
      }
      container transparent {
        description 
          "Set the device to transparent mode";
        presence true;
        uses device-modes;
      }
    }
  }

  /////////////////////////////////////////////////////////
  // native / vtp
  /////////////////////////////////////////////////////////
  augment "/ios:native/ios:vtp" {
    uses config-vtp-grouping;
  } 
}
