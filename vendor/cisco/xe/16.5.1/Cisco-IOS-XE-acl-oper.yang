module Cisco-IOS-XE-acl-oper {
    yang-version 1;
    namespace "http://cisco.com/ns/yang/Cisco-IOS-XE-acl-oper";
    prefix acl-ios-xe-oper;

    import ietf-yang-types {
        prefix yang;
    }

    organization
        "Cisco Systems, Inc.";

    contact
        "Cisco Systems, Inc. Customer Service Postal: 170 W Tasman Drive
        San Jose, CA 95134 Tel: +1 1800 553-NETS E-mail: cs-yang@cisco.com";

    description
        "This module contains a collection of YANG definitions for ACL statistical data."+
        "Copyright (c) 2016-2017 by Cisco Systems, Inc."+
        "All rights reserved."; 

  // =========================================================================
  // REVISION 
  // =========================================================================

  revision 2017-02-07 {
    description
      "Initial revision";
  }

    grouping ace-oper-data {
        description "ACE oper data";

        leaf match-counter {
            type yang:counter64;
            description "Number of matches for an access list entry";
        }
    }

    grouping access-list-entry {
        description "Entry representing ACE list entry";
        leaf rule-name {
            type uint32;
            description "Entry number.";
        }

        container access-list-entries-oper-data {
            description "Per access list entries operational data";
            uses acl-ios-xe-oper:ace-oper-data;
       }
    }

    grouping access-list {
        description "A list of access-list-entry(ACE)";

        leaf access-control-list-name {
            type string;
            description "The name of access-list. A device MAY restrict the length
            and value of this name, possibly space and special characters are not
            allowed";
        }
        container access-list-entries {
            description "A list of access-list-entry(ACE)";

            list access-list-entry {
                key "rule-name";
 
                description "List of access list entries(ACE)";
                uses acl-ios-xe-oper:access-list-entry;
            }
        }
    }

    container access-lists {
        config false;
        description
            "This is top level container for Access Control Lists. It can have one
            or more Access Control List.";

        list access-list {
            key "access-control-list-name";
            description "An access list (acl) is an ordered list of
                access list entries (ACE). Each access control entries has a
                list of match criteria, and a list of actions.
                Since there are several kinds of access control lists
                implemented with different attributes for
                each and different for each vendor, this
                model accommodates customizing access control lists for
                each kind and for each vendor.";

            uses acl-ios-xe-oper:access-list;
        }
    }
}
