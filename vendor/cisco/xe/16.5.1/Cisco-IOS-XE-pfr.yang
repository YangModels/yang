module Cisco-IOS-XE-pfr {
  namespace "http://cisco.com/ns/yang/Cisco-IOS-XE-pfr";
  prefix ios-pfr;

  import ietf-inet-types {
    prefix inet;
  }


  import Cisco-IOS-XE-native {
    prefix ios;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Performance Routing (PfR) Yang Model.
     Copyright (c) 2016 by Cisco Systems, Inc.
     All rights reserved."; 

  // =========================================================================
  // REVISION 
  // =========================================================================

  revision 2017-02-07 {
    description
      "Initial revision";
  }

  grouping config-pfr-grouping {
    container border {
      description
        "Enter PfR border router configuration submode";
      presence "true";
      container pfr-Mode__config-pfr-br {
        container active-probe {
          description
            "Specify active probe parameters";
          container address {
            description
              "Identify probe address parameters";
            container source {
              description
                "Identify probe source address";
              container interface {
                description
                  "Identify probe source address from interface";
                uses ios-ifc:interface-grouping;
              }
            }
          }
        }
        container local {
          description
            "Specify the local interface for PfR connection";
          container interface {
            uses ios-ifc:interface-grouping;
          }
        }
        leaf logging {
          description
            "Event logging";
          type empty;
        }
        container master {
          description
            "Specify the PfR master controller IP address";
          list ipv4 {
            key "ipv4";
            leaf ipv4 {
              description
                "IP address";
              type inet:ipv4-address;
            }
            leaf key-chain {
              description
                "name of key-chain";
              type string;
            }
          }
        }
        leaf port {
          description
            "Specify PfR port number";
          type uint16 {
            range "1..65535";
          }
        }
        leaf shutdown {
          description
            "Disable PfR border router functionality";
          type empty;
        }
      }
    }
    container master {
      description
        "Enter PfR master controller configuration submode";
      presence "true";
      container icmp-Mode-config-pfr-mc {
        container active-probe {
          description
            "Manually create an active probe for a known target";
          leaf echo {
            description
              "IP address of probe target";
            type inet:host;
          }
          container jitter {
            description
              "Perform jitter probe operations (requires a responder)";
            list ipv4-or-hostname {
              key "ipv4-or-hostname";
              leaf ipv4-or-hostname {
                description
                  "IP address of probe target";
                type inet:host;
              }
              leaf target-port {
                description
                  "Target Port Number";
                type uint16 {
                  range "1..65535";
                }
              }
            }
          }
          container tcp-conn {
            description
              "Perform TCP Connection / Disconnect probe operations";
            list ipv4-or-hostname {
              key "ipv4-or-hostname";
              leaf ipv4-or-hostname {
                description
                  "IP address of probe target";
                type inet:host;
              }
              leaf target-port {
                description
                  "Target Port Number";
                type uint16 {
                  range "1..65535";
                }
              }
            }
          }
          container udp-echo {
            description
              "Perform UDP Echo probe operations (requires a responder)";
            list ipv4-or-hostname {
              key "ipv4-or-hostname";
              leaf ipv4-or-hostname {
                description
                  "IP address of probe target";
                type inet:host;
              }
              leaf target-port {
                description
                  "Target Port Number";
                type uint16 {
                  range "1..65535";
                }
              }
            }
          }
        }
        container application {
          description
            "Define application";
          container define {
            description
              "Define application";
            list app-def {
              key "app-def";
              leaf app-def {
                description
                  "Application definition name";
                type string;
              }
              leaf access-list {
                description
                  "Application definition access-list name";
                type string;
              }
              leaf nbar {
                description
                  "Define nbar application";
                type empty;
              }
            }
          }
        }
        container backoff {
          description
            "Specify backoff timer parameters";
          list boff {
            key "boff";
            leaf boff {
              description
                "Specify minimum value of backoff timer (secs)";
              type uint16 {
                range "90..7200";
              }
            }
            list boff0 {
              key "boff0";
              leaf boff0 {
                description
                  "Specify maximum value of backoff timer (secs)";
                type uint16 {
                  range "90..7200";
                }
              }
              leaf bstep {
                description
                  "Specify optional backoff timer step (secs)";
                type uint16 {
                  range "90..7110";
                }
              }
            }
          }
        }
        leaf bandwidth-resolution {
          description
            "Enable/configure Bandwidth Resolution";
          type empty;
        }
        container border {
          description
            "Enter PfR managed border router configuration submode";
          list ipv4 {
            key "ipv4";
            leaf ipv4 {
              description
                "IP address of border router";
              type inet:ipv4-address;
            }
            list key-chain {
              description
                "Specify a key-chain";
              key "kc-name";
              leaf kc-name {
                description
                  "name of key-chain";
                type string;
              }
              leaf interface {
                description
                  "Specify an PfR managed border router interface";
                type empty;
              }
            }
            leaf interface {
              description
                "Specify an PfR managed border router interface";
              type empty;
            }
          }
        }
        container delay {
          description
            "Specify delay parameters";
          leaf relative {
            description
              "short/long term in percentage. e.g. 125 is short/long = 1.25";
            type uint16 {
              range "1..1000";
            }
          }
          leaf threshold {
            description
              "Maximum absolute delay threshold (msecs)";
            type uint16 {
              range "1..10000";
            }
          }
        }
        leaf exporter {
          description
            "name of flow exporter";
          type string;
        }
        leaf holddown {
          description
            "Specify hold-down timer parameter (secs)";
          type uint16 {
            range "90..65535";
          }
        }
        container jitter {
          description
            "Specify jitter parameters";
          leaf threshold {
            description
              "Maximum absolute jitter threshold (ms)";
            type uint16 {
              range "1..1000";
            }
          }
        }
        leaf keepalive {
          description
            "Specify keepalive interval in seconds";
          type uint16 {
            range "0..1000";
          }
        }
        container learn {
          description
            "Enter prefix and traffic class learning submode";
          presence "true";
          container lrn-Mode__config-pfr-mc-learn {
            container aggregation-type {
              description
                "Type of prefix to aggregate";
              leaf bgp {
                description
                  "Aggregate prefixes learned via BGP";
                type empty;
              }
              leaf non-bgp {
                description
                  "Aggregate prefixes not learned via BGP";
                type empty;
              }
              leaf prefix-length {
                description
                  "Specify the prefix mask";
                type uint8 {
                  range "1..32";
                }
              }
            }
            leaf delay {
              description
                "Learn top prefixes based on delay";
              type empty;
            }
            container expire {
              description
                "Set expiry criteria for learn prefixes";
              container after {
                description
                  "Specify expiry criteria for learn prefixes";
                leaf session {
                  description
                    "Specify the value";
                  type uint16 {
                    range "1..65535";
                  }
                }
                leaf time {
                  description
                    "Specify the value";
                  type uint16 {
                    range "1..65535";
                  }
                }
              }
            }
            container inside {
              description
                "Learn prefixes inside the network";
              leaf bgp {
                description
                  "Learn inside prefixes advertised by BGP out PfR External Interfaces";
                type empty;
              }
            }
            container list {
              description
                "Create PfR Learn Traffic Class List and enter the sub-mode";
              container seq {
                description
                  "PfR Learn Traffic Class List sequence number";
                list pfr-tc {
                  key "pfr-tc";
                  leaf pfr-tc {
                    description
                      "PfR Learn Traffic Class List sequence number";
                    type uint16 {
                      range "1..65535";
                    }
                  }
                  leaf refname {
                    description
                      "PfR Learn Traffic Class List reference name";
                    type empty;
                  }
                }
              }
            }
            leaf monitor-period {
              description
                "Specify the period in minutes";
              type uint16 {
                range "1..1440";
              }
            }
            leaf periodic-interval {
              description
                "Specify the interval in minutes";
              type uint16 {
                range "0..10080";
              }
            }
            container prefixes {
              description
                "Number of prefixes to learn";
              list prnum {
                key "prnum";
                leaf prnum {
                  description
                    "Specify the number of prefixes";
                  type uint32 {
                    range "0..100000";
                  }
                }
                leaf applications {
                  description
                    "Specify the number of appl";
                  type uint16 {
                    range "0..50000";
                  }
                }
              }
            }
            leaf throughput {
              description
                "Learn top prefixes based on throughput";
              type empty;
            }
            container traffic-class {
              description
                "Set traffic class filters";
              container aggregate {
                description
                  "Traffic class aggregation specification";
                leaf access-list {
                  description
                    "IP access-list name";
                  type string;
                }
              }
              container filter {
                description
                  "Traffic class filter specification";
                leaf access-list {
                  description
                    "IP access-list name";
                  type string;
                }
              }
              container keys {
                description
                  "Specify Learn keys for applications";
                container dport {
                  description
                    "Learn top appls based on destination port";
                  presence "true";
                  leaf dscp {
                    description
                      "Learn top appls based on DSCP";
                    type empty;
                  }
                  leaf protocol {
                    description
                      "Learn top appls based on protocol";
                    type empty;
                  }
                  leaf sport {
                    description
                      "Learn top appls based on source port";
                    type empty;
                  }
                }
                container dscp {
                  description
                    "Learn top appls based on DSCP";
                  presence "true";
                  leaf dport {
                    description
                      "Learn top appls based on destination port";
                    type empty;
                  }
                  leaf protocol {
                    description
                      "Learn top appls based on protocol";
                    type empty;
                  }
                  leaf sport {
                    description
                      "Learn top appls based on source port";
                    type empty;
                  }
                }
                container protocol {
                  description
                    "Learn top appls based on protocol";
                  presence "true";
                  leaf dport {
                    description
                      "Learn top appls based on destination port";
                    type empty;
                  }
                  leaf dscp {
                    description
                      "Learn top appls based on DSCP";
                    type empty;
                  }
                  container sport {
                    description
                      "Learn top appls based on source port";
                    presence "true";
                    leaf dport {
                      description
                        "Learn top appls based on destination port";
                      type empty;
                    }
                    leaf dscp {
                      description
                        "Learn top appls based on DSCP";
                      type empty;
                    }
                  }
                }
                container sport {
                  description
                    "Learn top appls based on source port";
                  presence "true";
                  leaf dport {
                    description
                      "Learn top appls based on destination port";
                    type empty;
                  }
                  leaf dscp {
                    description
                      "Learn top appls based on DSCP";
                    type empty;
                  }
                  leaf protocol {
                    description
                      "Learn top appls based on protocol";
                    type empty;
                  }
                }
              }
            }
          }
        }
        leaf logging {
          description
            "Event Logging";
          type empty;
        }
        container loss {
          description
            "Specify loss parameters";
          leaf relative {
            description
              "short/long term in percentage. e.g. 125 is short/long = 1.25";
            type uint16 {
              range "1..1000";
            }
          }
          leaf threshold {
            description
              "Maximum absolute lost packet threshold in percentage e.g., 1 is 0.0001 percent";
            type uint32 {
              range "1..1000000";
            }
          }
        }
        container max {
          description
            "Specify the upper limit";
          container prefix {
            description
              "Specify prefix upper limit";
            container total {
              description
                "Specify max total prefix limit";
              list maxpr {
                key "maxpr";
                leaf maxpr {
                  description
                    "Specify the max total prefix limit value";
                  type uint32 {
                    range "1..100000";
                  }
                }
                leaf learn {
                  description
                    "Specify max learn prefix limit value";
                  type uint32 {
                    range "0..100000";
                  }
                }
              }
            }
          }
          container range {
            description
              "Specify range value";
            container receive {
              description
                "Specify receive range";
              leaf percent {
                description
                  "Specify the percentage range";
                type uint8 {
                  range "0..100";
                }
              }
            }
          }
        }
        container max-range-utilization {
          description
            "Configure the maximum range for utilization of all exits";
          leaf percent {
            description
              "Specify the percentage range";
            type uint8 {
              range "1..100";
            }
          }
        }
        container mc-peer {
          description
            "Enable MC-to-MC peering";
          presence "true";
          list ipv4 {
            key "ipv4";
            leaf ipv4 {
              description
                "IP address of head-end MC peer";
              type inet:ipv4-address;
            }
            list interface {
              key "interface";
              leaf interface {
                description
                  "Loopback interface";
                type string;
              }
              leaf description {
                description
                  "MC site description (max 40 char)";
                type string;
              }
              leaf domain {
                description
                  "Domain value";
                type uint16 {
                  range "1..65535";
                }
              }
            }
          }
          leaf description {
            description
              "MC site description (max 40 char)";
            type string;
          }
          container domain {
            description
              "SAF domain ID to be used for MC-to-MC peering";
            list dmval {
              key "dmval";
              leaf dmval {
                description
                  "Domain value";
                type uint16 {
                  range "1..65535";
                }
              }
              list ipv4 {
                key "ipv4";
                leaf ipv4 {
                  description
                    "IP address of head-end MC peer";
                  type inet:ipv4-address;
                }
                leaf interface {
                  description
                    "Loopback interface";
                  type string;
                }
              }
              leaf description {
                description
                  "MC site description (max 40 char)";
                type string;
              }
              leaf eigrp {
                description
                  "Loopback interface";
                type string;
              }
              leaf head-end {
                description
                  "Loopback interface";
                type string;
              }
            }
          }
          container eigrp {
            description
              "Use explicit EIGRP configuration instead of auto-config";
            list interface {
              key "interface";
              leaf interface {
                description
                  "Loopback interface";
                type string;
              }
              leaf description {
                description
                  "MC site description (max 40 char)";
                type string;
              }
              leaf domain {
                description
                  "Domain value";
                type uint16 {
                  range "1..65535";
                }
              }
            }
          }
          container head-end {
            description
              "Specify this router as head-end MC-peer";
            list interface {
              key "interface";
              leaf interface {
                description
                  "Loopback interface";
                type string;
              }
              leaf description {
                description
                  "MC site description (max 40 char)";
                type string;
              }
              leaf domain {
                description
                  "Domain value";
                type uint16 {
                  range "1..65535";
                }
              }
            }
          }
        }
        container mode {
          description
            "Specify PfR operating mode settings";
          container monitor {
            description
              "Specify PfR prefix monitoring policy settings";
            container active {
              description
                "Enable active monitoring mode";
              presence "true";
              leaf throughput {
                description
                  "Enable active monitoring with throughput from passive mode";
                type empty;
              }
            }
            leaf both {
              description
                "Enable active and passive monitoring modes";
              type empty;
            }
            leaf fast {
              description
                "Enable fast monitoring mode";
              type empty;
            }
            leaf passive {
              description
                "Enable passive monitoring mode";
              type empty;
            }
          }
          container route {
            description
              "Specify PfR route control policy settings";
            leaf control {
              description
                "Enable PfR to control routes automatically";
              type empty;
            }
            container metric {
              description
                "Specify PfR route protocol related settings";
              container bgp {
                description
                  "Specify PfR bgp protocol settings";
                leaf local-pref {
                  description
                    "Specify the local preference for bgp controlled routes";
                  type uint16 {
                    range "1..65535";
                  }
                }
              }
              container eigrp {
                description
                  "Specify PfR eigrp routes related settings";
                leaf tag {
                  description
                    "Specify a tag value for PfR controlled eigrp routes";
                  type uint16 {
                    range "1..65535";
                  }
                }
              }
              container static {
                description
                  "Specify PfR static routes related settings";
                leaf tag {
                  description
                    "Specify a tag value for PfR controlled static routes";
                  type uint16 {
                    range "1..65535";
                  }
                }
              }
            }
            leaf observe {
              description
                "PfR offers route control advice, but does not take any action";
              type empty;
            }
            container protocol {
              description
                "Specify OER route control protocol";
              leaf pbr {
                description
                  "Specify OER route control protocol Policy-Based-Routing";
                type empty;
              }
            }
          }
          container verify {
            description
              "Specify verification behavior";
            leaf bidirectional {
              description
                "Verify bidirectional traffic of applications";
              type empty;
            }
          }
        }
        container mos {
          description
            "Specify mos parameters";
          container threshold {
            description
              "Minimum MOS threshold";
            list mos-thresh {
              key "mos-thresh";
              leaf mos-thresh {
                description
                  "Minimum absolute MOS threshold 1.00 - 5.00";
                type string;
              }
              leaf percent {
                description
                  "Maximum percentage probe with MOS below threshold";
                type uint8 {
                  range "1..100";
                }
              }
            }
          }
        }
        leaf periodic {
          description
            "Specify periodic rotation timer value (secs)";
          type uint16 {
            range "90..7200";
          }
        }
        leaf policy-rules {
          description
            "pfr-map name";
          type string;
        }
        leaf port {
          description
            "Specify tcp port number for PfR communication";
          type uint16 {
            range "1..65535";
          }
        }
        container probe {
          description
            "Specify number of packets for jitter probe";
          leaf packets {
            description
              "probe packets <number>";
            type uint8 {
              range "1..255";
            }
          }
        }
        container resolve {
          description
            "Specify PfR policy resolver settings";
          leaf cost {
            description
              "Specify PfR cost policy resolver settings";
            type empty;
          }
          container delay {
            description
              "Specify PfR delay policy resolver settings";
            container priority {
              description
                "Specify the order in which resolver will consider this policy";
              list del-pol {
                key "del-pol";
                leaf del-pol {
                  description
                    "Specify this policy's priority; 1 being highest";
                  type uint8 {
                    range "1..9";
                  }
                }
                leaf variance {
                  description
                    "Specify range; e.g. 25 means all exits measuring up to 25% worse than the best exit are considered equivalent";
                  type uint8 {
                    range "1..100";
                  }
                }
              }
            }
          }
          leaf equivalent-path-round-robin {
            description
              "Specify equivalent-path round-robin resolver";
            type empty;
          }
          container jitter {
            description
              "Specify PfR jitter policy resolver settings";
            container priority {
              description
                "Specify the order in which resolver will consider this policy";
              list jit-pol {
                key "jit-pol";
                leaf jit-pol {
                  description
                    "Specify this policy's priority; 1 being highest";
                  type uint8 {
                    range "1..9";
                  }
                }
                leaf variance {
                  description
                    "Specify range; e.g. 25 means all exits measuring up to 25% worse than the best exit are considered equivalent";
                  type uint8 {
                    range "1..100";
                  }
                }
              }
            }
          }
          container loss {
            description
              "Specify PfR loss policy resolver settings";
            container priority {
              description
                "Specify the order in which resolver will consider this policy";
              list loss-pol {
                key "loss-pol";
                leaf loss-pol {
                  description
                    "Specify this policy's priority; 1 being highest";
                  type uint8 {
                    range "1..9";
                  }
                }
                leaf variance {
                  description
                    "Specify range; e.g. 25 means all exits measuring up to 25% worse than the best exit are considered equivalent";
                  type uint8 {
                    range "1..100";
                  }
                }
              }
            }
          }
          container mos {
            description
              "Specify PfR MOS policy resolver settings";
            container priority {
              description
                "Specify the order in which resolver will consider this policy";
              list mos-pol {
                key "mos-pol";
                leaf mos-pol {
                  description
                    "Specify this policy's priority; 1 being highest";
                  type uint8 {
                    range "1..9";
                  }
                }
                leaf variance {
                  description
                    "Specify range; e.g. 25 means all exits measuring up to 25% worse than the best exit are considered equivalent";
                  type uint8 {
                    range "1..100";
                  }
                }
              }
            }
          }
        }
        container rsvp {
          description
            "Specify rsvp parameters";
          leaf post-dial-delay {
            description
              "RSVP post-dial-delay in msecs";
            type uint16 {
              range "0..500";
            }
          }
          leaf signaling-retries {
            description
              "Number of signaling-retries";
            type uint8 {
              range "0..1";
            }
          }
        }
        leaf shutdown {
          description
            "Disable PfR master controller functionality";
          type empty;
        }
        container target-discovery {
          description
            "Enable/configure Target Discovery";
          presence "true";
          container responder-list {
            description
              "Specify static list of responders";
            list td-num {
              key "td-num";
              leaf td-num {
                description
                  "Prefix-list containing list of responders";
                type string;
              }
              leaf inside-prefixes {
                description
                  "Prefix-list containing list of inside prefixes";
                type string;
              }
            }
          }
        }
        container traceroute {
          description
            "Configure Traceroute global parameters";
          leaf probe-delay {
            description
              "Specify the time between two probes in msec";
            type uint16 {
              range "0..65535";
            }
          }
        }
        leaf trigger-log-percentage {
          description
            "Specify the percentage of out-of-policy TCs that will trigger a syslog";
          type uint8 {
            range "0..100";
          }
        }
        container unreachable {
          description
            "Specify unreachable parameters";
          leaf relative {
            description
              "short/long term in percentage. e.g. 125 is short/long = 1.25";
            type uint16 {
              range "1..1000";
            }
          }
          leaf threshold {
            description
              "Maximum absolute unreachable threshold (flows-per-million)";
            type uint32 {
              range "1..1000000";
            }
          }
        }
      }
    }
  }

  grouping config-pfr-map-grouping {
    container match {
      description
        "Match values for PfR policy";
      container ip {
        description
          "IP specific information";
        leaf address {
          description
            "Match address";
          type empty;
        }
      }
      container pfr {
        description
          "Match PfR prefixes";
        leaf learn {
          description
            "Match PfR learned prefixes";
          type empty;
        }
      }
      container traffic-class {
        description
          "Specify Traffic class";
        leaf access-list {
          description
            "Specify Traffic class(es) using access-list";
          type empty;
        }
        leaf application {
          description
            "Specify the application to learn";
          type empty;
        }
        leaf prefix-list {
          description
            "Specify Traffic class(es) using prefix-list";
          type empty;
        }
      }
    }
    container set {
      description
        "Set values for PfR policy";
      container active-probe {
        description
          "Manually create an active probe for a known target";
        container echo {
          description
            "Perform ICMP echo probe operations";
          list ipv4-or-hostname {
            key "ipv4-or-hostname";
            leaf ipv4-or-hostname {
              description
                "IP address of probe target";
              type inet:host;
            }
            leaf dscp {
              description
                "Specify the DSCP value";
              type empty;
            }
          }
        }
        container jitter {
          description
            "Perform jitter probe operations (requires a responder)";
          list ipv4-or-hostname {
            key "ipv4-or-hostname";
            leaf ipv4-or-hostname {
              description
                "IP address of probe target";
              type inet:host;
            }
            leaf target-port {
              description
                "Required Target Port for udp-echo or tcp-conn or jitter";
              type empty;
            }
          }
        }
        container tcp-conn {
          description
            "Perform TCP Connection / Disconnect probe operations";
          list ipv4-or-hostname {
            key "ipv4-or-hostname";
            leaf ipv4-or-hostname {
              description
                "IP address of probe target";
              type inet:host;
            }
            leaf target-port {
              description
                "Required Target Port for udp-echo or tcp-conn or jitter";
              type empty;
            }
          }
        }
        container udp-echo {
          description
            "Perform UDP Echo probe operations (requires a responder)";
          list ipv4-or-hostname {
            key "ipv4-or-hostname";
            leaf ipv4-or-hostname {
              description
                "IP address of probe target";
              type inet:host;
            }
            leaf target-port {
              description
                "Required Target Port for udp-echo or tcp-conn or jitter";
              type empty;
            }
          }
        }
      }
      container backoff {
        description
          "Specify backoff timer parameters";
        list boff-t {
          key "boff-t";
          leaf boff-t {
            description
              "Specify minimum value of backoff timer (secs)";
            type uint16 {
              range "90..7200";
            }
          }
          list boff-t0 {
            key "boff-t0";
            leaf boff-t0 {
              description
                "Specify maximum value of backoff timer (secs)";
              type uint16 {
                range "90..7200";
              }
            }
            leaf boff-rng {
              description
                "Specify optional backoff timer step (secs)";
              type uint16 {
                range "90..7110";
              }
            }
          }
        }
      }
      container delay {
        description
          "Specify delay parameters";
        leaf relative {
          description
            "Maximum allowable relative change from short to long term";
          type empty;
        }
        leaf threshold {
          description
            "Maximum allowable absolute delay";
          type empty;
        }
      }
      leaf holddown {
        description
          "Specify hold-down timer parameter (secs)";
        type uint16 {
          range "90..65535";
        }
      }
      leaf interface {
        description
          "Set the forwarding interface to Null0";
        type string;
      }
      leaf jitter {
        description
          "Specify jitter parameters";
        type empty;
      }
      container link-group {
        description
          "Specify the link group";
        list lg-name {
          key "lg-name";
          leaf lg-name {
            description
              "Specify primary link group name";
            type string;
          }
          container fallback {
            description
              "Specify the fallback link group";
            presence "true";
            leaf fall-name {
              description
                "Specify Fallback link group name";
              type string;
            }
          }
        }
      }
      container loss {
        description
          "Specify loss parameters";
        leaf relative {
          description
            "short/long term in percentage. e.g. 125 is short/long = 1.25";
          type uint16 {
            range "1..1000";
          }
        }
        leaf threshold {
          description
            "Maximum absolute lost packet threshold in percentage e.g., 1 is 0.0001 percent";
          type uint32 {
            range "1..1000000";
          }
        }
      }
      leaf mode {
        description
          "Specify PfR operating mode settings";
        type empty;
      }
      leaf mos {
        description
          "Specify mos parameters";
        type empty;
      }
      leaf next-hop {
        description
          "Specify the next-hop ip address";
        type empty;
      }
      leaf periodic {
        description
          "Specify periodic rotation timer value";
        type empty;
      }
      leaf probe {
        description
          "Specify active probe parameter";
        type empty;
      }
      leaf resolve {
        description
          "Specify PfR policy resolver settings";
        type empty;
      }
      leaf traceroute {
        description
          "Enable traceroute";
        type empty;
      }
      leaf trap-enable {
        description
          "Enable PfR MIB Traps";
        type empty;
      }
      leaf trigger-log-percentage {
        description
          "Specify the percentage of out-of-policy TCs that will trigger a syslog";
        type empty;
      }
      leaf unreachable {
        description
          "Specify unreachable parameters";
        type empty;
      }
    }
  }

  /////////////////////////////////////////////////////////
  // native / pfr
  /////////////////////////////////////////////////////////
  augment "/ios:native/ios:pfr" {
    uses config-pfr-grouping;
  }

  /////////////////////////////////////////////////////////
  // native / pfr-map
  /////////////////////////////////////////////////////////
  augment "/ios:native/ios:pfr-map" {
    uses config-pfr-map-grouping;
  }
}
