module Cisco-IOS-XE-utd {
  namespace "http://cisco.com/ns/yang/Cisco-IOS-XE-utd";
  prefix ios-utd;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Unified Threat Defense (UTD) Yang model.
     Copyright (c) 2016 by Cisco Systems, Inc.
     All rights reserved."; 

  // =========================================================================
  // REVISION 
  // =========================================================================

  revision 2017-02-07 {
    description
      "Initial revision";
  }

  typedef syslog-level-type {
    type enumeration {
      enum "alert";
      enum "crit";
      enum "debug";
      enum "emerg";
      enum "err";
      enum "info";
      enum "notice";
      enum "warning";
    }
  }

  grouping hour-minute-grouping {
    leaf hours {
      type uint8 {
        range "0..23";
      }
    }
    leaf minutes {
      type uint8 {
        range "0..59";
      }
    }
  }

  grouping username-password-grouping {
    leaf username {
      description
        "Provide the username for authentication";
      type string;
    }
    leaf password {
      description
        "Provide the password for authentication";
      type string;
    }
  }

  grouping utd-engine-standard-grouping {
    container logging {
      description
        "Provide config options for logging the alerts";
      container server {
        description
          "Log the alerts to a server";
        leaf name {
          type string;
        }
        leaf level {
          description
            "Provide the log level";
          type syslog-level-type;
        }
        leaf syslog {
          description
            "Log the alerts to IOS syslogs";
          type empty;
        }
      }
      container syslog {
        description
          "Log the alerts to IOS syslogs";
        presence "true";
        leaf level {
          description
            "Provide the log level";
          type syslog-level-type;
        }
      }
    }
    leaf policy {
      description
        "Provide the policy option (default=balanced)";
      type enumeration {
        enum "balanced";
        enum "connectivity";
        enum "security";
      }
    }
    container signature {
      description
        "Provide config options for the signatures";
      container update {
        description
          "Provide config options for the signature updates";
        container occur-at {
          description
            "Specify update occurence by calendar time";
          container daily {
            description
              "Option for daily update";
            uses hour-minute-grouping;
          }
          container monthly {
            description
              "Option for monthly update";
            leaf days {
              type string;
            }
            uses hour-minute-grouping;
          }
          container weekly {
            description
              "Option for weekly update";
            leaf days {
              type string;
            }
            uses hour-minute-grouping;
          }
        }
        container server {
          description
            "Provide config options for the signature update server";
          container cisco {
            description
              "Use Cisco site to provide updates";
            uses username-password-grouping;
          }
          container url {
            description
              "Enter the complete URL for the path to the update server";
            choice url-uname-passwd {
              case all-case {
                container all {
                  leaf name {
                    type string;
                  }
                  uses username-password-grouping;
                }
              }
              case name-only {
                leaf name {
                  type string;
                }
              }
            }
          }
        }
      }
    }
    leaf threat {
      description
        "Provide the threat detection/protection option (default=detection)";
      type enumeration {
        enum "detection";
        enum "protection";
      }
    }
    leaf whitelist {
      description
        "Enable whitelisting under the utd engine";
      type empty;
    }
  }

  grouping config-utd-engine-grouping {
    container utd-engine { //70305
    description
       "Global Unified Threat Defense Engine";
      container utd {
        container engine {
          description
            "UTD engine";
          container advanced {
            description
              "UTD engine advanced";
            container default {
              description
                "Set a command to its defaults";
              container threat {
                description
                  "Provide threat detection";
                presence "true";
              }
            }
            container threat {
              description
                "Provide threat detection";
              presence "true";
              leaf detection {
                description
                  "Provide threat detection";
                type empty;
              }
            }
          }
          container standard {
            description
              "UTD engine standard";
            status deprecated;
            container default {
              description
                "Set a command to its defaults";
              leaf policy {
                description
                  "Provide the policy option (default=balanced)";
                type empty;
              }
              leaf threat {
                description
                  "Provide the threat detection/protection option (default=detection)";
                type empty;
              }
            }
            uses utd-engine-standard-grouping;
          }
        }
        container whitelist {
          description
            "UTD whitelist config submode";
          status deprecated;
          container signature {
            description
              "Provide signatures for the whitelist";
            leaf id {
              description
                "Provide signature id for the whitelist";
              type uint64 {
                range "0..4294967295";
              }
            }
            leaf comment {
              description
                "Provide a comment for the signature";
              type string;
            }
          }
        }
      }
    }
  }

  grouping config-utd-grouping {
    container utd { //70298
      description
        "Global Unified Threat Defense";
      presence "true";
    }
  }

  /////////////////////////////////////////////////////////
  // native / utd
  // native / utd-engine
  /////////////////////////////////////////////////////////
  augment "/ios:native" {
    uses config-utd-grouping;
    uses config-utd-engine-grouping;
  } //augment
} //module
