/*
 * Generated by confdc --mib2yang-std
 * Source: mgmt/dmi/model/common/mib-source/hand-processed/CISCO-ENHANCED-MEMPOOL-MIB.mib
 */
/*
 * This YANG module has been generated by smidump 0.5.0:
 *
 *      smidump -f yang CISCO-ENHANCED-MEMPOOL-MIB
 *
 * Do not edit. Edit the source file instead!
 */

module CISCO-ENHANCED-MEMPOOL-MIB {

  namespace "urn:ietf:params:xml:ns:yang:smiv2:CISCO-ENHANCED-MEMPOOL-MIB";
  prefix CISCO-ENHANCED-MEMPOOL-MIB;

  import ENTITY-MIB {
    prefix "entity-mib";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-memory@cisco.com";

  description
   "New MIB module for monitoring the memory pools
    of all physical entities on a managed system.";

  revision 2008-12-05 {
    description
     "Added the following High Capacity and Overflow objects
      in cempMemPoolTable.
      cempMemPoolUsedOvrflw, cempMemPoolHCUsed,
      cempMemPoolFreeOvrflw, cempMemPoolHCFree,
      cempMemPoolLargestFreeOvrflw, cempMemPoolHCLargestFree,
      cempMemPoolLowestFreeOvrflw, cempMemPoolHCLowestFree,
      cempMemPoolUsedLowWaterMarkOvrflw,
      cempMemPoolHCUsedLowWaterMark,
      cempMemPoolSharedOvrflw, cempMemPoolHCShared.
      Added couple of new groups cempMemPoolHCGroup and
      cempMemPoolOvrflwGroup.
      Added a new compliance cempMIBComplianceRev3 which deprecates
      cempMIBComplianceRev2.";
  }

  revision 2008-05-07 {
    description
     "Added a new object cempMemPoolShared in cempMemPoolTable.
      Deprecated cempMemPoolGroup OBJECT-GROUP. 
      Added cempMemPoolGroupRev1 OBJECT-GROUP.  
      Deprecated cempMIBComplianceRev1 MODULE-COMPLIANCE. 
      Added cempMIBComplianceRev2 MODULE-COMPLIANCE.";
  }

  revision 2003-02-24 {
    description
     "Revised version of this MIB,added Objects
      to the existing cempMemPoolTable, added buffer pools.
         Different types of memory buffer pools
         may be present in a managed device. For example:
         1. Public buffers, these are standard pools of packets 
            of different sizes (eg: 104B, 600B, 1536B, 4520B,
            5024B, 18024B ...). 
         2. Private [Interface] buffers (eg. ipc, channel ...).
         3. Header pool. 
            Pool of dynamic packet headers. Header buffers 
            have no associated data blocks or particles.
            (Particles are a mechanism for representing a 
            data packet as a collection of discontigious 
            buffers.).
            The new objects added are
            cempMemPoolUsedLowWaterMark, cempMemPoolAllocHit,
            cempMemPoolAllocMiss, cempMemPoolFreeHit, 
            cempMemPoolFreeMiss, cempMemBufferPoolTable
            & cempMemBufferCachePoolTable.";
  }

  revision 2001-06-05 {
    description
     "Initial version of this MIB.";
  }

  typedef CempMemPoolIndex {
    type int32 {
      range "1..2147483647";
    }
    description
     "A unique value, greater than zero, for each memory
      pool in a particular physical entity. It is recommended 
      that values are assigned contiguously starting from 1 
      such that the index will be unique within a particular 
      physical entity.";
  }

  typedef CempMemPoolIndexOrNone {
    type int32 {
      range "0..2147483647";
    }
    description
     "This textual convention is an extension of the
      CempMemPoolIndex. The latter defines a value greater 
      than zero to identify a memory pool in a particular 
      physical entity. This extension permits the additional 
      value of zero. The value zero is object-specific and 
      must therefore be defined as part of the description 
      of any object which uses this syntax. Examples of the 
      usage of zero might include situations where memory
      pool was unknown, or when none or all memory pools 
      need to be referenced.";
  }

  typedef CempMemPoolTypes {
    type enumeration {
      enum "other" {
        value "1";
      }
      enum "processorMemory" {
        value "2";
      }
      enum "ioMemory" {
        value "3";
      }
      enum "pciMemory" {
        value "4";
      }
      enum "fastMemory" {
        value "5";
      }
      enum "multibusMemory" {
        value "6";
      }
      enum "interruptStackMemory" {
        value "7";
      }
      enum "processStackMemory" {
        value "8";
      }
      enum "localExceptionMemory" {
        value "9";
      }
      enum "virtualMemory" {
        value "10";
      }
      enum "reservedMemory" {
        value "11";
      }
      enum "imageMemory" {
        value "12";
      }
      enum "asicMemory" {
        value "13";
      }
      enum "posixMemory" {
        value "14";
      }
    }
    description
     "Represents the different types of memory pools that
      may be present in a managed device. 
      Note that only the processor pool is required to be
      supported by all devices.  Support for other pool types
      is dependent on the device being managed.
      
      processorMemory -
               processor associated heap memory.
      ioMemory - 
               shared memory for buffer data and
               controller descriptor blocks.
      pciMemory - 
               Peripheral Component Interconnect bus
               memory which is visible to all devices on 
               the PCI buses in a platform.
      fastMemory - 
               memory defined by the particular platform 
               for speed critical applications.
      multibusMemory - 
               memory present on some platforms that
               is used as a fallback pool.
      interruptStackMemory - 
               memory for allocating interrupt stacks. 
               It is usually allocated from heap.
      processStackMemory - 
               memory for allocating process stacks. 
               It is usually allocated from heap.
      localExceptionMemory - 
               memory reserved for processing 
               a system core dump.
      virtualMemory - 
               memory used to increase available RAM.
      reservedMemory - 
               memory used for packet headers, 
               particle headers and particles. 
      imageMemory - 
               memory which corresponds to the image 
               file system.
      asicMemory - 
               Application Specific Integrated Circuit
               memory.
      posixMemory -
                Heap memory associated with posix style
                processes in ion.";
  }

  typedef CempMemBufferPoolIndex {
    type uint32 {
      range "0..4294967295";
    }
    description
     "A unique value, greater than zero, for each buffer
      pool in the memory pool on a physical entity. It is 
      recommended that values are assigned contiguously 
      starting from 1 such that the index will be unique
      within a physical entity. Note that the index does 
      not overlap among different memory pools.";
  }


  container CISCO-ENHANCED-MEMPOOL-MIB {
    config false;

    container cempNotificationConfig {
      smiv2:oid "1.3.6.1.4.1.9.9.221.1.2";

      leaf cempMemBufferNotifyEnabled {
        type boolean;
        description
         "This variable controls generation of the
          cempMemBufferNotify.
          
          When this variable is 'true', generation of
          cempMemBufferNotify is enabled.  When this variable
          is 'false', generation of cempMemBufferNotify
          is disabled.";
        smiv2:defval "false";
        smiv2:max-access "read-write";
        smiv2:oid "1.3.6.1.4.1.9.9.221.1.2.1";
      }
    }

    container cempMemPoolTable {
      description
       "A table of memory pool monitoring entries for all
        physical entities on a managed system.";
      smiv2:oid "1.3.6.1.4.1.9.9.221.1.1.1";

      list cempMemPoolEntry {
        key "entPhysicalIndex cempMemPoolIndex";
        description
         "An entry in the memory pool monitoring table.";
        smiv2:oid "1.3.6.1.4.1.9.9.221.1.1.1.1";

        leaf entPhysicalIndex {
          type leafref {
            path "/entity-mib:ENTITY-MIB/entity-mib:entPhysicalTable/entity-mib:entPhysicalEntry/entity-mib:entPhysicalIndex";
          }
        }

        leaf cempMemPoolIndex {
          type CISCO-ENHANCED-MEMPOOL-MIB:CempMemPoolIndex;
          description
           "Within each physical entity, the unique value
            greater than zero, used to represent each memory pool.  
            It is recommended that values are assigned
            contiguously starting from 1.";
          smiv2:max-access "not-accessible";
          smiv2:oid "1.3.6.1.4.1.9.9.221.1.1.1.1.1";
        }

        leaf cempMemPoolType {
          type CISCO-ENHANCED-MEMPOOL-MIB:CempMemPoolTypes;
          description
           "The type of memory pool for which this entry
            contains information.";
          smiv2:max-access "read-only";
          smiv2:oid "1.3.6.1.4.1.9.9.221.1.1.1.1.2";
        }

        leaf cempMemPoolName {
          type snmp-framework:SnmpAdminString;
          description
           "A textual name assigned to the memory pool. This
            object is suitable for output to a human operator,
            and may also be used to distinguish among the various
            pool types.";
          smiv2:max-access "read-only";
          smiv2:oid "1.3.6.1.4.1.9.9.221.1.1.1.1.3";
        }

        leaf cempMemPoolPlatformMemory {
          type snmpv2-tc:AutonomousType;
          description
           "An indication of the platform-specific memory
            pool type. The associated instance of cempMemPoolType
            is used to indicate the general type of memory pool.
            
            If no platform specific memory hardware type
            identifier exists for this physical entity, or the
            value is unknown by this agent, then the value { 0 0 }
            is returned.";
          smiv2:max-access "read-only";
          smiv2:oid "1.3.6.1.4.1.9.9.221.1.1.1.1.4";
        }

        leaf cempMemPoolAlternate {
          type CISCO-ENHANCED-MEMPOOL-MIB:CempMemPoolIndexOrNone;
          description
           "Indicates whether or not this memory pool has an
            alternate pool configured.  Alternate pools are
            used for fallback when the current pool runs out
            of memory.
            
            If an instance of this object has a value of zero,
            then this pool does not have an alternate.  Otherwise
            the value of this object is the same as the value of
            cempMemPoolType of the alternate pool.";
          smiv2:max-access "read-only";
          smiv2:oid "1.3.6.1.4.1.9.9.221.1.1.1.1.5";
        }

        leaf cempMemPoolValid {
          type boolean;
          description
           "Indicates whether or not cempMemPoolUsed,
            cempMemPoolFree, cempMemPoolLargestFree and 
            cempMemPoolLowestFree in this entry contain accurate 
            data. If an instance of this object has the value 
            false (which in and of itself indicates an internal 
            error condition), the values of these objects
            in the conceptual row may contain inaccurate 
            information (specifically, the reported values may be 
            less than the actual values).";
          smiv2:max-access "read-only";
          smiv2:oid "1.3.6.1.4.1.9.9.221.1.1.1.1.6";
        }

        leaf cempMemPoolUsed {
          type yang:gauge32;
          units "bytes";
          description
           "Indicates the number of bytes from the memory pool
            that are currently in use by applications on the
            physical entity.";
          smiv2:max-access "read-only";
          smiv2:oid "1.3.6.1.4.1.9.9.221.1.1.1.1.7";
        }

        leaf cempMemPoolFree {
          type yang:gauge32;
          units "bytes";
          description
           "Indicates the number of bytes from the memory pool
            that are currently unused on the physical entity.
            
            Note that the sum of cempMemPoolUsed and cempMemPoolFree 
            is the total amount of memory in the pool";
          smiv2:max-access "read-only";
          smiv2:oid "1.3.6.1.4.1.9.9.221.1.1.1.1.8";
        }

        leaf cempMemPoolLargestFree {
          type yang:gauge32;
          units "bytes";
          description
           "Indicates the largest number of contiguous bytes
            from the memory pool that are currently unused on
            the physical entity.";
          smiv2:max-access "read-only";
          smiv2:oid "1.3.6.1.4.1.9.9.221.1.1.1.1.9";
        }

        leaf cempMemPoolLowestFree {
          type yang:gauge32;
          units "bytes";
          description
           "The lowest amount of available memory in the memory pool
            recorded at any time during the operation of the system.";
          smiv2:max-access "read-only";
          smiv2:oid "1.3.6.1.4.1.9.9.221.1.1.1.1.10";
        }

        leaf cempMemPoolUsedLowWaterMark {
          type yang:gauge32;
          description
           "Indicates the lowest number of bytes from the memory pool
            that have been used by applications on the physical entity
            since sysUpTime.Similarly,the Used High
            Watermark indicates the largest number of bytes from
            the memory pool that have been used by applications on
            the physical entity since sysUpTime.This can be
            derived as follows:
            Used High Watermark = cempMemPoolUsed +
            cempMemPoolFree  - cempMemPoolLowestFree.";
          smiv2:max-access "read-only";
          smiv2:oid "1.3.6.1.4.1.9.9.221.1.1.1.1.11";
        }

        leaf cempMemPoolAllocHit {
          type yang:counter32;
          description
           "Indicates the number of successful allocations from
            the memory pool";
          smiv2:max-access "read-only";
          smiv2:oid "1.3.6.1.4.1.9.9.221.1.1.1.1.12";
        }

        leaf cempMemPoolAllocMiss {
          type yang:counter32;
          description
           "Indicates the number of unsuccessful allocations from
            the memory pool";
          smiv2:max-access "read-only";
          smiv2:oid "1.3.6.1.4.1.9.9.221.1.1.1.1.13";
        }

        leaf cempMemPoolFreeHit {
          type yang:counter32;
          description
           "Indicates the number of successful frees/
            deallocations from the memory pool";
          smiv2:max-access "read-only";
          smiv2:oid "1.3.6.1.4.1.9.9.221.1.1.1.1.14";
        }

        leaf cempMemPoolFreeMiss {
          type yang:counter32;
          description
           "Indicates the number of unsuccessful attempts
            to free/deallocate memory from the memory pool.
            For example, this could be due to ownership errors 
            where the application that did not assign the 
            memory is trying to free it.";
          smiv2:max-access "read-only";
          smiv2:oid "1.3.6.1.4.1.9.9.221.1.1.1.1.15";
        }

        leaf cempMemPoolShared {
          type yang:gauge32;
          units "bytes";
          description
           "Indicates the number of bytes from the memory pool
            that are currently shared on the physical entity.";
          smiv2:max-access "read-only";
          smiv2:oid "1.3.6.1.4.1.9.9.221.1.1.1.1.16";
        }

        leaf cempMemPoolUsedOvrflw {
          type yang:gauge32;
          units "bytes";
          description
           "This object represents the upper 32-bits of cempMemPoolUsed.
            This object needs to be supported only if the used bytes in the
            memory pool exceeds 32-bits, otherwise this object value would
            be set to 0.";
          smiv2:max-access "read-only";
          smiv2:oid "1.3.6.1.4.1.9.9.221.1.1.1.1.17";
        }

        leaf cempMemPoolHCUsed {
          type yang:gauge64;
          units "bytes";
          description
           "Indicates the number of bytes from the memory pool
            that are currently in use by applications on the
            physical entity. This object is a 64-bit version of
            cempMemPoolUsed.";
          smiv2:max-access "read-only";
          smiv2:oid "1.3.6.1.4.1.9.9.221.1.1.1.1.18";
        }

        leaf cempMemPoolFreeOvrflw {
          type yang:gauge32;
          units "bytes";
          description
           "This object represents the upper 32-bits of cempMemPoolFree.
            This object needs to be supported only if the unused bytes in
            the memory pool exceeds 32-bits, otherwise this object value
            would be set to 0.";
          smiv2:max-access "read-only";
          smiv2:oid "1.3.6.1.4.1.9.9.221.1.1.1.1.19";
        }

        leaf cempMemPoolHCFree {
          type yang:gauge64;
          units "bytes";
          description
           "Indicates the number of bytes from the memory pool
            that are currently unused on the physical entity.
            This object is a 64-bit version of cempMemPoolFree.";
          smiv2:max-access "read-only";
          smiv2:oid "1.3.6.1.4.1.9.9.221.1.1.1.1.20";
        }

        leaf cempMemPoolLargestFreeOvrflw {
          type yang:gauge32;
          units "bytes";
          description
           "This object represents the upper 32-bits of
            cempMemPoolLargestFree. This object needs to 
            be supported only if the value of 
            cempMemPoolLargestFree exceeds 32-bits, otherwise
            this object value would be set to 0.";
          smiv2:max-access "read-only";
          smiv2:oid "1.3.6.1.4.1.9.9.221.1.1.1.1.21";
        }

        leaf cempMemPoolHCLargestFree {
          type yang:gauge64;
          units "bytes";
          description
           "Indicates the largest number of contiguous bytes from the
            memory pool that are currently unused on the physical entity.
            This object is a 64-bit version of cempMemPoolLargestFree.";
          smiv2:max-access "read-only";
          smiv2:oid "1.3.6.1.4.1.9.9.221.1.1.1.1.22";
        }

        leaf cempMemPoolLowestFreeOvrflw {
          type yang:gauge32;
          units "bytes";
          description
           "This object represents the upper 32-bits of
            cempMemPoolLowestFree. This object needs to
            be supported only if the value of
            cempMemPoolLowestFree exceeds 32-bits, otherwise
            this object value would be set to 0.";
          smiv2:max-access "read-only";
          smiv2:oid "1.3.6.1.4.1.9.9.221.1.1.1.1.23";
        }

        leaf cempMemPoolHCLowestFree {
          type yang:gauge64;
          units "bytes";
          description
           "The lowest amount of available memory in the memory pool
            recorded at any time during the operation of the system.
            This object is a 64-bit version of cempMemPoolLowestFree.";
          smiv2:max-access "read-only";
          smiv2:oid "1.3.6.1.4.1.9.9.221.1.1.1.1.24";
        }

        leaf cempMemPoolUsedLowWaterMarkOvrflw {
          type yang:gauge32;
          units "bytes";
          description
           "This object represents the upper 32-bits of
            cempMemPoolUsedLowWaterMark. This object
            needs to be supported only if the value of
            cempMemPoolUsedLowWaterMark exceeds 32-bits,
            otherwise this object value would be set to 0.";
          smiv2:max-access "read-only";
          smiv2:oid "1.3.6.1.4.1.9.9.221.1.1.1.1.25";
        }

        leaf cempMemPoolHCUsedLowWaterMark {
          type yang:gauge64;
          units "bytes";
          description
           "Indicates the lowest number of bytes from the memory
            pool that have been used by applications on the physical
            entity since sysUpTime. This object is a 64-bit version
            of cempMemPoolUsedLowWaterMark.";
          smiv2:max-access "read-only";
          smiv2:oid "1.3.6.1.4.1.9.9.221.1.1.1.1.26";
        }

        leaf cempMemPoolSharedOvrflw {
          type yang:gauge32;
          units "bytes";
          description
           "This object represents the upper 32-bits of cempMemPoolShared.
            This object needs to be supported only if the value of
            cempMemPoolShared exceeds 32-bits, otherwise this object value
            would be set to 0.";
          smiv2:max-access "read-only";
          smiv2:oid "1.3.6.1.4.1.9.9.221.1.1.1.1.27";
        }

        leaf cempMemPoolHCShared {
          type yang:gauge64;
          units "bytes";
          description
           "Indicates the number of bytes from the memory pool that are
            currently shared on the physical entity. This object is a
            64-bit version of cempMemPoolShared.";
          smiv2:max-access "read-only";
          smiv2:oid "1.3.6.1.4.1.9.9.221.1.1.1.1.28";
        }
      }
    }

    container cempMemBufferPoolTable {
      description
       "Entries in this table define entities (buffer pools
        in this case) which are contained in an entity 
        (memory pool) defined by an entry from
        cempMemPoolTable.
        -- Basic Pool Architecture --
        1)Pools are classified as being either Static or 
          Dynamic. Static pools make no attempt to increase 
          the number of buffers contained within them if the 
          number of free buffers (cempMemBufferFree) are less
          than the number of minimum buffers (cempMemBufferMin).
          With Dynamic pools, the pool attempts to meet the 
          demands of its users.
        2)Buffers in a pool are classified as being either 
          Permanent or Temporary. Permanent buffers, as their
          name suggests, are always in the pool and are never
          destroyed unless the number of permanent buffers 
          (cempMemBufferPermanent) is changed. Temporary
          buffers are transient buffers that are created in
          dynamic pools whenever the free count 
          (cempMemBufferFree) of buffers in the pool drops 
          below the minimum (cempMemBufferMin).
        3)Buffers pools are classified as either Public or 
          Private. Public pools are available for all users 
          to allocate buffers from. Private pools are
          primarily used by interface drivers.";
      smiv2:oid "1.3.6.1.4.1.9.9.221.1.1.2";

      list cempMemBufferPoolEntry {
        key "entPhysicalIndex cempMemBufferPoolIndex";
        description
         "This contains all the memory buffer pool
          configurations object values. The 
          entPhysicalIndex identifies the entity on which
          memory buffer pools are present.";
        smiv2:oid "1.3.6.1.4.1.9.9.221.1.1.2.1";

        leaf entPhysicalIndex {
          type leafref {
            path "/entity-mib:ENTITY-MIB/entity-mib:entPhysicalTable/entity-mib:entPhysicalEntry/entity-mib:entPhysicalIndex";
          }
        }

        leaf cempMemBufferPoolIndex {
          type CISCO-ENHANCED-MEMPOOL-MIB:CempMemBufferPoolIndex;
          description
           "Within a physical entity, a unique value used
            to represent each buffer pool.";
          smiv2:max-access "not-accessible";
          smiv2:oid "1.3.6.1.4.1.9.9.221.1.1.2.1.1";
        }

        leaf cempMemBufferMemPoolIndex {
          type CISCO-ENHANCED-MEMPOOL-MIB:CempMemPoolIndexOrNone;
          description
           "This index corresponds to the memory pool (with
            cemMemPoolIndex as index in cempMemPoolTable) 
            from which buffers are allocated.";
          smiv2:max-access "read-only";
          smiv2:oid "1.3.6.1.4.1.9.9.221.1.1.2.1.2";
        }

        leaf cempMemBufferName {
          type snmp-framework:SnmpAdminString;
          description
           "A textual name assigned to the buffer pool. This
            object is suitable for output to a human operator,
            and may also be used to distinguish among the various
            buffer types.
            For example: 'Small', 'Big', 'Serial0/1' etc.";
          smiv2:max-access "read-only";
          smiv2:oid "1.3.6.1.4.1.9.9.221.1.1.2.1.3";
        }

        leaf cempMemBufferDynamic {
          type boolean;
          description
           "Boolean poolDynamic; if TRUE, the number of buffers
            in the pool is adjusted (adding more packet buffers 
            or deleting excesses) dynamically by the background 
            process. If FALSE, the number of buffers in the pool 
            is never adjusted, even if it falls below the minimum,
            or to zero.";
          smiv2:max-access "read-only";
          smiv2:oid "1.3.6.1.4.1.9.9.221.1.1.2.1.4";
        }

        leaf cempMemBufferSize {
          type uint32;
          units "bytes";
          description
           "Indicates the size of buffer element in number of bytes
            on the physical entity.";
          smiv2:max-access "read-write";
          smiv2:oid "1.3.6.1.4.1.9.9.221.1.1.2.1.5";
        }

        leaf cempMemBufferMin {
          type uint32;
          description
           "Indicates the minimum number of free buffers
            allowed in the buffer pool or low-water mark (lwm). 
            For example of its usage :
            If cempMemBufferFree < cempMemBufferMin & pool is 
            dynamic, then signal for growth of particular buffer
            pool.";
          smiv2:max-access "read-write";
          smiv2:oid "1.3.6.1.4.1.9.9.221.1.1.2.1.6";
        }

        leaf cempMemBufferMax {
          type uint32;
          description
           "Indicates the maximum number of free buffers
            allowed in the buffer pool or high-water mark (hwm).
            For example of its usage :
            If cempMemBufferFree > cempMemBufferMax & pool is 
            dynamic, then signal for trim of particular buffer
            pool.";
          smiv2:max-access "read-write";
          smiv2:oid "1.3.6.1.4.1.9.9.221.1.1.2.1.7";
        }

        leaf cempMemBufferPermanent {
          type uint32;
          description
           "Indicates the total number of permanent buffers in the
            pool on the physical entity.";
          smiv2:max-access "read-write";
          smiv2:oid "1.3.6.1.4.1.9.9.221.1.1.2.1.8";
        }

        leaf cempMemBufferTransient {
          type uint32;
          description
           "Indicates the initial number of temporary buffers
            in the pool on the physical entity. This object 
            instructs the system to create this many number of
            temporary extra buffers, just after a system restart. 
            A change in this object will be effective only after
            a system restart.";
          smiv2:max-access "read-write";
          smiv2:oid "1.3.6.1.4.1.9.9.221.1.1.2.1.9";
        }

        leaf cempMemBufferTotal {
          type yang:gauge32;
          description
           "Indicates the total number of buffers
            (include allocated and free buffers) in the
            buffer pool on the physical entity.";
          smiv2:max-access "read-only";
          smiv2:oid "1.3.6.1.4.1.9.9.221.1.1.2.1.10";
        }

        leaf cempMemBufferFree {
          type yang:gauge32;
          description
           "Indicates the current number of free buffers in
            the buffer pool on the physical entity.
            Note that the cempMemBufferFree is less than or equal 
            to cempMemBufferTotal.";
          smiv2:max-access "read-only";
          smiv2:oid "1.3.6.1.4.1.9.9.221.1.1.2.1.11";
        }

        leaf cempMemBufferHit {
          type yang:counter32;
          description
           "Indicates the number of buffers successfully
            allocated from the buffer pool.";
          smiv2:max-access "read-only";
          smiv2:oid "1.3.6.1.4.1.9.9.221.1.1.2.1.12";
        }

        leaf cempMemBufferMiss {
          type yang:counter32;
          description
           "Indicates the number of times a buffer has been
            requested, but no buffers were available in the
            buffer pool, or when there were fewer than min 
            buffers(cempMemBufferMin) in the buffer pool.
            Note : For interface pools, a miss is actually 
            a fall back to its corresponding public buffer pool.";
          smiv2:max-access "read-only";
          smiv2:oid "1.3.6.1.4.1.9.9.221.1.1.2.1.13";
        }

        leaf cempMemBufferFreeHit {
          type yang:counter32;
          description
           "Indicates the number of successful frees/deallocations
            from the buffer pool.";
          smiv2:max-access "read-only";
          smiv2:oid "1.3.6.1.4.1.9.9.221.1.1.2.1.14";
        }

        leaf cempMemBufferFreeMiss {
          type yang:counter32;
          description
           "Indicates the number of unsuccessful attempts
            to free/deallocate a buffer from the buffer pool. 
            For example, this could be due to ownership errors
            where the application that did not assign the 
            buffer is trying to free it.";
          smiv2:max-access "read-only";
          smiv2:oid "1.3.6.1.4.1.9.9.221.1.1.2.1.15";
        }

        leaf cempMemBufferPermChange {
          type int32;
          description
           "This value is the difference of the desired number
            of permanent buffer & total number of permanent 
            buffers present in the pool. A positive value of 
            this object tells the number of buffers needed & a 
            negative value of the object tells the extra number 
            of buffers in the pool.";
          smiv2:max-access "read-only";
          smiv2:oid "1.3.6.1.4.1.9.9.221.1.1.2.1.16";
        }

        leaf cempMemBufferPeak {
          type yang:counter32;
          description
           "Indicates the peak number of buffers in pool on the
            physical entity.";
          smiv2:max-access "read-only";
          smiv2:oid "1.3.6.1.4.1.9.9.221.1.1.2.1.17";
        }

        leaf cempMemBufferPeakTime {
          type yang:timestamp;
          description
           "Indicates the time of most recent change in the peak
            number of buffers (cempMemBufferPeak object) in the pool.";
          smiv2:max-access "read-only";
          smiv2:oid "1.3.6.1.4.1.9.9.221.1.1.2.1.18";
        }

        leaf cempMemBufferTrim {
          type yang:counter32;
          description
           "The number of buffers that have been trimmed from the
            pool when the number of free buffers 
            (cempMemBufferFree) exceeded the number of max
            allowed buffers(cempMemBufferMax).";
          smiv2:max-access "read-only";
          smiv2:oid "1.3.6.1.4.1.9.9.221.1.1.2.1.19";
        }

        leaf cempMemBufferGrow {
          type yang:counter32;
          description
           "The number of buffers that have been created in the
            pool when the number of free buffers(cempMemBufferFree)
            was less than minimum(cempMemBufferMix).";
          smiv2:max-access "read-only";
          smiv2:oid "1.3.6.1.4.1.9.9.221.1.1.2.1.20";
        }

        leaf cempMemBufferFailures {
          type yang:counter32;
          description
           "The number of failures to grant a buffer to a
            requester due to reasons other than insufficient 
            memory. For example, in systems where there are 
            different execution contexts, it may be too
            expensive to create new buffers when running in
            certain contexts. In those cases it may be 
            preferable to fail the request.";
          smiv2:max-access "read-only";
          smiv2:oid "1.3.6.1.4.1.9.9.221.1.1.2.1.21";
        }

        leaf cempMemBufferNoStorage {
          type yang:counter32;
          description
           "The number of times the system tried to create new
            buffers, but could not due to insufficient free 
            memory in the system.";
          smiv2:max-access "read-only";
          smiv2:oid "1.3.6.1.4.1.9.9.221.1.1.2.1.22";
        }
      }
    }

    container cempMemBufferCachePoolTable {
      description
       "A table that lists the cache buffer pools
        configured on a managed system. 
        1)To provide a noticeable performance boost, 
          Cache Pool can be used. A Cache Pool is effectively
          a lookaside list of free buffers that can be 
          accessed quickly. Cache Pool is tied to Buffer Pool. 
        2)Cache pools can optionally have a threshold value
          on the number of cache buffers used in a pool. This
          can provide flow control management by having a 
          implementation specific approach such as invoking a
          vector when pool cache rises above the optional 
          threshold set for it on creation.";
      smiv2:oid "1.3.6.1.4.1.9.9.221.1.1.3";

      list cempMemBufferCachePoolEntry {
        key "entPhysicalIndex cempMemBufferPoolIndex";
        description
         "Each entry represents one of the cache buffer pools
          available in the system and it contains the
          parameters configured for it.
          Note : cempMemBufferCachePoolTable has a sparse
          dependency with cempMemBufferPoolTable (i.e all the
          entires in cempMemBufferPoolTable need not have an
          entry in cempMemBufferCachePoolTable.";
        smiv2:oid "1.3.6.1.4.1.9.9.221.1.1.3.1";

        leaf entPhysicalIndex {
          type leafref {
            path "/entity-mib:ENTITY-MIB/entity-mib:entPhysicalTable/entity-mib:entPhysicalEntry/entity-mib:entPhysicalIndex";
          }
        }

        leaf cempMemBufferPoolIndex {
          type leafref {
            path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferPoolIndex";
          }
        }

        leaf cempMemBufferCacheSize {
          type uint32;
          description
           "Indicates the number of buffers in the cache pool
            on the physical entity.";
          smiv2:max-access "read-only";
          smiv2:oid "1.3.6.1.4.1.9.9.221.1.1.3.1.1";
        }

        leaf cempMemBufferCacheTotal {
          type yang:gauge32;
          description
           "Indicates the maximum number of free buffers
            allowed in the cache pool.";
          smiv2:max-access "read-only";
          smiv2:oid "1.3.6.1.4.1.9.9.221.1.1.3.1.2";
        }

        leaf cempMemBufferCacheUsed {
          type yang:gauge32;
          description
           "Indicates the number of cache buffers from the
            pool that are currently used on the physical entity.
            Note that the cempMemBufferCacheUsed is less than or 
            equal to cempMemBufferCacheTotal.";
          smiv2:max-access "read-only";
          smiv2:oid "1.3.6.1.4.1.9.9.221.1.1.3.1.3";
        }

        leaf cempMemBufferCacheHit {
          type yang:counter32;
          description
           "Indicates the number of buffers successfully
            allocated from the cache pool.";
          smiv2:max-access "read-only";
          smiv2:oid "1.3.6.1.4.1.9.9.221.1.1.3.1.4";
        }

        leaf cempMemBufferCacheMiss {
          type yang:counter32;
          description
           "Indicates the number of times a buffer has been
            requested, but no buffers were available in the
            cache pool.";
          smiv2:max-access "read-only";
          smiv2:oid "1.3.6.1.4.1.9.9.221.1.1.3.1.5";
        }

        leaf cempMemBufferCacheThreshold {
          type yang:gauge32;
          description
           "Indicates the threshold limit for number of cache
            buffers used(cempMemBufferCacheUsed).";
          smiv2:max-access "read-only";
          smiv2:oid "1.3.6.1.4.1.9.9.221.1.1.3.1.6";
        }

        leaf cempMemBufferCacheThresholdCount {
          type yang:counter32;
          description
           "Indicates how many times the number of cache
            buffers used(cempMemBufferCacheUsed) has crossed the
            threshold value(cempMemBufferCacheThreshold).";
          smiv2:max-access "read-only";
          smiv2:oid "1.3.6.1.4.1.9.9.221.1.1.3.1.7";
        }
      }
    }
  }

  notification cempMemBufferNotify {
    description
     "Whenever cempMemBufferPeak object is updated in the
      buffer pool, a cempMemBufferNotify notification
      is sent. The sending of these notifications can be 
      enabled/disabled via the cempMemBufferNotifyEnabled object.";
    smiv2:oid "1.3.6.1.4.1.9.9.221.0.1";

    container object-1 {

      leaf entPhysicalIndex {
        type leafref {
          path "/entity-mib:ENTITY-MIB/entity-mib:entPhysicalTable/entity-mib:entPhysicalEntry/entity-mib:entPhysicalIndex";
        }
      }

      leaf cempMemBufferPoolIndex {
        type leafref {
          path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferPoolIndex";
        }
      }

      leaf cempMemBufferName {
        type leafref {
          path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferName";
        }
      }
    }

    container object-2 {

      leaf entPhysicalIndex {
        type leafref {
          path "/entity-mib:ENTITY-MIB/entity-mib:entPhysicalTable/entity-mib:entPhysicalEntry/entity-mib:entPhysicalIndex";
        }
      }

      leaf cempMemBufferPoolIndex {
        type leafref {
          path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferPoolIndex";
        }
      }

      leaf cempMemBufferPeak {
        type leafref {
          path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferPeak";
        }
      }
    }

    container object-3 {

      leaf entPhysicalIndex {
        type leafref {
          path "/entity-mib:ENTITY-MIB/entity-mib:entPhysicalTable/entity-mib:entPhysicalEntry/entity-mib:entPhysicalIndex";
        }
      }

      leaf cempMemBufferPoolIndex {
        type leafref {
          path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferPoolIndex";
        }
      }

      leaf cempMemBufferPeakTime {
        type leafref {
          path "/CISCO-ENHANCED-MEMPOOL-MIB:CISCO-ENHANCED-MEMPOOL-MIB/CISCO-ENHANCED-MEMPOOL-MIB:cempMemBufferPoolTable/CISCO-ENHANCED-MEMPOOL-MIB:cempMemBufferPoolEntry/CISCO-ENHANCED-MEMPOOL-MIB:cempMemBufferPeakTime";
        }
      }
    }
  }

  smiv2:alias "ciscoEnhancedMemPoolMIB" {
    smiv2:oid "1.3.6.1.4.1.9.9.221";
  }

  smiv2:alias "cempMIBNotifications" {
    smiv2:oid "1.3.6.1.4.1.9.9.221.0";
  }

  smiv2:alias "cempMIBObjects" {
    smiv2:oid "1.3.6.1.4.1.9.9.221.1";
  }

  smiv2:alias "cempMemPool" {
    smiv2:oid "1.3.6.1.4.1.9.9.221.1.1";
  }

  smiv2:alias "cempNotificationConfig" {
    smiv2:oid "1.3.6.1.4.1.9.9.221.1.2";
  }

  smiv2:alias "cempMIBConformance" {
    smiv2:oid "1.3.6.1.4.1.9.9.221.3";
  }

  smiv2:alias "cempMIBCompliances" {
    smiv2:oid "1.3.6.1.4.1.9.9.221.3.1";
  }

  smiv2:alias "cempMIBGroups" {
    smiv2:oid "1.3.6.1.4.1.9.9.221.3.2";
  }

}
