/*
 * Generated by confdc --mib2yang-std
 * Source: mgmt/dmi/model/common/mib-source/CISCO-AAA-SESSION-MIB.mib
 */
/*
 * This YANG module has been generated by smidump 0.5.0:
 *
 *      smidump -f yang CISCO-AAA-SESSION-MIB
 *
 * Do not edit. Edit the source file instead!
 */

module CISCO-AAA-SESSION-MIB {

  namespace "urn:ietf:params:xml:ns:yang:smiv2:CISCO-AAA-SESSION-MIB";
  prefix CISCO-AAA-SESSION-MIB;

  import IF-MIB {
    prefix "if-mib";
  }

  import SNMPv2-TC {
    prefix "snmpv2-tc";
  }

  import ietf-inet-types {
    prefix "inet";
  }

  import ietf-yang-smiv2 {
    prefix "smiv2";
  }

  import ietf-yang-types {
    prefix "yang";
  }

  organization
   "Cisco Systems, Inc.";

  contact
   "       Cisco Systems
    Customer Service
    
    Postal: 170 W. Tasman Drive
    San Jose, CA  95134
    USA
    
    Tel: +1 800 553-NETS
    
    E-mail: cs-aaa@cisco.com";

  description
   "This MIB module provides data for accounting sessions
    based on Authentication, Authorization, Accounting
    (AAA) protocols.
    
    
    References:
        RFC 2139 RADIUS Accounting
        The TACACS+ Protocol Version 1.78, Internet Draft";

  revision 2006-03-21 {
    description
     "Added the casnNasPort and casnVaiIfIndex objects to the
      casnActiveTable.";
  }

  revision 2002-04-11 {
    description
     "Imported Unsigned32 from SNMPv2-SMI instead of CISCO-TC";
  }

  revision 1999-11-16 {
    description
     "Initial version";
  }

  typedef CctCallId {
    type uint32;
    description
     "Represents a Call Identifier.
      The call identifier is used as an unique identifier for an
      call within the system.
      
      A zero value indicates no call ID.";
  }

  typedef CasnSessionId {
    type uint32 {
      range "1..4294967295";
    }
    description
     "Represents an Accounting Session Identifier.
      The session identifier is used as an unique identifier for
      a session within the system.";
  }


  container CISCO-AAA-SESSION-MIB {
    config false;

    container casnActive {
      smiv2:oid "1.3.6.1.4.1.9.9.150.1.1";

      leaf casnActiveTableEntries {
        type yang:gauge32;
        description
         "Number of entries currently in casnActiveTable";
        smiv2:max-access "read-only";
        smiv2:oid "1.3.6.1.4.1.9.9.150.1.1.1";
      }

      leaf casnActiveTableHighWaterMark {
        type yang:gauge32;
        description
         "Maximum number of entries present in casnActiveTable
          since last system re-initialization.
          
          This corresponds to the maximum value reported by
          casnActiveTableEntries.";
        smiv2:max-access "read-only";
        smiv2:oid "1.3.6.1.4.1.9.9.150.1.1.2";
      }
    }

    container casnGeneral {
      smiv2:oid "1.3.6.1.4.1.9.9.150.1.2";

      leaf casnTotalSessions {
        type yang:counter32;
        description
         "Total number of sessions since last system
          re-initialization.
          
          This value includes all sessions currently in the
          casnActiveTable and all previous sessions whether
          terminated via casnDisconnect or via other
          mechanisms.";
        smiv2:max-access "read-only";
        smiv2:oid "1.3.6.1.4.1.9.9.150.1.2.1";
      }

      leaf casnDisconnectedSessions {
        type yang:counter32;
        description
         "Total number of sessions which have been disconnected using
          casnDisconnect since last system re-initialization.
          
          This value includes any sessions still in the
          casnActiveTable with a casnDisconnect value of true(1) and
          all previous sessions which terminated as a result of
          setting casnDisconnect.";
        smiv2:max-access "read-only";
        smiv2:oid "1.3.6.1.4.1.9.9.150.1.2.2";
      }
    }

    container casnActiveTable {
      description
       "This table contains entries for active AAA accounting
        sessions in the system.";
      smiv2:oid "1.3.6.1.4.1.9.9.150.1.1.3";

      list casnActiveEntry {
        key "casnSessionId";
        description
         "The information regarding a single accounting session.
          
          Entries are created when a new accounting session
          is begun.
          
          Entries are removed when the accounting session
          is ended.
          
          Initiating termination of a session with the object
          casnDisconnect will cause removal of the entry when
          the session completes termination.";
        smiv2:oid "1.3.6.1.4.1.9.9.150.1.1.3.1";

        leaf casnSessionId {
          type CISCO-AAA-SESSION-MIB:CasnSessionId;
          description
           "This is the session identification used by the
            accounting protocol.
            
            This value is unique to a session within the system,
            even if multiple accounting protocols are in use.
            
            The value of this object corresponds to these
            accounting protocol attributes.
               RADIUS:  attribute 44, Acct-Session-Id
               TACACS+: attribute 'task_id'";
          smiv2:max-access "not-accessible";
          smiv2:oid "1.3.6.1.4.1.9.9.150.1.1.3.1.1";
        }

        leaf casnUserId {
          type snmpv2-tc:DisplayString {
            length "0..255";
          }
          description
           "The User login ID or zero length string if unavailable.
            
            The value of this object corresponds to these
            accounting protocol attributes.
               RADIUS:  attribute 1, User-Name
               TACACS+: attribute 'user'";
          smiv2:max-access "read-only";
          smiv2:oid "1.3.6.1.4.1.9.9.150.1.1.3.1.2";
        }

        leaf casnIpAddr {
          type inet:ipv4-address;
          description
           "The IP address of the session or 0.0.0.0 if not
            applicable or unavailable.
            
            RADIUS:  attribute 8, Framed-IP-Address
            TACACS+: attribute 'addr'";
          smiv2:max-access "read-only";
          smiv2:oid "1.3.6.1.4.1.9.9.150.1.1.3.1.3";
        }

        leaf casnIdleTime {
          type yang:gauge32;
          units "seconds";
          description
           "The elapsed time that this session has been idle.
            
            This is the time since the last user-level data has been
            received or transmitted. Protocol level handshaking
            associated with the call is considered to be idle for
            this object.";
          smiv2:max-access "read-only";
          smiv2:oid "1.3.6.1.4.1.9.9.150.1.1.3.1.4";
        }

        leaf casnDisconnect {
          type boolean;
          description
           "This object is used to terminate this session.
            
            Setting the value to true(1) will initiate termination
            of this session.
            
            The entry will be removed once the session has completed
            termination.
            
            Once this object has been set to true(1), the session
            termination process can not be cancelled by setting the
            value false(2).";
          smiv2:max-access "read-write";
          smiv2:oid "1.3.6.1.4.1.9.9.150.1.1.3.1.5";
        }

        leaf casnCallTrackerId {
          type CISCO-AAA-SESSION-MIB:CctCallId;
          description
           "The value of this object is the entry index in the
            CISCO-CALL-TRACKER-MIB cctActiveTable of the call
            corresponding to this accounting session.
            
            Using the value of this object to query the
            cctActiveTable will provide more detailed data regarding
            the session represented by this casnActiveEntry.";
          smiv2:max-access "read-only";
          smiv2:oid "1.3.6.1.4.1.9.9.150.1.1.3.1.6";
        }

        leaf casnNasPort {
          type snmpv2-tc:RowPointer;
          description
           "The value of this object identifies a particular
            conceptual row associated with the session identified by
            casnSessionId.  The conceptual row that this object points
            to represents a port that is used to transport a session.
            
            If the port transporting the session cannot be determined,
            the value of this object will be zeroDotZero.
            
            For example, suppose a session is established using an ATM
            PVC.  If the ifIndex of the ATM interface is 7, and the 
            VPI/VCI values of the PVC are 1, 100 respectively, then
            the value of this object might be as follows:
            
                   casnNasPort.15 = atmVclAdminStatus.7.1.100
                               ^                      ^ ^  ^
                               |                      | |  |
               casnSessionId --+                      | |  |
                     ifIndex -------------------------+ |  |
                   atmVclVpi ---------------------------+  |
                   atmVclVci ------------------------------+
            
            where atmVclAdminStatus is the first accessible object
            of the atmVclTable of the ATM-MIB.";
          smiv2:max-access "read-only";
          smiv2:oid "1.3.6.1.4.1.9.9.150.1.1.3.1.7";
        }

        leaf casnVaiIfIndex {
          type if-mib:InterfaceIndexOrZero;
          description
           "The ifIndex of the Virtual Access Interface (VAI)
            that is associated with the PPP session.
            
            This interface may not be represented in the IF-MIB in
            which case the value of this object will be zero.";
          smiv2:max-access "read-only";
          smiv2:oid "1.3.6.1.4.1.9.9.150.1.1.3.1.8";
        }
      }
    }
  }

  smiv2:alias "ciscoAAASessionMIB" {
    smiv2:oid "1.3.6.1.4.1.9.9.150";
  }

  smiv2:alias "casnMIBObjects" {
    smiv2:oid "1.3.6.1.4.1.9.9.150.1";
  }

  smiv2:alias "casnActive" {
    smiv2:oid "1.3.6.1.4.1.9.9.150.1.1";
  }

  smiv2:alias "casnGeneral" {
    smiv2:oid "1.3.6.1.4.1.9.9.150.1.2";
  }

  smiv2:alias "casnMIBNotificationPrefix" {
    smiv2:oid "1.3.6.1.4.1.9.9.150.2";
  }

  smiv2:alias "casnMIBNotifications" {
    smiv2:oid "1.3.6.1.4.1.9.9.150.2.1";
  }

  smiv2:alias "casnMIBConformance" {
    smiv2:oid "1.3.6.1.4.1.9.9.150.3";
  }

  smiv2:alias "casnMIBCompliances" {
    smiv2:oid "1.3.6.1.4.1.9.9.150.3.1";
  }

  smiv2:alias "casnMIBGroups" {
    smiv2:oid "1.3.6.1.4.1.9.9.150.3.2";
  }

}
