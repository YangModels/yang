/*
 * Generated by confdc --mib2yang-std
 * Source: mgmt/dmi/model/common/mib-source/CISCO-IPSLA-JITTER-MIB.mib
 */
/*
 * This YANG module has been generated by smidump 0.5.0:
 *
 *      smidump -f yang CISCO-IPSLA-JITTER-MIB
 *
 * Do not edit. Edit the source file instead!
 */

module CISCO-IPSLA-JITTER-MIB {

  namespace "urn:ietf:params:xml:ns:yang:smiv2:CISCO-IPSLA-JITTER-MIB";
  prefix CISCO-IPSLA-JITTER-MIB;

  import CISCO-IPSLA-TC-MIB {
    prefix "cisco-ipsla";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  organization
   "Cisco Systems, Inc.";

  contact
   "Cisco Systems, Inc.
    Customer Service
    
    Postal: 170 W Tasman Drive
    San Jose, CA 95134
    
    Tel: +1 800 553 NETS
    Email: cs-ipsla@cisco.com";

  description
   "This MIB module defines templates for IP SLA operations of UDP
    Jitter and ICMP Jitter. 
    
    The UDP Jitter operation is designed to measure the delay 
    variance and packet loss in IP networks by generating synthetic 
    UDP traffic. 
    
    The ICMP Jitter operation provides capability to measure metrics 
    such as RTT (Round Trip Time), jitter, packet loss, one-way 
    latency by sending ICMP Timestamp stream to the destination 
    devices.";

  revision 2007-07-24 {
    description
     "Initial version of this MIB module.";
  }


  container CISCO-IPSLA-JITTER-MIB {
    config false;

    container cipslaUdpJitterTmplTable {
      description
       "A table that contains UDP jitter template specific definitions.";
      smiv2:oid "1.3.6.1.4.1.9.9.635.1.1";

      list cipslaUdpJitterTmplEntry {
        key "cipslaUdpJitterTmplName";
        description
         "A row entry representing an IPSLA UDP jitter template.";
        smiv2:oid "1.3.6.1.4.1.9.9.635.1.1.1";

        leaf cipslaUdpJitterTmplName {
          type snmp-framework:SnmpAdminString {
            length "1..64";
          }
          description
           "A string which specifies the UDP Jitter template name.";
          smiv2:max-access "not-accessible";
          smiv2:oid "1.3.6.1.4.1.9.9.635.1.1.1.1";
        }

        leaf cipslaUdpJitterTmplDescription {
          type snmp-framework:SnmpAdminString {
            length "0..128";
          }
          description
           "A string which provides description of UDP Jitter
            template.";
          smiv2:defval "";
          smiv2:max-access "read-write";
          smiv2:oid "1.3.6.1.4.1.9.9.635.1.1.1.2";
        }

        leaf cipslaUdpJitterTmplControlEnable {
          type boolean;
          description
           "If this object is enabled, then the IP SLA application
            will send control messages to a responder, residing on the
            target router to respond to the data request packets being
            sent by the source router.";
          smiv2:defval "true";
          smiv2:max-access "read-write";
          smiv2:oid "1.3.6.1.4.1.9.9.635.1.1.1.3";
        }

        leaf cipslaUdpJitterTmplTimeOut {
          type uint32 {
            range "0..604800000";
          }
          units "milliseconds";
          description
           "Specifies the duration to wait for a IP SLA operation
            completion. 
            
            For connection oriented protocols, this may cause the
            connection to be closed by the operation.  Once closed, it
            will be assumed that the connection reestablishment
            will be performed.  To prevent unwanted closure of
            connections, be sure to set this value to a realistic
            connection timeout.";
          smiv2:defval "5000";
          smiv2:max-access "read-write";
          smiv2:oid "1.3.6.1.4.1.9.9.635.1.1.1.4";
        }

        leaf cipslaUdpJitterTmplVerifyData {
          type boolean;
          description
           "When set to true, the resulting data in each IP SLA
            operation is compared with the expected data.  This
            includes checking header information (if possible) and
            exact packet size.";
          smiv2:defval "false";
          smiv2:max-access "read-write";
          smiv2:oid "1.3.6.1.4.1.9.9.635.1.1.1.5";
        }

        leaf cipslaUdpJitterTmplCodecType {
          type cisco-ipsla:IpSlaCodecType;
          description
           "Specifies the codec type to be used with UDP jitter operation.
            
            If codec-type is configured the following parameters cannot be 
            configured.
            cipslaUdpJitterReqDataSize
            cipslaUdpJitterInterval
            cipslaUdpJitterNumPkts";
          smiv2:max-access "read-write";
          smiv2:oid "1.3.6.1.4.1.9.9.635.1.1.1.6";
        }

        leaf cipslaUdpJitterTmplCodecInterval {
          type uint32 {
            range "4..60000";
          }
          units "milliseconds";
          description
           "This field represents the inter-packet delay between
            packets and is in milliseconds. This object is applicable
            only to UDP jitter operation  which uses codec type.";
          smiv2:max-access "read-write";
          smiv2:oid "1.3.6.1.4.1.9.9.635.1.1.1.7";
        }

        leaf cipslaUdpJitterTmplCodecPayload {
          type uint32 {
            range "0..16384";
          }
          units "octets";
          description
           "This object represents the number of octets that needs to be
            placed into the Data portion of the message. This value is
            used only for UDP jitter operation  which uses codec type.";
          smiv2:max-access "read-write";
          smiv2:oid "1.3.6.1.4.1.9.9.635.1.1.1.8";
        }

        leaf cipslaUdpJitterTmplCodecNumPkts {
          type uint32 {
            range "1..60000";
          }
          units "packets";
          description
           "This value represents the number of packets that need to
            be transmitted. This value is used only for UDP jitter 
            operation which uses codec type.";
          smiv2:max-access "read-write";
          smiv2:oid "1.3.6.1.4.1.9.9.635.1.1.1.9";
        }

        leaf cipslaUdpJitterTmplInterval {
          type uint32 {
            range "4..60000";
          }
          units "milliseconds";
          description
           "This value represents the inter-packet delay between packets
            and is in milliseconds.";
          smiv2:defval "20";
          smiv2:max-access "read-write";
          smiv2:oid "1.3.6.1.4.1.9.9.635.1.1.1.10";
        }

        leaf cipslaUdpJitterTmplNumPkts {
          type uint32 {
            range "1..60000";
          }
          units "packets";
          description
           "This value represents the number of packets that need to be
            transmitted.";
          smiv2:defval "10";
          smiv2:max-access "read-write";
          smiv2:oid "1.3.6.1.4.1.9.9.635.1.1.1.11";
        }

        leaf cipslaUdpJitterTmplSrcAddrType {
          type inet-address:InetAddressType;
          description
           "An enumerated value which specifies the IP address type
            of the source. It must be used along with the
            cipslaUdpJitterTmplSrcAddr object.";
          smiv2:defval "ipv4";
          smiv2:max-access "read-write";
          smiv2:oid "1.3.6.1.4.1.9.9.635.1.1.1.12";
        }

        leaf cipslaUdpJitterTmplSrcAddr {
          type inet-address:InetAddress;
          description
           "This field specifies the IP address of the source.";
          smiv2:max-access "read-write";
          smiv2:oid "1.3.6.1.4.1.9.9.635.1.1.1.13";
        }

        leaf cipslaUdpJitterTmplSrcPort {
          type inet:port-number;
          description
           "This object represents the source's port number. If this
            object is not specified, the application will get a
            port allocated by the system.";
          smiv2:defval "0";
          smiv2:max-access "read-write";
          smiv2:oid "1.3.6.1.4.1.9.9.635.1.1.1.14";
        }

        leaf cipslaUdpJitterTmplPrecision {
          type enumeration {
            enum "milliseconds" {
              value "1";
            }
            enum "microseconds" {
              value "2";
            }
          }
          description
           "This object specifies the accuracy of jitter statistics in
            rttMonJitterStatsTable that needs to be calculated.
            milliseconds(1) - The accuracy of stats will be of milliseconds.
            microseconds(2) - The accuracy of stats will be in microseconds.";
          smiv2:defval "milliseconds";
          smiv2:max-access "read-write";
          smiv2:oid "1.3.6.1.4.1.9.9.635.1.1.1.15";
        }

        leaf cipslaUdpJitterTmplReqDataSize {
          type uint32 {
            range "16..65024";
          }
          units "octets";
          description
           "This object represents the number of octets to be
            placed into the ARR Data portion of the request
            message, when using SNA protocols.
            
            For non-ARR protocols' IP SLA request/responses,
            this value represents the native payload size.
            
            REMEMBER:  The ARR Header overhead is not included
                       in this value.";
          smiv2:defval "32";
          smiv2:max-access "read-write";
          smiv2:oid "1.3.6.1.4.1.9.9.635.1.1.1.16";
        }

        leaf cipslaUdpJitterTmplPktPriority {
          type enumeration {
            enum "normal" {
              value "1";
            }
            enum "high" {
              value "2";
            }
          }
          description
           "This object specifies the priority that will be assigned
            to operation packet.
            
            normal(1) - The packet is of normal priority.
            high(2)   - The packet is of high priority.";
          smiv2:defval "normal";
          smiv2:max-access "read-write";
          smiv2:oid "1.3.6.1.4.1.9.9.635.1.1.1.17";
        }

        leaf cipslaUdpJitterTmplTOS {
          type uint32 {
            range "0..255";
          }
          description
           "This object represents the type of service octet in an
            IP header.";
          reference
           "Refer to the following documents for TOS definition.
            RFC791/1349  for IPv4, IPv6, draft-ietf-diffserv-header-02.txt";
          smiv2:defval "0";
          smiv2:max-access "read-write";
          smiv2:oid "1.3.6.1.4.1.9.9.635.1.1.1.18";
        }

        leaf cipslaUdpJitterTmplVrfName {
          type snmp-framework:SnmpAdminString {
            length "0..32";
          }
          description
           "This field is used to specify the VRF name in
            which the IP SLA operation will be used. For regular IP SLA
            operation this field should not be configured. The agent
            will use this field to identify the VPN routing table for
            this operation.";
          smiv2:defval "";
          smiv2:max-access "read-write";
          smiv2:oid "1.3.6.1.4.1.9.9.635.1.1.1.19";
        }

        leaf cipslaUdpJitterTmplThreshold {
          type uint32 {
            range "0..2147483647";
          }
          units "milliseconds";
          description
           "This object defines an administrative threshold limit.
            If the IP SLA operation time exceeds this limit, then
            one threshold crossing occurrence will be counted.";
          smiv2:defval "5000";
          smiv2:max-access "read-write";
          smiv2:oid "1.3.6.1.4.1.9.9.635.1.1.1.20";
        }

        leaf cipslaUdpJitterTmplNTPTolAbs {
          type uint32 {
            range "0..100000";
          }
          units "microseconds";
          description
           "This object specifies the total clock synchronization error
            on source and responder that is considered tolerable for 
            oneway measurement when NTP is used as clock synchronization 
            mechanism.  The total clock synchronization error is sum of
            NTP offsets on source and responder. The value specified is 
            microseconds. This value can be set only for UDP jitter operation 
            with precision of microsecond.";
          smiv2:defval "0";
          smiv2:max-access "read-write";
          smiv2:oid "1.3.6.1.4.1.9.9.635.1.1.1.21";
        }

        leaf cipslaUdpJitterTmplNTPTolPct {
          type uint32 {
            range "0..100";
          }
          description
           "This object specifies the total clock synchronization error
            on source and responder that is considered tolerable for 
            oneway measurement when NTP is used as clock synchronization 
            mechanism.  The total clock synchronization error is sum of 
            NTP offsets on source and responder. The value is expressed 
            as the percentage of actual oneway latency that is measured. 
            This value can be set only for UDP jitter operation with precision 
            of microsecond.";
          smiv2:defval "0";
          smiv2:max-access "read-write";
          smiv2:oid "1.3.6.1.4.1.9.9.635.1.1.1.22";
        }

        leaf cipslaUdpJitterTmplNTPTolType {
          type enumeration {
            enum "percent" {
              value "1";
            }
            enum "absolute" {
              value "2";
            }
          }
          description
           "This object specifies whether the value specified for oneway
            NTP sync tolerance is absolute value or percent value.
            
            percent(1)  - The value for oneway NTP sync tolerance is 
                          absolute value.
            absolute(2) - The value for oneway NTP sync tolerance is 
                          percent value.";
          smiv2:defval "percent";
          smiv2:max-access "read-write";
          smiv2:oid "1.3.6.1.4.1.9.9.635.1.1.1.23";
        }

        leaf cipslaUdpJitterTmplIcpifFactor {
          type uint32 {
            range "0..20";
          }
          description
           "The advantage factor is dependant on the type of access and
            how the service is to be used.
            Conventional Wire-line     0
            Mobility within Building    5
            Mobility within geographic area  10
            Access to hard-to-reach location   20
            
            It is used when calculating the ICPIF value.";
          smiv2:defval "0";
          smiv2:max-access "read-write";
          smiv2:oid "1.3.6.1.4.1.9.9.635.1.1.1.24";
        }

        leaf cipslaUdpJitterTmplStatsHours {
          type uint32 {
            range "0..25";
          }
          units "hours";
          description
           "The maximum number of hours for which statistics are
            maintained. Specifically this is the number of hourly
            groups to keep before rolling over.
            
            The value of one is not advisable because the hourly
            group will close and immediately be deleted before
            the network management station will have the
            opportunity to retrieve the statistics.
            
            The value of zero will shut off data collection.";
          smiv2:defval "2";
          smiv2:max-access "read-write";
          smiv2:oid "1.3.6.1.4.1.9.9.635.1.1.1.25";
        }

        leaf cipslaUdpJitterTmplDistBuckets {
          type uint32 {
            range "1..20";
          }
          description
           "The maximum number of statistical distribution
            buckets to accumulate.
            
            Since this index does not rollover, only the first
            cipslaUdpJitterTmplDistBuckets will be kept.
            
            The last bucket will contain all entries from its 
            distribution interval start point to infinity.";
          smiv2:defval "1";
          smiv2:max-access "read-write";
          smiv2:oid "1.3.6.1.4.1.9.9.635.1.1.1.26";
        }

        leaf cipslaUdpJitterTmplDistInterval {
          type uint32 {
            range "1..100";
          }
          units "milliseconds";
          description
           "The statistical distribution buckets interval.
            
            Distribution Bucket Example:
            
            cipslaUdpJitterTmplDistBuckets = 5 buckets
            cipslaUdpJitterTmplDistInterval = 10 milliseconds
            
            | Bucket 1 | Bucket 2 | Bucket 3 | Bucket 4 | Bucket 5  |
            |  0-9 ms  | 10-19 ms | 20-29 ms | 30-39 ms | 40-Inf ms |
            
            Odd Example:
            
            cipslaUdpJitterTmplDistBuckets = 1 buckets
            cipslaUdpJitterTmplDistInterval = 10 milliseconds
            
            | Bucket 1  |
            |  0-Inf ms |
            
            Thus, this odd example shows that the value of
            cipslaUdpJitterTmplDistInterval does not apply when
            cipslaUdpJitterTmplDistBuckets is one.";
          smiv2:defval "20";
          smiv2:max-access "read-write";
          smiv2:oid "1.3.6.1.4.1.9.9.635.1.1.1.27";
        }

        leaf cipslaUdpJitterTmplStorageType {
          type snmpv2-tc:StorageType;
          description
           "The storage type of this conceptual row.";
          smiv2:defval "nonVolatile";
          smiv2:max-access "read-write";
          smiv2:oid "1.3.6.1.4.1.9.9.635.1.1.1.28";
        }

        leaf cipslaUdpJitterTmplRowStatus {
          type snmpv2-tc:RowStatus;
          description
           "The status of the conceptual UDP Jitter template control row.
            When the status is active, all the read-create objects in that 
            row can be modified.";
          smiv2:max-access "read-write";
          smiv2:oid "1.3.6.1.4.1.9.9.635.1.1.1.30";
        }
      }
    }

    container cipslaIcmpJitterTmplTable {
      description
       "A table that contains ICMP jitter template specific definitions.";
      smiv2:oid "1.3.6.1.4.1.9.9.635.1.2";

      list cipslaIcmpJitterTmplEntry {
        key "cipslaIcmpJitterTmplName";
        description
         "A row entry representing an IP SLA ICMP Jitter template.";
        smiv2:oid "1.3.6.1.4.1.9.9.635.1.2.1";

        leaf cipslaIcmpJitterTmplName {
          type snmp-framework:SnmpAdminString {
            length "1..64";
          }
          description
           "A string which specifies the ICMP jitter template name.";
          smiv2:max-access "not-accessible";
          smiv2:oid "1.3.6.1.4.1.9.9.635.1.2.1.1";
        }

        leaf cipslaIcmpJitterTmplDescription {
          type snmp-framework:SnmpAdminString {
            length "0..128";
          }
          description
           "A string which provides description of ICMP Jitter
            template.";
          smiv2:defval "";
          smiv2:max-access "read-write";
          smiv2:oid "1.3.6.1.4.1.9.9.635.1.2.1.2";
        }

        leaf cipslaIcmpJitterTmplTimeOut {
          type uint32 {
            range "0..604800000";
          }
          units "milliseconds";
          description
           "Specifies the duration to wait for a IP SLA operation
            completion.
            
            For connection oriented protocols, this may cause the
            connection to be closed by the operation.  Once closed, it
            will be assumed that the connection reestablishment
            will be performed.  To prevent unwanted closure of
            connections, be sure to set this value to a realistic
            connection timeout.";
          smiv2:defval "5000";
          smiv2:max-access "read-write";
          smiv2:oid "1.3.6.1.4.1.9.9.635.1.2.1.3";
        }

        leaf cipslaIcmpJitterTmplVerifyData {
          type boolean;
          description
           "When set to true, the resulting data in each IP SLA
            operation is compared with the expected data.  This
            includes checking header information (if possible) and
            exact packet size.";
          smiv2:defval "false";
          smiv2:max-access "read-write";
          smiv2:oid "1.3.6.1.4.1.9.9.635.1.2.1.4";
        }

        leaf cipslaIcmpJitterTmplNumPkts {
          type uint32 {
            range "1..60000";
          }
          units "packets";
          description
           "This value represents the number of packets that need to be
            transmitted.";
          smiv2:defval "10";
          smiv2:max-access "read-write";
          smiv2:oid "1.3.6.1.4.1.9.9.635.1.2.1.5";
        }

        leaf cipslaIcmpJitterTmplInterval {
          type uint32 {
            range "4..60000";
          }
          units "milliseconds";
          description
           "This value represents the inter-packet delay between packets
            and is in milliseconds.";
          smiv2:defval "20";
          smiv2:max-access "read-write";
          smiv2:oid "1.3.6.1.4.1.9.9.635.1.2.1.6";
        }

        leaf cipslaIcmpJitterTmplSrcAddrType {
          type inet-address:InetAddressType;
          description
           "An enumerated value which specifies the IP address type
            of the source. It must be used along with the
            cipslaIcmpJitterTmplSrcAddr object.";
          smiv2:defval "ipv4";
          smiv2:max-access "read-write";
          smiv2:oid "1.3.6.1.4.1.9.9.635.1.2.1.7";
        }

        leaf cipslaIcmpJitterTmplSrcAddr {
          type inet-address:InetAddress;
          description
           "A string which specifies the IP address of the source.";
          smiv2:max-access "read-write";
          smiv2:oid "1.3.6.1.4.1.9.9.635.1.2.1.8";
        }

        leaf cipslaIcmpJitterTmplTOS {
          type uint32 {
            range "0..255";
          }
          description
           "This object represents the type of service octet in an
            IP header.";
          reference
           "Refer to the following documents for TOS definition.
            RFC791/1349  for IPv4, IPv6, draft-ietf-diffserv-header-02.txt";
          smiv2:defval "0";
          smiv2:max-access "read-write";
          smiv2:oid "1.3.6.1.4.1.9.9.635.1.2.1.9";
        }

        leaf cipslaIcmpJitterTmplVrfName {
          type snmp-framework:SnmpAdminString {
            length "0..32";
          }
          description
           "This field is used to specify the VRF name in
            which the IP SLA operation will be used. For regular IP SLA
            operation this field should not be configured. The agent
            will use this field to identify the VPN routing Table for
            this operation.";
          smiv2:defval "";
          smiv2:max-access "read-write";
          smiv2:oid "1.3.6.1.4.1.9.9.635.1.2.1.10";
        }

        leaf cipslaIcmpJitterTmplThreshold {
          type uint32 {
            range "0..2147483647";
          }
          units "milliseconds";
          description
           "This object defines an administrative threshold limit.
            If the IP SLA operation time exceeds this limit, then 
            one threshold crossing occurrence will be counted.";
          smiv2:defval "5000";
          smiv2:max-access "read-write";
          smiv2:oid "1.3.6.1.4.1.9.9.635.1.2.1.11";
        }

        leaf cipslaIcmpJitterTmplStatsHours {
          type uint32 {
            range "0..25";
          }
          units "hours";
          description
           "The maximum number of hourss for which statistics are
            maintained. Specifically this is the number of hourly
            groups to keep before rolling over.
            
            The value of one is not advisable because the hourly
            group will close and immediately be deleted before
            the network management station will have the
            opportunity to retrieve the statistics.
            
            The value of zero will shut off data collection.";
          smiv2:defval "2";
          smiv2:max-access "read-write";
          smiv2:oid "1.3.6.1.4.1.9.9.635.1.2.1.12";
        }

        leaf cipslaIcmpJitterTmplDistBuckets {
          type uint32 {
            range "1..20";
          }
          description
           "The maximum number of statistical distribution
            buckets to accumulate.
            
            Since this index does not rollover, only the first
            cipslaIcmpJitterTmplDistBuckets will be kept.
            
            The last bucket will contain all entries from its 
            distribution interval start point to infinity.";
          smiv2:defval "1";
          smiv2:max-access "read-write";
          smiv2:oid "1.3.6.1.4.1.9.9.635.1.2.1.13";
        }

        leaf cipslaIcmpJitterTmplDistInterval {
          type uint32 {
            range "1..100";
          }
          units "milliseconds";
          description
           "The statistical distribution buckets interval.
            
            Distribution Bucket Example:
            
            cipslaIcmpJitterTmplDistBuckets = 5 buckets
            cipslaIcmpJitterTmplDistInterval = 10 milliseconds
            
            | Bucket 1 | Bucket 2 | Bucket 3 | Bucket 4 | Bucket 5  |
            |  0-9 ms  | 10-19 ms | 20-29 ms | 30-39 ms | 40-Inf ms |
            
            Odd Example:
            
            cipslaIcmpJitterTmplDistBuckets = 1 buckets
            cipslaIcmpJitterTmplDistInterval = 10 milliseconds
            
            | Bucket 1  |
            |  0-Inf ms |
            
            Thus, this odd example shows that the value of
            cipslaIcmpJitterTmplDistInterval does not apply when
            cipslaIcmpJitterTmplDistBuckets is one.";
          smiv2:defval "20";
          smiv2:max-access "read-write";
          smiv2:oid "1.3.6.1.4.1.9.9.635.1.2.1.14";
        }

        leaf cipslaIcmpJitterTmplStorageType {
          type snmpv2-tc:StorageType;
          description
           "The storage type of this conceptual row.";
          smiv2:defval "nonVolatile";
          smiv2:max-access "read-write";
          smiv2:oid "1.3.6.1.4.1.9.9.635.1.2.1.15";
        }

        leaf cipslaIcmpJitterTmplRowStatus {
          type snmpv2-tc:RowStatus;
          description
           "The status of the conceptual ICMP jitter template control row.
            When the status is active, all the read-create objects in 
            that row can be modified.";
          smiv2:max-access "read-write";
          smiv2:oid "1.3.6.1.4.1.9.9.635.1.2.1.16";
        }
      }
    }
  }

  smiv2:alias "ciscoIpSlaJitterMIB" {
    smiv2:oid "1.3.6.1.4.1.9.9.635";
  }

  smiv2:alias "ciscoIpSlaJitterMIBNotifs" {
    smiv2:oid "1.3.6.1.4.1.9.9.635.0";
  }

  smiv2:alias "ciscoIpSlaJitterMIBObjects" {
    smiv2:oid "1.3.6.1.4.1.9.9.635.1";
  }

  smiv2:alias "ciscoIpSlaJitterMIBConform" {
    smiv2:oid "1.3.6.1.4.1.9.9.635.2";
  }

  smiv2:alias "ciscoIpSlaJitterMIBCompliances" {
    smiv2:oid "1.3.6.1.4.1.9.9.635.2.1";
  }

  smiv2:alias "ciscoIpSlaJitterMIBGroups" {
    smiv2:oid "1.3.6.1.4.1.9.9.635.2.2";
  }

}
