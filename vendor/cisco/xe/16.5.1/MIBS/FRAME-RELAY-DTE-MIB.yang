/*
 * Generated by confdc --mib2yang-std
 * Source: mgmt/dmi/model/common/mib-source/FRAME-RELAY-DTE-MIB.mib
 */
/*
 * This YANG module has been generated by smidump 0.5.0:
 *
 *      smidump -f yang FRAME-RELAY-DTE-MIB
 *
 * Do not edit. Edit the source file instead!
 */

module FRAME-RELAY-DTE-MIB {

  namespace "urn:ietf:params:xml:ns:yang:smiv2:FRAME-RELAY-DTE-MIB";
  prefix FRAME-RELAY-DTE-MIB;

  import IF-MIB {
    prefix "if-mib";
  }

  import SNMPv2-TC {
    prefix "snmpv2-tc";
  }

  import ietf-yang-smiv2 {
    prefix "smiv2";
  }

  import ietf-yang-types {
    prefix "yang";
  }

  organization
   "IETF IPLPDN Working Group";

  contact
   "       Caralyn Brown
    Postal: Cadia Networks, Inc.
            1 Corporate Drive
            Andover, Massachusetts  01810
    Tel:    +1 508 689 2400 x133
    E-Mail: cbrown@cadia.com
    
            Fred Baker
    Postal: Cisco Systems
            519 Lado Drive
            Santa Barbara, California 93111
    Tel:    +1 408 526 425
    E-Mail: fred@cisco.com";

  description
   "The MIB module to describe the use of a Frame Relay
    interface by a DTE.";

  revision 1997-05-01 {
    description
     "Converted from SMIv1 to SMIv2. (Thus, indices are
      read-only rather than being not-accessible.) Added
      objects and made clarifications based on implementation
      experience.";
  }

  revision 1992-04-01 {
    description
     "Published as RFC 1315, the initial version of this MIB
      module.";
  }

  typedef DLCI {
    type int32 {
      range "0..8388607";
    }
    description
     "The range of DLCI values.  Note that this varies by
      interface configuration; normally, interfaces may use
      0..1023, but may be configured to use ranges as large
      as 0..2^23.";
  }


  container FRAME-RELAY-DTE-MIB {
    config false;

    container frameRelayTrapControl {
      smiv2:oid "1.3.6.1.2.1.10.32.4";

      leaf frTrapState {
        type enumeration {
          enum "enabled" {
            value "1";
          }
          enum "disabled" {
            value "2";
          }
        }
        description
         "This variable indicates whether the system produces
          the frDLCIStatusChange trap.";
        smiv2:defval "disabled";
        smiv2:max-access "read-write";
        smiv2:oid "1.3.6.1.2.1.10.32.4.1";
      }

      leaf frTrapMaxRate {
        type int32 {
          range "0..3600000";
        }
        description
         "This variable indicates the number of milliseconds
          that must elapse between trap emissions.  If events
          occur more rapidly, the impementation may simply fail
          to trap, or may queue traps until an appropriate time.";
        smiv2:defval "0";
        smiv2:max-access "read-write";
        smiv2:oid "1.3.6.1.2.1.10.32.4.2";
      }
    }

    container frDlcmiTable {
      description
       "The Parameters for the Data Link Connection Management
        Interface for the frame relay service on this
        interface.";
      reference
       "American National Standard T1.617-1991, Annex D";
      smiv2:oid "1.3.6.1.2.1.10.32.1";

      list frDlcmiEntry {
        key "frDlcmiIfIndex";
        description
         "The Parameters for a particular Data Link Connection
          Management Interface.";
        smiv2:oid "1.3.6.1.2.1.10.32.1.1";

        leaf frDlcmiIfIndex {
          type if-mib:InterfaceIndex;
          description
           "The ifIndex value of the corresponding ifEntry.";
          smiv2:max-access "read-only";
          smiv2:oid "1.3.6.1.2.1.10.32.1.1.1";
        }

        leaf frDlcmiState {
          type enumeration {
            enum "noLmiConfigured" {
              value "1";
            }
            enum "lmiRev1" {
              value "2";
            }
            enum "ansiT1617D" {
              value "3";
            }
            enum "ansiT1617B" {
              value "4";
            }
            enum "itut933A" {
              value "5";
            }
            enum "ansiT1617D1994" {
              value "6";
            }
          }
          description
           "This variable states which Data Link Connection
            Management scheme is active (and by implication, what
            DLCI it uses) on the Frame Relay interface.";
          reference
           "American National Standard T1.617-1991, American
            National Standard T1.617a-1994, ITU-T Recommendation
            Q.933 (03/93).";
          smiv2:max-access "read-write";
          smiv2:oid "1.3.6.1.2.1.10.32.1.1.2";
        }

        leaf frDlcmiAddress {
          type enumeration {
            enum "q921" {
              value "1";
            }
            enum "q922March90" {
              value "2";
            }
            enum "q922November90" {
              value "3";
            }
            enum "q922" {
              value "4";
            }
          }
          description
           "This variable states which address format is in use on
            the Frame Relay interface.";
          smiv2:max-access "read-write";
          smiv2:oid "1.3.6.1.2.1.10.32.1.1.3";
        }

        leaf frDlcmiAddressLen {
          type enumeration {
            enum "twoOctets" {
              value "2";
            }
            enum "threeOctets" {
              value "3";
            }
            enum "fourOctets" {
              value "4";
            }
          }
          description
           "This variable states the address length in octets.  In
            the case of Q922 format, the length indicates the
            entire length of the address including the control
            portion.";
          smiv2:max-access "read-write";
          smiv2:oid "1.3.6.1.2.1.10.32.1.1.4";
        }

        leaf frDlcmiPollingInterval {
          type int32 {
            range "5..30";
          }
          units "seconds";
          description
           "This is the number of seconds between successive
            status enquiry messages.";
          reference
           "American National Standard T1.617-1991, Section D.7
            Timer T391.";
          smiv2:defval "10";
          smiv2:max-access "read-write";
          smiv2:oid "1.3.6.1.2.1.10.32.1.1.5";
        }

        leaf frDlcmiFullEnquiryInterval {
          type int32 {
            range "1..255";
          }
          description
           "Number of status enquiry intervals that pass before
            issuance of a full status enquiry message.";
          reference
           "American National Standard T1.617-1991, Section D.7
            Counter N391.";
          smiv2:defval "6";
          smiv2:max-access "read-write";
          smiv2:oid "1.3.6.1.2.1.10.32.1.1.6";
        }

        leaf frDlcmiErrorThreshold {
          type int32 {
            range "1..10";
          }
          description
           "This is the maximum number of unanswered Status
            Enquiries the equipment shall accept before declaring
            the interface down.";
          reference
           "American National Standard T1.617-1991, Section D.5.1
            Counter N392.";
          smiv2:defval "3";
          smiv2:max-access "read-write";
          smiv2:oid "1.3.6.1.2.1.10.32.1.1.7";
        }

        leaf frDlcmiMonitoredEvents {
          type int32 {
            range "1..10";
          }
          description
           "This is the number of status polling intervals over
            which the error threshold is counted.  For example, if
            within 'MonitoredEvents' number of events the station
            receives 'ErrorThreshold' number of errors, the
            interface is marked as down.";
          reference
           "American National Standard T1.617-1991, Section D.5.2
            Counter N393.";
          smiv2:defval "4";
          smiv2:max-access "read-write";
          smiv2:oid "1.3.6.1.2.1.10.32.1.1.8";
        }

        leaf frDlcmiMaxSupportedVCs {
          type FRAME-RELAY-DTE-MIB:DLCI;
          description
           "The maximum number of Virtual Circuits allowed for
            this interface.  Usually dictated by the Frame Relay
            network.
            
            In response to a SET, if a value less than zero or
            higher than the agent's maximal capability is
            configured, the agent should respond badValue";
          smiv2:max-access "read-write";
          smiv2:oid "1.3.6.1.2.1.10.32.1.1.9";
        }

        leaf frDlcmiMulticast {
          type enumeration {
            enum "nonBroadcast" {
              value "1";
            }
            enum "broadcast" {
              value "2";
            }
          }
          description
           "This indicates whether the Frame Relay interface is
            using a multicast service.";
          smiv2:max-access "read-write";
          smiv2:oid "1.3.6.1.2.1.10.32.1.1.10";
        }

        leaf frDlcmiStatus {
          type enumeration {
            enum "running" {
              value "1";
            }
            enum "fault" {
              value "2";
            }
            enum "initializing" {
              value "3";
            }
          }
          description
           "This indicates the status of the Frame Relay interface
            as determined by the performance of the dlcmi.  If no
            dlcmi is running, the Frame Relay interface will stay
            in the running state indefinitely.";
          smiv2:max-access "read-only";
          smiv2:oid "1.3.6.1.2.1.10.32.1.1.11";
        }

        leaf frDlcmiRowStatus {
          type snmpv2-tc:RowStatus;
          description
           "SNMP Version 2 Row Status Variable.  Writable objects
            in the table may be written in any RowStatus state.";
          smiv2:max-access "read-write";
          smiv2:oid "1.3.6.1.2.1.10.32.1.1.12";
        }
      }
    }

    container frCircuitTable {
      description
       "A table containing information about specific Data
        Link Connections (DLC) or virtual circuits.";
      smiv2:oid "1.3.6.1.2.1.10.32.2";

      list frCircuitEntry {
        key "frCircuitIfIndex frCircuitDlci";
        description
         "The information regarding a single Data Link
          Connection.  Discontinuities in the counters contained
          in this table are indicated by the value in
          frCircuitCreationTime.";
        smiv2:oid "1.3.6.1.2.1.10.32.2.1";

        leaf frCircuitIfIndex {
          type if-mib:InterfaceIndex;
          description
           "The ifIndex Value of the ifEntry this virtual circuit
            is layered onto.";
          smiv2:max-access "read-only";
          smiv2:oid "1.3.6.1.2.1.10.32.2.1.1";
        }

        leaf frCircuitDlci {
          type FRAME-RELAY-DTE-MIB:DLCI;
          description
           "The Data Link Connection Identifier for this virtual
            circuit.";
          reference
           "American National Standard T1.618-1991, Section 3.3.6";
          smiv2:max-access "read-only";
          smiv2:oid "1.3.6.1.2.1.10.32.2.1.2";
        }

        leaf frCircuitState {
          type enumeration {
            enum "invalid" {
              value "1";
            }
            enum "active" {
              value "2";
            }
            enum "inactive" {
              value "3";
            }
          }
          description
           "Indicates whether the particular virtual circuit is
            operational.  In the absence of a Data Link Connection
            Management Interface, virtual circuit entries (rows)
            may be created by setting virtual circuit state to
            'active', or deleted by changing Circuit state to
            'invalid'.
            
            Whether or not the row actually disappears is left to
            the implementation, so this object may actually read as
            'invalid' for some arbitrary length of time.  It is
            also legal to set the state of a virtual circuit to
            'inactive' to temporarily disable a given circuit.
            
            The use of 'invalid' is deprecated in this SNMP Version
            2 MIB, in favor of frCircuitRowStatus.";
          smiv2:defval "active";
          smiv2:max-access "read-write";
          smiv2:oid "1.3.6.1.2.1.10.32.2.1.3";
        }

        leaf frCircuitReceivedFECNs {
          type yang:counter32;
          description
           "Number of frames received from the network indicating
            forward congestion since the virtual circuit was
            created.  This occurs when the remote DTE sets the FECN
            flag, or when a switch in the network enqueues the
            frame to a trunk whose transmission queue is
            congested.";
          reference
           "American National Standard T1.618-1991, Section 3.3.3";
          smiv2:max-access "read-only";
          smiv2:oid "1.3.6.1.2.1.10.32.2.1.4";
        }

        leaf frCircuitReceivedBECNs {
          type yang:counter32;
          description
           "Number of frames received from the network indicating
            backward congestion since the virtual circuit was
            created.  This occurs when the remote DTE sets the BECN
            flag, or when a switch in the network receives the
            frame from a trunk whose transmission queue is
            congested.";
          reference
           "American National Standard T1.618-1991, Section 3.3.4";
          smiv2:max-access "read-only";
          smiv2:oid "1.3.6.1.2.1.10.32.2.1.5";
        }

        leaf frCircuitSentFrames {
          type yang:counter32;
          description
           "The number of frames sent from this virtual circuit
            since it was created.";
          smiv2:max-access "read-only";
          smiv2:oid "1.3.6.1.2.1.10.32.2.1.6";
        }

        leaf frCircuitSentOctets {
          type yang:counter32;
          description
           "The number of octets sent from this virtual circuit
            since it was created.  Octets counted are the full
            frame relay header and the payload, but do not include
            the flag characters or CRC.";
          smiv2:max-access "read-only";
          smiv2:oid "1.3.6.1.2.1.10.32.2.1.7";
        }

        leaf frCircuitReceivedFrames {
          type yang:counter32;
          description
           "Number of frames received over this virtual circuit
            since it was created.";
          smiv2:max-access "read-only";
          smiv2:oid "1.3.6.1.2.1.10.32.2.1.8";
        }

        leaf frCircuitReceivedOctets {
          type yang:counter32;
          description
           "Number of octets received over this virtual circuit
            since it was created.  Octets counted include the full
            frame relay header, but do not include the flag
            characters or the CRC.";
          smiv2:max-access "read-only";
          smiv2:oid "1.3.6.1.2.1.10.32.2.1.9";
        }

        leaf frCircuitCreationTime {
          type yang:timestamp;
          description
           "The value of sysUpTime when the virtual circuit was
            created, whether by the Data Link Connection Management
            Interface or by a SetRequest.";
          smiv2:max-access "read-only";
          smiv2:oid "1.3.6.1.2.1.10.32.2.1.10";
        }

        leaf frCircuitLastTimeChange {
          type yang:timestamp;
          description
           "The value of sysUpTime when last there was a change in
            the virtual circuit state";
          smiv2:max-access "read-only";
          smiv2:oid "1.3.6.1.2.1.10.32.2.1.11";
        }

        leaf frCircuitCommittedBurst {
          type int32 {
            range "0..2147483647";
          }
          description
           "This variable indicates the maximum amount of data, in
            bits, that the network agrees to transfer under normal
            conditions, during the measurement interval.";
          reference
           "American National Standard T1.617-1991, Section
            6.5.19";
          smiv2:defval "0";
          smiv2:max-access "read-write";
          smiv2:oid "1.3.6.1.2.1.10.32.2.1.12";
        }

        leaf frCircuitExcessBurst {
          type int32 {
            range "0..2147483647";
          }
          description
           "This variable indicates the maximum amount of
            uncommitted data bits that the network will attempt to
            deliver over the measurement interval.
            
            By default, if not configured when creating the entry,
            the Excess Information Burst Size is set to the value
            of ifSpeed.";
          reference
           "American National Standard T1.617-1991, Section
            6.5.19";
          smiv2:max-access "read-write";
          smiv2:oid "1.3.6.1.2.1.10.32.2.1.13";
        }

        leaf frCircuitThroughput {
          type int32 {
            range "0..2147483647";
          }
          description
           "Throughput is the average number of 'Frame Relay
            Information Field' bits transferred per second across a
            user network interface in one direction, measured over
            the measurement interval.
            
            If the configured committed burst rate and throughput
            are both non-zero, the measurement interval, T, is
                T=frCircuitCommittedBurst/frCircuitThroughput.
            
            If the configured committed burst rate and throughput
            are both zero, the measurement interval, T, is
                       T=frCircuitExcessBurst/ifSpeed.";
          reference
           "American National Standard T1.617-1991, Section
            6.5.19";
          smiv2:defval "0";
          smiv2:max-access "read-write";
          smiv2:oid "1.3.6.1.2.1.10.32.2.1.14";
        }

        leaf frCircuitMulticast {
          type enumeration {
            enum "unicast" {
              value "1";
            }
            enum "oneWay" {
              value "2";
            }
            enum "twoWay" {
              value "3";
            }
            enum "nWay" {
              value "4";
            }
          }
          description
           "This indicates whether this VC is used as a unicast VC
            (i.e. not multicast) or the type of multicast service
            subscribed to";
          reference
           "Frame Relay PVC Multicast Service and Protocol
            Description Implementation: FRF.7 Frame Relay Forum
            Technical Committe October 21, 1994";
          smiv2:defval "unicast";
          smiv2:max-access "read-write";
          smiv2:oid "1.3.6.1.2.1.10.32.2.1.15";
        }

        leaf frCircuitType {
          type enumeration {
            enum "static" {
              value "1";
            }
            enum "dynamic" {
              value "2";
            }
          }
          description
           "Indication of whether the VC was manually created
            (static), or dynamically created (dynamic) via the data
            link control management interface.";
          smiv2:max-access "read-only";
          smiv2:oid "1.3.6.1.2.1.10.32.2.1.16";
        }

        leaf frCircuitDiscards {
          type yang:counter32;
          description
           "The number of inbound frames dropped because of format
            errors, or because the VC is inactive.";
          smiv2:max-access "read-only";
          smiv2:oid "1.3.6.1.2.1.10.32.2.1.17";
        }

        leaf frCircuitReceivedDEs {
          type yang:counter32;
          description
           "Number of frames received from the network indicating
            that they were eligible for discard since the virtual
            circuit was created.  This occurs when the remote DTE
            sets the DE flag, or when in remote DTE's switch
            detects that the frame was received as Excess Burst
            data.";
          reference
           "American National Standard T1.618-1991, Section 3.3.4";
          smiv2:max-access "read-only";
          smiv2:oid "1.3.6.1.2.1.10.32.2.1.18";
        }

        leaf frCircuitSentDEs {
          type yang:counter32;
          description
           "Number of frames sent to the network indicating that
            they were eligible for discard since the virtual
            circuit was created.   This occurs when the local DTE
            sets the DE flag, indicating that during Network
            congestion situations those frames should be discarded
            in preference of other frames sent without the DE bit
            set.";
          reference
           "American National  Standard  T1.618-1991, Section
            3.3.4";
          smiv2:max-access "read-only";
          smiv2:oid "1.3.6.1.2.1.10.32.2.1.19";
        }

        leaf frCircuitLogicalIfIndex {
          type if-mib:InterfaceIndex;
          description
           "Normally the same value as frDlcmiIfIndex, but
            different when an implementation associates a virtual
            ifEntry with a DLC or set of DLCs in order to associate
            higher layer objects such as the ipAddrEntry with a
            subset of the virtual circuits on a Frame Relay
            interface. The type of such ifEntries is defined by the
            higher layer object; for example, if PPP/Frame Relay is
            implemented, the ifType of this ifEntry would be PPP.
            If it is not so defined, as would be the case with an
            ipAddrEntry, it should be of type Other.";
          smiv2:max-access "read-write";
          smiv2:oid "1.3.6.1.2.1.10.32.2.1.20";
        }

        leaf frCircuitRowStatus {
          type snmpv2-tc:RowStatus;
          description
           "This object is used to create a new row or modify or
            destroy an existing row in the manner described in the
            definition of the RowStatus textual convention.
            Writable objects in the table may be written in any
            RowStatus state.";
          smiv2:max-access "read-write";
          smiv2:oid "1.3.6.1.2.1.10.32.2.1.21";
        }
      }
    }

    container frErrTable {
      description
       "A table containing information about Errors on the
        Frame Relay interface.  Discontinuities in the counters
        contained in this table are the same as apply to the
        ifEntry associated with the Interface.";
      smiv2:oid "1.3.6.1.2.1.10.32.3";

      list frErrEntry {
        key "frErrIfIndex";
        description
         "The error information for a single frame relay
          interface.";
        smiv2:oid "1.3.6.1.2.1.10.32.3.1";

        leaf frErrIfIndex {
          type if-mib:InterfaceIndex;
          description
           "The ifIndex Value of the corresponding ifEntry.";
          smiv2:max-access "read-only";
          smiv2:oid "1.3.6.1.2.1.10.32.3.1.1";
        }

        leaf frErrType {
          type enumeration {
            enum "unknownError" {
              value "1";
            }
            enum "receiveShort" {
              value "2";
            }
            enum "receiveLong" {
              value "3";
            }
            enum "illegalAddress" {
              value "4";
            }
            enum "unknownAddress" {
              value "5";
            }
            enum "dlcmiProtoErr" {
              value "6";
            }
            enum "dlcmiUnknownIE" {
              value "7";
            }
            enum "dlcmiSequenceErr" {
              value "8";
            }
            enum "dlcmiUnknownRpt" {
              value "9";
            }
            enum "noErrorSinceReset" {
              value "10";
            }
          }
          description
           "The type of error that was last seen  on  this interface:
            
            receiveShort: frame was not long enough to allow
                    demultiplexing - the address field was incomplete,
                    or for virtual circuits using Multiprotocol over
                    Frame Relay, the protocol identifier was missing
                    or incomplete.
            
            receiveLong: frame exceeded maximum length configured for this
                         interface.
            
            illegalAddress: address field did not match configured format.
            
            unknownAddress: frame received on a virtual circuit which was not
                            active or administratively disabled.
            
            dlcmiProtoErr: unspecified error occurred when attempting to
                           interpret link maintenance frame.
            
            dlcmiUnknownIE: link maintenance frame contained an Information
                            Element type which is not valid for the
                            configured link maintenance protocol.
            
            dlcmiSequenceErr: link maintenance frame contained a sequence
                              number other than the expected value.
            
            dlcmiUnknownRpt: link maintenance frame contained a Report Type
                             Information Element whose value was not valid
                             for the configured link maintenance protocol.
            
            noErrorSinceReset: no errors have been detected since the last
                               cold start or warm start.";
          smiv2:max-access "read-only";
          smiv2:oid "1.3.6.1.2.1.10.32.3.1.2";
        }

        leaf frErrData {
          type binary {
            length "1..1600";
          }
          description
           "An octet string containing as much of the error packet
            as possible.  As a minimum, it must contain the Q.922
            Address or as much as was delivered.  It is desirable
            to include all header and demultiplexing information.";
          smiv2:max-access "read-only";
          smiv2:oid "1.3.6.1.2.1.10.32.3.1.3";
        }

        leaf frErrTime {
          type yang:timestamp;
          description
           "The value of sysUpTime at which the error was
            detected.";
          smiv2:max-access "read-only";
          smiv2:oid "1.3.6.1.2.1.10.32.3.1.4";
        }

        leaf frErrFaults {
          type yang:counter32;
          description
           "The number of times the interface has gone down since
            it was initialized.";
          smiv2:max-access "read-only";
          smiv2:oid "1.3.6.1.2.1.10.32.3.1.5";
        }

        leaf frErrFaultTime {
          type yang:timestamp;
          description
           "The value of sysUpTime at the time when the interface
            was taken down due to excessive errors.  Excessive
            errors is defined as the time when a DLCMI exceeds the
            frDlcmiErrorThreshold number of errors within
            frDlcmiMonitoredEvents. See FrDlcmiEntry for further
            details.";
          smiv2:max-access "read-only";
          smiv2:oid "1.3.6.1.2.1.10.32.3.1.6";
        }
      }
    }
  }

  notification frDLCIStatusChange {
    description
     "This trap indicates that the indicated Virtual Circuit
      has changed state.  It has either been created or
      invalidated, or has toggled between the active and
      inactive states.  If, however, the reason for the state
      change is due to the DLCMI going down, per-DLCI traps
      should not be generated.";
    smiv2:oid "1.3.6.1.2.1.10.32.0.1";

    container object-1 {

      leaf frCircuitIfIndex {
        type leafref {
          path "/FRAME-RELAY-DTE-MIB:FRAME-RELAY-DTE-MIB/FRAME-RELAY-DTE-MIB:frCircuitTable/FRAME-RELAY-DTE-MIB:frCircuitEntry/FRAME-RELAY-DTE-MIB:frCircuitIfIndex";
        }
      }

      leaf frCircuitDlci {
        type leafref {
          path "/FRAME-RELAY-DTE-MIB:FRAME-RELAY-DTE-MIB/FRAME-RELAY-DTE-MIB:frCircuitTable/FRAME-RELAY-DTE-MIB:frCircuitEntry/FRAME-RELAY-DTE-MIB:frCircuitDlci";
        }
      }

      leaf frCircuitState {
        type leafref {
          path "/FRAME-RELAY-DTE-MIB:FRAME-RELAY-DTE-MIB/FRAME-RELAY-DTE-MIB:frCircuitTable/FRAME-RELAY-DTE-MIB:frCircuitEntry/FRAME-RELAY-DTE-MIB:frCircuitState";
        }
      }
    }
  }

  smiv2:alias "frameRelayDTE" {
    smiv2:oid "1.3.6.1.2.1.10.32";
  }

  smiv2:alias "frameRelayTraps" {
    smiv2:oid "1.3.6.1.2.1.10.32.0";
  }

  smiv2:alias "frameRelayTrapControl" {
    smiv2:oid "1.3.6.1.2.1.10.32.4";
  }

  smiv2:alias "frConformance" {
    smiv2:oid "1.3.6.1.2.1.10.32.6";
  }

  smiv2:alias "frGroups" {
    smiv2:oid "1.3.6.1.2.1.10.32.6.1";
  }

  smiv2:alias "frCompliances" {
    smiv2:oid "1.3.6.1.2.1.10.32.6.2";
  }

}
