module Cisco-IOS-XE-coap {
  namespace "http://cisco.com/ns/yang/Cisco-IOS-XE-coap";
  prefix ios-coap;

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Contrained Application Protocol (CoAP) Yang Model.
     Copyright (c) 2016 by Cisco Systems, Inc.
     All rights reserved."; 

  // =========================================================================
  // REVISION 
  // =========================================================================

  revision 2017-02-07 {
    description
      "Initial revision";
  }

  /////////////////////////////////////////////////////////
  // native / coap
  /////////////////////////////////////////////////////////
  grouping config-coap-grouping {
    container coap {
      description
        "CoAP Global Configuration Commands";
      container http {
        description
          "CoAP http server";
        leaf enable {
          description
            "CoAP http server enable";
          type empty;
        }
      }
    }
  }

  /////////////////////////////////////////////////////////
  // native / coap
  /////////////////////////////////////////////////////////
  augment "/ios:native" {
    uses config-coap-grouping;
  }
}
