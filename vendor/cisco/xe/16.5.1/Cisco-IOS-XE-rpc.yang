module Cisco-IOS-XE-rpc {
  namespace "http://cisco.com/ns/yang/Cisco-IOS-XE-rpc";
  prefix ios-xe-rpc;


  organization "Cisco Systems";

  contact
    <mailto:cs-yang@cisco.com>;

  description
    "NED RPC YANG module for IOS
     Copyright (c) 2016 by Cisco Systems, Inc.
     All rights reserved."; 

  // =========================================================================
  // REVISION 
  // =========================================================================

  revision 2017-02-07 {
    description
      "Initial revision";
  }

  grouping cisco-xe-rpc-output {
    description 
      "Used to return output from RPCs";
    leaf result {
      type string;
      description 
        "Output returned by the network element";
    }
  }

  rpc switch {
    input {
      leaf switch-number {
        mandatory true;
        type uint8 {
          range "1..9";
         }
      }
      choice pri-renum-stack {
        mandatory true;
        case priority-case {
        leaf priority {
	  description 
	    "<1-15>  Switch Priority";
          type uint8 {
	    range "1..15";
          }
        }
	}
	case renumver-case {
        leaf renumber {
	  description 
	    "<1-9>  New number of the Switch";
          type uint8 {
	    range "1..9";
          }
        }
	}
	case stack-case {
	container statck {
          leaf port {
	    description 
	      "<1-2>  Stack port number to enable/disable";
            type uint8 {
	      range "1..2";
            }
          }
          }
        }
      }
    }
    output {
      uses cisco-xe-rpc-output; 
    }
  }
  rpc default {
    description 
      "Set a command to its defaults";
    input {
      choice default-choice {
        mandatory true;
        case interface-case {
          leaf interface {
            description 
	      "Select an interface to configure";
            type string {
	      pattern "([0-9a-zA-Z.]+)";
	    }
          }
        }
      }
    }
    output {
      uses cisco-xe-rpc-output; 
    }
  }
  rpc reload {
    description 
      "Halt and perform a cold restart";
    output {
      uses cisco-xe-rpc-output; 
    }
  }
  rpc license {
    input {
      container smart {
        choice smart-choice {
	  mandatory true;
	  case register-case {
	    container register {
	      leaf idtoken {
	        type empty;
	      }
	    }
	  }
	  case deregister-case {
	    leaf deregister {
	      type empty;
            }
	  }
	  case renew-case {
	    container renew {
	      leaf id {
	        type empty;
              }
	      leaf auth {
	        type empty;
              }
	    }
	  }
	}
      }
    }
    output {
      uses cisco-xe-rpc-output; 
    }
  }
}
