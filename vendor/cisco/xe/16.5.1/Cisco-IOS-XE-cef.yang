module Cisco-IOS-XE-cef {
  namespace "http://cisco.com/ns/yang/Cisco-IOS-XE-cef";
  prefix ios-cef;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Cisco Express Forwarding (CEF) Yang model.
     Copyright (c) 2016 by Cisco Systems, Inc.
     All rights reserved."; 

  // =========================================================================
  // REVISION 
  // =========================================================================

  revision 2017-02-07 {
    description
      "Initial revision";
  }

  grouping config-ip-cef-grouping {
    leaf distributed {
      description
        "Distributed Cisco Express Forwarding";
      type empty;
    }
    container load-sharing {
      description "Load sharing";
      container algorithm {
        description "Per-destination load sharing algorithm selection";
        container include-ports {
          description "Algorithm that includes layer 4 ports";
          container destination {
            description "Use destination port in hash function";
            presence "true";
            leaf dest-range {
              description "<1-FFFFFFFF>  Fixed ID";
              type string;
            }
          }
          container source {
            description "Use source port in hash function";
            presence true;
            leaf source-range {
              description "<1-FFFFFFFF>  Fixed ID";
              type string;
            }
            container destination {
              description "Use source and destination ports in hash function";
              presence true;
              leaf dest-range {
                description "<1-FFFFFFFF>  Fixed ID";
                type string;
              }
              container gtp {
                description "Use GTP te-id as source and destination ports in hash function";
                presence true;
                leaf gtp-range {
                  description "<1-FFFFFFFF>  Fixed ID";
                  type string;
                }
              }
            }
          }
        }
      }
    }
    //accounting          Enable CEF accounting
    //event-log           CEF event log commands
    //table               Set CEF forwarding table characteristics
    //traffic-statistics  Enable collection of traffic statistics
  }

  grouping config-ipv6-cef-grouping {
    container accounting {
      description
        "Enable CEF accounting";
      leaf per-prefix {
        description
          "Enable per prefix accounting";
        type empty;
      }
      leaf prefix-length {
        description
          "Enable prefix length accounting";
        type empty;
      }
    }
    leaf distributed {
      description
        "Distributed Cisco Express Forwarding";
      type empty;
    }
  }

  grouping config-cef-grouping {
    container cef {
      description "Cisco Express Forwarding";
      container table {
        description "Set CEF forwarding table characteristics";
        container output-chain {
          description "Set table output chain characteristics";
          container build {
            description "Set table output chain building characteristics";
            container favor {
              description "Set which table output chain building characteristics to favor";
              leaf convergence-speed {
                description "Favor faster convergence";
                type empty;
              }
              leaf memory-utilization {
                description "Favor smaller memory utilization";
                type empty;
              }
            }
          }
        }
      }
    }
  }

  /////////////////////////////////////////////////////////
  // native /  cef
  /////////////////////////////////////////////////////////
  augment "/ios:native" {
    uses config-cef-grouping;
  }

  /////////////////////////////////////////////////////////
  // native / ip / cef
  /////////////////////////////////////////////////////////
  augment "/ios:native/ios:ip/ios:cef" {
    uses config-ip-cef-grouping;
  }

  /////////////////////////////////////////////////////////
  // native / ipv6  / cef
  /////////////////////////////////////////////////////////
  augment "/ios:native/ios:ipv6/ios:cef" {
    uses config-ipv6-cef-grouping;
  } //augment
} //module
