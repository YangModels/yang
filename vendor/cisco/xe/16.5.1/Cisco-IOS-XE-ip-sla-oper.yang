module Cisco-IOS-XE-ip-sla-oper {

    yang-version 1;

    namespace "http://cisco.com/ns/yang/Cisco-IOS-XE-ip-sla-oper";
    prefix ip-sla-ios-xe-oper;

    import ietf-yang-types {
        prefix yang;
    }

    organization
        "Cisco Systems, Inc.";

    contact
        "Cisco Systems, Inc. Customer Service Postal: 170 W Tasman Drive
         San Jose, CA 95134 Tel: +1 1800 553-NETS E-mail: cs-yang@cisco.com";
    
    description
        "This module contains a collection of YANG definitions for
         monitoring IP SLA statistics of a Network Element."+
        "Copyright (c) 2016-2017 by Cisco Systems, Inc."+
        "All rights reserved."; 

  // =========================================================================
  // REVISION 
  // =========================================================================

  revision 2017-02-07 {
    description
      "Initial revision";
  }

    grouping sla-time-values {

        leaf min {
            type uint32;
        }

        leaf avg {
            type uint32;
        }

        leaf max {
            type uint32;
        }

        leaf accuracy {
            type accuracy-type;
        }
    }

    grouping sla-packet-loss-info {

        leaf loss-period-count {
            type uint32;
        }

        leaf loss-period-len-min {
            type uint32;
        }

        leaf loss-period-len-max {
            type uint32;
        }

        leaf inter-loss-period-len-min {
            type uint32;
        }

        leaf inter-loss-period-len-max {
            type uint32;
        }
    }

    grouping voice-score {
        leaf icpif {
            type uint32;
        }

        leaf mos {
            type uint32;
        }
    }

    grouping latest-rtt-type {
        choice latestrtt-choice {
            description
                "The last Round Trip Time recorded for this SLA.";

            case known-rtt-value {
                leaf rtt {
                    type uint64;
                }
            }
            case unknown-rtt {
                leaf unknown {
                    type empty;
                }
            }
            case could-not-find-rtt {
                leaf could-not-find {
                    type empty;
                    description
                        "One of no-connection/busy/timeout";

                }
            }
        }
    }

    grouping time-to-live-type {
        choice timetolive-choice {
            description
                "Time-to-live for the SLA operation.";
 
            case finite-ttl {
                leaf ttl {
                    type uint64;
                }
            }
            case forever-ttl {
                leaf forever {
                    type empty;
                }
            }
        }
    }

    grouping rtt-info {
        container latest-rtt {
            uses ip-sla-ios-xe-oper:latest-rtt-type;
        }

        container time-to-live {
            uses ip-sla-ios-xe-oper:time-to-live-type;
        }
   }

    grouping y1731-interval-stats {
        leaf intv-start-time {
            type yang:date-and-time;
        }

        leaf init-count {
            type uint32;
        }

        leaf complete-count {
            type uint32;
        }

        leaf valid {
            type boolean;
        }
    }

    grouping rtt {
        leaf rtt-count {
            type uint32;
        }

        container sla-time-values {
            uses ip-sla-ios-xe-oper:sla-time-values;
        }
    }

    grouping oneway-latency {
        leaf sample-count {
            type uint32;
        }

        container sd {
            uses ip-sla-ios-xe-oper:sla-time-values;
        }

        container ds {
            uses ip-sla-ios-xe-oper:sla-time-values;
        }
    }

    grouping jitter {
        leaf sd-sample-count {
            type uint32;
        }
                    
        leaf ds-sample-count {
            type uint32;
        }
                    
        container sd {
            uses ip-sla-ios-xe-oper:sla-time-values;
        }

        container ds {
            uses ip-sla-ios-xe-oper:sla-time-values;
        }
    }

    grouping over-threshold {
        leaf rtt-count {
            type uint32;
        }

        leaf percent {
            type uint8;
        }
    }
 
    grouping packet-loss {
        leaf unprocessed-packets {
            when "(../../../oper-type='ethernet-jitter') or" +
                 "(../../../oper-type='ethernet-echo')" ;
            type uint32;
        }
                    
        leaf sd-count {
            type uint32;
        }

        container sd-loss {
            when "(../../../oper-type!='ethernet-jitter') and" +
                 "(../../../oper-type!='ethernet-echo')" ;

            uses ip-sla-ios-xe-oper:sla-packet-loss-info;
        }
                    
        leaf ds-count {
            type uint32;
        }

        container ds-loss {
             when "(../../../oper-type!='ethernet-jitter') and" +
                  "(../../../oper-type!='ethernet-echo')" ;

             uses ip-sla-ios-xe-oper:sla-packet-loss-info;
        }

        leaf out-of-sequence {
            type uint32;
        }

        leaf drops {
            type uint32;
        }

        leaf late-arrivals {
            type uint32;
        }

        leaf skipped-packets {
            type uint32;
        }
    }

    grouping icmp-packet-loss {
        leaf late-arrivals {
            type uint32;
        }

        leaf out-of-sequence {
            type uint32;
        }

        leaf out-of-sequence-sd {
            type uint32;
        }

        leaf ds-out-of-sequence-ds {
            type uint32;
        }

        leaf out-of-sequence-both {
            type uint32;
        }

        leaf skipped-packets {
            type uint32;
        }

        leaf unprocessed-packets {
            type uint32;
        }
                    
        leaf packet-loss {
            type uint32;
        }
                   
        leaf loss-period-count {
            type uint32;
        }

        leaf loss-period-len-min {
            type uint32;
        }

        leaf loss-period-len-max {
            type uint32;
        }

        leaf inter-loss-period-len-min {
            type uint32;
        }

        leaf inter-loss-period-len-max {
            type uint32;
        }
    }

    grouping stats {
        container rtt {
            uses rtt;
        }

        container oneway-latency {
            uses ip-sla-ios-xe-oper:oneway-latency;
        }

        container jitter {
            uses jitter;
        }

        container over-threshold {
            uses ip-sla-ios-xe-oper:over-threshold;
        }

        container packet-loss {
            when "(../../oper-type!='icmp-jitter')";

            uses ip-sla-ios-xe-oper:packet-loss;
        }

        container icmp-packet-loss {
            when "(../../oper-type='icmp-jitter')";

            uses ip-sla-ios-xe-oper:icmp-packet-loss;
        }

        container voice-score {
            uses ip-sla-ios-xe-oper:voice-score;
        }
    }

    grouping sla-oper-entry {
        leaf oper-id {
            type uint32;
            description
                "The name of the memory pool.";
        }

        leaf oper-type {
            type ip-sla-ios-xe-oper:sla-oper-type;
        }

        leaf latest-return-code {
            type ip-sla-ios-xe-oper:sla-return-code;
        }

        leaf success-count {
            type uint32;
        }

        leaf failure-count {
            type uint32;
        }

        leaf latest-oper-start-time {
            type yang:date-and-time;
            description
                "The time-stamp for the latest SLA operation.";
        }

        container rtt-info {
            uses ip-sla-ios-xe-oper:rtt-info;
        }

        container measure-stats {
            when "(../oper-type='y1731-delay') or" +
                 "(../oper-type='y1731-loss')" ;
                uses ip-sla-ios-xe-oper:y1731-interval-stats;
        }

        container stats {
            when "(../oper-type!='unknown') and" +
                 "(../oper-type!='y1731-delay') and" +
                 "(../oper-type!='y1731-loss')";

            uses ip-sla-ios-xe-oper:stats;
        }
    }

    typedef sla-oper-type {
        type enumeration {
            enum unknown;
            enum udp-echo;
            enum udp-jitter;
            enum icmp-jitter;
            enum ethernet-jitter;
            enum ethernet-echo;
            enum y1731-delay;
            enum y1731-loss;
            enum video;
            enum mcast;
            enum pong;
            enum path-jitter;
        }
    }

    typedef sla-return-code {
        type enumeration {
            enum unknown;
            enum ok;
            enum disconnected;
            enum busy;
            enum timeout;
            enum no-connection;
            enum internal-error;
            enum operation-failure;
            enum could-not-find; 
        }
    }

    typedef accuracy-type {
        type enumeration {
            enum milliseconds;
            enum microseconds;
        }
    }

    typedef rtt-type {
        type enumeration {
            enum rtt-known;
            enum rtt-unknown;
            enum rtt-could-not-find;
        }
    }

    typedef ttl-type {
        type enumeration {
            enum ttl-finite;
            enum ttl-forever;
        }
    }

    container ip-sla-stats {
        config false;

        description
          "Data nodes for All IP SLA Statistics.";

        list sla-oper-entry {
            key "oper-id";

            description
                "The list of IP SLA operations with statistics info.";

            uses ip-sla-ios-xe-oper:sla-oper-entry;
        }
    }
}
