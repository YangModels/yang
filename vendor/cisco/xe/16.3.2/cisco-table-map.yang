/*---------------------------------------------------------------
 *  cisco-table-map.yang - Tablemap config yang
 * 
 *  April 2015, Xia Wu   
 *                                           
 *  Copyright (c) 2015 by Cisco Systems, Inc.
 *  All rights reserved.                     
 *-------------------------------------------------------------------
 */

module cisco-table-map {
    namespace "urn:cisco:params:xml:ns:yang:table-map";
    prefix tablemap;
    
    import cisco-qos-common {
        prefix qos;
    }
    
    organization "Cisco Systems";
    contact
    "Editor:   Xia Wu
               <mailto:xiaw2@cisco.com>";
    description
    "This module contains YANG definitions for
    configuring table-map
     
    Copyright (c) 2015 by Cisco Systems, Inc.
    All rights reserved.";
    
    revision 2015-05-19 {
        description "first revision";
        reference "ietf-diffserv-action.yang";
    }

    feature table-map-template-support {
        description
            " This feature allows table-map template to be configured";
    }
    
  
    container table-maps {
        if-feature table-map-template-support;
        description "table-map template";
        list table-entry {
            key "table-name";
            description "list of table-map templates";

            leaf table-name {
                type string;
                description "table-map name";
            }       
            
            leaf from-type {
                type qos:match-type;
                description "table-map mapping from type";
            }
            
            leaf to-type {
                type qos:match-type;
                description "table-map mapping to type";
            }
            
            leaf-list from-value {
                type uint8;
                description "value mapped from";
            }
            
            leaf to-value {
                type uint8;
                description "value mapped to";
            }
            
            leaf default-mapping-alg {
                type enumeration {
                    enum fixed;
                    enum copy;
                    enum ignore;
                }
                
                default copy;
                description "deafult mapping algorithm";
        }
            
        choice default-mapping-value {
            when "default-mapping-alg = ''" {
                description "mapping value based on different mapping algorithm";
            }
            case fixed {
                 leaf value {
                       type uint32;
                       description "mapping value";
                   }
            }
                
            case default {
                   leaf default {
                       type empty;
                       description "default mapping";
                   }
            }
            description "napping value";
        }          
        }
    }
}
