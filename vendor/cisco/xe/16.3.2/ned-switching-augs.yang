module ned-switching-augs {
    namespace "http://cisco.com/ns/yang/ned/ios/switching/augs";
    prefix ned-sw-a;

    import tailf-common {
       prefix tailf;
    }
    import ietf-inet-types {
      prefix inet;
    }
    import ned {
       prefix ned;
    }

    organization "Cisco Systems";

    description
       "NED YANG module for IOS
        Copyright (c) 2016 by Cisco Systems, Inc.
        All rights reserved.";

    ////////////////////////////////////////////////////////////////////////////
    // REVISION
    ///////////////////////////////////////////////////////////////////////////
    revision 2016-09-01 {
      description "Added ip dhcp relay";
    }
    revision 2016-04-21 {
       description "Removed policy table-map actions";
    }
    revision 2016-04-20 {
       description "Added type string in vlan-list";
    }
    revision 2016-04-07 {
       description "Added vlan augment";
    }
    revision 2016-04-07 {
       description "Added Copyright";
    }
    revision 2016-02-26 {
       description "Added interface auto-qos and policy table-map actions";
    }

    ////////////////////////////////////////////////////////////////////////////////
    // GROUPING
    ///////////////////////////////////////////////////////////////////////////////
    grouping arp-access-list-mac {
      container mac {
        description "Sender MAC address";
        tailf:cli-compact-syntax;
        list sender-mac-address {
          description "Sender MAC address";
          tailf:cli-drop-node-name;
          tailf:cli-suppress-mode;
          tailf:cli-compact-syntax;
          key mac-address;
          leaf mac-address {
            type string;
          }
          leaf mac-address-mask {
            description
              "Sender MAC address mask";
            tailf:cli-drop-node-name;
            type string;
          }
          leaf log {
            description
              "Log on match";
            type empty;
          }
        }
        container any {
          description
            "Any MAC address";
          presence true;
          leaf log {
            description
              "Log on match";
            type empty;
          }
        }      
        container host {
          description
            "Single Sender host";
          list sender-mac-address {
            tailf:alt-name "host";
            description "Sender MAC address";
            tailf:cli-drop-node-name;
            tailf:cli-suppress-mode;
            tailf:cli-compact-syntax;
            key mac-address;
            leaf mac-address {
              type string;
            }
            leaf log {
              description
                "Log on match";
              type empty;
            }
          }
        }
      }
    }
    grouping arp-access-list-ip-grouping {
      container ip {
        description 
          "Sender IP address";
        tailf:cli-compact-syntax;
        list sender-ip-address {
          description "Sender IP address";
          tailf:cli-drop-node-name;
          tailf:cli-suppress-mode;
          tailf:cli-compact-syntax;
          key ip-address;
          leaf ip-address {
            type string;
          }
          leaf ip-address-mask {
            description "Sender IP wildcard mask";
            tailf:cli-drop-node-name;
            tailf:cli-hide-in-submode;
            type string;
          }
          uses arp-access-list-mac;
        }
        container any {
          description 
            "Any Sender IP address";
          uses arp-access-list-mac;
        }
        container host {
          description 
            "Single Sender host";        
          list ip-address {
            description "Sender IP address";
            tailf:cli-drop-node-name;
            tailf:cli-suppress-mode;
            tailf:cli-compact-syntax;
            key ip-address;
            leaf ip-address {
              type string;
            }
            uses arp-access-list-mac;
          }
        }
      }
    }
    grouping arp-access-list-request-response-grouping {    
      uses arp-access-list-ip-grouping;
      container request {
        description
          "ARP Request";
        uses arp-access-list-ip-grouping;
      }
      container response {
        description
          "ARP Response";
        uses arp-access-list-ip-grouping;
      }
    }
    grouping arp-access-list-config-grouping {
      container permit {
        description "Specify packets to forward";
        tailf:cli-compact-syntax;
        uses arp-access-list-request-response-grouping;
      }
      container deny {
        description "Specify packets to reject";
        uses arp-access-list-request-response-grouping;
      }
    }    
    grouping template-grouping {
      container service-policy {
        description "Configure CPL Service Policy";
        container input {
          description "Assign policy-map to the input of an interface";
          leaf policy-map-name {
            tailf:cli-drop-node-name;
            description "policy-map name";
            type string;
          }
        }
        container output {
          description "Assign policy-map to the output of an interface";
          leaf policy-map-name {
            tailf:cli-drop-node-name;
            description "policy-map name";
            type string;
          }
        }
      }
      container switchport {
        description "Set switching mode characteristics";
        container mode {
          description "Set trunking mode of the interface";
          leaf trunk {
            description "Set trunking mode to TRUNK unconditionally";
            type empty;
          }
          leaf access {
            description "Set trunking mode to ACCESS unconditionally";
            type empty;
          }
        }
        leaf nonegotiate {
          description "Device will not engage in negotiation protocol on this interface";
          type empty;
        }
        container block {
          description "Disable forwarding of unknown uni/multi cast addresses";
          leaf unicast {
            description "Block unknown unicast addresses";
            type empty;
          }
        }
        container port-security {
          description "Security related command";
          presence true;
          container aging {
            description "Port-security aging commands";
            leaf static {
              description "Enable aging for configured secure addresses";
                type empty;
            }
            leaf time {
              description "Port-security aging time";              
              type uint16 {
                range "1..1440";
              }              
            }
            container type {
              description "Port-security aging type";
              presence true;
              leaf inactivity {
                description "Aging based on inactivity time period";
                type empty;
              }
            }
          }
          container maximum {
            description "Max secure addresses";
            list range {
              tailf:cli-drop-node-name;
              tailf:cli-suppress-mode;
              key "range";
              leaf range {
                description "Maximum addresses";
                type uint16 {
                  range "1..3072";
                }
              }
              container vlan {
                description "Max secure addresses per vlan";
                presence true;
                leaf access {
                  description "access vlan";
                  type empty;
                }
              }
            }
          }
          container violation {
            description "Security violation mode";
            leaf restrict {
              description "Security violation restrict mode";
              type empty;
            }
            leaf shutdown {
              description "Security violation shutdown mode";
              type empty;
            }
          }
        }
        container access {
          description "Set access mode characteristics of the interface";
          leaf vlan {
            description "VLAN ID of the VLAN when this port is in access mode";
            type uint16 {
              range "1..4094";
            }
          }
        }
        container voice {
          description "Voice appliance attributes";
          leaf vlan {
            description "Vlan for voice traffic";
            type uint16 {
              range "1..4094";
            }
          }
        }
      }
      container spanning-tree {
        description "Spanning Tree Subsystem";
        presence true;
        container bpduguard {
          description "Don't accept BPDUs on this interface";
          leaf enable {
            description "Enable BPDU guard for this interface";
              type empty;
          }
        }
        leaf service-policy {
          description "help";
          type empty;
        }
        container portfast {
          description "Portfast options for the interface";
          leaf disable {
            description
              "Disable portfast for this interface";
            type empty;
          }
          leaf edge {
            description
              "Enable portfast edge on the interface";
            type empty;
          }
          leaf network {
            description
              "Enable portfast network on the interface";
            type empty;
          }
        }
      }
      container storm-control {
        description "storm configuration";
        container broadcast {
          description "Broadcast address storm control";
          container level {
            description "Set storm suppression level on this interface";
            container pps {
              description "Enter suppression level in packets per second";
              tailf:cli-sequence-commands;
              leaf threshold {              
                description "Enter threshold";
                tailf:cli-drop-node-name;
                type string;
              }           
            }
            container bps {
              description "Enter suppression level in bits per second";
              tailf:cli-sequence-commands;
              leaf threshold {              
                description "Enter threshold";
                tailf:cli-drop-node-name;
                type decimal64 {
                  fraction-digits 1;
                  range "0.0..10000000000.0";
                }
              }
              leaf b-unit{
                tailf:cli-drop-node-name;
                type string;
              }
            }          
            leaf threshold {            
              description "Enter threshold";
              tailf:cli-drop-node-name;
              type decimal64 {
                fraction-digits 2;
                range "0.00..100.00";
              }            
            }
          }
        }
        container action {
          description
            "Action to take for storm-control";
          leaf shutdown {
            description
              "Shutdown this interface if a storm occurs";
            tailf:cli-full-command;
            type empty;
          }
          leaf trap {
            description
              "Send SNMP trap if a storm occurs";
            tailf:cli-full-command;
            type empty;
          }
        }
      }
      leaf load-interval {
        description "Load interval delay in seconds";
        type uint16 {
          range "30..600";
        }
      }
      container ip {
        description "IP template config";
        container dhcp {
          description "DHCP template config";
          container snooping {
            description "DHCP Snooping";
            container limit {
              description "DHCP Snooping limit";
              leaf rate {
                description "DHCP snooping rate limit";
                type uint16 {
                  range "1..2048";
                }
              }
            }
          }
        }
      }
    }
    grouping device-tracking-grouping {
      // interface * / device-tracking
      container device-tracking {
        description 
          "Configure device-tracking on the interface";
        leaf attach-policy {
          description 
            "Apply a policy for feature device-tracking";
          type string;
        }
      }
    }
    // auto qos {trust|video|voip} groupings
    grouping auto-qos-grouping {
      container auto {
        tailf:info "Configure Automation";
        description "Configure Automation";
        container qos {
            tailf:info "Configure AutoQoS";
            description "Configure AutoQoS";
            container classify {
                tailf:info "Configure classification for untrusted devices";
                description "Configure classification for untrusted devices";
                presence true;
                leaf police {
                    tailf:info "Configure QoS policing for untrusted devices";
                    description "Configure QoS policing for untrusted devices";
                    type empty;
                }
            }
            container trust {
                tailf:info "Trust the DSCP/CoS marking";
                description "Trust the DSCP/CoS marking";
                presence true;
                leaf cos {
                    tailf:info "Trust the CoS marking";
                    description "Trust the CoS marking";
                    tailf:cli-full-command;
                    type empty;
                }
                leaf dscp {
                    tailf:info "Trust the DSCP marking";
                    description "Trust the DSCP marking";
                    tailf:cli-full-command;
                    type empty;
                }
            }
            container video {
                tailf:info "Configure AutoQoS for video devices";
                description "Configure AutoQoS for video devices";
                leaf cts {
                    tailf:info "Trust the QoS marking of the Cisco Telepresence System";
                    description "Trust the QoS marking of the Cisco Telepresence System";
                    tailf:cli-full-command;
                    type empty;
                }
                leaf ip-camera {
                    tailf:info "Trust the QoS marking of the Ip Video Surveillance camera";
                    description "Trust the QoS marking of the Ip Video Surveillance camera";
                    tailf:cli-full-command;
                    type empty;
                }
                leaf media-player {
                    tailf:info "Trust the Qos marking of the Cisco Media Player";
                    description "Trust the Qos marking of the Cisco Media Player";
                    tailf:cli-full-command;
                    type empty;
                }
            }
            container voip {
                tailf:info "Configure AutoQoS for VoIP";
                description "Configure AutoQoS for VoIP";
                presence true;
                leaf cisco-phone {
                    tailf:info "Trust the QoS marking of Cisco IP Phone";
                    description "Trust the QoS marking of Cisco IP Phone";
                    tailf:cli-full-command;
                    type empty;
                }
                leaf cisco-softphone {
                    tailf:info "Trust the QoS marking of Cisco IP SoftPhone";
                    description "Trust the QoS marking of Cisco IP SoftPhone";
                    tailf:cli-full-command;
                    type empty;
                }
                leaf trust {
                    tailf:info "Trust the DSCP/CoS marking";
                    description "Trust the DSCP/CoS marking";
                    tailf:cli-full-command;
                    type empty;
                }
            }
        }
      }
    }

    ////////////////////////////////////////////////////////////////////////////////
    // AUGMENT
    ///////////////////////////////////////////////////////////////////////////////
    
    ///=================================================
    /// coap
    ///================================================
    augment /ned:native {
      container coap {
        description "CoAP Global Configuration Commands";
        container http {
          description "CoAP http server";
          leaf enable {
            description "CoAP http server enable";
            type empty;
          }
        }
      }
    }
    
    ///==================================================
    /// energywise
    ///=========================================
    augment /ned:native {
      container energywise {
        description "EnergyWise Global Configuration Commands";
        list domain {
          tailf:cli-suppress-mode;
          description "Set the EnergyWise domain this entity should join";
          key "word";
          leaf word {
            tailf:cli-drop-node-name;
            type string;
          }
          container security {
            description "Set security parameters for this EnergyWise domain";
            container shared-secret {
              description "Set the shared secret for this EnergyWise domain";
              list zero {
                tailf:cli-suppress-mode;
                tailf:alt-name "0";
                description "Specifies an UNENCRYPTED shared secret for the domain will follow";
                key "word";
                leaf word {
                  tailf:cli-drop-node-name;
                  type string;
                }
               container protocol {
                 description "Specify a communication protocol to use to communicate with the EnergyWise domain";
                 container udp {
                   description "UDP protocol";
                   tailf:cli-sequence-commands;
                   tailf:cli-compact-syntax;
                   leaf port {
                     description "Specify a port number to use to communicate with the EnergyWise domain";
                     type uint16 {
                      range "1..65000";
                     } 
                   }
                   leaf ip {
                     description "Specify an ipaddress to use to communicate with the EnergyWise domain";
                     type inet:ipv4-address;
                   }
                 }
               }
              }
            }
          }
        }
      }
    }

    augment /ned:native/ned:interface/ned:FastEthernet {
      uses auto-qos-grouping;
      uses device-tracking-grouping;
    }
    augment /ned:native/ned:interface/ned:GigabitEthernet {
      uses auto-qos-grouping;
      uses device-tracking-grouping;
    }
    augment /ned:native/ned:interface/ned:TenGigabitEthernet {
      uses auto-qos-grouping;
      uses device-tracking-grouping;
    }
    augment /ned:native/ned:interface/ned:Port-channel {
      uses auto-qos-grouping;
    }
    augment /ned:native/ned:interface/ned:Port-channel-subinterface/ned:Port-channel {
      uses auto-qos-grouping;
    }
    augment /ned:native {
      container template {
        description "Select a template to configure";
        container IP_CAMERA_INTERFACE_TEMPLATE {
          description "built-in modified";
          tailf:cli-add-mode;
          tailf:cli-mode-name "config-template";          
          uses template-grouping;       
        }
        container LAP_INTERFACE_TEMPLATE {
          description "built-in modified";
          tailf:cli-add-mode;
          tailf:cli-mode-name "config-template";          
          uses template-grouping;
        }
        container AP_INTERFACE_TEMPLATE {
          description "built-in modified";
          tailf:cli-add-mode;
          tailf:cli-mode-name "config-template";          
          uses template-grouping;
        }
        container DMP_INTERFACE_TEMPLATE {
          description "built-in modified";
          tailf:cli-add-mode;
          tailf:cli-mode-name "config-template";
          uses template-grouping;
        }
        container IP_PHONE_INTERFACE_TEMPLATE {
          description "built-in modified";
          tailf:cli-add-mode;
          tailf:cli-mode-name "config-template";
          uses template-grouping;          
        }
        container MSP_CAMERA_INTERFACE_TEMPLATE {
          description "built-in modified";
          tailf:cli-add-mode;
          tailf:cli-mode-name "config-template";
          uses template-grouping;
        }
        container MSP_VC_INTERFACE_TEMPLATE {
          description "built-in modified";
          tailf:cli-add-mode;
          tailf:cli-mode-name "config-template";
          uses template-grouping;
        }
        container PRINTER_INTERFACE_TEMPLATE {
          description "built-in modified";
          tailf:cli-add-mode;
          tailf:cli-mode-name "config-template";
          uses template-grouping;
        }
        container ROUTER_INTERFACE_TEMPLATE {
          description "built-in modified";
          tailf:cli-add-mode;
          tailf:cli-mode-name "config-template";
          uses template-grouping;
        }
        container SWITCH_INTERFACE_TEMPLATE {
          description "built-in modified";
          tailf:cli-add-mode;
          tailf:cli-mode-name "config-template";
          uses template-grouping;
        }
        container TP_INTERFACE_TEMPLATE {
          description "built-in modified";
          tailf:cli-add-mode;
          tailf:cli-mode-name "config-template";          
          uses template-grouping;
        }
      }
    }
    augment /ned:native {
      list service-template {
        description "Configure a service-template/identity policy";
        key "word";
        leaf word {
          tailf:cli-drop-node-name;
          type string;
        }
        container inactivity-timer{
          description "Inactivity timeout value in seconds";
          tailf:cli-sequence-commands;
          tailf:cli-compact-syntax;
          leaf value {
            description "Enter a value between 1 and 65535";
            tailf:cli-drop-node-name;
            type uint16{
              range "1..65535";
            }
          }
          leaf probe{
            description "ARP probe";
            type empty;
          }
        }
        leaf vlan {
          description "Vlan to be applied";
          type uint16{          
            range "1..4094";
          }
        }
        container linksec {
          description "Configure link security parameters";
          leaf policy{
            description "Set the link security policy";
            type enumeration {
              enum "must-not-secure";
              enum "must-secure";
              enum "should-secure";
            }
          }
        }
        container voice {
          description 
            "Voice feature";
          leaf vlan {
            description 
              "Critical voice vlan";
            type empty;
          }
        }
      }
    } 
    augment /ned:native {
      container arp {
        description "Set a static ARP entry";
        list access-list {
          description "Named access-list";
          key name;
          leaf name {
            type string;
          }
          uses arp-access-list-config-grouping;
          container default {
            description "Set a command to its defaults";
            uses arp-access-list-config-grouping; 
          }
          container no {
            description "Negate a command or set its defaults";
            uses arp-access-list-config-grouping;
          }
        }
      }
    }
    augment /ned:native/ned:ip/ned:igmp/ned:snooping {
      container vlan {
        tailf:info "IGMP Snooping enable for Catalyst VLAN";
        description "IGMP Snooping enable for Catalyst VLAN";
        list range {
          tailf:cli-drop-node-name;
          tailf:cli-suppress-mode;
          key "range";
          leaf range {
            tailf:info "Vlan number";
            description "Vlan number";
            type uint16 {
              range "1..1001 | 1006..4094";
            }
          }
          leaf immediate-leave {
            tailf:info "Enable IGMPv2 immediate leave processing";
            description "Enable IGMPv2 immediate leave processing";
            type empty;
          }
          leaf last-member-query-count {
            tailf:info "Last member query count";
            description "Interval (milliseconds)";
            type uint8 {
              range "1..7";
            }
          }
          leaf last-member-query-interval {
            tailf:info "Last member query interval";
            description "Interval (milliseconds)";
            type uint16 {
              range "100..32767";
            }
          }
          container mrouter {
            tailf:info "Configure an L2 port as a multicast router port";
            description "Configure an L2 port as a multicast router port";
            leaf interface {
              tailf:info "next-hop interface to mrouter";
              description "GigabitEthernet IEEE 802.3z";
              type string;
            }
            container learn {
              tailf:info "Set the multicast router learning method";
              description "Set the multicast router learning method";
              leaf cgmp {
                tailf:info "Learn the multicast router snooping CGMP packets";
                description "Learn the multicast router snooping CGMP packets";
                type empty;
              }
              leaf pim-dvmrp {
                tailf:info "Learn the multicast router snooping PIM-DVMRP packets";
                description "Learn the multicast router snooping PIM-DVMRP packets";
                type empty;
              }
            }
          }
          container querier {
            tailf:info "Enable IGMP querier for this Vlan";
            description "Enable IGMP querier for this Vlan";
            presence true;
            leaf address {
              tailf:info "IGMP querier source IP address";
              description "IGMP querier source IP address";
              type inet:ipv4-address;
            }
            leaf max-response-time {
              tailf:info "IGMP querier maximum response time (sec)";
              description "IGMP querier maximum response time (sec)";
              type uint8 {
                range "1..25";
              }
            }
            leaf query-interval {
              tailf:info "IGMP querier query interval (sec)";
              description "IGMP querier query interval (sec)";
              type uint16 {
                range "1..18000";
              }
            }
            container tcn {
              tailf:info "IGMP querier TCN related parameters";
              description "IGMP querier TCN related parameters";
              container query {
                tailf:info "IGMP querier TCN query related parameters";
                description "IGMP querier TCN query related parameters";
                leaf count {
                  tailf:info "IGMP querier TCN query count";
                  description "IGMP querier TCN query count";
                  type uint8 {
                    range "1..10";
                  }
                }
                leaf interval {
                  tailf:info "IGMP querier TCN query interval (sec)";
                  description "IGMP querier TCN query interval (sec)";
                  type uint8 {
                    range "1..255";
                  }
                }
              }
            }
            container timer {
              tailf:info "IGMP other querier timer";
              description "IGMP other querier timer";
              leaf expiry {
                tailf:info "IGMP querier other querier time out (sec)";
                description "IGMP querier other querier time out (sec)";
                type uint16 {
                  range "60..300";
                }
              }
            }
            leaf version {
              tailf:info "IGMP version";
              description "IGMP version";
              type uint8 {
                range "1..2";
              }
            }
          }
          leaf robustness-variable {
            tailf:info "IGMP snooping vlan robustness variable";
            description "Robustness variable";
            type uint8 {
              range "1..3";
            }
          }
          container static {
            tailf:info "Configure an L2 port as a member of a group";
            description "Configure an L2 port as a member of a group";
            list ipv4 {
              tailf:cli-drop-node-name;
              tailf:cli-suppress-mode;
              key "ipv4";
              leaf ipv4 {
                tailf:info "IP address of the group";
                description "IP address of the group";
                type inet:ipv4-address;
              }
              leaf interface {
                tailf:info "Specify an interface statically configured";
                description "GigabitEthernet IEEE 802.3z";
                type string;
              }
            }
          }
        }
      }
    }
    augment /ned:native/ned:vlan {
      leaf vlan-id {
        description "ISL VLAN IDs 1-4094";
        tailf:cli-drop-node-name;
        type string;
      }
      //vlan configuration
      leaf configuration {
        tailf:info "vlan feature configuration mode";
        description "VLAN ID List Eg. 1-10,15";
        type string {
	  pattern "([0-9]{1,4}(-[0-9]{1,4})?(,[0-9]{1,4}(-[0-9]{1,4})?)*)";
	}
      }
      // vlan access-map
      list access-map {
        tailf:info "Create vlan access-map or enter vlan access-map command mode";
        description "Create vlan access-map or enter vlan access-map command mode";
        tailf:cli-mode-name "config-access-map";
        key "map_tag";
        leaf map_tag {
          tailf:info "Vlan access map tag";
          description "Vlan access map tag";
          type string;
        }
        container action {
          tailf:info "Take the action";
          description "Take the action";
          leaf drop {
            tailf:info "Drop packets";
            description "Drop packets";
            type empty;
          }
          leaf forward {
            tailf:info "Forward packets";
            description "Forward packets";
            type empty;
          }
        }
        container match {
          tailf:info "Match values.";
          description "Match values.";
          container ip {
            tailf:info "IP based match";
            description "IP based match";
            leaf-list address {
              tailf:info "Match IP address to access control.";
              description "Match IP address to access control.";
              tailf:cli-flat-list-syntax;
              type ned:exp-acl-type;
            }
          }
          container ipv6 {
            tailf:info "IPv6 based match";
            description "IPv6 based match";
            leaf-list address {
              tailf:info "Match IPv6 address to access control.";
              description "Match IPv6 address to access control.";
              tailf:cli-flat-list-syntax;
              type string;
            }
          }
          container mac {
            tailf:info "MAC based match";
            description "MAC based match";
            leaf-list address {
              tailf:info "Match MAC address to access control.";
              description "Match MAC address to access control.";
              tailf:cli-flat-list-syntax;
              type string;
            }
          }
        } 
      }
      //vlan filter
      container filter {
        tailf:info "Apply a VLAN Map";
        description  "Apply a VLAN Map";
        tailf:cli-compact-syntax;
        tailf:cli-sequence-commands;
        leaf map-name {
          tailf:cli-drop-node-name;
          tailf:info "VLAN map name";
          description "VLAN map name";
          type string {
            tailf:info "WORD;;VLAN map name";
          }
        }
        leaf-list vlan-list {
          tailf:info "VLANs to apply filter to";
          description "VLANs to apply filter to";
          tailf:cli-range-list-syntax;
          type union {
            type uint16 {
              tailf:info "<1-4094>;;VLAN id";
              range "1..4094";
            }
            type string;
            type enumeration {
              enum all {
                tailf:info "Add this filter to all VLANs";
              }
            } 
          }
        }
      }

      // vlan group
      list group {
        tailf:info "Create a vlan group";
        description "Create a vlan group";
        tailf:cli-suppress-mode;
        key "group_name";
        leaf group_name {
          tailf:info "Group name starts with alphabet";
          description "Group name starts with alphabet";
          type string;
        }
        leaf-list vlan-list {
          tailf:info "List of vlans in this group";
          description "List of vlans in this group";
          tailf:cli-range-list-syntax;
          type union {
            type uint16 {
              tailf:info "<1-4094>;;VLAN id";
              range "1..4094";
            }
            type string;
          }
        }
      }
    }
}
