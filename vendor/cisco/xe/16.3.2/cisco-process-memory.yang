module cisco-process-memory {

     yang-version 1;

     namespace "urn:cisco:params:xml:ns:yang:cisco-process-memory";
     prefix pmemory;


     organization
        "Cisco Systems, Inc.";

    contact
        " Cisco Systems, Inc.
          Customer Service

          Postal: 170 W Tasman Drive
          San Jose, CA 95134

          Tel: +1 1800 553-NETS

          E-mail: cs-yang@cisco.com";
    
    description
        " This module contains a collection of YANG definitions for
          monitoring memory usage of processes in a Network Element.";
    
    reference "TODO";

    revision 2015-04-09 {
        description "Proposed";
    }

    container process-memory-usage {
        config false;
        description
            "Data nodes for System wide Process Memory Statistics.";

        list process {
            key "pid name";

            description
                "The list of software processes on the device.";

            leaf pid {
                type uint32;
                description
                  "Process-ID of the process.";
            }

            leaf name {
                type string;
                description
                    "The name of the process.";
            }

            leaf tty {
                type uint16;
                description
                    "TTY bound to by the process.";
            }

            leaf allocated-memory {
                type uint64;
                units "bytes";
                description "Total memory allocated to this process (bytes)";
            }

            leaf freed-memory {
                type uint64;
                units "bytes";
                description "Total memory freed by this process (bytes)";
            }

            leaf holding-memory {
                type uint64;
                units "bytes";
                description "Total memory currently held by this process (bytes)";
            }

            leaf get-buffers {
                type uint32;
                description "Get Buffers of this process (bytes)";
            }

            leaf ret-buffers {
                type uint32;
                description "Return Buffers of this process (bytes)";
            }
        }
    }

}
