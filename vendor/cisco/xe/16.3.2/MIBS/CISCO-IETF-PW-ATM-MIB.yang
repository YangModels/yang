/*
 * Generated by confdc --mib2yang-std
 * Source: mgmt/dmi/model/common/mib-source/CISCO-IETF-PW-ATM-MIB.mib
 */
/*
 * This YANG module has been generated by smidump 0.5.0:
 *
 *      smidump -f yang CISCO-IETF-PW-ATM-MIB
 *
 * Do not edit. Edit the source file instead!
 */

module CISCO-IETF-PW-ATM-MIB {

  namespace "urn:ietf:params:xml:ns:yang:smiv2:CISCO-IETF-PW-ATM-MIB";
  prefix CISCO-IETF-PW-ATM-MIB;

  import ATM-TC-MIB {
    prefix "atm-tc";
  }

  import CISCO-IETF-PW-MIB {
    prefix "cisco-ietf";
  }

  import IF-MIB {
    prefix "if-mib";
  }

  import SNMPv2-TC {
    prefix "snmpv2-tc";
  }

  import ietf-yang-smiv2 {
    prefix "smiv2";
  }

  import ietf-yang-types {
    prefix "yang";
  }

  organization
   "Cisco Systems, Inc";

  contact
   "Cisco Systems
    Customer Service
    
    Postal: 170 W Tasman Drive
    San Jose, CA 95134
    USA
    
    Tel:    +1 800 553-NETS
    Email:  cs-atm@cisco.com";

  description
   "This MIB contains managed object definitions for Pseudo Wire
    emulation of ATM over Packet Switched Networks(PSN).
    
    This MIB reports to the PW-MIB. The PW-MIB contains
    structures and MIB associations generic to Pseudo-Wire
    Virtual Circuit (VC) emulation. VC-specific MIBs (such as
    this) contain config and stats for specific VC types.";

  revision 2005-04-19 {
    description
     "Updated Mib police review comments";
  }

  revision 2003-02-16 {
    description
     "Initial Version";
  }


  container CISCO-IETF-PW-ATM-MIB {
    config false;

    container cpwVcAtmTable {
      description
       "This table specifies the information for an ATM interface, VC,
        VP to be carried over PSN.";
      smiv2:oid "1.3.6.1.4.1.9.10.9000.1.1";

      list cpwVcAtmEntry {
        key "cpwVcIndex";
        description
         "A row in this table represents an ATM interface, VC, VP
          that needs to be adapted and carried over PSN. This table
          is indexed by CpwVcIndex in CISCO-IETF-PW-MIB.";
        smiv2:oid "1.3.6.1.4.1.9.10.9000.1.1.1";

        leaf cpwVcIndex {
          type leafref {
            path "/cisco-ietf:CISCO-IETF-PW-MIB/cisco-ietf:cpwVcTable/cisco-ietf:cpwVcEntry/cisco-ietf:cpwVcIndex";
          }
        }

        leaf cpwAtmIf {
          type if-mib:InterfaceIndex;
          description
           "The ATM Interface that receives cells from the ATM network.";
          smiv2:max-access "read-write";
          smiv2:oid "1.3.6.1.4.1.9.10.9000.1.1.1.1";
        }

        leaf cpwAtmVpi {
          type atm-tc:AtmVpIdentifier;
          description
           "VPI value of this ATM VC.";
          smiv2:max-access "read-write";
          smiv2:oid "1.3.6.1.4.1.9.10.9000.1.1.1.2";
        }

        leaf cpwAtmVci {
          type atm-tc:AtmVcIdentifier;
          description
           "VCI value of this ATM VC.";
          smiv2:max-access "read-write";
          smiv2:oid "1.3.6.1.4.1.9.10.9000.1.1.1.3";
        }

        leaf cpwAtmClpQosMapping {
          type boolean;
          description
           "This Object indicates whether the CLP bits are considered when
            determining the value placed in the Quality of Service fields
            (e.g. EXP fields of the MPLS Label Stack) of the encapsulating
            protocol.";
          smiv2:max-access "read-write";
          smiv2:oid "1.3.6.1.4.1.9.10.9000.1.1.1.4";
        }

        leaf cpwAtmRowStatus {
          type snmpv2-tc:RowStatus;
          description
           "This Object is used to create, modify or delete a row in this
            table.";
          smiv2:max-access "read-write";
          smiv2:oid "1.3.6.1.4.1.9.10.9000.1.1.1.5";
        }

        leaf cpwAtmOamCellSupported {
          type boolean;
          description
           "This Object indicates whether OAM Cells are transported on this
            VC.";
          smiv2:max-access "read-write";
          smiv2:oid "1.3.6.1.4.1.9.10.9000.1.1.1.6";
        }

        leaf cpwAtmQosScalingFactor {
          type int32;
          description
           "This Object represents the scaling factor (% value) to be
            applied to ATM QoS rates when calculating QoS rates for the
            PSN domain . For example, in the cell transport mode the
            bandwidth needed in the PSN domain will be higher (since PSN
            Transport header, PW header, and optional control word have
            to transmitted with every cell), whereas in the AAL5 mode
            the bandwidth needed in PSN domain will be less since cell
            headers will be removed after reassembly.";
          smiv2:defval "100";
          smiv2:max-access "read-write";
          smiv2:oid "1.3.6.1.4.1.9.10.9000.1.1.1.7";
        }

        leaf cpwAtmCellPacking {
          type boolean;
          description
           "This object is used to identify if the VC is configured to do
            Cell Packing.";
          smiv2:max-access "read-write";
          smiv2:oid "1.3.6.1.4.1.9.10.9000.1.1.1.8";
        }

        leaf cpwAtmMncp {
          type int32;
          description
           "This object indicates the maximum number of cells that get
            packed in one packet.";
          smiv2:max-access "read-write";
          smiv2:oid "1.3.6.1.4.1.9.10.9000.1.1.1.9";
        }

        leaf cpwAtmPeerMncp {
          type int32;
          description
           "This Object represents the maximum number of cell
            that can be packed in one packet for peer interface.";
          smiv2:max-access "read-only";
          smiv2:oid "1.3.6.1.4.1.9.10.9000.1.1.1.10";
        }

        leaf cpwAtmEncap {
          type enumeration {
            enum "mpls" {
              value "1";
            }
            enum "l2tpv3" {
              value "2";
            }
            enum "unknown" {
              value "3";
            }
          }
          description
           "This object indicates if the packet going on the pseudowire
            is mpls or l2tpv3 encapsulated.";
          smiv2:max-access "read-write";
          smiv2:oid "1.3.6.1.4.1.9.10.9000.1.1.1.11";
        }

        leaf cpwAtmMcptTimeout {
          type int32;
          description
           "This Object represents which MCPT timeout value.";
          smiv2:max-access "read-write";
          smiv2:oid "1.3.6.1.4.1.9.10.9000.1.1.1.12";
        }
      }
    }
  }

  smiv2:alias "cpwVcAtmPerfTable" {
    description
     "This table specifies performance-related attributes
      for an ATM vc, vp and the interface.";
    smiv2:oid "1.3.6.1.4.1.9.10.9000.1.2";
  }

  smiv2:alias "cpwVcAtmPerfEntry" {
    description
     "A row in this table represents an ATM interface, VC, VP
      that needs to be adapted and carried over PSN. This table 
      is indexed by CpwVcIndex in CISCO-IETF-PW-MIB.";
    smiv2:oid "1.3.6.1.4.1.9.10.9000.1.2.1";
  }

  augment "/CISCO-IETF-PW-ATM-MIB:CISCO-IETF-PW-ATM-MIB/CISCO-IETF-PW-ATM-MIB:cpwVcAtmTable/CISCO-IETF-PW-ATM-MIB:cpwVcAtmEntry" {
    description
     "A row in this table represents an ATM interface, VC, VP
      that needs to be adapted and carried over PSN. This table 
      is indexed by CpwVcIndex in CISCO-IETF-PW-MIB.";
    smiv2:oid "1.3.6.1.4.1.9.10.9000.1.2.1";

    leaf cpwAtmCellsReceived {
      type yang:counter32;
      description
       "This object can be used to obtain the information on the
        number of cells that were received and sent to the PSN.";
      smiv2:max-access "read-only";
      smiv2:oid "1.3.6.1.4.1.9.10.9000.1.2.1.1";
    }

    leaf cpwAtmCellsSent {
      type yang:counter32;
      description
       "This object can be used to obtain the information on the
        number of cells that were received from the PSN and sent
        over the ATM network.";
      smiv2:max-access "read-only";
      smiv2:oid "1.3.6.1.4.1.9.10.9000.1.2.1.2";
    }

    leaf cpwAtmCellsRejected {
      type yang:counter32;
      description
       "This Object indicates the number of cells that were rejected by
        this VC because of policing.";
      smiv2:max-access "read-only";
      smiv2:oid "1.3.6.1.4.1.9.10.9000.1.2.1.3";
    }

    leaf cpwAtmCellsTagged {
      type yang:counter32;
      description
       "This Object indicates the number of cells that were Tagged.";
      smiv2:max-access "read-only";
      smiv2:oid "1.3.6.1.4.1.9.10.9000.1.2.1.4";
    }

    leaf cpwAtmHCCellsReceived {
      type yang:counter64;
      description
       "High Capacity counter for the number of cells that were
        received by this VC.";
      smiv2:max-access "read-only";
      smiv2:oid "1.3.6.1.4.1.9.10.9000.1.2.1.5";
    }

    leaf cpwAtmHCCellsRejected {
      type yang:counter64;
      description
       "High Capacity counter for the number of cells that were
        rejected by this VC because of policing.";
      smiv2:max-access "read-only";
      smiv2:oid "1.3.6.1.4.1.9.10.9000.1.2.1.6";
    }

    leaf cpwAtmHCCellsTagged {
      type yang:counter64;
      description
       "High Capacity counter for the number of cells that were tagged";
      smiv2:max-access "read-only";
      smiv2:oid "1.3.6.1.4.1.9.10.9000.1.2.1.7";
    }

    leaf cpwAtmAvgCellsPacked {
      type yang:counter32;
      description
       "It indicates the Average number of cells that
        were received in one packet.";
      smiv2:max-access "read-only";
      smiv2:oid "1.3.6.1.4.1.9.10.9000.1.2.1.8";
    }

    leaf cpwAtmPktsReceived {
      type yang:counter32;
      description
       "This object can be used to obtain the information on the
        number of packets that were received and sent to the PSN.";
      smiv2:max-access "read-only";
      smiv2:oid "1.3.6.1.4.1.9.10.9000.1.2.1.9";
    }

    leaf cpwAtmPktsSent {
      type yang:counter32;
      description
       "This object indicates the number of packets that were sent
        to the atm network.";
      smiv2:max-access "read-only";
      smiv2:oid "1.3.6.1.4.1.9.10.9000.1.2.1.10";
    }

    leaf cpwAtmPktsRejected {
      type yang:counter32;
      description
       "This object indicates the number of packets that were rejected
        because of Policing.";
      smiv2:max-access "read-only";
      smiv2:oid "1.3.6.1.4.1.9.10.9000.1.2.1.11";
    }
  }

  smiv2:alias "cpwVcAtmMIB" {
    smiv2:oid "1.3.6.1.4.1.9.10.9000";
  }

  smiv2:alias "cpwVcAtmNotifications" {
    smiv2:oid "1.3.6.1.4.1.9.10.9000.0";
  }

  smiv2:alias "cpwVcAtmObjects" {
    smiv2:oid "1.3.6.1.4.1.9.10.9000.1";
  }

  smiv2:alias "cpwVcAtmConformance" {
    smiv2:oid "1.3.6.1.4.1.9.10.9000.2";
  }

  smiv2:alias "cpwVcAtmGroups" {
    smiv2:oid "1.3.6.1.4.1.9.10.9000.2.1";
  }

  smiv2:alias "cpwVcAtmCompliances" {
    smiv2:oid "1.3.6.1.4.1.9.10.9000.2.2";
  }

}
