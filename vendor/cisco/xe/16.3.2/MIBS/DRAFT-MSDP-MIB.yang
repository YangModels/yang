/*
 * Generated by confdc --mib2yang-std
 * Source: mgmt/dmi/model/common/mib-source/DRAFT-MSDP-MIB.mib
 */
/*
 * This YANG module has been generated by smidump 0.5.0:
 *
 *      smidump -f yang DRAFT-MSDP-MIB
 *
 * Do not edit. Edit the source file instead!
 */

module DRAFT-MSDP-MIB {

  namespace "urn:ietf:params:xml:ns:yang:smiv2:DRAFT-MSDP-MIB";
  prefix DRAFT-MSDP-MIB;

  import SNMPv2-TC {
    prefix "snmpv2-tc";
  }

  import ietf-inet-types {
    prefix "inet";
  }

  import ietf-yang-smiv2 {
    prefix "smiv2";
  }

  import ietf-yang-types {
    prefix "yang";
  }

  organization
   "IETF MSDP Working Group";

  contact
   " Bill Fenner
    75 Willow Road
    Menlo Park, CA  94025
    Phone: +1 650 867 6073
    E-mail: fenner@research.att.com
    
    Dave Thaler
    One Microsoft Way
    Redmond, WA  98052
    Phone: +1 425 703 8835
    Email: dthaler@microsoft.com";

  description
   "An experimental MIB module for MSDP Management.";

  revision 1999-12-16 {
    description
     "[Revision added by libsmi due to a LAST-UPDATED clause.]";
  }


  container DRAFT-MSDP-MIB {
    config false;

    container msdp {
      smiv2:oid "1.3.6.1.3.92.1.1";

      leaf msdpEnabled {
        type boolean;
        description
         "The state of MSDP on this MSDP speaker - globally
          enabled or disabled.";
        smiv2:max-access "read-write";
        smiv2:oid "1.3.6.1.3.92.1.1.1";
      }

      leaf msdpCacheLifetime {
        type yang:timeticks;
        description
         "The lifetime given to SA cache entries when created
          or refreshed.  A value of 0 means no SA caching is
          done by this MSDP speaker.";
        smiv2:max-access "read-write";
        smiv2:oid "1.3.6.1.3.92.1.1.2";
      }

      leaf msdpNumSACacheEntries {
        type yang:gauge32;
        description
         "The total number of entries in the SA Cache table.";
        smiv2:max-access "read-only";
        smiv2:oid "1.3.6.1.3.92.1.1.3";
      }

      leaf msdpSAHoldDownPeriod {
        type int32 {
          range "1..2147483647";
        }
        units "seconds";
        description
         "The number of seconds in the MSDP SA Hold-down
          period";
        smiv2:defval "90";
        smiv2:max-access "read-only";
        smiv2:oid "1.3.6.1.3.92.1.1.9";
      }
    }

    container msdpRequestsTable {
      description
       "The (conceptual) table listing group ranges and MSDP
        peers used when deciding where to send an SA Request
        message when required.  If SA Caching is enabled, this
        table may be empty.";
      smiv2:oid "1.3.6.1.3.92.1.1.4";

      list msdpRequestsEntry {
        key "msdpRequestsGroupAddress msdpRequestsGroupMask";
        description
         "An entry (conceptual row) representing a group range
          used when deciding where to send an SA Request
          message.";
        smiv2:oid "1.3.6.1.3.92.1.1.4.1";

        leaf msdpRequestsGroupAddress {
          type inet:ipv4-address;
          description
           "The group address that, when combined with the mask
            in this entry, represents the group range for which
            this peer will service MSDP SA Requests.";
          smiv2:max-access "not-accessible";
          smiv2:oid "1.3.6.1.3.92.1.1.4.1.1";
        }

        leaf msdpRequestsGroupMask {
          type inet:ipv4-address;
          description
           "The mask that, when combined with the group address
            in this entry, represents the group range for which
            this peer will service MSDP SA Requests.";
          smiv2:max-access "not-accessible";
          smiv2:oid "1.3.6.1.3.92.1.1.4.1.2";
        }

        leaf msdpRequestsPeer {
          type inet:ipv4-address;
          description
           "The peer to which MSDP SA Requests for groups
            matching this entry's group range will be sent.  Must
            match the INDEX of a row in the msdpPeerTable.";
          smiv2:max-access "read-write";
          smiv2:oid "1.3.6.1.3.92.1.1.4.1.3";
        }

        leaf msdpRequestsStatus {
          type snmpv2-tc:RowStatus;
          description
           "The status of this row, by which new rows may be
            added to the table.";
          smiv2:max-access "read-write";
          smiv2:oid "1.3.6.1.3.92.1.1.4.1.4";
        }
      }
    }

    container msdpPeerTable {
      description
       "The (conceptual) table listing the MSDP speaker's
        peers.";
      smiv2:oid "1.3.6.1.3.92.1.1.5";

      list msdpPeerEntry {
        key "msdpPeerRemoteAddress";
        description
         "An entry (conceptual row) representing an MSDP peer.";
        smiv2:oid "1.3.6.1.3.92.1.1.5.1";

        leaf msdpPeerRemoteAddress {
          type inet:ipv4-address;
          description
           "The address of the remote MSDP peer.";
          smiv2:max-access "not-accessible";
          smiv2:oid "1.3.6.1.3.92.1.1.5.1.1";
        }

        leaf msdpPeerState {
          type enumeration {
            enum "inactive" {
              value "1";
            }
            enum "listen" {
              value "2";
            }
            enum "connecting" {
              value "3";
            }
            enum "established" {
              value "4";
            }
            enum "disabled" {
              value "5";
            }
          }
          description
           "The state of the MSDP TCP connection with this peer.";
          smiv2:max-access "read-only";
          smiv2:oid "1.3.6.1.3.92.1.1.5.1.3";
        }

        leaf msdpPeerRPFFailures {
          type yang:counter32;
          description
           "The number of RPF failures on SA messages received
            from this peer.";
          smiv2:max-access "read-only";
          smiv2:oid "1.3.6.1.3.92.1.1.5.1.4";
        }

        leaf msdpPeerInSAs {
          type yang:counter32;
          description
           "The number of MSDP SA messages received on this
            connection.  This object should be initialized to zero
            when the connection is established.";
          smiv2:max-access "read-only";
          smiv2:oid "1.3.6.1.3.92.1.1.5.1.5";
        }

        leaf msdpPeerOutSAs {
          type yang:counter32;
          description
           "The number of MSDP SA messages transmitted on this
            connection.  This object should be initialized to zero
            when the connection is established.";
          smiv2:max-access "read-only";
          smiv2:oid "1.3.6.1.3.92.1.1.5.1.6";
        }

        leaf msdpPeerInSARequests {
          type yang:counter32;
          description
           "The number of MSDP SA-Request messages received on
            this connection.  This object should be initialized to
            zero when the connection is established.";
          smiv2:max-access "read-only";
          smiv2:oid "1.3.6.1.3.92.1.1.5.1.7";
        }

        leaf msdpPeerOutSARequests {
          type yang:counter32;
          description
           "The number of MSDP SA-Request messages transmitted on
            this connection.  This object should be initialized to
            zero when the connection is established.";
          smiv2:max-access "read-only";
          smiv2:oid "1.3.6.1.3.92.1.1.5.1.8";
        }

        leaf msdpPeerInSAResponses {
          type yang:counter32;
          description
           "The number of MSDP SA-Response messages received on
            this connection.  This object should be initialized to
            zero when the connection is established.";
          smiv2:max-access "read-only";
          smiv2:oid "1.3.6.1.3.92.1.1.5.1.9";
        }

        leaf msdpPeerOutSAResponses {
          type yang:counter32;
          description
           "The number of MSDP SA Response messages transmitted
            on this TCP connection.  This object should be
            initialized to zero when the connection is
            established.";
          smiv2:max-access "read-only";
          smiv2:oid "1.3.6.1.3.92.1.1.5.1.10";
        }

        leaf msdpPeerInControlMessages {
          type yang:counter32;
          description
           "The total number of MSDP messages received on this
            TCP connection.  This object should be initialized to
            zero when the connection is established.";
          smiv2:max-access "read-only";
          smiv2:oid "1.3.6.1.3.92.1.1.5.1.11";
        }

        leaf msdpPeerOutControlMessages {
          type yang:counter32;
          description
           "The total number of MSDP messages transmitted on this
            TCP connection.  This object should be initialized to
            zero when the connection is established.";
          smiv2:max-access "read-only";
          smiv2:oid "1.3.6.1.3.92.1.1.5.1.12";
        }

        leaf msdpPeerInDataPackets {
          type yang:counter32;
          description
           "The total number of encapsulated data packets
            received from this peer.  This object should be
            initialized to zero when the connection is
            established.";
          smiv2:max-access "read-only";
          smiv2:oid "1.3.6.1.3.92.1.1.5.1.13";
        }

        leaf msdpPeerOutDataPackets {
          type yang:counter32;
          description
           "The total number of encapsulated data packets sent to
            this peer.  This object should be initialized to zero
            when the connection is established.";
          smiv2:max-access "read-only";
          smiv2:oid "1.3.6.1.3.92.1.1.5.1.14";
        }

        leaf msdpPeerFsmEstablishedTransitions {
          type yang:counter32;
          description
           "The total number of times the MSDP FSM transitioned
            into the established state.";
          smiv2:max-access "read-only";
          smiv2:oid "1.3.6.1.3.92.1.1.5.1.15";
        }

        leaf msdpPeerFsmEstablishedTime {
          type yang:gauge32;
          units "seconds";
          description
           "This timer indicates how long (in seconds) this peer
            has been in the Established state or how long since
            this peer was last in the Established state.  It is
            set to zero when a new peer is configured or the MSDP
            speaker is booted.";
          smiv2:max-access "read-only";
          smiv2:oid "1.3.6.1.3.92.1.1.5.1.16";
        }

        leaf msdpPeerInMessageElapsedTime {
          type yang:gauge32;
          units "seconds";
          description
           "Elapsed time in seconds since the last MSDP message
            was received from the peer.  Each time
            msdpPeerInControlMessages is incremented, the value of
            this object is set to zero (0).";
          smiv2:max-access "read-only";
          smiv2:oid "1.3.6.1.3.92.1.1.5.1.17";
        }

        leaf msdpPeerLocalAddress {
          type inet:ipv4-address;
          description
           "The local IP address of this entry's MSDP
            connection.";
          smiv2:max-access "read-write";
          smiv2:oid "1.3.6.1.3.92.1.1.5.1.18";
        }

        leaf msdpPeerSAAdvPeriod {
          type int32 {
            range "1..2147483647";
          }
          units "seconds";
          description
           "Time interval in seconds for the
            MinSAAdvertisementInterval MSDP timer.";
          smiv2:defval "60";
          smiv2:max-access "read-write";
          smiv2:oid "1.3.6.1.3.92.1.1.5.1.19";
        }

        leaf msdpPeerConnectRetryInterval {
          type int32 {
            range "1..65535";
          }
          units "seconds";
          description
           "Time interval in seconds for the ConnectRetry timer.";
          smiv2:defval "120";
          smiv2:max-access "read-write";
          smiv2:oid "1.3.6.1.3.92.1.1.5.1.20";
        }

        leaf msdpPeerHoldTimeConfigured {
          type int32 {
            range "0|3..65535";
          }
          units "seconds";
          description
           "Time interval in seconds for the Hold Timer
            configured for this MSDP speaker with this peer.";
          smiv2:defval "90";
          smiv2:max-access "read-write";
          smiv2:oid "1.3.6.1.3.92.1.1.5.1.21";
        }

        leaf msdpPeerKeepAliveConfigured {
          type int32 {
            range "0..21845";
          }
          units "seconds";
          description
           "Time interval in seconds for the KeepAlive timer
            configured for this MSDP speaker with this peer.  A
            reasonable maximum value for this timer would be
            configured to be one third of that of
            msdpPeerHoldTimeConfigured.  If the value of this
            object is zero (0), no periodic KEEPALIVE messages are
            sent to the peer after the MSDP connection has been
            established.";
          smiv2:defval "30";
          smiv2:max-access "read-write";
          smiv2:oid "1.3.6.1.3.92.1.1.5.1.22";
        }

        leaf msdpPeerDataTtl {
          type int32 {
            range "0..255";
          }
          description
           "The minimum TTL a packet is required to have before
            it may be forwarded using SA encapsulation to this
            peer.";
          smiv2:max-access "read-write";
          smiv2:oid "1.3.6.1.3.92.1.1.5.1.23";
        }

        leaf msdpPeerProcessRequestsFrom {
          type boolean;
          description
           "This object indicates whether or not to process MSDP
            SA Request messages from this peer.  If True(1), MSDP
            SA Request messages from this peer are processed and
            replied to (if appropriate) with SA Response messages.
            If False(2), MSDP SA Request messages from this peer
            are silently ignored.  It defaults to False when
            msdpCacheLifetime is 0 and True when msdpCacheLifetime
            is non-0.";
          smiv2:max-access "read-write";
          smiv2:oid "1.3.6.1.3.92.1.1.5.1.24";
        }

        leaf msdpPeerStatus {
          type snmpv2-tc:RowStatus;
          description
           "The RowStatus object by which peers can be added and
            deleted.  A transition to 'active' will cause the MSDP
            Start Event to be generated.  A transition out of the
            'active' state will cause the MSDP Stop Event to be
            generated.  Care should be used in providing write
            access to this object without adequate
            authentication.";
          smiv2:max-access "read-write";
          smiv2:oid "1.3.6.1.3.92.1.1.5.1.25";
        }

        leaf msdpPeerRemotePort {
          type int32 {
            range "0..65535";
          }
          description
           "The remote port for the TCP connection between the
            MSDP peers.";
          smiv2:max-access "read-only";
          smiv2:oid "1.3.6.1.3.92.1.1.5.1.26";
        }

        leaf msdpPeerLocalPort {
          type int32 {
            range "0..65535";
          }
          description
           "The local port for the TCP connection between the
            MSDP peers.";
          smiv2:max-access "read-only";
          smiv2:oid "1.3.6.1.3.92.1.1.5.1.27";
        }

        leaf msdpPeerEncapsulationState {
          type enumeration {
            enum "default" {
              value "1";
            }
            enum "received" {
              value "2";
            }
            enum "advertising" {
              value "3";
            }
            enum "sent" {
              value "4";
            }
            enum "agreed" {
              value "5";
            }
            enum "failed" {
              value "6";
            }
          }
          description
           "The status of the encapsulation negotiation state
            machine.";
          smiv2:max-access "read-only";
          smiv2:oid "1.3.6.1.3.92.1.1.5.1.28";
        }

        leaf msdpPeerEncapsulationType {
          type enumeration {
            enum "tcp" {
              value "1";
            }
            enum "udp" {
              value "2";
            }
            enum "gre" {
              value "3";
            }
          }
          description
           "The encapsulation in use when encapsulating data in
            SA messages to this peer.";
          smiv2:max-access "read-only";
          smiv2:oid "1.3.6.1.3.92.1.1.5.1.29";
        }

        leaf msdpPeerConnectionAttempts {
          type yang:counter32;
          description
           "The number of times the state machine has
            transitioned from inactive to connecting.";
          smiv2:max-access "read-only";
          smiv2:oid "1.3.6.1.3.92.1.1.5.1.30";
        }

        leaf msdpPeerInNotifications {
          type yang:counter32;
          description
           "The number of MSDP Notification messages received on
            this connection.  This object should be initialized to
            zero when the connection is established.";
          smiv2:max-access "read-only";
          smiv2:oid "1.3.6.1.3.92.1.1.5.1.31";
        }

        leaf msdpPeerOutNotifications {
          type yang:counter32;
          description
           "The number of MSDP Notification messages transmitted
            on this connection.  This object should be initialized
            to zero when the connection is established.";
          smiv2:max-access "read-only";
          smiv2:oid "1.3.6.1.3.92.1.1.5.1.32";
        }

        leaf msdpPeerLastError {
          type binary {
            length "2";
          }
          description
           "The last error code and subcode seen by this peer on
            this connection.  If no error has occurred, this field
            is zero.  Otherwise, the first byte of this two byte
            OCTET STRING contains the error code, and the second
            byte contains the subcode.";
          smiv2:defval "'0000'H";
          smiv2:max-access "read-only";
          smiv2:oid "1.3.6.1.3.92.1.1.5.1.33";
        }
      }
    }

    container msdpSACacheTable {
      description
       "The (conceptual) table listing the MSDP SA
        advertisements currently in the MSDP speaker's cache.";
      smiv2:oid "1.3.6.1.3.92.1.1.6";

      list msdpSACacheEntry {
        key "msdpSACacheGroupAddr msdpSACacheSourceAddr msdpSACacheOriginRP";
        description
         "An entry (conceptual row) representing an MSDP SA
          advert.";
        smiv2:oid "1.3.6.1.3.92.1.1.6.1";

        leaf msdpSACacheGroupAddr {
          type inet:ipv4-address;
          description
           "The group address of the SA Cache entry.";
          smiv2:max-access "not-accessible";
          smiv2:oid "1.3.6.1.3.92.1.1.6.1.1";
        }

        leaf msdpSACacheSourceAddr {
          type inet:ipv4-address;
          description
           "The source address of the SA Cache entry.";
          smiv2:max-access "not-accessible";
          smiv2:oid "1.3.6.1.3.92.1.1.6.1.2";
        }

        leaf msdpSACacheOriginRP {
          type inet:ipv4-address;
          description
           "The address of the RP which originated the last SA
            message accepted for this entry.";
          smiv2:max-access "not-accessible";
          smiv2:oid "1.3.6.1.3.92.1.1.6.1.3";
        }

        leaf msdpSACachePeerLearnedFrom {
          type inet:ipv4-address;
          description
           "The peer from which this SA Cache entry was last
            accepted.  This address must correspond to the
            msdpPeerRemoteAddress value for a row in the MSDP Peer
            Table.";
          smiv2:max-access "read-only";
          smiv2:oid "1.3.6.1.3.92.1.1.6.1.4";
        }

        leaf msdpSACacheRPFPeer {
          type inet:ipv4-address;
          description
           "The peer from which an SA message corresponding to
            this cache entry would be accepted (i.e. the RPF peer
            for msdpSACacheOriginRP).  This may be different than
            msdpSACachePeerLearnedFrom if this entry was created
            by an MSDP SA-Response.  This address must correspond
            to the msdpPeerRemoteAddress value for a row in the
            MSDP Peer Table.";
          smiv2:max-access "read-only";
          smiv2:oid "1.3.6.1.3.92.1.1.6.1.5";
        }

        leaf msdpSACacheInSAs {
          type yang:counter32;
          description
           "The number of MSDP SA messages received relevant to
            this cache entry.  This object must be initialized to
            zero when creating a cache entry.";
          smiv2:max-access "read-only";
          smiv2:oid "1.3.6.1.3.92.1.1.6.1.6";
        }

        leaf msdpSACacheInDataPackets {
          type yang:counter32;
          description
           "The number of MSDP encapsulated data packets received
            relevant to this cache entry.  This object must be
            initialized to zero when creating a cache entry.";
          smiv2:max-access "read-only";
          smiv2:oid "1.3.6.1.3.92.1.1.6.1.7";
        }

        leaf msdpSACacheUpTime {
          type yang:timeticks;
          description
           "The time since this entry was placed in the SA
            cache.";
          smiv2:max-access "read-only";
          smiv2:oid "1.3.6.1.3.92.1.1.6.1.8";
        }

        leaf msdpSACacheExpiryTime {
          type yang:timeticks;
          description
           "The time remaining before this entry will expire from
            the SA cache.";
          smiv2:max-access "read-only";
          smiv2:oid "1.3.6.1.3.92.1.1.6.1.9";
        }

        leaf msdpSACacheStatus {
          type snmpv2-tc:RowStatus;
          description
           "The status of this row in the table.  The only
            allowable actions are to retreive the status, which
            will be `active', or to set the status to `destroy' in
            order to remove this entry from the cache.";
          smiv2:max-access "read-write";
          smiv2:oid "1.3.6.1.3.92.1.1.6.1.10";
        }
      }
    }
  }

  notification msdpEstablished {
    description
     "The MSDP Established event is generated when the MSDP
      FSM enters the ESTABLISHED state.";
    smiv2:oid "1.3.6.1.3.92.1.1.7.1";

    container object-1 {

      leaf msdpPeerRemoteAddress {
        type leafref {
          path "/DRAFT-MSDP-MIB:DRAFT-MSDP-MIB/DRAFT-MSDP-MIB:msdpPeerTable/DRAFT-MSDP-MIB:msdpPeerEntry/DRAFT-MSDP-MIB:msdpPeerRemoteAddress";
        }
      }

      leaf msdpPeerFsmEstablishedTransitions {
        type leafref {
          path "/DRAFT-MSDP-MIB:DRAFT-MSDP-MIB/DRAFT-MSDP-MIB:msdpPeerTable/DRAFT-MSDP-MIB:msdpPeerEntry/DRAFT-MSDP-MIB:msdpPeerFsmEstablishedTransitions";
        }
      }
    }
  }

  notification msdpBackwardTransition {
    description
     "The MSDPBackwardTransition Event is generated when
      the MSDP FSM moves from a higher numbered state to a
      lower numbered state.";
    smiv2:oid "1.3.6.1.3.92.1.1.7.2";

    container object-1 {

      leaf msdpPeerRemoteAddress {
        type leafref {
          path "/DRAFT-MSDP-MIB:DRAFT-MSDP-MIB/DRAFT-MSDP-MIB:msdpPeerTable/DRAFT-MSDP-MIB:msdpPeerEntry/DRAFT-MSDP-MIB:msdpPeerRemoteAddress";
        }
      }

      leaf msdpPeerState {
        type leafref {
          path "/DRAFT-MSDP-MIB:DRAFT-MSDP-MIB/DRAFT-MSDP-MIB:msdpPeerTable/DRAFT-MSDP-MIB:msdpPeerEntry/DRAFT-MSDP-MIB:msdpPeerState";
        }
      }
    }
  }

  smiv2:alias "msdpMIB" {
    smiv2:oid "1.3.6.1.3.92";
  }

  smiv2:alias "msdpMIBobjects" {
    smiv2:oid "1.3.6.1.3.92.1";
  }

  smiv2:alias "msdp" {
    smiv2:oid "1.3.6.1.3.92.1.1";
  }

  smiv2:alias "msdpTraps" {
    smiv2:oid "1.3.6.1.3.92.1.1.7";
  }

  smiv2:alias "msdpMIBConformance" {
    smiv2:oid "1.3.6.1.3.92.1.1.8";
  }

  smiv2:alias "msdpMIBCompliances" {
    smiv2:oid "1.3.6.1.3.92.1.1.8.1";
  }

  smiv2:alias "msdpMIBGroups" {
    smiv2:oid "1.3.6.1.3.92.1.1.8.2";
  }

}
