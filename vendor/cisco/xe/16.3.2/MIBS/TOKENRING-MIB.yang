/*
 * Generated by confdc --mib2yang-std
 * Source: mgmt/dmi/model/common/mib-source/TOKENRING-MIB.mib
 */
/*
 * This YANG module has been generated by smidump 0.5.0:
 *
 *      smidump -f yang TOKENRING-MIB
 *
 * Do not edit. Edit the source file instead!
 */

module TOKENRING-MIB {

  namespace "urn:ietf:params:xml:ns:yang:smiv2:TOKENRING-MIB";
  prefix TOKENRING-MIB;

  import ietf-yang-smiv2 {
    prefix "smiv2";
  }

  import ietf-yang-types {
    prefix "yang";
  }

  organization
   "IETF Interfaces MIB Working Group";

  contact
   "        Keith McCloghrie
    
    Postal: cisco Systems, Inc.
            170 West Tasman Drive,
            San Jose, CA 95134-1706
    
    
            US
    
     Phone: +1 408 526 5260
     EMail: kzm@cisco.com";

  description
   "The MIB module for IEEE Token Ring entities.";

  revision 1994-10-23 {
    description
     "[Revision added by libsmi due to a LAST-UPDATED clause.]";
  }

  identity dot5TestInsertFunc {
    base smiv2:object-identity;
    description
     "Invoking this test causes the station to test the insert
      ring logic of the hardware if the station's lobe media
      cable is connected to a wiring concentrator.  Note that
      this command inserts the station into the network, and
      thus, could cause problems if the station is connected
      to a operational network.";
    smiv2:oid "1.3.6.1.2.1.10.9.3.1";
  }

  identity dot5TestFullDuplexLoopBack {
    base smiv2:object-identity;
    description
     "Invoking this test on a 802.5 interface causes the
      interface to check the path from memory through the
      chip set's internal logic and back to memory, thus
      checking the proper functioning of the system's
      interface to the chip set.";
    smiv2:oid "1.3.6.1.2.1.10.9.3.2";
  }

  identity dot5ChipSetIBM16 {
    base smiv2:object-identity;
    description
     "IBM's 16/4 Mbs chip set.";
    smiv2:oid "1.3.6.1.2.1.10.9.4.1";
  }

  identity dot5ChipSetTItms380 {
    base smiv2:object-identity;
    description
     "Texas Instruments' TMS 380 4Mbs chip-set";
    smiv2:oid "1.3.6.1.2.1.10.9.4.2";
  }

  identity dot5ChipSetTItms380c16 {
    base smiv2:object-identity;
    description
     "Texas Instruments' TMS 380C16 16/4 Mbs chip-set";
    smiv2:oid "1.3.6.1.2.1.10.9.4.3";
  }


  container TOKENRING-MIB {
    config false;

    container dot5Table {
      description
       "This table contains Token Ring interface
        parameters and state variables, one entry
        per 802.5 interface.";
      smiv2:oid "1.3.6.1.2.1.10.9.1";

      list dot5Entry {
        key "dot5IfIndex";
        description
         "A list of Token Ring status and parameter
          values for an 802.5 interface.";
        smiv2:oid "1.3.6.1.2.1.10.9.1.1";

        leaf dot5IfIndex {
          type int32;
          description
           "The value of this object identifies the
            802.5 interface for which this entry
            contains management information.  The
            value of this object for a particular
            interface has the same value as the
            ifIndex object, defined in MIB-II for
            the same interface.";
          smiv2:max-access "read-only";
          smiv2:oid "1.3.6.1.2.1.10.9.1.1.1";
        }

        leaf dot5Commands {
          type enumeration {
            enum "noop" {
              value "1";
            }
            enum "open" {
              value "2";
            }
            enum "reset" {
              value "3";
            }
            enum "close" {
              value "4";
            }
          }
          description
           "When this object is set to the value of
            open(2), the station should go into the
            open state.  The progress and success of
            the open is given by the values of the
            objects dot5RingState and
            dot5RingOpenStatus.
                When this object is set to the value
            of reset(3), then the station should do
            a reset.  On a reset, all MIB counters
            should retain their values, if possible.
            Other side affects are dependent on the
            hardware chip set.
                When this object is set to the value
            of close(4), the station should go into
            the stopped state by removing itself
            from the ring.
                Setting this object to a value of
            noop(1) has no effect.
                When read, this object always has a
            value of noop(1).
                The open(2) and close(4) values
            correspond to the up(1) and down(2) values
            of MIB-II's ifAdminStatus and ifOperStatus,
            i.e., the setting of ifAdminStatus and
            
            
            dot5Commands affects the values of both
            dot5Commands and ifOperStatus.";
          smiv2:max-access "read-write";
          smiv2:oid "1.3.6.1.2.1.10.9.1.1.2";
        }

        leaf dot5RingStatus {
          type int32 {
            range "0..262143";
          }
          description
           "The current interface status which can
            be used to diagnose fluctuating problems
            that can occur on token rings, after a
            station has successfully been added to
            the ring.
               Before an open is completed, this
            object has the value for the 'no status'
            condition.  The dot5RingState and
            dot5RingOpenStatus objects provide for
            debugging problems when the station
            can not even enter the ring.
                The object's value is a sum of
            values, one for each currently applicable
            condition.  The following values are
            defined for various conditions:
            
                    0 = No Problems detected
                   32 = Ring Recovery
                   64 = Single Station
                  256 = Remove Received
                  512 = reserved
                 1024 = Auto-Removal Error
                 2048 = Lobe Wire Fault
                 4096 = Transmit Beacon
                 8192 = Soft Error
                16384 = Hard Error
                32768 = Signal Loss
               131072 = no status, open not completed.";
          smiv2:max-access "read-only";
          smiv2:oid "1.3.6.1.2.1.10.9.1.1.3";
        }

        leaf dot5RingState {
          type enumeration {
            enum "opened" {
              value "1";
            }
            enum "closed" {
              value "2";
            }
            enum "opening" {
              value "3";
            }
            enum "closing" {
              value "4";
            }
            enum "openFailure" {
              value "5";
            }
            enum "ringFailure" {
              value "6";
            }
          }
          description
           "The current interface state with respect
            to entering or leaving the ring.";
          smiv2:max-access "read-only";
          smiv2:oid "1.3.6.1.2.1.10.9.1.1.4";
        }

        leaf dot5RingOpenStatus {
          type enumeration {
            enum "noOpen" {
              value "1";
            }
            enum "badParam" {
              value "2";
            }
            enum "lobeFailed" {
              value "3";
            }
            enum "signalLoss" {
              value "4";
            }
            enum "insertionTimeout" {
              value "5";
            }
            enum "ringFailed" {
              value "6";
            }
            enum "beaconing" {
              value "7";
            }
            enum "duplicateMAC" {
              value "8";
            }
            enum "requestFailed" {
              value "9";
            }
            enum "removeReceived" {
              value "10";
            }
            enum "open" {
              value "11";
            }
          }
          description
           "This object indicates the success, or the
            reason for failure, of the station's most
            recent attempt to enter the ring.";
          smiv2:max-access "read-only";
          smiv2:oid "1.3.6.1.2.1.10.9.1.1.5";
        }

        leaf dot5RingSpeed {
          type enumeration {
            enum "unknown" {
              value "1";
            }
            enum "oneMegabit" {
              value "2";
            }
            enum "fourMegabit" {
              value "3";
            }
            enum "sixteenMegabit" {
              value "4";
            }
          }
          description
           "The ring-speed at the next insertion into
            the ring.  Note that this may or may not be
            different to the current ring-speed which is
            given by MIB-II's ifSpeed.  For interfaces
            which do not support changing ring-speed,
            dot5RingSpeed can only be set to its current
            value.  When dot5RingSpeed has the value
            unknown(1), the ring's actual ring-speed is
            to be used.";
          smiv2:max-access "read-write";
          smiv2:oid "1.3.6.1.2.1.10.9.1.1.6";
        }

        leaf dot5UpStream {
          type yang:mac-address;
          description
           "The MAC-address of the up stream neighbor
            station in the ring.";
          smiv2:max-access "read-only";
          smiv2:oid "1.3.6.1.2.1.10.9.1.1.7";
        }

        leaf dot5ActMonParticipate {
          type enumeration {
            enum "true" {
              value "1";
            }
            enum "false" {
              value "2";
            }
          }
          description
           "If this object has a value of true(1) then
            this interface will participate in the
            active monitor selection process.  If the
            value is false(2) then it will not.
            Setting this object does not take effect
            until the next Active Monitor election, and
            might not take effect until the next time
            the interface is opened.";
          smiv2:max-access "read-write";
          smiv2:oid "1.3.6.1.2.1.10.9.1.1.8";
        }

        leaf dot5Functional {
          type yang:mac-address;
          description
           "The bit mask of all Token Ring functional
            addresses for which this interface will
            accept frames.";
          smiv2:max-access "read-write";
          smiv2:oid "1.3.6.1.2.1.10.9.1.1.9";
        }

        leaf dot5LastBeaconSent {
          type yang:timestamp;
          description
           "The value of MIB-II's sysUpTime object at which
            the local system last transmitted a Beacon frame
            on this interface.";
          smiv2:max-access "read-only";
          smiv2:oid "1.3.6.1.2.1.10.9.1.1.10";
        }
      }
    }

    container dot5StatsTable {
      description
       "A table containing Token Ring statistics,
        one entry per 802.5 interface.
            All the statistics are defined using
        the syntax Counter32 as 32-bit wrap around
        counters.  Thus, if an interface's
        hardware maintains these statistics in
        16-bit counters, then the agent must read
        the hardware's counters frequently enough
        to prevent loss of significance, in order
        to maintain 32-bit counters in software.";
      smiv2:oid "1.3.6.1.2.1.10.9.2";

      list dot5StatsEntry {
        key "dot5StatsIfIndex";
        description
         "An entry contains the 802.5 statistics
          for a particular interface.";
        smiv2:oid "1.3.6.1.2.1.10.9.2.1";

        leaf dot5StatsIfIndex {
          type int32;
          description
           "The value of this object identifies the
            802.5 interface for which this entry
            contains management information.  The
            value of this object for a particular
            interface has the same value as MIB-II's
            ifIndex object for the same interface.";
          smiv2:max-access "read-only";
          smiv2:oid "1.3.6.1.2.1.10.9.2.1.1";
        }

        leaf dot5StatsLineErrors {
          type yang:counter32;
          description
           "This counter is incremented when a frame
            or token is copied or repeated by a
            station, the E bit is zero in the frame
            or token and one of the following
            conditions exists: 1) there is a
            non-data bit (J or K bit) between the SD
            and the ED of the frame or token, or
            2) there is an FCS error in the frame.";
          smiv2:max-access "read-only";
          smiv2:oid "1.3.6.1.2.1.10.9.2.1.2";
        }

        leaf dot5StatsBurstErrors {
          type yang:counter32;
          description
           "This counter is incremented when a station
            detects the absence of transitions for five
            half-bit timers (burst-five error).";
          smiv2:max-access "read-only";
          smiv2:oid "1.3.6.1.2.1.10.9.2.1.3";
        }

        leaf dot5StatsACErrors {
          type yang:counter32;
          description
           "This counter is incremented when a station
            receives an AMP or SMP frame in which A is
            equal to C is equal to 0, and then receives
            another SMP frame with A is equal to C is
            equal to 0 without first receiving an AMP
            frame. It denotes a station that cannot set
            the AC bits properly.";
          smiv2:max-access "read-only";
          smiv2:oid "1.3.6.1.2.1.10.9.2.1.4";
        }

        leaf dot5StatsAbortTransErrors {
          type yang:counter32;
          description
           "This counter is incremented when a station
            transmits an abort delimiter while
            transmitting.";
          smiv2:max-access "read-only";
          smiv2:oid "1.3.6.1.2.1.10.9.2.1.5";
        }

        leaf dot5StatsInternalErrors {
          type yang:counter32;
          description
           "This counter is incremented when a station
            recognizes an internal error.";
          smiv2:max-access "read-only";
          smiv2:oid "1.3.6.1.2.1.10.9.2.1.6";
        }

        leaf dot5StatsLostFrameErrors {
          type yang:counter32;
          description
           "This counter is incremented when a station
            is transmitting and its TRR timer expires.
            This condition denotes a condition where a
            transmitting station in strip mode does not
            receive the trailer of the frame before the
            TRR timer goes off.";
          smiv2:max-access "read-only";
          smiv2:oid "1.3.6.1.2.1.10.9.2.1.7";
        }

        leaf dot5StatsReceiveCongestions {
          type yang:counter32;
          description
           "This counter is incremented when a station
            recognizes a frame addressed to its
            specific address, but has no available
            buffer space indicating that the station
            is congested.";
          smiv2:max-access "read-only";
          smiv2:oid "1.3.6.1.2.1.10.9.2.1.8";
        }

        leaf dot5StatsFrameCopiedErrors {
          type yang:counter32;
          description
           "This counter is incremented when a station
            recognizes a frame addressed to its
            specific address and detects that the FS
            field A bits are set to 1 indicating a
            possible line hit or duplicate address.";
          smiv2:max-access "read-only";
          smiv2:oid "1.3.6.1.2.1.10.9.2.1.9";
        }

        leaf dot5StatsTokenErrors {
          type yang:counter32;
          description
           "This counter is incremented when a station
            acting as the active monitor recognizes an
            error condition that needs a token
            transmitted.";
          smiv2:max-access "read-only";
          smiv2:oid "1.3.6.1.2.1.10.9.2.1.10";
        }

        leaf dot5StatsSoftErrors {
          type yang:counter32;
          description
           "The number of Soft Errors the interface
            has detected. It directly corresponds to
            the number of Report Error MAC frames
            that this interface has transmitted.
            Soft Errors are those which are
            recoverable by the MAC layer protocols.";
          smiv2:max-access "read-only";
          smiv2:oid "1.3.6.1.2.1.10.9.2.1.11";
        }

        leaf dot5StatsHardErrors {
          type yang:counter32;
          description
           "The number of times this interface has
            detected an immediately recoverable
            fatal error.  It denotes the number of
            times this interface is either
            transmitting or receiving beacon MAC
            frames.";
          smiv2:max-access "read-only";
          smiv2:oid "1.3.6.1.2.1.10.9.2.1.12";
        }

        leaf dot5StatsSignalLoss {
          type yang:counter32;
          description
           "The number of times this interface has
            detected the loss of signal condition from
            the ring.";
          smiv2:max-access "read-only";
          smiv2:oid "1.3.6.1.2.1.10.9.2.1.13";
        }

        leaf dot5StatsTransmitBeacons {
          type yang:counter32;
          description
           "The number of times this interface has
            transmitted a beacon frame.";
          smiv2:max-access "read-only";
          smiv2:oid "1.3.6.1.2.1.10.9.2.1.14";
        }

        leaf dot5StatsRecoverys {
          type yang:counter32;
          description
           "The number of Claim Token MAC frames
            received or transmitted after the interface
            has received a Ring Purge MAC frame.  This
            counter signifies the number of times the
            ring has been purged and is being recovered
            back into a normal operating state.";
          smiv2:max-access "read-only";
          smiv2:oid "1.3.6.1.2.1.10.9.2.1.15";
        }

        leaf dot5StatsLobeWires {
          type yang:counter32;
          description
           "The number of times the interface has
            detected an open or short circuit in the
            lobe data path.  The adapter will be closed
            and dot5RingState will signify this
            condition.";
          smiv2:max-access "read-only";
          smiv2:oid "1.3.6.1.2.1.10.9.2.1.16";
        }

        leaf dot5StatsRemoves {
          type yang:counter32;
          description
           "The number of times the interface has
            received a Remove Ring Station MAC frame
            request.  When this frame is received
            the interface will enter the close state
            and dot5RingState will signify this
            condition.";
          smiv2:max-access "read-only";
          smiv2:oid "1.3.6.1.2.1.10.9.2.1.17";
        }

        leaf dot5StatsSingles {
          type yang:counter32;
          description
           "The number of times the interface has
            sensed that it is the only station on the
            ring.  This will happen if the interface
            is the first one up on a ring, or if
            there is a hardware problem.";
          smiv2:max-access "read-only";
          smiv2:oid "1.3.6.1.2.1.10.9.2.1.18";
        }

        leaf dot5StatsFreqErrors {
          type yang:counter32;
          description
           "The number of times the interface has
            detected that the frequency of the
            incoming signal differs from the expected
            frequency by more than that specified by
            the IEEE 802.5 standard.";
          smiv2:max-access "read-only";
          smiv2:oid "1.3.6.1.2.1.10.9.2.1.19";
        }
      }
    }

    container dot5TimerTable {
      status obsolete;
      description
       "This table contains Token Ring interface
        timer values, one entry per 802.5
        interface.";
      smiv2:oid "1.3.6.1.2.1.10.9.5";

      list dot5TimerEntry {
        key "dot5TimerIfIndex";
        status obsolete;
        description
         "A list of Token Ring timer values for an
          802.5 interface.";
        smiv2:oid "1.3.6.1.2.1.10.9.5.1";

        leaf dot5TimerIfIndex {
          type int32;
          status obsolete;
          description
           "The value of this object identifies the
            802.5 interface for which this entry
            contains timer values.  The value of
            
            
            this object for a particular interface
            has the same value as MIB-II's ifIndex
            object for the same interface.";
          smiv2:max-access "read-only";
          smiv2:oid "1.3.6.1.2.1.10.9.5.1.1";
        }

        leaf dot5TimerReturnRepeat {
          type int32;
          status obsolete;
          description
           "The time-out value used to ensure the
            interface will return to Repeat State, in
            units of 100 micro-seconds.  The value
            should be greater than the maximum ring
            latency.";
          smiv2:max-access "read-only";
          smiv2:oid "1.3.6.1.2.1.10.9.5.1.2";
        }

        leaf dot5TimerHolding {
          type int32;
          status obsolete;
          description
           "Maximum period of time a station is
            permitted to transmit frames after capturing
            a token, in units of 100 micro-seconds.";
          smiv2:max-access "read-only";
          smiv2:oid "1.3.6.1.2.1.10.9.5.1.3";
        }

        leaf dot5TimerQueuePDU {
          type int32;
          status obsolete;
          description
           "The time-out value for enqueuing of an SMP
            PDU after reception of an AMP or SMP
            frame in which the A and C bits were
            equal to 0, in units of 100
            micro-seconds.";
          smiv2:max-access "read-only";
          smiv2:oid "1.3.6.1.2.1.10.9.5.1.4";
        }

        leaf dot5TimerValidTransmit {
          type int32;
          status obsolete;
          description
           "The time-out value used by the active
            monitor to detect the absence of valid
            transmissions, in units of 100
            micro-seconds.";
          smiv2:max-access "read-only";
          smiv2:oid "1.3.6.1.2.1.10.9.5.1.5";
        }

        leaf dot5TimerNoToken {
          type int32;
          status obsolete;
          description
           "The time-out value used to recover from
            various-related error situations.
            If N is the maximum number of stations on
            the ring, the value of this timer is
            normally:
            dot5TimerReturnRepeat + N*dot5TimerHolding.";
          smiv2:max-access "read-only";
          smiv2:oid "1.3.6.1.2.1.10.9.5.1.6";
        }

        leaf dot5TimerActiveMon {
          type int32;
          status obsolete;
          description
           "The time-out value used by the active
            monitor to stimulate the enqueuing of an
            AMP PDU for transmission, in units of
            100 micro-seconds.";
          smiv2:max-access "read-only";
          smiv2:oid "1.3.6.1.2.1.10.9.5.1.7";
        }

        leaf dot5TimerStandbyMon {
          type int32;
          status obsolete;
          description
           "The time-out value used by the stand-by
            monitors to ensure that there is an active
            monitor on the ring and to detect a
            continuous stream of tokens, in units of
            100 micro-seconds.";
          smiv2:max-access "read-only";
          smiv2:oid "1.3.6.1.2.1.10.9.5.1.8";
        }

        leaf dot5TimerErrorReport {
          type int32;
          status obsolete;
          description
           "The time-out value which determines how
            often a station shall send a Report Error
            MAC frame to report its error counters,
            in units of 100 micro-seconds.";
          smiv2:max-access "read-only";
          smiv2:oid "1.3.6.1.2.1.10.9.5.1.9";
        }

        leaf dot5TimerBeaconTransmit {
          type int32;
          status obsolete;
          description
           "The time-out value which determines how
            long a station shall remain in the state
            of transmitting Beacon frames before
            entering the Bypass state, in units of
            100 micro-seconds.";
          smiv2:max-access "read-only";
          smiv2:oid "1.3.6.1.2.1.10.9.5.1.10";
        }

        leaf dot5TimerBeaconReceive {
          type int32;
          status obsolete;
          description
           "The time-out value which determines how
            long a station shall receive Beacon
            frames from its downstream neighbor
            before entering the Bypass state, in
            units of 100 micro-seconds.";
          smiv2:max-access "read-only";
          smiv2:oid "1.3.6.1.2.1.10.9.5.1.11";
        }
      }
    }
  }

  smiv2:alias "dot5" {
    smiv2:oid "1.3.6.1.2.1.10.9";
  }

  smiv2:alias "dot5Tests" {
    smiv2:oid "1.3.6.1.2.1.10.9.3";
  }

  smiv2:alias "dot5TestInsertFunc" {
    description
     "Invoking this test causes the station to test the insert
      ring logic of the hardware if the station's lobe media
      cable is connected to a wiring concentrator.  Note that
      this command inserts the station into the network, and
      thus, could cause problems if the station is connected
      to a operational network.";
    smiv2:oid "1.3.6.1.2.1.10.9.3.1";
  }

  smiv2:alias "dot5TestFullDuplexLoopBack" {
    description
     "Invoking this test on a 802.5 interface causes the
      interface to check the path from memory through the
      chip set's internal logic and back to memory, thus
      checking the proper functioning of the system's
      interface to the chip set.";
    smiv2:oid "1.3.6.1.2.1.10.9.3.2";
  }

  smiv2:alias "dot5ChipSets" {
    smiv2:oid "1.3.6.1.2.1.10.9.4";
  }

  smiv2:alias "dot5ChipSetIBM16" {
    description
     "IBM's 16/4 Mbs chip set.";
    smiv2:oid "1.3.6.1.2.1.10.9.4.1";
  }

  smiv2:alias "dot5ChipSetTItms380" {
    description
     "Texas Instruments' TMS 380 4Mbs chip-set";
    smiv2:oid "1.3.6.1.2.1.10.9.4.2";
  }

  smiv2:alias "dot5ChipSetTItms380c16" {
    description
     "Texas Instruments' TMS 380C16 16/4 Mbs chip-set";
    smiv2:oid "1.3.6.1.2.1.10.9.4.3";
  }

  smiv2:alias "dot5Conformance" {
    smiv2:oid "1.3.6.1.2.1.10.9.6";
  }

  smiv2:alias "dot5Groups" {
    smiv2:oid "1.3.6.1.2.1.10.9.6.1";
  }

  smiv2:alias "dot5Compliances" {
    smiv2:oid "1.3.6.1.2.1.10.9.6.2";
  }

}
