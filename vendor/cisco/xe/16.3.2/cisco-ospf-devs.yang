module cisco-ospf-devs {
  namespace "http://cisco.com/ns/cisco-ospf/devs";

  prefix cospf-devs;

  import ietf-routing {
    prefix rt;
  }

  import ietf-ospf {
    prefix ospf;
  }

  import cisco-ospf {
    prefix cisco-ospf;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for cisco-ospf
     module.
     Copyright (c) 2016 by Cisco Systems, Inc.
     All rights reserved.";

  revision 2016-03-30 {
    description
      "Update description with copyright notice.";
  }

  revision 2015-09-11 {
    description
      "Initial Revision";

    reference
      "RFC 6020: YANG - A Data Modeling Language for the
       Network Configuration Protocol (NETCONF)";
  }

  deviation "/rt:routing/rt:routing-instance/rt:routing-protocols" +
            "/rt:routing-protocol/ospf:ospf/ospf:instance" +
            "/cisco-ospf:microloop-avoidance" {
    deviate not-supported;
    description "Not supported in IOS-XE 3.17 release.";
  }

  deviation "/rt:routing/rt:routing-instance/rt:routing-protocols" +
            "/rt:routing-protocol/ospf:ospf/ospf:instance" +
            "/ospf:database-control/cisco-ospf:database-filter" {
    deviate not-supported;
    description  "Not supported in IOS-XE 3.17 release.";
  }

  deviation "/rt:routing/rt:routing-instance/rt:routing-protocols" +
            "/rt:routing-protocol/ospf:ospf/ospf:instance" +
            "/ospf:database-control/cisco-ospf:flood-reduction" {
    deviate not-supported;
    description  "Not supported in IOS-XE 3.17 release.";
  }

  deviation "/rt:routing/rt:routing-instance/rt:routing-protocols" +
            "/rt:routing-protocol/ospf:ospf/ospf:instance" +
            "/ospf:database-control/cisco-ospf:ignore-lsa" {
    deviate not-supported;
    description  "Not supported in IOS-XE 3.17 release.";
  }

  deviation "/rt:routing/rt:routing-instance/rt:routing-protocols" +
            "/rt:routing-protocol/ospf:ospf/ospf:instance" +
            "/ospf:database-control/cisco-ospf:lsa/cisco-ospf:refresh" {
    deviate not-supported;
    description  "Not supported in IOS-XE 3.17 release.";
  }

  deviation "/rt:routing/rt:routing-instance/rt:routing-protocols" +
            "/rt:routing-protocol/ospf:ospf/ospf:instance" +
            "/ospf:reload-control/cisco-ospf:max-metric" {
    deviate not-supported;
    description "Not supported in IOS-XE 3.17 release.";
  }


  deviation "/rt:routing/rt:routing-instance/rt:routing-protocols" +
            "/rt:routing-protocol/ospf:ospf/ospf:instance/ospf:area" +
            "/ospf:interface/cisco-ospf:database-filter" {
    deviate not-supported;
    description  "Not supported in IOS-XE 3.17 release.";
  }

  deviation "/rt:routing/rt:routing-instance/rt:routing-protocols" +
            "/rt:routing-protocol/ospf:ospf/ospf:instance/ospf:area" +
            "/ospf:interface/cisco-ospf:flood-reduction" {
    deviate not-supported;
    description  "Not supported in IOS-XE 3.17 release.";
  }

  deviation "/rt:routing/rt:routing-instance/rt:routing-protocols" +
            "/rt:routing-protocol/ospf:ospf/ospf:instance" +
            "/cisco-ospf:log-adjacency-changes" {
    deviate not-supported;
    description  "Not supported in IOS-XE 3.17 release.";
  }

  deviation "/rt:routing/rt:routing-instance/rt:routing-protocols" +
            "/rt:routing-protocol/ospf:ospf/ospf:instance" +
            "/cisco-ospf:summary-prefixes" {
    deviate not-supported;
    description  "Not supported in IOS-XE 3.17 release.";
  }

  deviation "/rt:routing/rt:routing-instance/rt:routing-protocols" +
            "/rt:routing-protocol/ospf:ospf/ospf:instance" +
            "/cisco-ospf:graceful-shutdown" {
    deviate not-supported;
    description  "Not supported in IOS-XE 3.17 release.";
  }

  deviation "/rt:routing/rt:routing-instance/rt:routing-protocols" +
            "/rt:routing-protocol/ospf:ospf/ospf:instance" +
            "/cisco-ospf:redistribution/cisco-ospf:maximum-prefix" {
    deviate not-supported;
    description  "Not supported in IOS-XE 3.17 release.";
  }

  deviation "/rt:routing/rt:routing-instance/rt:routing-protocols" +
            "/rt:routing-protocol/ospf:ospf/ospf:instance" +
            "/cisco-ospf:redistribution/cisco-ospf:subscriber" {
    deviate not-supported;
    description  "Not supported in IOS-XE 3.17 release.";
  }

  deviation "/rt:routing/rt:routing-instance/rt:routing-protocols" +
            "/rt:routing-protocol/ospf:ospf/ospf:instance" +
            "/cisco-ospf:discard-route" {
    deviate not-supported;
    description  "Not supported in IOS-XE 3.17 release.";
  }
}
