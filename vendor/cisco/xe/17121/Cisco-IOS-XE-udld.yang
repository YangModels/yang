module Cisco-IOS-XE-udld {
  yang-version 1.1;
  namespace "http://cisco.com/ns/yang/Cisco-IOS-XE-udld";
  prefix ios-udld;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native UniDirectional Link Detection (UDLD) Yang Model.
     Copyright (c) 2016-2017 by Cisco Systems, Inc.
     All rights reserved.";

  revision 2022-11-01 {
    description
      "- Update yang-version to 1.1";
    cisco-semver:module-version "1.2.0";
  }
  revision 2021-11-01 {
    description
      "Added leaf node to enable udld alert on interface";
    cisco-semver:module-version "1.1.0";
  }
  revision 2019-07-01 {
    description
      "Establish semantic version baseline";
    cisco-semver:module-version "1.0.0";
  }
  revision 2019-01-22 {
    description
      "Added leaf for App-hosting Gigabit Ethernet interface";
  }
  revision 2017-11-27 {
    description
      "Added Change 25GE name";
  }
  revision 2017-11-14 {
    description
      "This revision has changes for new 100GE interface addition";
  }
  revision 2017-09-15 {
    description
      "This revision has changes for new 2gig interface addition";
  }
  revision 2017-08-16 {
    description
      "This revision has changes for new 5gig and 25gig interfaces addition";
  }
  revision 2017-02-07 {
    description
      "Initial revision";
  }

  grouping config-interface-udld-grouping {
    container udld {
      description
        "Configure UDLD enabled or disabled and ignore global UDLD setting";
      container port {
        description
          "Enable UDLD protocol on this interface despite global UDLD setting";
        presence "true";
        choice port-choice {
          leaf aggressive {
            description
              "Enable UDLD protocol in aggressive mode on this interface despite global UDLD setting";
            type empty;
          }
          leaf disable {
            description
              "Disable UDLD protocol on this interface despite global UDLD setting";
            type empty;
          }
          leaf alert {
            description
              "Enable UDLD protocol in alert mode on this interface";
            type empty;
          }
        }
      }
    }
  }

  grouping config-udld-grouping {
    leaf aggressive {
      description
        "Enable UDLD protocol in aggressive mode on fiber ports exceptwhere locally configured";
      type empty;
    }
    leaf enable {
      description
        "Enable UDLD protocol on fiber ports except where locally configured";
      type empty;
    }
    container message {
      description
        "Set UDLD message parameters";
      leaf time {
        description
          "Set UDLD message time period";
        type uint8 {
          range "1..90";
        }
      }
    }
    container recovery {
      description
        "Enable timer to recover from udld error disable state";
      presence "true";
      leaf interval {
        description
          "timer-interval(sec)";
        type uint32 {
          range "30..86400";
        }
      }
    }
  }

  augment "/ios:native/ios:udld" {
    uses config-udld-grouping;
  }

  augment "/ios:native/ios:interface/ios:FastEthernet" {
    uses config-interface-udld-grouping;
  }

  augment "/ios:native/ios:interface/ios:GigabitEthernet" {
    uses config-interface-udld-grouping;
  }

  augment "/ios:native/ios:interface/ios:TenGigabitEthernet" {
    uses config-interface-udld-grouping;
  }

  augment "/ios:native/ios:interface/ios:FiveGigabitEthernet" {
    uses config-interface-udld-grouping;
  }

  augment "/ios:native/ios:interface/ios:AppGigabitEthernet" {
    uses config-interface-udld-grouping;
  }

  augment "/ios:native/ios:interface/ios:TwentyFiveGigE" {
    uses config-interface-udld-grouping;
  }

  augment "/ios:native/ios:interface/ios:TwoGigabitEthernet" {
    uses config-interface-udld-grouping;
  }

  augment "/ios:native/ios:interface/ios:FortyGigabitEthernet" {
    uses config-interface-udld-grouping;
  }

  augment "/ios:native/ios:interface/ios:HundredGigE" {
    uses config-interface-udld-grouping;
  }

  augment "/ios:native/ios:interface/ios:Tunnel" {
    uses config-interface-udld-grouping;
  }

  augment "/ios:native/ios:interface/ios:Loopback" {
    uses config-interface-udld-grouping;
  }
}
