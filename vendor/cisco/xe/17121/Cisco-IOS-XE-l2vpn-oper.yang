module Cisco-IOS-XE-l2vpn-oper {
  yang-version 1.1;
  namespace "http://cisco.com/ns/yang/Cisco-IOS-XE-l2vpn-oper";
  prefix l2vpn-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for L2VPN services operational data.
     Copyright (c) 2022 by Cisco Systems, Inc.
     All rights reserved.";

  revision 2023-03-01 {
    description
      "- Added more detailed PW info to the l2vpn-atom-vc-data
       - Added MAC withdraw counters to VC statistics";
    reference
      "1.1.0";
    cisco-semver:module-version "1.1.0";
  }
  revision 2022-11-01 {
    description
      "Initial revision";
    reference
      "1.0.0";
    cisco-semver:module-version "1.0.0";
  }

  typedef l2vpn-service-type {
    type enumeration {
      enum l2vpn-service-invalid {
        value 0;
        description
          "Invalid service type";
      }
      enum l2vpn-service-vpws {
        value 1;
        description
          "L2VPN service type xconnect";
      }
      enum l2vpn-service-vpls {
        value 2;
        description
          "L2VPN service type VPLS";
      }
      enum l2vpn-service-transport {
        value 3;
        description
          "L2VPN service type Transport";
      }
      enum l2vpn-service-bd {
        value 4;
        description
          "L2VPN service type bridge-domain";
      }
      enum l2vpn-service-evpn {
        value 5;
        description
          "L2VPN service type evpn";
      }
    }
    description
      "L2VPN service type";
  }

  typedef l2vpn-ac-circuit-type {
    type enumeration {
      enum ac-circuit-invalid {
        value 0;
        description
          "Invalid attachment circuit type";
      }
      enum ac-circuit-fr-dlci {
        value 1;
        description
          "Attachment circuit type FR DLCI";
      }
      enum ac-circuit-fr-dlci-local {
        value 2;
        description
          "Attachment circuit type FR DLCI local";
      }
      enum ac-circuit-atm-aal5 {
        value 3;
        description
          "Attachment circuit type ATM AAL5";
      }
      enum ac-circuit-atm-cell {
        value 4;
        description
          "Attachment circuit type ATM cell";
      }
      enum ac-circuit-ether-vlan {
        value 5;
        description
          "Attachment circuit type ethernet VLAN";
      }
      enum ac-circuit-ether {
        value 6;
        description
          "Attachment circuit type ethernet";
      }
      enum ac-circuit-hdlc {
        value 7;
        description
          "Attachment circuit type HDLC";
      }
      enum ac-circuit-ppp {
        value 8;
        description
          "Attachment circuit type PPP";
      }
      enum ac-circuit-cem {
        value 9;
        description
          "Attachment circuit type CEM";
      }
      enum ac-circuit-atm-vcc-cell {
        value 10;
        description
          "Attachment circuit type ATM VCC cell";
      }
      enum ac-circuit-atm-vpc-cell {
        value 11;
        description
          "Attachment circuit type ATM VPC cell";
      }
      enum ac-circuit-ip {
        value 12;
        description
          "Attachment circuit type IP";
      }
      enum ac-circuit-vfi {
        value 13;
        description
          "Attachment circuit type VFI";
      }
      enum ac-circuit-satop-e1 {
        value 15;
        description
          "Attachment circuit type satop E1";
      }
      enum ac-circuit-satop-t1 {
        value 16;
        description
          "Attachment circuit type satop T1";
      }
      enum ac-circuit-satop-e3 {
        value 17;
        description
          "Attachment circuit type satop E3";
      }
      enum ac-circuit-satop-t3 {
        value 18;
        description
          "Attachment circuit type satop T3";
      }
      enum ac-circuit-ces-psn-basic {
        value 19;
        description
          "Attachment circuit type CES PSN basic";
      }
      enum ac-circuit-ces-psn-cas {
        value 20;
        description
          "Attachment circuit type CES PSN CAS";
      }
      enum ac-circuit-atm-vc-unknown {
        value 21;
        description
          "Attachment circuit type ATM VC unknown";
      }
      enum ac-circuit-atm-vp-unknown {
        value 22;
        description
          "Attachment circuit type ATM VP unknown";
      }
      enum ac-circuit-atom {
        value 23;
        description
          "Attachment circuit type ATOM";
      }
      enum ac-circuit-l2tpv2 {
        value 24;
        description
          "Attachment circuit type L2TPV2";
      }
      enum ac-circuit-l2tpv3 {
        value 25;
        description
          "Attachment circuit type L2TPV3";
      }
      enum ac-circuit-pw-udp {
        value 26;
        description
          "Attachment circuit type PW UDP";
      }
      enum ac-circuit-dossis {
        value 27;
        description
          "Attachment circuit type DOCSIS";
      }
      enum ac-circuit-dossis-vlan {
        value 28;
        description
          "Attachment circuit type DOCSIS VLAN";
      }
    }
    description
      "L2VPN attachment circuit type";
  }

  typedef l2vpn-pw-encap-type {
    type enumeration {
      enum l2vpn-pw-encap-invalid {
        value 0;
        description
          "Invalid PW encap type";
      }
      enum l2vpn-pw-encap-l2tpv3 {
        value 1;
        description
          "PW encap type L2TPV3";
      }
      enum l2vpn-pw-encap-l2tpv2 {
        value 2;
        description
          "PW encap type L2TPV2";
      }
      enum l2vpn-pw-encap-mpls {
        value 3;
        description
          "PW encap type MPLS";
      }
      enum l2vpn-pw-encap-udp {
        value 4;
        description
          "PW encap type UDP";
      }
    }
    description
      "L2VPN PW encap type";
  }

  typedef l2vpn-xconnect-segment-state {
    type enumeration {
      enum xconnect-segment-state-undefined {
        value 0;
        description
          "Xconnect segment state is undefined";
      }
      enum xconnect-segment-state-up {
        value 1;
        description
          "Xconnect segment is up";
      }
      enum xconnect-segment-state-down {
        value 2;
        description
          "Xconnect segment is down";
      }
      enum xconnect-segment-state-admin-down {
        value 3;
        description
          "Xconnect segment is admin down";
      }
      enum xconnect-segment-state-recovering {
        value 4;
        description
          "Xconnect segment is recovering";
      }
      enum xconnect-segment-state-standby {
        value 5;
        description
          "Xconnect segment is standby";
      }
      enum xconnect-segment-state-hot-standby {
        value 6;
        description
          "Xconnect segment is hot standby";
      }
      enum xconnect-segment-state-inactive {
        value 7;
        description
          "Xconnect segment is inactive";
      }
    }
    description
      "L2VPN xconnect segment state";
  }

  typedef l2vpn-xconnect-state {
    type enumeration {
      enum xconnect-state-undefined {
        value 0;
        description
          "Xconnect state is undefined";
      }
      enum xconnect-state-up {
        value 1;
        description
          "Xconnect state is up";
      }
      enum xconnect-state-down {
        value 2;
        description
          "Xconnect state is down";
      }
      enum xconnect-state-admin-down {
        value 3;
        description
          "Xconnect state is admin down";
      }
      enum xconnect-state-recovering {
        value 4;
        description
          "Xconnect state is recovering";
      }
      enum xconnect-state-standby {
        value 5;
        description
          "Xconnect state is standby";
      }
      enum xconnect-state-hot-standby {
        value 6;
        description
          "Xconnect state is hot standby";
      }
      enum xconnect-state-incomplete {
        value 7;
        description
          "Xconnect state is incomplete";
      }
      enum xconnect-state-no-hardware {
        value 8;
        description
          "Xconnect state is no hardware";
      }
    }
    description
      "L2VPN xconnect state";
  }

  typedef l2vpn-fwd-type {
    type enumeration {
      enum l2vpn-fwd-type-invalid {
        value 0;
        description
          "L2VPN forwarder type invalid";
      }
      enum l2vpn-fwd-type-ac {
        value 1;
        description
          "L2VPN forwarder type attachment circuit";
      }
      enum l2vpn-fwd-type-pw {
        value 2;
        description
          "L2VPN forwarder type pseudo-wire";
      }
      enum l2vpn-fwd-type-vfi {
        value 3;
        description
          "L2VPN forwarder type virtual forwarding interface";
      }
      enum l2vpn-fwd-type-bd {
        value 4;
        description
          "L2VPN forwarder type bridge domain";
      }
    }
    description
      "L2VPN forwarder type";
  }

  typedef l2vpn-vc-status {
    type enumeration {
      enum l2vpn-vc-undefined {
        value 0;
        description
          "L2VPN VC status Undefined";
      }
      enum l2vpn-vc-up {
        value 1;
        description
          "L2VPN VC status Up";
      }
      enum l2vpn-vc-down {
        value 2;
        description
          "L2VPN VC status Down";
      }
      enum l2vpn-vc-admin-down {
        value 3;
        description
          "L2VPN VC status Admin Down";
      }
      enum l2vpn-vc-recovering {
        value 4;
        description
          "L2VPN VC status Recovering";
      }
      enum l2vpn-vc-standby {
        value 5;
        description
          "L2VPN VC status Standby";
      }
      enum l2vpn-vc-hot-standby {
        value 6;
        description
          "L2VPN VC status Hot Standby";
      }
      enum l2vpn-vc-state-max {
        value 7;
        description
          "L2VPN VC status State Max";
      }
    }
    description
      "VC status change";
  }

  typedef l2vpn-atom-service-type {
    type enumeration {
      enum l2vpn-atom-invalid {
        value 0;
        description
          "Invalid service type";
      }
      enum l2vpn-atom-p2p {
        value 1;
        description
          "L2VPN ATOM service type P2P";
      }
      enum l2vpn-atom-vfi {
        value 2;
        description
          "L2VPN ATOM service type VFI";
      }
      enum l2vpn-atom-transport {
        value 3;
        description
          "L2VPN ATOM service type transport";
      }
      enum l2vpn-atom-bd {
        value 4;
        description
          "L2VPN ATOM service type bridge-domain";
      }
      enum l2vpn-atom-evpn {
        value 5;
        description
          "L2VPN ATOM service type EVPN";
      }
    }
    description
      "L2VPN ATOM service type";
  }

  typedef l2vpn-atom-vc-protocol-type {
    type enumeration {
      enum l2vpn-atom-vc-proto-ldp {
        value 0;
        description
          "L2VPN ATOM signalling protocol type LDP";
      }
      enum l2vpn-atom-vc-proto-none {
        value 1;
        description
          "L2VPN ATOM signalling protocol none";
      }
      enum l2vpn-atom-vc-proto-bgp {
        value 2;
        description
          "L2VPN ATOM signalling protocol type BGP";
      }
      enum l2vpn-atom-vc-proto-cnt {
        value 3;
        description
          "L2VPN ATOM signalling protocol type invalid";
      }
    }
    description
      "L2VPN ATOM signalling protocol type";
  }

  typedef l2vpn-atom-pw-cw {
    type enumeration {
      enum l2vpn-atom-pw-cw-off {
        value 0;
        description
          "PW control word off";
      }
      enum l2vpn-atom-pw-cw-on {
        value 1;
        description
          "PW control word on";
      }
      enum l2vpn-atom-pw-cw-unkn {
        value 2;
        description
          "PW control word unknown";
      }
    }
    description
      "L2VPN ATOM PW Control word";
  }

  typedef l2vpn-cw-auto-sense {
    type enumeration {
      enum l2vpn-cw-autosense-off {
        value 0;
        description
          "Control word auto sense off";
      }
      enum l2vpn-cw-autosense-on {
        value 1;
        description
          "Control word auto sense on";
      }
      enum l2vpn-cw-autosense-unkn {
        value 2;
        description
          "Control word auto sense unknown";
      }
    }
    description
      "L2VPN ATOM PW Control word Auto sense";
  }

  typedef l2vpn-pw-lb-mode {
    type enumeration {
      enum l2vpn-pw-def-lb-mode {
        value 0;
        description
          "PW load-balance mode default";
      }
      enum l2vpn-pw-lb-mode-ecmp {
        value 1;
        description
          "PW load-balance mode ECMP";
      }
    }
    description
      "L2VPN PW load-balance mode";
  }

  typedef l2vpn-pw-lb-fc {
    type enumeration {
      enum l2vpn-pw-default-lb-fc {
        value 0;
        description
          "PW load-balance default flow classification";
      }
      enum l2vpn-pw-lb-fc-eth-src-mac {
        value 1;
        description
          "PW load-balance flow classification ethernet source MAC";
      }
      enum l2vpn-pw-lb-fc-eth-dst-mac {
        value 2;
        description
          "PW load-balance flow classification ethernet destination MAC";
      }
      enum l2vpn-pw-lb-fc-eth-src-dst-mac {
        value 3;
        description
          "PW load-balance flow classification ethernet source and destination MAC";
      }
      enum l2vpn-pw-lb-fc-ip-src-addr {
        value 4;
        description
          "PW load-balance flow classification source IP address";
      }
      enum l2vpn-pw-lb-fc-ip-dst-addr {
        value 5;
        description
          "PW load-balance flow classification destination IP address";
      }
      enum l2vpn-pw-lb-fc-ip-src-dst-addr {
        value 6;
        description
          "PW load-balance flow classification source and destination IP address";
      }
    }
    description
      "L2VPN PW load-balance flow classification";
  }

  typedef l2vpn-atom-vc-type {
    type enumeration {
      enum l2vpn-atom-vc-type-inv {
        value 0;
        description
          "Invalid virtual circuit type";
      }
      enum l2vpn-atom-vc-type-fr-dlci {
        value 1;
        description
          "Virtual circuit type FR DLCI";
      }
      enum l2vpn-atom-vc-type-atm-aal5 {
        value 2;
        description
          "Virtual circuit type ATM AAL5";
      }
      enum l2vpn-atom-vc-type-atm-cell {
        value 3;
        description
          "Virtual circuit type ATM cell";
      }
      enum l2vpn-atom-vc-type-ether-vlan {
        value 4;
        description
          "Virtual circuit type ethernet vlan";
      }
      enum l2vpn-atom-vc-type-ether {
        value 5;
        description
          "Virtual circuit type ethernet";
      }
      enum l2vpn-atom-vc-type-hdlc {
        value 6;
        description
          "Virtual circuit type HDLC";
      }
      enum l2vpn-atom-vc-type-ppp {
        value 7;
        description
          "Virtual circuit type PPP";
      }
      enum l2vpn-atom-vc-type-cem {
        value 8;
        description
          "Virtual circuit type CEm";
      }
      enum l2vpn-atom-vc-type-atm-vcc-cell {
        value 9;
        description
          "Virtual circuit type ATM VCC cell";
      }
      enum l2vpn-atom-vc-type-atm-vpc-cell {
        value 10;
        description
          "Virtual circuit type ATM VPC cell";
      }
      enum l2vpn-atom-vc-type-ip {
        value 11;
        description
          "Virtual circuit type IP";
      }
      enum l2vpn-atom-vc-type-satop-e1 {
        value 17;
        description
          "Virtual circuit type satop E1";
      }
      enum l2vpn-atom-vc-type-satop-t1 {
        value 18;
        description
          "Virtual circuit type satop T1";
      }
      enum l2vpn-atom-vc-type-satop-e3 {
        value 19;
        description
          "Virtual circuit type satop E3";
      }
      enum l2vpn-atom-vc-type-satop-t3 {
        value 20;
        description
          "Virtual circuit type satop T3";
      }
      enum l2vpn-atom-vc-type-cesopsn-basic {
        value 21;
        description
          "Virtual circuit type CES PSN basic";
      }
      enum l2vpn-atom-vc-type-cesopsn-tdm-cas {
        value 22;
        description
          "Virtual circuit type CES PSN TDM CAS";
      }
    }
    description
      "L2VPN ATOM VC type";
  }

  typedef l2vpn-atom-mgr-vc-last-error {
    type enumeration {
      enum l2vpn-vc-err-none {
        value 0;
        description
          "L2VPN ATOM manager VC error none";
      }
      enum l2vpn-vc-no-lcl-bdg-err {
        value 1;
        description
          "L2VPN ATOM manager VC no local binding error";
      }
      enum l2vpn-vc-no-rmt-bdg-err {
        value 2;
        description
          "L2VPN ATOM manager VC no remote binding error";
      }
      enum l2vpn-vc-mis-cw-err {
        value 3;
        description
          "L2VPN ATOM manager VC missing control word error";
      }
      enum l2vpn-vc-cbit-mism-err {
        value 4;
        description
          "L2VPN ATOM manager VC CBIT mismatch error";
      }
      enum l2vpn-vc-type-mism-err {
        value 5;
        description
          "L2VPN ATOM manager VC type mismatch error";
      }
      enum l2vpn-vc-mtu-mism-err {
        value 6;
        description
          "L2VPN ATOM manager VC MTU mismatch error";
      }
      enum l2vpn-vc-imp-rw-mism-err {
        value 7;
        description
          "L2VPN ATOM manager VC imposition rewrite mismatch error";
      }
      enum l2vpn-vc-tdm-mism-err {
        value 8;
        description
          "L2VPN ATOM manager VC TDM mismatch error";
      }
      enum l2vpn-vc-lcl-ac-not-rdy-err {
        value 9;
        description
          "L2VPN ATOM manager VC local AC not ready error";
      }
      enum l2vpn-vc-rmt-not-rdy-err {
        value 10;
        description
          "L2VPN ATOM manager VC remote not ready error";
      }
      enum l2vpn-vc-lcl-ac-down-err {
        value 11;
        description
          "L2VPN ATOM manager VC local AC Down error";
      }
      enum l2vpn-vc-rmt-ac-down-err {
        value 12;
        description
          "L2VPN ATOM manager VC remote AC Down error";
      }
      enum l2vpn-vc-lcl-ac-hard-down-err {
        value 13;
        description
          "L2VPN ATOM manager VC local AC Hard Down error";
      }
      enum l2vpn-vc-dp-flt-err {
        value 14;
        description
          "L2VPN ATOM manager VC dataplane fault error";
      }
      enum l2vpn-vc-bfd-flt-err {
        value 15;
        description
          "L2VPN ATOM manager VC BFD fault error";
      }
      enum l2vpn-vc-adj-down-err {
        value 16;
        description
          "L2VPN ATOM manager VC adjacency down error";
      }
      enum l2vpn-vc-lcl-bdg-aloc-no-ac-pw-err {
        value 17;
        description
          "L2VPN ATOM manager error in allocating VC local binding no AC PW type";
      }
      enum l2vpn-vc-lcl-bdg-alloc-no-cap-err {
        value 18;
        description
          "L2VPN ATOM manager error in allocating VC local binding no CAP";
      }
      enum l2vpn-vc-lcl-bdg-aloc-no-vc-type-err {
        value 19;
        description
          "L2VPN ATOM manager error in allocating VC local binding no VC type";
      }
      enum l2vpn-vc-lcl-bdg-mtu-err {
        value 20;
        description
          "L2VPN ATOM manager VC local binding MTU error";
      }
      enum l2vpn-vc-lcl-bdg-tdm-err {
        value 21;
        description
          "L2VPN ATOM manager VC local binding TDM error";
      }
      enum l2vpn-vc-lcl-bdg-dyn-lbl-err {
        value 22;
        description
          "L2VPN ATOM manager VC local binding Dynamic label error";
      }
      enum l2vpn-vc-lcl-bdg-stat-lbl-err {
        value 23;
        description
          "L2VPN ATOM manager VC local binding Static label error";
      }
      enum l2vpn-vc-lcl-bdg-rrp-no-cp-info-err {
        value 24;
        description
          "L2VPN ATOM manager VC local binding RRP no checkpoint info error";
      }
      enum l2vpn-vc-lcl-bdg-rrp-no-cp-lbl-err {
        value 25;
        description
          "L2VPN ATOM manager VC local binding RRP no checkpoint label error";
      }
      enum l2vpn-vc-lcl-bdg-rrp-cp-lbl-aloc-err {
        value 26;
        description
          "L2VPN ATOM manager VC local binding RRP checkpoint label allocation error";
      }
      enum l2vpn-vc-lcl-bdg-rrp-cp-lb-mt-err {
        value 27;
        description
          "L2VPN ATOM manager VC local binding RRP checkpoint label mismatch error";
      }
      enum l2vpn-vc-lcl-xc-sh-down-err {
        value 28;
        description
          "L2VPN ATOM manager VC local XC shut down error";
      }
      enum l2vpn-vc-lcl-pw-sh-down-err {
        value 29;
        description
          "L2VPN ATOM manager VC local PW shut down error";
      }
      enum l2vpn-vc-lcl-pw-bw-not-admt-err {
        value 30;
        description
          "L2VPN ATOM manager VC local PW BW not admitted error";
      }
      enum l2vpn-vc-lcl-bdg-cbit-err {
        value 31;
        description
          "L2VPN ATOM manager VC local binding CBIT error";
      }
    }
    description
      "L2VPN ATOM MGR VC last error";
  }

  typedef l2vpn-vc-next-hop-type {
    type enumeration {
      enum l2vpn-vc-no-nh {
        value 0;
        description
          "No Next hop";
      }
      enum l2vpn-vc-nh-p2p {
        value 1;
        description
          "Next hop is via a P2P link";
      }
      enum l2vpn-vc-nh-ipv4-addr {
        value 2;
        description
          "Next hop IPV4 address";
      }
      enum l2vpn-vc-nh-ipv6-addr {
        value 3;
        description
          "Next hop IPV6 address";
      }
    }
    description
      "Describes supported next hop types";
  }

  typedef l2vpn-pref-path-type {
    type enumeration {
      enum l2vpn-pref-not-conf {
        value 0;
        description
          "No preferred path configured";
      }
      enum l2vpn-pref-no-route {
        value 1;
        description
          "No route available to preferred path";
      }
      enum l2vpn-pref-out-if {
        value 2;
        description
          "Output tunnel interface";
      }
      enum l2vpn-pref-next-hop-addr {
        value 3;
        description
          "Next hop IPV4 address";
      }
    }
    description
      "Describes supported preferred path types";
  }

  typedef l2vpn-def-path-state {
    type enumeration {
      enum l2vpn-def-path-none {
        value 0;
        description
          "Default path none";
      }
      enum l2vpn-def-path-disabled {
        value 1;
        description
          "Default path disabled";
      }
      enum l2vpn-def-path-active {
        value 2;
        description
          "Default path active";
      }
      enum l2vpn-def-path-no-route {
        value 3;
        description
          "No route to default path";
      }
      enum l2vpn-def-path-ready {
        value 4;
        description
          "Default path ready";
      }
    }
    description
      "Describes default path state";
  }

  typedef l2vpn-vc-status-tlv {
    type enumeration {
      enum l2vpn-vc-stat-tlv-dis {
        value 0;
        description
          "L2VPN VC status TLV disabled";
      }
      enum l2vpn-vc-stat-tlv-en {
        value 1;
        description
          "L2VPN VC status TLV enabled";
      }
      enum l2vpn-vc-stat-tlv-unkn {
        value 2;
        description
          "L2VPN VC status TLV unknown";
      }
      enum l2vpn-vc-stat-tlv-sup {
        value 3;
        description
          "L2VPN VC status TLV supported";
      }
      enum l2vpn-vc-stat-tlv-not-sup {
        value 4;
        description
          "L2VPN VC status TLV not supported";
      }
    }
    description
      "L2VPN VC status TLV";
  }

  typedef l2vpn-atom-ldp-status {
    type enumeration {
      enum l2vpn-atom-ldp-def {
        value 0;
        description
          "L2VPN ATOM LDP status default";
      }
      enum l2vpn-atom-ldp-down {
        value 1;
        description
          "L2VPN ATOM LDP status down";
      }
      enum l2vpn-atom-ldp-down-no-sig {
        value 2;
        description
          "L2VPN ATOM LDP status down no signal";
      }
      enum l2vpn-atom-ldp-down-no-bind {
        value 3;
        description
          "L2VPN ATOM LDP status down no binding";
      }
      enum l2vpn-atom-ldp-up {
        value 4;
        description
          "L2VPN ATOM LDP status up";
      }
    }
    description
      "L2VPN ATOM LDP status";
  }

  typedef l2vpn-atom-mgr-state {
    type enumeration {
      enum l2vpn-atom-mgr-state-idle {
        value 0;
        description
          "L2VPN ATOM Manager state idle";
      }
      enum l2vpn-atom-mgr-state-prov {
        value 1;
        description
          "L2VPN ATOM Manager state provisioned";
      }
      enum l2vpn-atom-mgr-state-stdby-lcl-rdy {
        value 2;
        description
          "L2VPN ATOM Manager state standby local ready";
      }
      enum l2vpn-atom-mgr-state-ldp-ready {
        value 3;
        description
          "L2VPN ATOM Manager state LDP ready";
      }
      enum l2vpn-atom-mgr-state-lcl-rdy {
        value 4;
        description
          "L2VPN ATOM Manager state local ready";
      }
      enum l2vpn-atom-mgr-state-rmt-rdy {
        value 5;
        description
          "L2VPN ATOM Manager state remote ready";
      }
      enum l2vpn-atom-mgr-state-rmt-inv {
        value 6;
        description
          "L2VPN ATOM Manager state remote invalid";
      }
      enum l2vpn-atom-mgr-state-est {
        value 7;
        description
          "L2VPN ATOM Manager state establishing";
      }
      enum l2vpn-atom-mgr-state-act {
        value 8;
        description
          "L2VPN ATOM Manager state activating";
      }
      enum l2vpn-atom-mgr-state-ested {
        value 9;
        description
          "L2VPN ATOM Manager state established";
      }
    }
    description
      "L2VPN ATOM Manager state";
  }

  typedef l2vpn-atom-mgr-fsm-state {
    type enumeration {
      enum lndrnd {
        value 0;
        description
          "Local not ready down and remote not ready down";
      }
      enum lnurnd {
        value 1;
        description
          "Local not ready up and remote not ready down";
      }
      enum lrdrnd {
        value 2;
        description
          "Local ready down and remote not ready down";
      }
      enum lrurnd {
        value 3;
        description
          "Local ready up and remote not ready down";
      }
      enum lndrrd {
        value 4;
        description
          "Local ready down and remote ready down";
      }
      enum lndrra {
        value 5;
        description
          "Local not ready down and remote ready adjacency down";
      }
      enum lndrraa {
        value 6;
        description
          "Local not ready down, remote ready adjacency down and remote down";
      }
      enum lndrru {
        value 7;
        description
          "Local not ready down and remote ready up";
      }
      enum lnurrd {
        value 8;
        description
          "Local not ready up and remote ready down";
      }
      enum lnurra {
        value 9;
        description
          "Local not ready up and remote ready adjacency down";
      }
      enum lnurraa {
        value 10;
        description
          "Local not ready up, remote ready adjacency down and remote down";
      }
      enum lnurru {
        value 11;
        description
          "Local not ready up and remote ready up";
      }
      enum lrdrrd {
        value 12;
        description
          "Local ready up and remote ready down";
      }
      enum lrdrra {
        value 13;
        description
          "Local ready down and remote ready adjacency down";
      }
      enum lrdrraa {
        value 14;
        description
          "Local ready down, remote ready adjacency down and remote down";
      }
      enum lrdrru {
        value 15;
        description
          "Local ready down and remote ready up";
      }
      enum lrurrd {
        value 16;
        description
          "Local ready up and remote ready down";
      }
      enum lrurra {
        value 17;
        description
          "Local ready up and remote ready adjacency down";
      }
      enum lrurraa {
        value 18;
        description
          "Local ready up, remote ready adjacency down and remote down";
      }
      enum lrurru {
        value 19;
        description
          "Local ready up and remote ready up";
      }
      enum lndrnddp {
        value 20;
        description
          "Local not ready down and remote not ready down DP fault";
      }
      enum lnurnddp {
        value 21;
        description
          "Local not ready up and remote not ready down DP fault";
      }
      enum lrdrnddp {
        value 22;
        description
          "Local ready down and remote not ready down DP fault";
      }
      enum lrurnddp {
        value 23;
        description
          "Local ready up and remote not ready down DP fault";
      }
      enum lndrrddp {
        value 24;
        description
          "Local not ready down and remote ready down DP fault";
      }
      enum lndrradp {
        value 25;
        description
          "Local not ready down and remote ready adjacency down DP fault";
      }
      enum lndrraadp {
        value 26;
        description
          "Local not ready down, remote ready adjacency down DP fault and remote down";
      }
      enum lndrrudp {
        value 27;
        description
          "Local not ready down and remote ready up DP fault";
      }
      enum lnurrddp {
        value 28;
        description
          "Local not ready up and remote ready down DP fault";
      }
      enum lnurradp {
        value 29;
        description
          "Local not ready up and remote ready adjacency down DP fault";
      }
      enum lnurraadp {
        value 30;
        description
          "Local not ready up, remote ready adjacency down DP fault and remote down";
      }
      enum lnurrudp {
        value 31;
        description
          "Local not ready up and remote ready up DP fault";
      }
      enum lrdrrddp {
        value 32;
        description
          "Local ready down and remote ready down DP fault";
      }
      enum lrdrradp {
        value 33;
        description
          "Local ready down and remote ready adjacency down DP fault";
      }
      enum lrdrraadp {
        value 34;
        description
          "Local ready down, remote ready adjacency down DP fault and remote down";
      }
      enum lrdrrudp {
        value 35;
        description
          "Local ready down and remote ready up DP fault";
      }
      enum lrurrddp {
        value 36;
        description
          "Local ready up and remote ready down DP fault";
      }
      enum lrurradp {
        value 37;
        description
          "Local ready up and remote ready adjacency down DP fault";
      }
      enum lrurraadp {
        value 38;
        description
          "Local ready up, remote ready adjacency down DP fault and remote down";
      }
      enum lrurrudp {
        value 39;
        description
          "Local ready up and remote ready up DP fault";
      }
      enum slndrnd {
        value 40;
        description
          "VC shut, Local not ready down and remote not ready down";
      }
      enum slnurnd {
        value 41;
        description
          "VC shut, Local not ready up and remote not ready down";
      }
      enum slrdrnd {
        value 42;
        description
          "VC shut, Local ready down and remote not ready down";
      }
      enum slrurnd {
        value 43;
        description
          "VC shut, Local ready up and remote not ready down";
      }
      enum slndrrd {
        value 44;
        description
          "VC shut, Local not ready down and remote ready down";
      }
      enum slndrra {
        value 45;
        description
          "VC shut, Local not ready down and remote ready adjacency down";
      }
      enum slndrraa {
        value 46;
        description
          "VC shut, Local not ready down, remote ready adjacency down and remote down";
      }
      enum slndrru {
        value 47;
        description
          "VC shut, Local not ready down, remote ready up";
      }
      enum slnurrd {
        value 48;
        description
          "VC shut, Local not ready up and remote ready down";
      }
      enum slnurra {
        value 49;
        description
          "VC shut, Local not ready up and remote ready adjacency down";
      }
      enum slnurraa {
        value 50;
        description
          "VC shut, Local not ready up, remote ready adjacency down and remote down";
      }
      enum slnurru {
        value 51;
        description
          "VC shut, Local not ready up and remote ready up";
      }
      enum slrdrrd {
        value 52;
        description
          "VC shut, Local ready down and remote ready down";
      }
      enum slrdrra {
        value 53;
        description
          "VC shut, Local ready down and remote ready adjacency down";
      }
      enum slrdrraa {
        value 54;
        description
          "VC shut, Local ready down, remote ready adjacency down and remote down";
      }
      enum slrdrru {
        value 55;
        description
          "VC shut, Local ready down and remote ready up";
      }
      enum slrurrd {
        value 56;
        description
          "VC shut, Local ready up and remote ready down";
      }
      enum slrurra {
        value 57;
        description
          "VC shut, Local ready up and remote ready adjacency down";
      }
      enum slrurraa {
        value 58;
        description
          "VC shut, Local ready up, remote ready adjacency down and remote down";
      }
      enum slrurru {
        value 59;
        description
          "VC shut, Local ready up and remote ready up";
      }
      enum slndrnddp {
        value 60;
        description
          "VC shut, Local not ready down and remote not ready down DP fault";
      }
      enum slnurnddp {
        value 61;
        description
          "VC shut, Local not ready up and remote not ready down DP fault";
      }
      enum slrdrnddp {
        value 62;
        description
          "VC shut, Local ready down and remote not ready down DP fault";
      }
      enum slrurnddp {
        value 63;
        description
          "VC shut, Local ready up and remote not ready down DP fault";
      }
      enum slndrrddp {
        value 64;
        description
          "VC shut, Local not ready down and remote ready down DP fault";
      }
      enum slndrradp {
        value 65;
        description
          "VC shut, Local not ready down and remote ready adjacency down DP fault";
      }
      enum slndrraadp {
        value 66;
        description
          "VC shut, Local not ready down, remote ready adjacency down DP fault and remote down";
      }
      enum slndrrudp {
        value 67;
        description
          "VC shut, Local not ready down and remote ready up DP fault";
      }
      enum slnurrddp {
        value 68;
        description
          "VC shut, Local not ready up and remote ready down DP fault";
      }
      enum slnurradp {
        value 69;
        description
          "VC shut, Local not ready up and remote ready adjacency down DP fault";
      }
      enum slnurraadp {
        value 70;
        description
          "VC shut, Local not ready up, remote ready adjacency down DP fault and remote down";
      }
      enum slnurrudp {
        value 71;
        description
          "VC shut, Local not ready up and remote ready up DP fault";
      }
      enum slrdrrddp {
        value 72;
        description
          "VC shut, Local not ready down and remote ready down DP fault";
      }
      enum slrdrradp {
        value 73;
        description
          "VC shut, Local ready down and remote ready adjacency down DP fault";
      }
      enum slrdrraadp {
        value 74;
        description
          "VC shut, Local ready down, remote ready adjacency down DP fault and remote down";
      }
      enum slrdrrudp {
        value 75;
        description
          "VC shut, Local ready down and remote ready up DP fault";
      }
      enum slrurrddp {
        value 76;
        description
          "VC shut, Local ready up and remote ready down DP fault";
      }
      enum slrurradp {
        value 77;
        description
          "VC shut, Local ready up and remote ready adjacency down DP fault";
      }
      enum slrurraadp {
        value 78;
        description
          "VC shut, Local ready up, remote ready adjacency down DP fault and remote down";
      }
      enum slrurrudp {
        value 79;
        description
          "VC shut, Local ready up and remote ready up DP fault";
      }
    }
    description
      "L2VPN ATOM Manager FSM state";
  }

  typedef l2vpn-feat-conf {
    type enumeration {
      enum l2vpn-feat-not-conf {
        value 0;
        description
          "L2VPN Feature not configured";
      }
      enum l2vpn-feat-conf {
        value 1;
        description
          "L2VPN Feature configured";
      }
    }
    description
      "L2VPN feature configuration";
  }

  typedef l2vpn-feat-en {
    type enumeration {
      enum l2vpn-feat-not-en {
        value 0;
        description
          "L2VPN Feature disabled";
      }
      enum l2vpn-feat-en {
        value 1;
        description
          "L2VPN Feature enabled";
      }
      enum l2vpn-feat-not-appl {
        value 2;
        description
          "L2VPN Feature not applicable";
      }
    }
    description
      "L2VPN feature enablement";
  }

  typedef l2vpn-atom-fec-type {
    type enumeration {
      enum l2vpn-atomvc-fec-unkn {
        value 0;
        description
          "L2VPN ATOM VC unknown FEC";
      }
      enum l2vpn-atomvc-fec-128 {
        value 1;
        description
          "L2VPN ATOM VC FEC type 128";
      }
      enum l2vpn-atomvc-fec-129 {
        value 2;
        description
          "L2VPN ATOM VC FEC type 129";
      }
    }
    description
      "L2VPN ATOM FEC type";
  }

  typedef l2vpn-circuit-status {
    type enumeration {
      enum l2vpn-ckt-stat-none {
        value 0;
        description
          "L2VPN circuit status none";
      }
      enum l2vpn-ckt-stat-up {
        value 1;
        description
          "L2VPN circuit status Up";
      }
      enum l2vpn-ckt-stat-down {
        value 2;
        description
          "L2VPN circuit status Down";
      }
      enum l2vpn-ckt-stat-ac-rx-tx-flt {
        value 3;
        description
          "L2VPN AC Rx/Tx fault";
      }
      enum l2vpn-ckt-stat-pw-rx-tx-flt {
        value 4;
        description
          "L2VPN PW interface Rx/Tx fault";
      }
      enum l2vpn-ckt-stat-ac-pw-rx-tx-flt {
        value 5;
        description
          "L2VPN AC and PW interface Rx/Tx fault";
      }
      enum l2vpn-ckt-stat-hard-down {
        value 6;
        description
          "L2VPN circuit status Hard Down";
      }
      enum l2vpn-ckt-stat-not-rdy {
        value 7;
        description
          "L2VPN circuit status not ready";
      }
      enum l2vpn-ckt-stat-ckt-stdby {
        value 8;
        description
          "L2VPN circuit status Standby";
      }
      enum l2vpn-ckt-stat-go-active {
        value 9;
        description
          "L2VPN circuit status go active";
      }
      enum l2vpn-ckt-stat-recovering {
        value 10;
        description
          "L2VPN circuit status Recovering";
      }
      enum l2vpn-ckt-stat-admin-down {
        value 11;
        description
          "L2VPN circuit status Admin Down";
      }
      enum l2vpn-ckt-stat-no-fault {
        value 12;
        description
          "L2VPN circuit status no fault";
      }
      enum l2vpn-ckt-stat-not-sent {
        value 13;
        description
          "L2VPN circuit status not sent";
      }
      enum l2vpn-ckt-stat-not-appl {
        value 14;
        description
          "L2VPN circuit status not applicable";
      }
    }
    description
      "L2VPN circuit status";
  }

  typedef l2vpn-pw-sequence {
    type enumeration {
      enum l2vpn-pw-seq-off {
        value 0;
        description
          "PW sequence off";
      }
      enum l2vpn-pw-seq-tx {
        value 1;
        description
          "PW sequence transmit";
      }
      enum l2vpn-pw-seq-rx {
        value 2;
        description
          "PW sequence receive";
      }
      enum l2vpn-pw-seq-trans {
        value 3;
        description
          "PW sequence transparent";
      }
      enum l2vpn-pw-seq-both {
        value 4;
        description
          "PW sequence both";
      }
    }
    description
      "L2VPN ATOM PW Sequencing";
  }

  typedef l2vpn-iw-type {
    type enumeration {
      enum l2vpn-iw-inv {
        value 0;
        description
          "Invalid interworking type";
      }
      enum l2vpn-iw-fr-dlci {
        value 1;
        description
          "Interworking type FR DLCI";
      }
      enum l2vpn-iw-fr-dlci-lcl {
        value 2;
        description
          "Interworking type FR DLCI local";
      }
      enum l2vpn-iw-atm-aal5 {
        value 3;
        description
          "Interworking type ATM AAL5";
      }
      enum l2vpn-iw-atm-cell {
        value 4;
        description
          "Interworking type ATM cell";
      }
      enum l2vpn-iw-eth-vlan {
        value 5;
        description
          "Interworking type ethernet VLAN";
      }
      enum l2vpn-iw-eth {
        value 6;
        description
          "Interworking type ethernet";
      }
      enum l2vpn-iw-hdlc {
        value 7;
        description
          "Interworking type HDLC";
      }
      enum l2vpn-iw-ppp {
        value 8;
        description
          "Interworking type PPP";
      }
      enum l2vpn-iw-cem {
        value 9;
        description
          "Interworking type CEM";
      }
      enum l2vpn-iw-atm-vcc-cell {
        value 10;
        description
          "Interworking type ATM VCC cell";
      }
      enum l2vpn-iw-atm-vpc-cell {
        value 11;
        description
          "Interworking type ATM VPC cell";
      }
      enum l2vpn-iw-ip {
        value 12;
        description
          "Interworking type IP";
      }
      enum l2vpn-iw-vfi {
        value 13;
        description
          "Interworking type VFI";
      }
      enum l2vpn-iw-satop-e1 {
        value 15;
        description
          "Interworking type SATOP E1";
      }
      enum l2vpn-iw-satop-t1 {
        value 16;
        description
          "Interworking type SATOP T1";
      }
      enum l2vpn-iw-satop-e3 {
        value 17;
        description
          "Interworking type SATOP E3";
      }
      enum l2vpn-iw-satop-t3 {
        value 18;
        description
          "Interworking type SATOP T3";
      }
      enum l2vpn-iw-ces-psn-basic {
        value 19;
        description
          "Interworking type CES PSN basic";
      }
      enum l2vpn-iw-ces-psn-cas {
        value 20;
        description
          "Interworking type CES PSN CAS";
      }
      enum l2vpn-iw-atm-vc-unknown {
        value 21;
        description
          "Interworking type ATM VC unknown";
      }
      enum l2vpn-iw-atm-vp-unknown {
        value 22;
        description
          "Interworking type ATM VP unknown";
      }
      enum l2vpn-iw-atom {
        value 23;
        description
          "Interworking type ATOM";
      }
      enum l2vpn-iw-l2tpv2 {
        value 24;
        description
          "Interworking type L2TPV2";
      }
      enum l2vpn-iw-l2tpv3 {
        value 25;
        description
          "Interworking type L2TPV3";
      }
      enum l2vpn-iw-pw-udp {
        value 26;
        description
          "Interworking type PW UDP";
      }
      enum l2vpn-iw-docsis {
        value 27;
        description
          "Interworking type DOCSIS";
      }
      enum l2vpn-iw-docsis-vlan {
        value 28;
        description
          "Interworking type DOCSIS VLAN";
      }
    }
    description
      "L2VPN interworking type";
  }

  typedef l2vpn-service-state {
    type enumeration {
      enum l2vpn-serv-undef {
        value 0;
        description
          "L2VPN state is undefined";
      }
      enum l2vpn-serv-up {
        value 1;
        description
          "L2VPN service is up";
      }
      enum l2vpn-serv-down {
        value 2;
        description
          "L2VPN service is down";
      }
      enum l2vpn-serv-admin-down {
        value 3;
        description
          "L2VPN service is admin down";
      }
      enum l2vpn-serv-recovering {
        value 4;
        description
          "L2VPN service is recovering";
      }
      enum l2vpn-serv-stdby {
        value 5;
        description
          "L2VPN service is standby";
      }
      enum l2vpn-serv-hot-stdby {
        value 6;
        description
          "L2VPN service is hot standby";
      }
    }
    description
      "L2VPN service state";
  }

  typedef l2vpn-vccv-cc-type-flags {
    type bits {
      bit vccv-cc-cw {
        position 0;
        description
          "VCCV CC control word";
      }
      bit vccv-cc-ra {
        position 1;
        description
          "VCCV CC router alert";
      }
      bit vccv-cc-ttl {
        position 2;
        description
          "VCCV CC TTL";
      }
    }
    description
      "L2VPN VCCV control channel type flags";
  }

  typedef l2vpn-vccv-cv-type-flags {
    type bits {
      bit vccv-cv-icmp {
        position 0;
        description
          "VCCV CV using ICMP";
      }
      bit vccv-cv-lspv {
        position 1;
        description
          "VCCV CV using LSPV";
      }
      bit vccv-cv-bfd-udp {
        position 2;
        description
          "VCCV CV using BFD UDP";
      }
      bit vccv-cv-bfd-udp-sig {
        position 3;
        description
          "VCCV CV using BFD UDP with signalling";
      }
      bit vccv-cv-bfd-raw {
        position 4;
        description
          "VCCV CV using BFD RAW";
      }
      bit vccv-cv-bfd-raw-sig {
        position 5;
        description
          "VCCV CV using BFD RAW with signalling";
      }
    }
    description
      "L2VPN VCCV connectivity verification type flags";
  }

  grouping fwd-info-ac {
    description
      "L2VPN forwarder info for attachment circuit";
    leaf if-name {
      type string;
      description
        "Attachment circuit interface ";
    }
    leaf group-name {
      type string;
      description
        "Attachment circuit group name";
    }
    leaf encap {
      type l2vpn-ios-xe-oper:l2vpn-ac-circuit-type;
      description
        "Attachment circuit encapsulation";
    }
    leaf state {
      type l2vpn-ios-xe-oper:l2vpn-xconnect-segment-state;
      description
        "Attachment circuit state";
    }
    leaf state-in-l2vpn-service {
      type l2vpn-ios-xe-oper:l2vpn-xconnect-state;
      description
        "Attachment circuit state in L2VPN service";
    }
    leaf priority {
      type uint32;
      description
        "Attachment circuit priority";
    }
  }

  grouping fwd-info-pw {
    description
      "L2VPN forwarder info for pseudo-wire";
    leaf if-name {
      type string;
      description
        "Pseudo-wire interface ";
    }
    leaf group-name {
      type string;
      description
        "Pseudo-wire group name";
    }
    leaf encap {
      type l2vpn-ios-xe-oper:l2vpn-pw-encap-type;
      description
        "Pseudo-wire encapsulation";
    }
    leaf peer-address {
      type inet:ipv4-address;
      description
        "Pseudo-wire peer ipv4 address";
    }
    leaf vcid {
      type uint32;
      description
        "Pseudo-wire virtual circuit id";
    }
    leaf state {
      type l2vpn-ios-xe-oper:l2vpn-xconnect-segment-state;
      description
        "Pseudo-wire state";
    }
    leaf state-in-l2vpn-service {
      type l2vpn-ios-xe-oper:l2vpn-xconnect-state;
      description
        "Pseudo-wire state in L2VPN service";
    }
    leaf priority {
      type uint32;
      description
        "Pseudo-wire priority";
    }
  }

  grouping fwd-info-vfi {
    description
      "L2VPN forwarder info for ";
    leaf if-name {
      type string;
      description
        " VPLS interface ";
    }
    leaf group-name {
      type string;
      description
        " VPLS group name";
    }
    leaf encap {
      type l2vpn-ios-xe-oper:l2vpn-pw-encap-type;
      description
        " VPLS encapsulation";
    }
    leaf state {
      type l2vpn-ios-xe-oper:l2vpn-xconnect-segment-state;
      description
        " VPLS state";
    }
    leaf state-in-l2vpn-service {
      type l2vpn-ios-xe-oper:l2vpn-xconnect-state;
      description
        " State in L2VPN service";
    }
    leaf priority {
      type uint32;
      description
        " VPLS priority";
    }
  }

  grouping fwd-info-bd {
    description
      "L2VPN forwarder info for bd";
    leaf if-name {
      type string;
      description
        "Bridge domain interface ";
    }
    leaf group-name {
      type string;
      description
        "Bridge domain group name";
    }
    leaf encap {
      type l2vpn-ios-xe-oper:l2vpn-pw-encap-type;
      description
        "Bridge domain encapsulation";
    }
    leaf state {
      type l2vpn-ios-xe-oper:l2vpn-xconnect-segment-state;
      description
        "Bridge domain state";
    }
    leaf state-in-l2vpn-service {
      type l2vpn-ios-xe-oper:l2vpn-xconnect-state;
      description
        "Bridge domain state in L2VPN service";
    }
    leaf priority {
      type uint32;
      description
        "Bridge domain priority";
    }
  }

  grouping forwarder {
    description
      "L2VPN forwarder info";
    choice fwd-type-choice {
      description
        "Type of the L2VPN forwarder";
      case l2vpn-fwd-type-ac {
        container attachment-circuit {
          description
            "L2VPN attachment-circuit information";
          uses l2vpn-ios-xe-oper:fwd-info-ac;
        }
      }
      case l2vpn-fwd-type-pw {
        container pseudowire {
          description
            "L2VPN pseudo-wire information";
          uses l2vpn-ios-xe-oper:fwd-info-pw;
        }
      }
      case l2vpn-fwd-type-vfi {
        container vfi {
          description
            "L2VPN VPLS information";
          uses l2vpn-ios-xe-oper:fwd-info-vfi;
        }
      }
      case l2vpn-fwd-type-bd {
        container bridge-domain {
          description
            "L2VPN bridge domain information";
          uses l2vpn-ios-xe-oper:fwd-info-bd;
        }
      }
    }
  }

  grouping l2vpn-xconnect-key {
    description
      "L2VPN xconnect key";
    leaf peer-address {
      type inet:ipv4-address;
      description
        "L2VPN xconnect peer ipv4 address";
    }
    leaf vcid {
      type uint32;
      description
        "L2VPN xconnect virtual circuit id";
    }
  }

  grouping standby-segments {
    description
      "L2VPN xconnect standby segments";
    container segment1 {
      description
        "L2VPN xconnect standby segment 1";
      uses l2vpn-ios-xe-oper:forwarder;
    }
    container segment2 {
      description
        "L2VPN xconnect standby segment 2";
      uses l2vpn-ios-xe-oper:forwarder;
    }
  }

  grouping l2vpn-xconnect-data {
    description
      "L2VPN xconnect data";
    leaf xconnect-name {
      type string;
      description
        "L2VPN xconnect service name";
    }
    leaf service-type {
      type l2vpn-ios-xe-oper:l2vpn-service-type;
      description
        "L2VPN xconnect service type";
    }
    leaf xconnect-state {
      type l2vpn-ios-xe-oper:l2vpn-xconnect-state;
      description
        "L2VPN xconnect state";
    }
    leaf description {
      type string;
      description
        "L2VPN xconnect description";
    }
    container segment1 {
      description
        "L2VPN xconnect segment 1";
      uses l2vpn-ios-xe-oper:forwarder;
    }
    container segment2 {
      description
        "L2VPN xconnect segment 2";
      uses l2vpn-ios-xe-oper:forwarder;
    }
    list standby {
      description
        "A List of L2VPN xconnect standby segments if present";
      uses l2vpn-ios-xe-oper:standby-segments;
    }
  }

  grouping l2vpn-services {
    description
      "L2VPN services";
    list l2vpn-xconnect {
      key "peer-address vcid";
      description
        "L2VPN xconnect";
      uses l2vpn-ios-xe-oper:l2vpn-xconnect-key;
      uses l2vpn-ios-xe-oper:l2vpn-xconnect-data;
    }
  }

  grouping l2vpn-vc-next-hop {
    description
      "L2VPN Next hop info";
    choice next-hop-type-choice {
      description
        "Type of the Next hop";
      case l2vpn-vc-no-nh {
        leaf no-nh {
          type empty;
          description
            "L2VPN VC no next hop";
        }
      }
      case l2vpn-vc-nh-p2p {
        leaf p2p {
          type empty;
          description
            "L2VPN VC next hop P2P";
        }
      }
      case l2vpn-vc-nh-ipv4-addr {
        leaf nh-ipv4-addr {
          type inet:ipv4-address;
          description
            "L2VPN VC next hop IPV4 address";
        }
      }
      case l2vpn-vc-nh-ipv6-addr {
        leaf nh-ipv6-addr {
          type inet:ipv6-address;
          description
            "L2VPN VC next hop IPV6 address";
        }
      }
    }
  }

  grouping l2vpn-vc-pref-path {
    description
      "L2VPN VC preferred path information";
    choice pref-path-type-choice {
      description
        "Type of the preferred path";
      case l2vpn-pref-not-conf {
        leaf not-conf {
          type empty;
          description
            "L2VPN VC preferred path not configured";
        }
      }
      case l2vpn-pref-no-route {
        leaf no-route {
          type empty;
          description
            "L2VPN VC no route to preferred path";
        }
      }
      case l2vpn-pref-out-if {
        leaf out-if {
          type string;
          description
            "L2VPN VC output tunnel interface";
        }
      }
      case l2vpn-pref-next-hop-addr {
        leaf nh-addr {
          type inet:ipv4-address;
          description
            "L2VPN VC next hop IPV4 address";
        }
      }
    }
  }

  grouping l2vpn-atom-bgp-info {
    description
      "L2VPN ATOM BGP signalling info";
    leaf local-ve-id {
      type uint32;
      description
        "Local VE identifier";
    }
    leaf remote-ve-id {
      type uint32;
      description
        "Remote VE identifier";
    }
  }

  grouping l2vpn-atom-ldp-info {
    description
      "L2VPN ATOM LDP signalling info";
    leaf tgt-hello-src {
      type inet:ipv4-address;
      description
        "Source of the targetted hello message";
    }
    leaf tgt-hello-dest {
      type inet:ipv4-address;
      description
        "Destination of the targetted hello message";
    }
    leaf status {
      type l2vpn-ios-xe-oper:l2vpn-atom-ldp-status;
      description
        "Status of the LDP";
    }
    leaf gr-config {
      type l2vpn-ios-xe-oper:l2vpn-feat-conf;
      description
        "Graceful restart configuration";
    }
    leaf gr {
      type l2vpn-ios-xe-oper:l2vpn-feat-en;
      description
        "Graceful restart feature";
    }
    leaf nsr-config {
      type l2vpn-ios-xe-oper:l2vpn-feat-conf;
      description
        "NSR configuration";
    }
    leaf nsr {
      type l2vpn-ios-xe-oper:l2vpn-feat-en;
      description
        "NSR feature";
    }
    leaf fec-type {
      type l2vpn-ios-xe-oper:l2vpn-atom-fec-type;
      description
        "Type of FEC";
    }
  }

  grouping l2vpn-atom-vpws-info {
    description
      "L2VPN ATOM VPWS information";
    leaf assoc-member-if {
      type string;
      description
        "Associated member interface name";
    }
    leaf group-name {
      type string;
      description
        "Group name";
    }
    leaf status {
      type l2vpn-ios-xe-oper:l2vpn-service-state;
      description
        "Status of service";
    }
    leaf iw-type {
      type l2vpn-ios-xe-oper:l2vpn-iw-type;
      description
        "Interworking type";
    }
  }

  grouping l2vpn-atom-vpls-info {
    description
      "L2VPN ATOM VPLS information";
    leaf bd-id {
      type uint32;
      description
        "Bridge domain id";
    }
  }

  grouping l2vpn-service-info {
    description
      "L2VPN service information";
    leaf service-name {
      type string;
      description
        "L2VPN service name";
    }
    leaf service-id {
      type uint32;
      description
        "Service Identification";
    }
    choice atom-service-type-choice {
      description
        "Type of L2VPN ATOM service";
      case l2vpn-service-vpws {
        container vpws-info {
          description
            "L2VPN VPWS service information";
          uses l2vpn-ios-xe-oper:l2vpn-atom-vpws-info;
        }
      }
      case l2vpn-service-vpls {
        container vpls-info {
          description
            "L2VPN VPLS service information";
          uses l2vpn-ios-xe-oper:l2vpn-atom-vpls-info;
        }
      }
    }
  }

  grouping signalling-proto-info {
    description
      "L2VPN signalling protocol info";
    leaf ldp-route-watch {
      type l2vpn-ios-xe-oper:l2vpn-feat-en;
      description
        "LDP route watch status";
    }
    leaf label-state {
      type l2vpn-ios-xe-oper:l2vpn-atom-mgr-state;
      description
        "Label status";
    }
    leaf fsm-state {
      type l2vpn-ios-xe-oper:l2vpn-atom-mgr-fsm-state;
      description
        "State machine status";
    }
    leaf local-dp-status-rcv {
      type l2vpn-ios-xe-oper:l2vpn-circuit-status;
      description
        "Local dataplane status received";
    }
    leaf bfd-dp-status-rcv {
      type l2vpn-ios-xe-oper:l2vpn-circuit-status;
      description
        "BFD dataplane status received";
    }
    leaf bfd-dp-pm-status-rcv {
      type l2vpn-ios-xe-oper:l2vpn-circuit-status;
      description
        "BFD peer monitor status received";
    }
    leaf status-rcv-ac {
      type l2vpn-ios-xe-oper:l2vpn-circuit-status;
      description
        "Status received from access circuit";
    }
    leaf status-sent-ac {
      type l2vpn-ios-xe-oper:l2vpn-circuit-status;
      description
        "Status sent to access circuit";
    }
    leaf status-rcv-pw {
      type l2vpn-ios-xe-oper:l2vpn-circuit-status;
      description
        "Status received from pseudowire interface";
    }
    leaf status-sent-nw-peer {
      type l2vpn-ios-xe-oper:l2vpn-circuit-status;
      description
        "Status sent to network peer";
    }
    leaf status-rcv-nw-peer {
      type l2vpn-ios-xe-oper:l2vpn-circuit-status;
      description
        "Status received from network peer";
    }
    leaf adj-status-remote-peer {
      type l2vpn-ios-xe-oper:l2vpn-circuit-status;
      description
        "Adjacency status of remote peer";
    }
    choice signalling-choice {
      description
        "Type of signalling for L2VPN negotiations";
      case l2vpn-atom-vc-proto-ldp {
        container ldp-info {
          description
            "L2VPN LDP signalling information";
          uses l2vpn-ios-xe-oper:l2vpn-atom-ldp-info;
        }
      }
      case l2vpn-atom-vc-proto-bgp {
        container bgp-info {
          description
            "L2VPN BGP signalling information";
          uses l2vpn-ios-xe-oper:l2vpn-atom-bgp-info;
        }
      }
    }
  }

  grouping l2vpn-binding-params {
    description
      "L2VPN binding parameters";
    leaf label {
      type uint32;
      description
        "VC label value";
    }
    leaf group-id {
      type uint32;
      description
        "Group identifier";
    }
    leaf if-name {
      type string;
      description
        "Interface name";
    }
    leaf mtu {
      type uint16;
      description
        "Maximum transmission unit";
    }
    leaf control-word {
      type l2vpn-ios-xe-oper:l2vpn-atom-pw-cw;
      description
        "Control word information";
    }
    leaf cw-auto-sense {
      type l2vpn-ios-xe-oper:l2vpn-cw-auto-sense;
      description
        "Control word auto sense";
    }
    leaf vc-type {
      type l2vpn-ios-xe-oper:l2vpn-atom-vc-type;
      description
        "Type of VC";
    }
    leaf vccv-cv-type {
      type l2vpn-ios-xe-oper:l2vpn-vccv-cv-type-flags;
      description
        "VCCV CV type flag";
    }
    leaf vccv-cc-type {
      type l2vpn-ios-xe-oper:l2vpn-vccv-cc-type-flags;
      description
        "VCCV CC type flag";
    }
    leaf status-tlv {
      type l2vpn-ios-xe-oper:l2vpn-vc-status-tlv;
      description
        "Status TLV configuration";
    }
  }

  grouping l2vpn-pw-data-params {
    description
      "L2vpn PW binding data parameters";
    container local-binding {
      description
        "Binding details of the local node";
      uses l2vpn-ios-xe-oper:l2vpn-binding-params;
    }
    container remote-binding {
      description
        "Binding details of the remote node";
      uses l2vpn-ios-xe-oper:l2vpn-binding-params;
    }
  }

  grouping l2vpn-atom-dataplane-params {
    description
      "VC statistics data";
    leaf segment-id {
      type uint32;
      description
        "SSM Segment ID";
    }
    leaf switch-id {
      type uint32;
      description
        "SSM Switch ID";
    }
    leaf pwid {
      type uint32;
      description
        "PW ID";
    }
  }

  grouping l2vpn-atom-vc-statistics {
    description
      "L2vpn dataplane parameters";
    leaf rx-pkts {
      type uint64;
      description
        "RX packets";
    }
    leaf rx-bytes {
      type uint64;
      description
        "RX bytes";
    }
    leaf rx-drops {
      type uint64;
      description
        "RX drops";
    }
    leaf seq-err-pkts {
      type uint64;
      description
        "RX sequential error packets";
    }
    leaf tx-pkts {
      type uint64;
      description
        "TX packets";
    }
    leaf tx-bytes {
      type uint64;
      description
        "TX bytes";
    }
    leaf tx-drops {
      type uint64;
      description
        "TX drops";
    }
    leaf mwc-tx {
      type uint64;
      description
        "MAC withdraw TX counter";
    }
    leaf mwc-rx {
      type uint64;
      description
        "MAC withdraw RX counter";
    }
  }

  grouping l2vpn-atom-vc-data {
    description
      "L2VPN L2 atom VC data";
    leaf local-if-name {
      type string;
      description
        "Local Interface name";
    }
    leaf circuit-type {
      type l2vpn-ios-xe-oper:l2vpn-ac-circuit-type;
      description
        "Circuit type";
    }
    leaf if-name {
      type string;
      description
        "Interface name";
    }
    leaf service-type {
      type l2vpn-ios-xe-oper:l2vpn-atom-service-type;
      description
        "Service Type";
    }
    leaf service-name {
      type string;
      description
        "Service name";
    }
    leaf vc-status {
      type l2vpn-ios-xe-oper:l2vpn-vc-status;
      description
        "VC status";
    }
    leaf create-time {
      type yang:date-and-time;
      description
        "L2VPN VC Create time";
    }
    leaf last-status-change {
      type yang:date-and-time;
      description
        "L2VPN VC last status change";
    }
    leaf last-fsm-change {
      type yang:date-and-time;
      description
        "L2VPN VC last FSM change";
    }
    leaf last-error {
      type l2vpn-ios-xe-oper:l2vpn-atom-mgr-vc-last-error;
      description
        "L2VPN VC last error";
    }
    leaf output-if {
      type string;
      description
        "L2VPN VC output interface";
    }
    leaf-list label-stack {
      type uint32;
      ordered-by user;
      description
        "L2VPN imposed label stack";
    }
    container preferred-path {
      description
        "L2VPN VC preferred path";
      uses l2vpn-ios-xe-oper:l2vpn-vc-pref-path;
    }
    leaf default-path {
      type l2vpn-ios-xe-oper:l2vpn-def-path-state;
      description
        "L2VPN VC default path";
    }
    container next-hop {
      description
        "L2VPN VC next hop";
      uses l2vpn-ios-xe-oper:l2vpn-vc-next-hop;
    }
    leaf lb-mode {
      type l2vpn-ios-xe-oper:l2vpn-pw-lb-mode;
      description
        "L2VPN load-balance mode";
    }
    leaf lb-flow-class {
      type l2vpn-ios-xe-oper:l2vpn-pw-lb-fc;
      description
        "L2VPN load-balance flow classification mode";
    }
    container service-info {
      description
        "L2VPN Service information";
      uses l2vpn-ios-xe-oper:l2vpn-service-info;
    }
    leaf signalling-proto {
      type l2vpn-ios-xe-oper:l2vpn-atom-vc-protocol-type;
      description
        "Signalling protocol type";
    }
    container signalling-info {
      description
        "Pseudowire signalling information";
      uses l2vpn-ios-xe-oper:signalling-proto-info;
    }
    leaf rx-sequence {
      type l2vpn-ios-xe-oper:l2vpn-pw-sequence;
      description
        "Receive sequencing";
    }
    leaf tx-sequence {
      type l2vpn-ios-xe-oper:l2vpn-pw-sequence;
      description
        "Transmit sequencing";
    }
    container pw-binding-data {
      description
        "Pseudowire binding data";
      uses l2vpn-ios-xe-oper:l2vpn-pw-data-params;
    }
    container dataplane-data {
      description
        "Dataplane Data";
      uses l2vpn-ios-xe-oper:l2vpn-atom-dataplane-params;
    }
    container vc-stats {
      description
        "VC Statistics";
      uses l2vpn-ios-xe-oper:l2vpn-atom-vc-statistics;
    }
  }

  grouping l2vpn-atom-key {
    description
      "L2VPN atom vc table key";
    leaf peer-address {
      type inet:ipv4-address;
      description
        "L2VPN vc peer ipv4 address";
    }
    leaf vcid {
      type uint32;
      description
        "L2VPN virtual circuit id";
    }
  }

  container l2vpn-oper-data {
    config false;
    description
      "L2VPN operational data";
    container l2vpn-services {
      presence "l2vpn-services";
      description
        "L2VPN services";
      uses l2vpn-ios-xe-oper:l2vpn-services;
    }
    list l2vpn-atom-vc-info {
      key "peer-address vcid";
      description
        "L2VPN atom VC Info";
      uses l2vpn-ios-xe-oper:l2vpn-atom-key;
      uses l2vpn-ios-xe-oper:l2vpn-atom-vc-data;
    }
  }
}
