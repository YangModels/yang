submodule Cisco-IOS-XE-logging {
  yang-version 1.1;
  belongs-to Cisco-IOS-XE-native {
    prefix ios;
  }

  import cisco-semver {
    prefix cisco-semver;
  }
  import ietf-inet-types {
    prefix inet;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Logging Yang Model.
     Copyright (c) 2016-2020 by Cisco Systems, Inc.
     All rights reserved.";

  revision 2023-03-01 {
    description
      "- Fix order of logging source-interface and switchport node";
    cisco-semver:module-version "4.4.0";
  }
  revision 2022-11-01 {
    description
      "- Update yang-version to 1.1";
    cisco-semver:module-version "4.3.0";
  }
  revision 2022-03-01 {
    description
      "- Fix for pattern issue in logging discriminator CLI";
    cisco-semver:module-version "4.2.0";
  }
  revision 2020-11-01 {
    description
      "- Restructure logging rate-limit for removing xpath ambiguity
       - Revision for string length of client-id trustpoint";
    cisco-semver:module-version "4.1.0";
  }
  revision 2020-07-01 {
    description
      "- Fix for trustpoint not needed while delete syslog profile
       - Restructure logging console/monitor for turbo parser and fix bugs";
    cisco-semver:module-version "4.0.0";
  }
  revision 2020-03-01 {
    description
      "- Add support for transport tls in logging host
       - Add support for tls-profile CLI
       - Add syslog-format in logging trap
       - logging persistent url pattern changed";
    cisco-semver:module-version "3.0.0";
  }
  revision 2019-11-01 {
    description
      "- limited logging-rate-limit-common-group/ranges to singleton
       - Fixed key fields of logging/source-interface
       - support for fqdn host CLI
       - Add missing descriptions to logging buffered
       - change date-type of leaf range in except container
       - change except to non presence container";
    cisco-semver:module-version "2.0.0";
  }
  revision 2019-07-01 {
    description
      "- Establish semantic version baseline
       - Add support for logging buffered xml
       - Remove default values for logging buffered
       - Add missing descriptions to logging buffered";
    cisco-semver:module-version "1.0.0";
  }
  revision 2018-11-07 {
    description
      "Cleanup spelling errors in description statements";
  }
  revision 2018-07-11 {
    description
      "Add full support for logging discriminator";
  }
  revision 2018-05-22 {
    description
      "Add default cli/value for logging buffered 4096 debugging";
  }
  revision 2018-03-18 {
    description
      "Add diff-dependency for logging discriminator,
       logging-level-type enumeration order fixed,
       Change logging remote-host to work correctly for
       oc-system mapping";
  }
  revision 2018-03-15 {
    description
      "Add dependency to buffered for persistent";
  }
  revision 2017-11-10 {
    description
      "Add more nodes under logging persistent";
  }
  revision 2017-08-25 {
    description
      "enforce order of deleting logging cli";
  }
  revision 2017-06-02 {
    description
      "logging host ipv6 more support";
  }
  revision 2017-03-01 {
    description
      "logging host/source-interface fix & enhancement";
  }
  revision 2017-02-07 {
    description
      "Initial revision";
  }

  typedef logging-level-type {
    type union {
      type uint16 {
        range "0..7";
      }
      type enumeration {
        enum emergencies;
        enum alerts;
        enum critical;
        enum errors;
        enum warnings;
        enum notifications;
        enum informational;
        enum debugging;
      }
    }
  }

  typedef logging-level-type-new {
    type enumeration {
      enum emergencies;
      enum alerts;
      enum critical;
      enum errors;
      enum warnings;
      enum notifications;
      enum informational;
      enum debugging;
    }
  }

  typedef severity-group-type {
    type string {
      pattern '[0-7](,[0-7])*';
    }
  }

  grouping logging-host-option-group {
    leaf discriminator {
      description
        "Specify a message discriminator identifier for this logging session";
      type string;
    }
  }

  grouping logging-host-transport-group {
    container transport {
      description
        "Specify the transport protocol (default=UDP)";
      container udp {
        description
          "User Datagram Protocol";
        leaf default-port {
          type empty;
        }
        list port-config {
          description
            "Port Number List";
          key "port-number";
          leaf port-number {
            description
              "Specify the UDP port number (default=514)";
            type uint16 {
              range "1..65535";
            }
          }
        }
        leaf-list port {
          status deprecated;
          type uint16;
        }
      }
      container tcp {
        description
          "Transport Control Protocol";
        leaf default-port {
          type empty;
        }
        list port-config {
          description
            "Port Number List";
          key "port-number";
          leaf port-number {
            description
              "Specify the TCP port number (default=601)";
            type uint16 {
              range "1..65535";
            }
          }
        }
        leaf-list port {
          status deprecated;
          type uint16;
        }
      }
      container tls {
        description
          "Transport Layer Security";
        leaf default-port {
          type empty;
        }
        list port {
          description
            "Port Number List";
          key "port-number";
          leaf port-number {
            description
              "Specify the TLS port number (default=6514)";
            type uint16 {
              range "1025..65535";
            }
          }
          leaf profile {
            description
              "Specify the TLS profile";
            must '/ios:native/ios:logging/ios:tls-profile[ios:profile=current()]' {
              error-message "Profile must be created 1st, deleted last";
            }
            type string;
          }
        }
        leaf profile {
          description
            "Specify the TLS profile created";
          must '/ios:native/ios:logging/ios:tls-profile[ios:profile=current()]' {
            error-message "Profile must be created 1st, deleted last";
          }
          type string;
        }
      }
    }
  }

  grouping logging-host-transport-config-group {
    list transport {
      description
        "Specify the transport protocol UDP,TCP";
      key "transport";
      leaf transport {
        description
          "Transport Protocol";
        type enumeration {
          enum udp;
          enum tcp;
        }
      }
      list port {
        description
          "port number List";
        key "port-number";
        leaf port-number {
          description
            "Specify the port number (default=514)";
          type uint16;
        }
        uses logging-host-option-group;
      }
      uses logging-host-option-group;
    }
  }

  grouping fqdn-host-vrf-list-group {
    list fqdn-host-vrf-transport-list {
      description
        "Configure IPv4,ipv6 syslog server";
      key "vrf";
      leaf vrf {
        description
          "Set VRF option";
        type string;
      }
      leaf maxip {
        description
          "Send log to 'n' number of syslog server";
        type uint16 {
          range "1..4";
        }
      }
      uses logging-host-option-group;
      uses logging-host-transport-config-group;
    }
  }

  grouping logging-host-transport-config {
    list transport {
      description
        "Specify the transport protocol UDP,TCP";
      key "transport";
      leaf transport {
        description
          "Transport Protocol";
        type enumeration {
          enum udp;
          enum tcp;
        }
      }
      leaf maxip {
        description
          "Send log to 'n' number of syslog server";
        type uint16 {
          range "1..4";
        }
      }
      list port {
        description
          "port number List";
        key "port-number";
        leaf port-number {
          description
            "Specify the port number (default=514)";
          type uint16;
        }
        uses logging-host-option-group;
      }
      uses logging-host-option-group;
    }
  }

  grouping fqdn-ipv4-host-list-group {
    list fqdn-ipv4-host-list {
      description
        "Configure IPv4 syslog server";
      key "ipv4-host";
      leaf ipv4-host {
        description
          "Fully Qualified Domain name of syslog server";
        type string;
      }
      leaf maxip {
        description
          "Send log to 'n' number of syslog server";
        type uint16 {
          range "1..4";
        }
      }
      uses logging-host-option-group;
      uses logging-host-transport-config;
      uses fqdn-host-vrf-list-group;
    }
  }

  grouping fqdn-ipv6-host-list-group {
    list fqdn-ipv6-host-list {
      description
        "Configure IPv6 syslog server";
      key "ipv6-host";
      leaf ipv6-host {
        description
          "Fully Qualified Domain name of syslog server";
        type string;
      }
      leaf maxip {
        description
          "Send log to 'n' number of syslog server";
        type uint16 {
          range "1..4";
        }
      }
      uses logging-host-option-group;
      uses logging-host-transport-config;
      uses fqdn-host-vrf-list-group;
    }
  }

  grouping logging-tls-version-group {
    container tls-version {
      description
        "TLS version for syslog connection";
      leaf version {
        description
          "TLS Version";
        type enumeration {
          enum TLSv1.1;
          enum TLSv1.2;
        }
      }
    }
  }

  grouping logging-tls-ciphersuite-group {
    container ciphersuite {
      description
        "Secure ciphersuite for syslog connection";
      leaf aes-128-cbc-sha {
        description
          "Encryption type tls_rsa_with_aes_cbc_128_sha ciphersuite";
        type empty;
      }
      leaf aes-256-cbc-sha {
        description
          "Encryption type tls_rsa_with_aes_cbc_256_sha ciphersuite";
        type empty;
      }
      leaf dhe-aes-cbc-sha2 {
        description
          "Encryption type tls_dhe_rsa_with_aes_cbc_sha2 (TLS version 1.1 & above) ciphersuite";
        type empty;
      }
      leaf dhe-aes-gcm-sha2 {
        description
          "Encryption type tls_dhe_rsa_with_aes_gcm_sha2 (TLS version 1.2 & above) ciphersuite";
        type empty;
      }
      leaf ecdhe-ecdsa-aes-gcm-sha2 {
        description
          "Encryption type tls_ecdhe_ecdsa_aes_gcm_sha2 (TLS version 1.2 & above) SuiteB ciphersuite";
        type empty;
      }
      leaf ecdhe-rsa-aes-cbc-sha2 {
        description
          "Encryption type tls_ecdhe_rsa_aes_cbc_sha2 (TLS version 1.2 & above) ciphersuite";
        type empty;
      }
      leaf ecdhe-rsa-aes-gcm-sha2 {
        description
          "Encryption type tls_ecdhe_rsa_aes_gcm_sha2 (TLS version 1.2 & above) ciphersuite";
        type empty;
      }
      leaf rsa-aes-cbc-sha2 {
        description
          "Encryption type tls_rsa_with_aes_cbc_sha2 (TLS version 1.2 & above) ciphersuite";
        type empty;
      }
      leaf rsa-aes-gcm-sha2 {
        description
          "Encryption type tls_rsa_with_aes_gcm_sha2 (TLS version 1.2 & above) ciphersuite";
        type empty;
      }
    }
  }

  grouping logging-tls-trustpoint-group {
    container client-id-trustpoint {
      description
        "Trustpoint for syslog client ID certificate";
      leaf trustpoint {
        description
          "Trustpoint name";
        type string {
          length "1..234";
        }
      }
    }
  }

  grouping logging-rate-limit-common-group {
    container common-options {
      leaf range {
        description
          "Messages per second";
        type uint16 {
          range "1..10000";
        }
      }
      container except {
        description
          "Messages of this severity or higher";
        leaf range {
          description
            "Logging severity level";
          type logging-level-type-new;
        }
      }
    }
  }

  grouping logging-rate-limit-common-group-deprecated {
    list ranges {
      status deprecated;
      max-elements 1;
      key "range";
      leaf range {
        status deprecated;
        description
          "Messages per second";
        type uint16 {
          range "1..10000";
        }
      }
      container except-config {
        status deprecated;
        description
          "Messages of this severity or higher";
        leaf range {
          status deprecated;
          description
            "Logging severity level";
          type logging-level-type-new;
        }
      }
      container except {
        status deprecated;
        description
          "Messages of this severity or higher";
        presence "true";
        leaf range {
          status deprecated;
          description
            "Logging severity level";
          type logging-level-type;
        }
      }
    }
  }

  grouping config-logging-discriminator-severity-actions {
    choice actions {
      leaf drops {
        description
          "To drop messages including the specified regular expression string";
        type severity-group-type;
      }
      leaf includes {
        description
          "To deliver messages including the specified regular expression string";
        type severity-group-type;
      }
    }
  }

  grouping config-logging-discriminator-common-actions {
    choice actions {
      leaf drops {
        description
          "To drop messages including the specified regular expression string";
        type string;
      }
      leaf includes {
        description
          "To deliver messages including the specified regular expression string";
        type string;
      }
    }
  }

  grouping config-logging-grouping {
    container logging {
      description
        "Modify message logging facilities";
      list discriminator {
        description
          "Create or modify a message discriminator";
        key "name";
        leaf name {
          type string;
        }
        container severity {
          description
            "Msg-body pattern for message filtering";
          uses config-logging-discriminator-severity-actions;
        }
        container facility {
          description
            "Facility pattern for message filtering";
          uses config-logging-discriminator-common-actions;
        }
        container mnemonics {
          description
            "Mnemonics pattern for message filtering";
          uses config-logging-discriminator-common-actions;
        }
        leaf rate-limit {
          description
            "Rate-limit value for message rate control";
          type uint16 {
            range "1..10000";
          }
        }
        container msg-body {
          description
            "Msg-body pattern for message filtering";
          uses config-logging-discriminator-common-actions {
            refine "actions/drops/drops";
            refine "actions/includes/includes";
          }
        }
      }
      container persistent {
        description
          "Set persistent logging parameters";
        presence "true";
        leaf url {
          description
            "URL to store logging messages";
          type string {
            pattern "(((bootflash:/)|(cns:/)|(flash:/)|(ftp:/)|(http:/)|(https:/)|(null:/)|(crashinfo:/)
                     (nvram:/)|(pram:/)|(rcp:/)|(scp:/)|(sftp:/)|(system:/)|(tar:/)|(tftp:/)|(tmpsys:/)|(webui:/)).*)";
          }
        }
        leaf size {
          description
            "Set disk space for writing log messages";
          type uint32 {
            range "16384..2147483647";
          }
        }
        leaf filesize {
          description
            "Set size of individual log files";
          type uint32 {
            range "8192..2147483647";
          }
        }
        leaf batch {
          description
            "Batch size for writing to persistent storage";
          type uint32 {
            range "4096..2147483647";
          }
        }
        leaf threshold {
          description
            "Setting threshold capacity. When setting circular logging is disabled";
          type uint8 {
            range "1..99";
          }
        }
        leaf immediate {
          description
            "Write log entry to storage immediately (no buffering).";
          type empty;
        }
        leaf notify {
          description
            "Notify when show logging [persistent] is activated.";
          type empty;
        }
        leaf protected {
          description
            "Eliminates manipulation on logging-persistent files";
          type empty;
        }
      }
      container monitor-config {
        choice config-options {
          case no-and-default-case {
            leaf monitor {
              description
                "Set console logging parameters";
              type boolean;
              default "true";
            }
          }
          case common-case {
            container common-config {
              container monitor {
                description
                  "Set terminal line (monitor) logging parameters";
                choice log-options {
                  case discriminatior-case {
                    container discriminator {
                      description
                        "Establish MD-Console association";
                      leaf name {
                        description
                          "discriminator name; string; max. 8 characters";
                        must '/ios:native/ios:logging/ios:discriminator[ios:name=current()]' {
                          error-message "discriminator must be created at first, deleted last";
                        }
                        type string;
                      }
                    }
                  }
                  case filtered-case {
                    leaf filtered {
                      description
                        "Enable filtered logging";
                      type empty;
                    }
                  }
                  case xxml-case {
                    leaf xxml {
                      description
                        "Enable logging in XML";
                      type empty;
                    }
                  }
                }
                leaf severity {
                  type logging-level-type;
                }
              }
            }
          }
        }
      }
      container monitor-conf {
        status deprecated;
        leaf monitor {
          description
            "DEPRECATED, use monitor-config";
          status deprecated;
          type boolean;
        }
      }
      container monitor {
        description
          "Set terminal line (monitor) logging parameters(DEPRECATED use monitor-config)";
        status deprecated;
        presence "true";
        leaf severity {
          status deprecated;
          type logging-level-type;
        }
        list discriminator {
          description
            "Establish MD-Console association(DEPRECATED)";
          status deprecated;
          key "name";
          leaf name {
            status deprecated;
            must '/ios:native/ios:logging/ios:discriminator[ios:name=current()]' {
              error-message "discriminator must be created at first, deleted last";
            }
            type string;
          }
          leaf severity {
            status deprecated;
            type logging-level-type;
          }
        }
      }
      leaf alarm {
        description
          "Configure syslog for alarms";
        type union {
          type uint8 {
            range "1..4";
          }
          type enumeration {
            enum critical;
            enum informational;
            enum major;
            enum minor;
          }
        }
      }
      container buffered {
        description
          "Set buffered logging parameters";
        choice buffered-params {
          leaf discriminator-config {
            description
              "Establish MD-Buffer association";
            type string;
          }
          leaf yxml {
            description
              "Enable logging in XML to XML logging buffer";
            type empty;
          }
        }
        leaf size-value {
          description
            "Logging buffer size";
          type uint32 {
            range "4096..2147483647";
          }
        }
        leaf severity-level {
          description
            "Logging severity level";
          type logging-level-type;
        }
        container size {
          status obsolete;
          leaf size-value {
            status obsolete;
            type uint32 {
              range "4096..2147483647";
            }
            default "4096";
          }
          leaf severity {
            status obsolete;
            type logging-level-type;
            default "debugging";
          }
        }
        choice buffered-param {
          case discriminator-param {
            list discriminator {
              status obsolete;
              description
                "(OBSOLETE, use discriminator-config)";
              key "name";
              leaf name {
                status obsolete;
                type string;
              }
              leaf size-value {
                status obsolete;
                type uint32 {
                  range "4096..2147483647";
                }
              }
              leaf severity {
                status obsolete;
                type logging-level-type;
              }
            }
          }
          case severity-level {
            leaf severity {
              status obsolete;
              type logging-level-type;
            }
          }
          case xxml-buffer {
            leaf xxml {
              status obsolete;
              description
                "Enable logging in XML to XML logging buffer(OBSOLETE)";
              type uint32 {
                range "4096..2147483647";
              }
            }
          }
        }
      }
      container console-config {
        choice config-options {
          case no-and-default-case {
            leaf console {
              description
                "Set console logging parameters";
              type boolean;
              default "true";
            }
          }
          case common-case {
            container common-config {
              container console {
                description
                  "Set console logging parameters";
                choice log-options {
                  case discriminatior-case {
                    container discriminator {
                      description
                        "Establish MD-Console association";
                      leaf name {
                        description
                          "discriminator name; string; max. 8 characters";
                        must '/ios:native/ios:logging/ios:discriminator[ios:name=current()]' {
                          error-message "discriminator must be created at first, deleted last";
                        }
                        type string;
                      }
                    }
                  }
                  case filtered-case {
                    leaf filtered {
                      description
                        "Enable filtered logging";
                      type empty;
                    }
                  }
                  case xxml-case {
                    leaf xxml {
                      description
                        "Enable logging in XML";
                      type empty;
                    }
                  }
                }
                leaf severity {
                  type logging-level-type;
                }
              }
            }
          }
        }
      }
      container console-guaranteed {
        container console {
          description
            "Set console logging parameters";
          leaf guaranteed {
            description
              "Guarantee console messages";
            type empty;
          }
        }
      }
      container console-conf {
        status deprecated;
        leaf console {
          description
            "Set console logging parameters(DEPRECATED, use console-config)";
          status deprecated;
          type boolean;
        }
      }
      container console {
        description
          "Set console logging parameters(DEPRECATED, use console-config)";
        status deprecated;
        presence "true";
        list discriminator {
          status deprecated;
          description
            "Establish MD-Console association(DEPRECATED, use console-config)";
          key "name";
          leaf name {
            status deprecated;
            must '/ios:native/ios:logging/ios:discriminator[ios:name=current()]' {
              error-message "discriminator must be created at first, deleted last";
            }
            type string;
          }
          leaf severity {
            status deprecated;
            type logging-level-type;
          }
        }
        leaf filtered {
          status deprecated;
          description
            "Enable filtered logging(DEPRECATED, use console-config)";
          type empty;
        }
        leaf guaranteed {
          status deprecated;
          description
            "Guarantee console messages(DEPRECATED, used console-config)";
          type empty;
        }
        leaf xxml {
          status deprecated;
          description
            "Enable logging in XML(DEPRECATED, use console-config)";
          type logging-level-type;
        }
        leaf severity {
          status deprecated;
          type logging-level-type;
        }
      }
      container event {
        description
          "Global interface events";
        container link-status {
          description
            "Globally enable/disable link UPDOWN message";
          leaf boot {
            description
              "Suppress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          type empty;
        }
      }
      leaf facility {
        description
          "Facility parameter for syslog messages";
        type enumeration {
          enum auth;
          enum cron;
          enum daemon;
          enum kern;
          enum local0;
          enum local1;
          enum local2;
          enum local3;
          enum local4;
          enum local5;
          enum local6;
          enum local7;
          enum lpr;
          enum mail;
          enum news;
          enum sys10;
          enum sys11;
          enum sys12;
          enum sys13;
          enum sys14;
          enum sys9;
          enum syslog;
          enum user;
          enum uucp;
        }
      }
      container history {
        description
          "Configure syslog history table";
        leaf size {
          description
            "Set history table size";
          type uint16;
        }
        leaf severity-level {
          type union {
            type uint8 {
              range "0..7";
            }
            type enumeration {
              enum emergencies;
              enum alerts;
              enum critical;
              enum errors;
              enum warnings;
              enum notifications;
              enum informational;
              enum debugging;
            }
          }
        }
      }
      container trap {
        description
          "Set trap server logging level";
        presence "true";
        choice level {
          case set-default {
            leaf trap-default {
              type empty;
            }
          }
          case set-level {
            leaf severity {
              type union {
                type uint8 {
                  range "0..7";
                }
                type enumeration {
                  enum alerts;
                  enum critical;
                  enum debugging;
                  enum emergencies;
                  enum errors;
                  enum informational;
                  enum notifications;
                  enum warnings;
                }
              }
              default "informational";
            }
          }
        }
        leaf syslog-format {
          description
            "Syslog format";
          type enumeration {
            enum rfc5424;
          }
        }
      }
      list tls-profile {
        description
          "TLS configurations for secure syslog connection:";
        key "profile";
        leaf profile {
          description
            "TLS profile name. Max 30 chars";
          type string {
            length "1..30";
          }
        }
        uses logging-tls-version-group;
        uses logging-tls-ciphersuite-group;
        uses logging-tls-trustpoint-group;
      }
      container host {
        description
          "Set syslog server IP address and parameters";
        list ipv4-host-list {
          key "ipv4-host";
          leaf ipv4-host {
            type inet:host;
          }
        }
        list ipv4-host-transport-list {
          key "ipv4-host";
          leaf ipv4-host {
            type inet:host;
          }
          uses logging-host-transport-group;
          uses logging-host-option-group;
        }
        list ipv4-host-vrf-list {
          key "ipv4-host vrf";
          leaf ipv4-host {
            type inet:host;
          }
          leaf vrf {
            description
              "Set VRF option";
            must '/ios:native/ios:vrf/ios:definition[ios:name=current()]/ios:address-family/ios:ipv4 or /ios:native/ios:ip/ios:vrf[ios:name=current()]' {
              error-message "VRF must be created 1st, deleted last";
            }
            type string;
          }
          uses logging-host-option-group;
        }
        list ipv4-host-vrf-transport-list {
          key "ipv4-host vrf";
          leaf ipv4-host {
            type inet:host;
          }
          leaf vrf {
            description
              "Set VRF option";
            must '/ios:native/ios:vrf/ios:definition[ios:name=current()]/ios:address-family/ios:ipv4 or /ios:native/ios:ip/ios:vrf[ios:name=current()]' {
              error-message "VRF must be created 1st, deleted last";
            }
            type string;
          }
          uses logging-host-transport-group;
          uses logging-host-option-group;
        }
        container ipv6 {
          description
            "Set syslog server IPv6 address";
          list ipv6-host-list {
            key "ipv6-host";
            leaf ipv6-host {
              type ios-types:ipv6-host;
            }
          }
          list ipv6-host-transport-list {
            key "ipv6-host";
            leaf ipv6-host {
              type ios-types:ipv6-host;
            }
            uses logging-host-transport-group;
            uses logging-host-option-group;
          }
          list ipv6-host-vrf-list {
            key "ipv6-host vrf";
            leaf ipv6-host {
              type ios-types:ipv6-host;
            }
            leaf vrf {
              description
                "Set VRF option";
              must '/ios:native/ios:vrf/ios:definition[ios:name=current()]/ios:address-family/ios:ipv6' {
                error-message "VRF must be created 1st, deleted last";
              }
              type string;
            }
            uses logging-host-option-group;
          }
          list ipv6-host-vrf-transport-list {
            key "ipv6-host vrf";
            leaf ipv6-host {
              type ios-types:ipv6-host;
            }
            leaf vrf {
              description
                "Set VRF option";
              must '/ios:native/ios:vrf/ios:definition[ios:name=current()]/ios:address-family/ios:ipv6' {
                error-message "VRF must be created 1st, deleted last";
              }
              type string;
            }
            uses logging-host-transport-group;
            uses logging-host-option-group;
          }
        }
        container fqdn {
          description
            "Configure periodic address resolution for syslog server";
          container ipv4 {
            description
              "Configure IPv4 syslog server";
            uses fqdn-ipv4-host-list-group;
          }
          container ipv6 {
            description
              "Configure IPv4 syslog server";
            uses fqdn-ipv6-host-list-group;
          }
        }
      }
      container origin-id {
        description
          "Add origin ID to syslog messages";
        choice origin-choice {
          case origin-type {
            leaf type-value {
              description
                "Use origin hostname/ip/ipv6 as ID";
              type enumeration {
                enum hostname;
                enum ip;
                enum ipv6;
              }
            }
          }
          case origin-name {
            leaf string {
              description
                "Define a unique text string as ID";
              type string;
            }
          }
        }
      }
      container rate-limit-config {
        choice config-options {
          case no-case {
            container no-rate-limit {
              leaf rate-limit {
                must ". = 'false'" {
                  error-message "rate limit cannot be setup without options";
                }
                type boolean;
              }
            }
          }
          case common-case {
            container common-config {
              container rate-limit {
                description
                  "Set messages per second limit";
                uses logging-rate-limit-common-group;
                container console {
                  description
                    "Rate limit only console messages";
                  uses logging-rate-limit-common-group;
                  container all {
                    description
                      "Rate limit all messages, including debug messages";
                    uses logging-rate-limit-common-group;
                  }
                }
                container all {
                  description
                    "Rate limit all messages, including debug messages";
                  uses logging-rate-limit-common-group;
                }
              }
            }
          }
        }
      }
      container rate-limit-conf {
        status deprecated;
        leaf rate-limit {
          description
            "DEPRECATED, use rate-limit";
          status deprecated;
          type boolean;
        }
      }
      container rate-limit {
        description
          "Set messages per second limit";
        status deprecated;
        presence "true";
        uses logging-rate-limit-common-group-deprecated;
        container console {
          status deprecated;
          description
            "Rate limit only console messages";
          uses logging-rate-limit-common-group-deprecated;
          container all {
            status deprecated;
            description
              "all";
            uses logging-rate-limit-common-group-deprecated;
          }
        }
        container all {
          status deprecated;
          description
            "Rate limit only console messages";
          uses logging-rate-limit-common-group-deprecated;
        }
      }
      container source-interface-conf {
        description
          "Specify interface for source address in logging transactions";
        leaf interface-name-non-vrf {
          type string;
        }
        list source-interface-vrf {
          description
            "Specify interface and vrf for source address in logging transactions";
          key "vrf";
          leaf vrf {
            description
              "Specify the vrf of source interface for logging transactions";
            type string;
          }
          leaf interface-name {
            type string;
            mandatory true;
          }
        }
      }
      list source-interface {
        status deprecated;
        description
          "Specify interface for source address in logging transactions";
        key "interface-name";
        leaf interface-name {
          status deprecated;
          type string;
        }
        leaf vrf {
          status deprecated;
          description
            "Specify the vrf of source interface for logging transactions";
          type string;
        }
      }
      container snmp-trap {
        description
          "Set SNMP trap logging level";
        leaf alerts {
          description
            "Immediate action needed           (severity=1)";
          type empty;
        }
        leaf critical {
          description
            "Critical conditions               (severity=2)";
          type empty;
        }
        leaf debugging {
          description
            "Debugging messages                (severity=7)";
          type empty;
        }
        leaf emergencies {
          description
            "System is unusable                (severity=0)";
          type empty;
        }
        leaf errors {
          description
            "Error conditions                  (severity=3)";
          type empty;
        }
        leaf informational {
          description
            "Informational messages            (severity=6)";
          type empty;
        }
        leaf notifications {
          description
            "Normal but significant conditions (severity=5)";
          type empty;
        }
        leaf warnings {
          description
            "Warning conditions                (severity=4)";
          type empty;
        }
      }
      leaf hostip {
        status deprecated;
        type inet:host;
      }
      container file {
        description
          "Set logging file parameters";
        leaf name {
          type string;
        }
        leaf max-size {
          type uint32;
        }
        leaf min-size {
          type uint32;
        }
        leaf severity {
          type logging-level-type;
        }
      }
      leaf snmp-authfail {
        type empty;
      }
      leaf buginf {
        description
          "Enable buginf logging for debugging";
        type empty;
      }
      leaf userinfo {
        description
          "Enable logging of user info on privileged mode enabling";
        type empty;
      }
    }
  }
}
