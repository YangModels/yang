submodule Cisco-IOS-XE-line {
  yang-version 1.1;
  belongs-to Cisco-IOS-XE-native {
    prefix ios;
  }

  import cisco-semver {
    prefix cisco-semver;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Line, configure a terminal line Yang Model.
     Copyright (c) 2016-2020 by Cisco Systems, Inc.
     All rights reserved.";

  revision 2023-07-01 {
    description
      "- Created line-grouping-aux";
    cisco-semver:module-version "4.3.0";
  }
  revision 2023-03-01 {
    description
      "- added type 6 encryption support for enable and line vty";
    cisco-semver:module-version "4.2.0";
  }
  revision 2022-11-01 {
    description
      "- added 'vrfname' under 'line vty access-class'
       - Update yang-version to 1.1";
    cisco-semver:module-version "4.1.0";
  }
  revision 2022-07-01 {
    description
      "- Created line-grouping-common, line-grouping-console, transport-input-grouping and line-grouping-transport-input-obsolete";
    cisco-semver:module-version "4.0.0";
  }
  revision 2022-03-01 {
    description
      "- Deprecated async-line
       - Added async-line-single and async-line-range";
    cisco-semver:module-version "3.2.0";
  }
  revision 2021-07-01 {
    description
      "- Removed 'presence' under 'line/login'";
    cisco-semver:module-version "3.1.0";
  }
  revision 2021-03-01 {
    description
      "- Initial revision for 17.5.1";
    cisco-semver:module-version "3.0.0";
  }
  revision 2020-11-01 {
    description
      "- Support for line auto-consolidation feature under line command
       - Hardening of line aux privilege level CLI
       - Support for autohangup under line";
    cisco-semver:module-version "2.0.0";
  }
  revision 2019-11-01 {
    description
      "- Add async line support";
    cisco-semver:module-version "1.1.0";
  }
  revision 2019-07-01 {
    description
      "- Establish semantic version baseline
       - Add session-disconnect-warning";
    cisco-semver:module-version "1.0.0";
  }
  revision 2018-11-07 {
    description
      "Renamed command to commands under line-group authorization inline with ios";
  }
  revision 2018-10-10 {
    description
      "Enabled configuration of multiple transport input/output protocol for single line console ";
  }
  revision 2018-08-10 {
    description
      "Enabled multiple authorization command for single line console ";
  }
  revision 2018-03-01 {
    description
      "Added line console authorization exec list commands ";
  }
  revision 2017-09-06 {
    description
      "Added line console/vty history ";
  }
  revision 2017-07-24 {
    description
      "Add session-limit";
  }
  revision 2017-06-02 {
    description
      "Add alt-name for console line";
  }
  revision 2017-05-29 {
    description
      "Added /line/vty/session-limit";
  }
  revision 2017-03-24 {
    description
      "Remove refuse-message and vacant-message";
  }
  revision 2017-02-07 {
    description
      "Initial revision";
  }

  grouping password-07-grouping {
    leaf level {
      description
        "Set exec level password";
      type uint8;
    }
    leaf type {
      type enumeration {
        enum 0;
        enum 6;
        enum 7;
      }
    }
    leaf secret {
      type string {
        pattern '.*';
      }
    }
  }

  grouping line-grouping-common {
    container authorization {
      description
        "Authorization parameters";
      list commands {
        description
          "For exec (shell) commands";
        key "enable-level auth-name";
        leaf enable-level {
          type uint8 {
            range "0..15";
          }
        }
        leaf auth-name {
          type string;
        }
      }
      container exec {
        description
          "For starting an exec (shell)";
        leaf authorization-name {
          description
            "Use an authorization list with this name";
          type string;
        }
        leaf default {
          description
            "Use the default authorization list";
          type empty;
        }
      }
    }
    container access-class {
      description
        "Filter connections based on an IP access list";
      list acccess-list {
        key "direction";
        leaf direction {
          type enumeration {
            enum in;
            enum out;
          }
        }
        leaf access-list {
          type ios-types:exp-acl-type;
          mandatory true;
        }
        leaf vrf-also {
          description
            "Same access list is applied for all VRFs";
          type empty;
        }
        leaf vrfname {
          description
            "Access list is applied for given VRFs";
          type string;
        }
      }
    }
    leaf no-activation-character {
      type boolean;
    }
    leaf activation-character {
      description
        "Define the activation character";
      type union {
        type string;
        type uint8 {
          range "0..127";
        }
      }
    }
    container autocommand {
      description
        "Automatically execute an EXEC command";
      leaf line {
        description
          "Appropriate EXEC command";
        type string;
      }
      container no-suppress-linenumber {
        description
          "Display service linenumber message";
        presence "true";
        leaf line {
          description
            "Appropriate EXEC command";
          type string;
        }
      }
    }
    container autocommand-options {
      description
        "Autocommand options";
      presence "true";
      container abort-character {
        description
          "Autocommand abort character";
        presence "true";
        leaf character {
          type union {
            type uint8;
            type string;
          }
        }
      }
      container delay {
        description
          "Delay autocommand execution";
        presence "true";
        leaf time {
          description
            "Time in seconds";
          type uint8 {
            range "0..120";
          }
        }
      }
      container nohangup {
        description
          "No hangup after autocommand completion";
        presence "true";
        leaf abort-character {
          description
            "Autocommand abort character";
          type empty;
        }
        leaf delay {
          description
            "Delay autocommand execution";
          type empty;
        }
      }
    }
    container autohangup_only {
      leaf autohangup {
        description
          "Automatically hangup when last connection closes";
        type empty;
      }
    }
    container autohangup {
      description
        "Automatically hangup when last connection closes";
      leaf session-timeout {
        description
          "Automatically hangup when current session Times-out";
        type boolean;
        default "true";
      }
    }
    leaf data-character-bits {
      description
        "Bits per character";
      type uint8 {
        range "7..8";
      }
    }
    container databits {
      description
        "Set number of data bits per character";
      leaf set-to-5 {
        description
          "Number of data bits";
        type empty;
      }
      leaf set-to-6 {
        description
          "Number of data bits";
        type empty;
      }
      leaf set-to-7 {
        description
          "Number of data bits";
        type empty;
      }
      leaf set-to-8 {
        description
          "Number of data bits";
        type empty;
      }
    }
    leaf domain-lookup {
      description
        "Enable domain lookups in show commands";
      type empty;
    }
    leaf editing {
      description
        "Enable command line editing";
      type empty;
    }
    container escape-character {
      description
        "Change the current line's escape character";
      leaf char {
        type union {
          type uint8;
          type enumeration {
            enum BREAK;
            enum DEFAULT;
            enum NONE;
          }
          type string;
        }
      }
      leaf soft {
        type empty;
      }
    }
    choice exec-choice {
      container no-exec {
        leaf exec {
          description
            "Configure EXEC";
          type boolean;
        }
      }
      container exec {
        container prompt {
          leaf timestamp {
            type empty;
          }
        }
      }
    }
    leaf exec-banner {
      description
        "Enable the display of the EXEC banner";
      type empty;
    }
    leaf exec-character-bits {
      description
        "Bits per character";
      type uint8 {
        range "7..8";
      }
    }
    container exec-timeout {
      description
        "Set the EXEC timeout";
      leaf minutes {
        description
          "<0-35791>;;Timeout in minutes";
        type uint32 {
          range "0..35791";
        }
      }
      leaf seconds {
        description
          "<0-2147483>;;Timeout in seconds";
        type uint32 {
          range "0..2147483";
        }
      }
    }
    container flowcontrol {
      description
        "Set the flow control";
      leaf NONE {
        description
          "Set no flow control";
        type empty;
      }
      leaf hardware {
        description
          "Set hardware flow control";
        type empty;
      }
      leaf software {
        description
          "Set software flow control";
        type empty;
      }
    }
    leaf full-help {
      description
        "Provide help to unprivileged user";
      type empty;
    }
    container history {
      description
        "Enable and control the command history function";
      presence "true";
      leaf size {
        description
          "Set history buffer size";
        type uint16 {
          range "0..256";
        }
      }
    }
    leaf international {
      description
        "Enable international 8-bit character support";
      type empty;
    }
    container ip {
      description
        "IP options";
      container netmask-format {
        description
          "Change display of netmasks";
        presence "true";
        leaf format {
          type enumeration {
            enum bit-count;
            enum decimal;
            enum hexadecimal;
          }
        }
      }
      leaf tcp {
        type empty;
      }
    }
    container ipv6 {
      container access-class {
        list access-class {
          key "access-class-name";
          leaf access-class-name {
            type string;
          }
          leaf enumeration-in-out {
            type enumeration {
              enum in;
              enum out;
            }
          }
          leaf vrfname {
            description
              "Access list is applied for given VRFs";
            type string;
          }
        }
      }
    }
    leaf length {
      description
        "Set number of lines on a screen";
      type uint16 {
        range "0..512";
      }
    }
    leaf line {
      type uint8;
    }
    leaf location {
      description
        "One text line describing the terminal's location";
      type string;
    }
    container logging {
      description
        "Modify message logging facilities";
      container synchronous {
        description
          "Synchronized message output";
        presence "true";
      }
    }
    container login {
      description
        "Enable password checking";
      leaf local {
        type empty;
      }
      leaf authentication {
        type string;
        default "default";
      }
    }
    container media-type {
      description
        "Console connection media type";
      leaf rj45 {
        description
          "Console connection set to RJ45";
        type empty;
      }
    }
    container modem {
      description
        "Configure the Modem Control Lines";
      leaf CTS-Alarm {
        description
          "Alarm device which only uses CTS for call control";
        type empty;
      }
      leaf DTR-active {
        description
          "Leave DTR low unless line has an active incoming connection or EXEC";
        type empty;
      }
      leaf Dialin {
        description
          "Configure line for a modern dial-in modem";
        type empty;
      }
      leaf Host {
        description
          "Devices that expect an incoming modem call";
        type empty;
      }
      leaf InOut {
        description
          "Configure line for incoming AND outgoing use of modem";
        type empty;
      }
      leaf Printer {
        description
          "Devices that require DSR/CD active";
        type empty;
      }
      leaf answer-timeout {
        description
          "Set interval between raising DTR and CTS response";
        type empty;
      }
      container autoconfigure {
        description
          "Automatically configure modem on line";
        leaf discovery {
          description
            "Attempt to determine modem type automatically";
          type empty;
        }
        leaf type {
          description
            "Modem Type";
          type string;
        }
      }
      leaf dtr-delay {
        description
          "Set interval during which DTR is held low";
        type empty;
      }
    }
    leaf monitor {
      description
        "Copy debug output to the current terminal line";
      type empty;
    }
    leaf motd-banner {
      description
        "Enable the display of the MOTD banner";
      type empty;
    }
    leaf notify {
      description
        "Inform users of output from concurrent sessions";
      type empty;
    }
    container padding {
      description
        "Set padding for a specified output character";
      leaf character {
        description
          "Character to be padded";
        type union {
          type uint8 {
            range "0..127";
          }
          type string;
        }
      }
      leaf null {
        type uint8;
      }
    }
    container parity {
      description
        "Set terminal parity";
      leaf even {
        description
          "Even parity";
        type empty;
      }
      leaf mark {
        description
          "Mark parity";
        type empty;
      }
      leaf none {
        description
          "No parity";
        type empty;
      }
      leaf odd {
        description
          "Odd parity";
        type empty;
      }
      leaf space {
        description
          "Space parity";
        type empty;
      }
    }
    container password {
      description
        "Set a password";
      uses password-07-grouping;
    }
    container prc {
      description
        "PRC commands";
      leaf expose {
        description
          "Expose PRC data";
        type empty;
      }
      leaf hide {
        description
          "Hide PRC data";
        type empty;
      }
    }
    container privilege {
      description
        "Change privilege level for line";
      container level {
        description
          "Assign default privilege level for line";
        leaf number {
          type uint8 {
            range "0..15";
          }
        }
      }
    }
    leaf rotary {
      description
        "Rotary group to add line to";
      type uint8 {
        range "1..99";
      }
    }
    leaf rxspeed {
      description
        "Receive speed";
      type uint32 {
        range "0..4294967295";
      }
    }
    container session-disconnect-warning {
      description
        "Set the session disconnect warning";
      leaf seconds {
        description
          "Session timeout warning in seconds";
        type uint32 {
          range "0..4294967295";
        }
      }
      leaf message {
        description
          "Optional warning message";
        type string;
      }
    }
    leaf session-limit {
      description
        "Set maximum number of sessions";
      type uint32;
    }
    container session-timeout {
      description
        "Set interval for closing connection when there is no input traffic";
      leaf session-timeout-value {
        type uint16 {
          range "0..35791";
        }
      }
      leaf output {
        description
          "Include output traffic as well as input traffic";
        type empty;
      }
    }
    leaf special-character-bits {
      description
        "Bits per character";
      type uint8 {
        range "7..8";
      }
    }
    leaf speed {
      description
        "Transmit and receive speeds";
      type uint32 {
        range "0..4294967295";
      }
    }
    leaf start-character {
      description
        "Define the start character";
      type union {
        type uint8;
        type string;
      }
    }
    leaf stop-character {
      description
        "Define the stop character";
      type union {
        type uint8;
        type string;
      }
    }
    leaf stopbits {
      description
        "Set async line stop bits";
      type enumeration {
        enum 1;
        enum 1.5;
        enum 2;
      }
    }
    leaf terminal-type {
      description
        "Terminal type";
      type string;
    }
    container timeout {
      description
        "Timeouts for the line";
      leaf login {
        description
          "Timeouts related to the login sequence";
        type empty;
      }
    }
    container telnet {
      description
        "Telnet protocol-specific configuration";
      leaf transparent {
        description
          "Send a CR as a CR followed by a NULL instead of a CR followed by a LF";
        type empty;
      }
    }
    container transport {
      description
        "Define transport protocols for line";
      container output {
        choice output-protocol {
          case all-protocol {
            leaf all {
              description
                "All protocols";
              type empty;
            }
          }
          case no-protocol {
            leaf none {
              description
                "Define no transport protocols for line";
              type empty;
            }
          }
          case other-protocol {
            leaf-list output {
              description
                "Define which protocols to use for outgoing connections";
              ordered-by user;
              type enumeration {
                enum acercon;
                enum lapb-ta;
                enum lat;
                enum mop;
                enum nasi;
                enum pad;
                enum rlogin;
                enum ssh;
                enum telnet;
                enum udptn;
                enum v120;
              }
            }
          }
        }
      }
      container preferred {
        description
          "Specify the preferred protocol to use";
        leaf protocol {
          type enumeration {
            enum acercon;
            enum lat;
            enum mop;
            enum nasi;
            enum none;
            enum pad;
            enum rlogin;
            enum ssh;
            enum telnet;
            enum udptn;
          }
        }
      }
    }
    leaf txspeed {
      description
        "Transmit speed";
      type uint32;
    }
    container usb-inactivity-timeout {
      description
        "Inactivity timeout for USB media type";
      leaf switch {
        description
          "Switch Number";
        type empty;
      }
    }
    leaf width {
      description
        "Number of characters on a screen line";
      type uint16 {
        range "0..512";
      }
    }
  }

  grouping line-grouping-deprecated {
    container authorization {
      status deprecated;
      description
        "Authorization parameters";
      list commands {
        status deprecated;
        description
          "For exec (shell) commands";
        key "enable-level auth-name";
        leaf enable-level {
          status deprecated;
          type uint8 {
            range "0..15";
          }
        }
        leaf auth-name {
          status deprecated;
          type string;
        }
      }
      container exec {
        status deprecated;
        description
          "For starting an exec (shell)";
        leaf authorization-name {
          status deprecated;
          description
            "Use an authorization list with this name";
          type string;
        }
        leaf default {
          status deprecated;
          description
            "Use the default authorization list";
          type empty;
        }
      }
    }
    container access-class {
      status deprecated;
      description
        "Filter connections based on an IP access list";
      list acccess-list {
        status deprecated;
        key "direction";
        leaf direction {
          status deprecated;
          type enumeration {
            enum in;
            enum out;
          }
        }
        leaf access-list {
          status deprecated;
          type ios-types:exp-acl-type;
          mandatory true;
        }
        leaf vrf-also {
          status deprecated;
          description
            "Same access list is applied for all VRFs";
          type empty;
        }
      }
    }
    leaf no-activation-character {
      status deprecated;
      type boolean;
    }
    leaf activation-character {
      status deprecated;
      description
        "Define the activation character";
      type union {
        type string;
        type uint8 {
          range "0..127";
        }
      }
    }
    container autocommand {
      status deprecated;
      description
        "Automatically execute an EXEC command";
      leaf line {
        status deprecated;
        description
          "Appropriate EXEC command";
        type string;
      }
      container no-suppress-linenumber {
        status deprecated;
        description
          "Display service linenumber message";
        presence "true";
        leaf line {
          status deprecated;
          description
            "Appropriate EXEC command";
          type string;
        }
      }
    }
    container autocommand-options {
      status deprecated;
      description
        "Autocommand options";
      presence "true";
      container abort-character {
        status deprecated;
        description
          "Autocommand abort character";
        presence "true";
        leaf character {
          status deprecated;
          type union {
            type uint8;
            type string;
          }
        }
      }
      container delay {
        status deprecated;
        description
          "Delay autocommand execution";
        presence "true";
        leaf time {
          status deprecated;
          description
            "Time in seconds";
          type uint8 {
            range "0..120";
          }
        }
      }
      container nohangup {
        status deprecated;
        description
          "No hangup after autocommand completion";
        presence "true";
        leaf abort-character {
          status deprecated;
          description
            "Autocommand abort character";
          type empty;
        }
        leaf delay {
          status deprecated;
          description
            "Delay autocommand execution";
          type empty;
        }
      }
    }
    container autohangup_only {
      status deprecated;
      leaf autohangup {
        status deprecated;
        description
          "Automatically hangup when last connection closes";
        type empty;
      }
    }
    container autohangup {
      status deprecated;
      description
        "Automatically hangup when last connection closes";
      leaf session-timeout {
        status deprecated;
        description
          "Automatically hangup when current session Times-out";
        type boolean;
        default "true";
      }
    }
    leaf data-character-bits {
      status deprecated;
      description
        "Bits per character";
      type uint8 {
        range "7..8";
      }
    }
    container databits {
      status deprecated;
      description
        "Set number of data bits per character";
      leaf set-to-5 {
        status deprecated;
        description
          "Number of data bits";
        type empty;
      }
      leaf set-to-6 {
        status deprecated;
        description
          "Number of data bits";
        type empty;
      }
      leaf set-to-7 {
        status deprecated;
        description
          "Number of data bits";
        type empty;
      }
      leaf set-to-8 {
        status deprecated;
        description
          "Number of data bits";
        type empty;
      }
    }
    leaf domain-lookup {
      status deprecated;
      description
        "Enable domain lookups in show commands";
      type empty;
    }
    leaf editing {
      status deprecated;
      description
        "Enable command line editing";
      type empty;
    }
    container escape-character {
      status deprecated;
      description
        "Change the current line's escape character";
      leaf char {
        status deprecated;
        type union {
          type uint8;
          type enumeration {
            enum BREAK;
            enum DEFAULT;
            enum NONE;
          }
          type string;
        }
      }
      leaf soft {
        status deprecated;
        type empty;
      }
    }
    choice exec-choice {
      container no-exec {
        status deprecated;
        leaf exec {
          description
            "Configure EXEC";
          type boolean;
        }
      }
      container exec {
        status deprecated;
        container prompt {
          status deprecated;
          leaf timestamp {
            status deprecated;
            type empty;
          }
        }
      }
    }
    leaf exec-banner {
      status deprecated;
      description
        "Enable the display of the EXEC banner";
      type empty;
    }
    leaf exec-character-bits {
      status deprecated;
      description
        "Bits per character";
      type uint8 {
        range "7..8";
      }
    }
    container exec-timeout {
      status deprecated;
      description
        "Set the EXEC timeout";
      leaf minutes {
        status deprecated;
        description
          "<0-35791>;;Timeout in minutes";
        type uint32 {
          range "0..35791";
        }
      }
      leaf seconds {
        status deprecated;
        description
          "<0-2147483>;;Timeout in seconds";
        type uint32 {
          range "0..2147483";
        }
      }
    }
    container flowcontrol {
      status deprecated;
      description
        "Set the flow control";
      leaf NONE {
        status deprecated;
        description
          "Set no flow control";
        type empty;
      }
      leaf hardware {
        status deprecated;
        description
          "Set hardware flow control";
        type empty;
      }
      leaf software {
        status deprecated;
        description
          "Set software flow control";
        type empty;
      }
    }
    leaf full-help {
      status deprecated;
      description
        "Provide help to unprivileged user";
      type empty;
    }
    container history {
      status deprecated;
      description
        "Enable and control the command history function";
      presence "true";
      leaf size {
        status deprecated;
        description
          "Set history buffer size";
        type uint16 {
          range "0..256";
        }
      }
    }
    leaf international {
      status deprecated;
      description
        "Enable international 8-bit character support";
      type empty;
    }
    container ip {
      status deprecated;
      description
        "IP options";
      container netmask-format {
        status deprecated;
        description
          "Change display of netmasks";
        presence "true";
        leaf format {
          status deprecated;
          type enumeration {
            enum bit-count;
            enum decimal;
            enum hexadecimal;
          }
        }
      }
      leaf tcp {
        status deprecated;
        type empty;
      }
    }
    container ipv6 {
      status deprecated;
      container access-class {
        status deprecated;
        list access-class {
          status deprecated;
          key "access-class-name";
          leaf access-class-name {
            status deprecated;
            type string;
          }
          leaf enumeration-in-out {
            status deprecated;
            type enumeration {
              enum in;
              enum out;
            }
          }
        }
      }
    }
    leaf length {
      status deprecated;
      description
        "Set number of lines on a screen";
      type uint16 {
        range "0..512";
      }
    }
    leaf line {
      status deprecated;
      type uint8;
    }
    leaf location {
      status deprecated;
      description
        "One text line describing the terminal's location";
      type string;
    }
    container logging {
      status deprecated;
      description
        "Modify message logging facilities";
      container synchronous {
        status deprecated;
        description
          "Synchronized message output";
        presence "true";
      }
    }
    container login {
      status deprecated;
      description
        "Enable password checking";
      leaf local {
        type empty;
      }
      leaf authentication {
        status deprecated;
        type string;
        default "default";
      }
    }
    container media-type {
      status deprecated;
      description
        "Console connection media type";
      leaf rj45 {
        description
          "Console connection set to RJ45";
        type empty;
      }
    }
    container modem {
      status deprecated;
      description
        "Configure the Modem Control Lines";
      leaf CTS-Alarm {
        status deprecated;
        description
          "Alarm device which only uses CTS for call control";
        type empty;
      }
      leaf DTR-active {
        status deprecated;
        description
          "Leave DTR low unless line has an active incoming connection or EXEC";
        type empty;
      }
      leaf Dialin {
        status deprecated;
        description
          "Configure line for a modern dial-in modem";
        type empty;
      }
      leaf Host {
        status deprecated;
        description
          "Devices that expect an incoming modem call";
        type empty;
      }
      leaf InOut {
        status deprecated;
        description
          "Configure line for incoming AND outgoing use of modem";
        type empty;
      }
      leaf Printer {
        status deprecated;
        description
          "Devices that require DSR/CD active";
        type empty;
      }
      leaf answer-timeout {
        status deprecated;
        description
          "Set interval between raising DTR and CTS response";
        type empty;
      }
      container autoconfigure {
        status deprecated;
        description
          "Automatically configure modem on line";
        leaf discovery {
          status deprecated;
          description
            "Attempt to determine modem type automatically";
          type empty;
        }
        leaf type {
          status deprecated;
          description
            "Modem Type";
          type string;
        }
      }
      leaf dtr-delay {
        status deprecated;
        description
          "Set interval during which DTR is held low";
        type empty;
      }
    }
    leaf monitor {
      status deprecated;
      description
        "Copy debug output to the current terminal line";
      type empty;
    }
    leaf motd-banner {
      status deprecated;
      description
        "Enable the display of the MOTD banner";
      type empty;
    }
    leaf notify {
      status deprecated;
      description
        "Inform users of output from concurrent sessions";
      type empty;
    }
    container padding {
      status deprecated;
      description
        "Set padding for a specified output character";
      leaf character {
        status deprecated;
        description
          "Character to be padded";
        type union {
          type uint8 {
            range "0..127";
          }
          type string;
        }
      }
      leaf null {
        status deprecated;
        type uint8;
      }
    }
    container parity {
      status deprecated;
      description
        "Set terminal parity";
      leaf even {
        status deprecated;
        description
          "Even parity";
        type empty;
      }
      leaf mark {
        status deprecated;
        description
          "Mark parity";
        type empty;
      }
      leaf none {
        status deprecated;
        description
          "No parity";
        type empty;
      }
      leaf odd {
        status deprecated;
        description
          "Odd parity";
        type empty;
      }
      leaf space {
        status deprecated;
        description
          "Space parity";
        type empty;
      }
    }
    container password {
      status deprecated;
      description
        "Set a password";
      uses password-07-grouping;
    }
    container prc {
      status deprecated;
      description
        "PRC commands";
      leaf expose {
        status deprecated;
        description
          "Expose PRC data";
        type empty;
      }
      leaf hide {
        status deprecated;
        description
          "Hide PRC data";
        type empty;
      }
    }
    container privilege {
      status deprecated;
      description
        "Change privilege level for line";
      container level {
        status deprecated;
        description
          "Assign default privilege level for line";
        leaf number {
          status deprecated;
          type uint8 {
            range "0..15";
          }
        }
      }
    }
    leaf rotary {
      status deprecated;
      description
        "Rotary group to add line to";
      type uint8 {
        range "1..99";
      }
    }
    leaf rxspeed {
      status deprecated;
      description
        "Receive speed";
      type uint32 {
        range "0..4294967295";
      }
    }
    container session-disconnect-warning {
      status deprecated;
      description
        "Set the session disconnect warning";
      leaf seconds {
        status deprecated;
        description
          "Session timeout warning in seconds";
        type uint32 {
          range "0..4294967295";
        }
      }
      leaf message {
        status deprecated;
        description
          "Optional warning message";
        type string;
      }
    }
    leaf session-limit {
      status deprecated;
      description
        "Set maximum number of sessions";
      type uint32;
    }
    container session-timeout {
      status deprecated;
      description
        "Set interval for closing connection when there is no input traffic";
      leaf session-timeout-value {
        status deprecated;
        type uint16 {
          range "0..35791";
        }
      }
      leaf output {
        status deprecated;
        description
          "Include output traffic as well as input traffic";
        type empty;
      }
    }
    leaf special-character-bits {
      status deprecated;
      description
        "Bits per character";
      type uint8 {
        range "7..8";
      }
    }
    leaf speed {
      status deprecated;
      description
        "Transmit and receive speeds";
      type uint32 {
        range "0..4294967295";
      }
    }
    leaf start-character {
      status deprecated;
      description
        "Define the start character";
      type union {
        type uint8;
        type string;
      }
    }
    leaf stop-character {
      status deprecated;
      description
        "Define the stop character";
      type union {
        type uint8;
        type string;
      }
    }
    leaf stopbits {
      status deprecated;
      description
        "Set async line stop bits";
      type enumeration {
        enum 1;
        enum 1.5;
        enum 2;
      }
    }
    leaf terminal-type {
      status deprecated;
      description
        "Terminal type";
      type string;
    }
    container timeout {
      status deprecated;
      description
        "Timeouts for the line";
      leaf login {
        status deprecated;
        description
          "Timeouts related to the login sequence";
        type empty;
      }
    }
    container telnet {
      status deprecated;
      description
        "Telnet protocol-specific configuration";
      leaf transparent {
        status deprecated;
        description
          "Send a CR as a CR followed by a NULL instead of a CR followed by a LF";
        type empty;
      }
    }
    container transport {
      status deprecated;
      description
        "Define transport protocols for line";
      container input {
        status deprecated;
        choice input-protocol {
          case all-protocol {
            leaf all {
              status deprecated;
              description
                "All protocols";
              type empty;
            }
          }
          case no-protocol {
            leaf none {
              status deprecated;
              description
                "Define no transport protocols for line";
              type empty;
            }
          }
          case other-protocol {
            leaf-list input {
              status deprecated;
              description
                "Define which protocols to use when connecting to the terminal server";
              ordered-by user;
              type enumeration {
                enum acercon;
                enum lapb-ta;
                enum lat;
                enum mop;
                enum nasi;
                enum pad;
                enum rlogin;
                enum ssh;
                enum telnet;
                enum udptn;
                enum v120;
              }
            }
          }
        }
      }
      container output {
        status deprecated;
        choice output-protocol {
          case all-protocol {
            leaf all {
              status deprecated;
              description
                "All protocols";
              type empty;
            }
          }
          case no-protocol {
            leaf none {
              status deprecated;
              description
                "Define no transport protocols for line";
              type empty;
            }
          }
          case other-protocol {
            leaf-list output {
              status deprecated;
              description
                "Define which protocols to use for outgoing connections";
              ordered-by user;
              type enumeration {
                enum acercon;
                enum lapb-ta;
                enum lat;
                enum mop;
                enum nasi;
                enum pad;
                enum rlogin;
                enum ssh;
                enum telnet;
                enum udptn;
                enum v120;
              }
            }
          }
        }
      }
      container preferred {
        status deprecated;
        description
          "Specify the preferred protocol to use";
        leaf protocol {
          status deprecated;
          type enumeration {
            enum acercon;
            enum lat;
            enum mop;
            enum nasi;
            enum none;
            enum pad;
            enum rlogin;
            enum ssh;
            enum telnet;
            enum udptn;
          }
        }
      }
    }
    leaf txspeed {
      status deprecated;
      description
        "Transmit speed";
      type uint32;
    }
    container usb-inactivity-timeout {
      status deprecated;
      description
        "Inactivity timeout for USB media type";
      leaf switch {
        status deprecated;
        description
          "Switch Number";
        type empty;
      }
    }
    leaf width {
      status deprecated;
      description
        "Number of characters on a screen line";
      type uint16 {
        range "0..512";
      }
    }
  }

  grouping config-line-grouping {
    container line {
      description
        "Configure a terminal line";
      leaf auto-consolidation {
        description
          "Enable/Disable auto-consolidation of terminal lines";
        default "true";
        type boolean;
      }
      list line-list {
        key "first-number";
        leaf first-number {
          description
            "First Line number";
          type uint8 {
            range "0..17";
          }
        }
        leaf last-number {
          type uint16 {
            range "1..17";
          }
        }
        uses line-grouping;
      }
      list aux {
        description
          "Auxiliary line";
        key "first";
        max-elements 1;
        leaf first {
          type enumeration {
            enum 0;
          }
        }
        uses line-grouping-aux;
      }
      list console {
        description
          "Primary terminal line";
        key "first";
        max-elements 1;
        leaf first {
          type enumeration {
            enum 0;
          }
        }
        uses line-grouping-console;
      }
      list vty {
        description
          "Virtual terminal";
        key "first";
        leaf first {
          type uint16 {
            range "0..1869";
          }
        }
        leaf last {
          type uint16 {
            range "1..1869";
          }
        }
        uses line-grouping;
      }
      list async-line-single {
        key "first-name";
        leaf first-name {
          description
            "First Line name";
          type string {
            pattern '([0-9])+(/([0-9])+)*';
          }
        }
        uses line-grouping;
      }
      list async-line-range {
        key "first-name last-name";
        leaf first-name {
          description
            "First Line name in the range";
          type string {
            pattern '([0-9])+(/([0-9])+)*';
          }
        }
        leaf last-name {
          description
            "Last Line name in the range";
          type string {
            pattern '([0-9])+(/([0-9])+)*';
          }
        }
        uses line-grouping;
      }
      list async-line {
        status deprecated;
        key "first-name";
        leaf first-name {
          status deprecated;
          description
            "First Line name";
          type string {
            pattern '([0-9])+(/([0-9])+)*';
          }
        }
        leaf last-name {
          status deprecated;
          type string {
            pattern '([0-9])+(/([0-9])+)*';
          }
        }
        uses line-grouping-deprecated;
      }
    }
  }

  grouping line-grouping-console {
    uses line-grouping-common {
      augment "transport" {
        uses line-grouping-transport-input-obsolete;
      }
    }
  }

  grouping transport-input-grouping {
    container input {
      choice input-protocol {
        case all-protocol {
          leaf all {
            description
              "All protocols";
            type empty;
          }
        }
        case no-protocol {
          leaf none {
            description
              "Define no transport protocols for line";
            type empty;
          }
        }
        case other-protocol {
          leaf-list input {
            description
              "Define which protocols to use when connecting to the terminal server";
            ordered-by user;
            type enumeration {
              enum acercon;
              enum lapb-ta;
              enum lat;
              enum mop;
              enum nasi;
              enum pad;
              enum rlogin;
              enum ssh;
              enum telnet;
              enum udptn;
              enum v120;
            }
          }
        }
      }
    }
  }

  grouping line-grouping {
    uses line-grouping-common {
      augment "transport" {
        uses transport-input-grouping;
      }
    }
  }

  grouping line-grouping-aux {
    uses line-grouping-common {
      augment "transport" {
        uses transport-input-grouping;
      }
    }
  }

  grouping line-grouping-transport-input-obsolete {
    container input {
      status obsolete;
      choice input-protocol {
        status obsolete;
        case all-protocol {
          status obsolete;
          leaf all {
            status obsolete;
            description
              "All protocols";
            type empty;
          }
        }
        case no-protocol {
          status obsolete;
          leaf none {
            status obsolete;
            description
              "Define no transport protocols for line";
            type empty;
          }
        }
        case other-protocol {
          status obsolete;
          leaf-list input {
            status obsolete;
            description
              "Define which protocols to use when connecting to the terminal server";
            ordered-by user;
            type enumeration {
              enum acercon;
              enum lapb-ta;
              enum lat;
              enum mop;
              enum nasi;
              enum pad;
              enum rlogin;
              enum ssh;
              enum telnet;
              enum udptn;
              enum v120;
            }
          }
        }
      }
    }
  }
}
