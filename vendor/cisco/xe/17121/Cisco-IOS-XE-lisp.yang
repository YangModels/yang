module Cisco-IOS-XE-lisp {
  yang-version 1.1;
  namespace "http://cisco.com/ns/yang/Cisco-IOS-XE-lisp";
  prefix ios-lisp;

  import cisco-semver {
    prefix cisco-semver;
  }
  import ietf-inet-types {
    prefix inet;
  }
  import Cisco-IOS-XE-types {
    prefix ios-types;
  }
  import Cisco-IOS-XE-native {
    prefix ios;
  }
  import Cisco-IOS-XE-features {
    prefix ios-features;
  }
  import Cisco-IOS-XE-interface-common {
    prefix ios-ifc;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Locator ID Separation Protocol (LISP) Yang model.
     Copyright (c) 2016-2021 by Cisco Systems, Inc.
     All rights reserved.";

  revision 2023-07-01 {
    description
      "- Added support for preserving priority from publication to database-mappings";
    cisco-semver:module-version "7.2.0";
  }
  revision 2023-03-01 {
    description
      "- Added support for silent host under database-mapping
       - Added support for conditional registration of proxy database-mappings";
    cisco-semver:module-version "7.1.0";
  }
  revision 2022-11-01 {
    description
      "- Updated yang-version to 1.1
       - Updated constraints for database mapping
       - Added support for track-peers keyword under locator set
       - Obsolete nodes corresponding to old-styled CLIs";
    cisco-semver:module-version "7.0.0";
  }
  revision 2022-07-01 {
    description
      "- Added support for bridged-vm keyword under dynamic-eid detection
         multiple-addr command to enable SGT propagation with roaming
       - Obsolete default containers
       - Added support for enhanced forwarding
       - Added support for affinity-id CLI
       - Added dependency between locator-set and decapsulation nodes
       - Added support for extranet config propagation";
    cisco-semver:module-version "6.0.0";
  }
  revision 2021-11-01 {
    description
      "- Added support for route-export destinations-summary";
    cisco-semver:module-version "5.1.0";
  }
  revision 2021-07-01 {
    description
      "- Deprecated 'source-locator', added container 'src-locator'
       - Added support for L2 Publish-Subscribe
       - Added support for dynamic-eid detection multiple-addr
       - Added support for local keyword in database-mapping CLI
       - Added support for service-etr keyword in database-mapping CLI
       - Added support for allow-locator-service-etr CLI
       - Added support for sgt-policy-native-forward keyword in proxy-itr
       - Added support for disable-first-packet-forwarding CLI
       - Blocking modification or removal of domain-id and multihoming-id";
    cisco-semver:module-version "5.0.0";
  }
  revision 2021-03-01 {
    description
      "- Added support for below CLIs under router lisp
           platform resource-usage local-host <>
           platform resource-usage maximum-local-hosts l2 <>
           platform resource-usage maximum-local-hosts l3 <>
           platform resource-usage warning <>
           default-etr disable-metric
           added default-etr-route-map to database-mapping command
       - Added 'cli-delete-when-empty' attribute to route-import";
    cisco-semver:module-version "4.0.0";
  }
  revision 2020-11-01 {
    description
      "- Added support for service insertion
       - Added Support for disabling extranet policy propagation
       - Added 'fabric border' under router lisp to describe role
       - Added dynamic-eid dataplane-detection support under service-ipv4";
  }
  revision 2020-07-01 {
    description
      "NEEDS TO BE FIXED";
    cisco-semver:module-version "3.0.0";
  }
  revision 2020-03-01 {
    description
      "- Added support for updated SGT configuration
       - Added support for TCP-AO config
       - Added support for additional route-tag configurations
       - Added 'first-packet-petr' under top and instance service af";
    cisco-semver:module-version "2.0.0";
  }
  revision 2019-11-01 {
    description
      "
       - Added site-id specific configuration
       - Added support for publish-summary-only configuration
       - Added new rloc attributes config;
       - Added interface-grouping instead of using type string;
       - Added new inheritance knob map-cache conservative-allocation under
       service
       - Added no-use-petr config";
    cisco-semver:module-version "1.1.0";
  }
  revision 2019-07-01 {
    description
      "- Establish semantic version baseline
       - Added leaf for 'consistency-check' under 'locator'
       - Added a leaf under 'route-tag' for 'site eid-record'
       - Add support for redundancy sso
       - Add support for TCP path mtu discovery option
       - Adding ipv6 support to database-mapping under dynamic-eid
       - Make 'service' container non-presence
       - Added leaf 'minimum-mask-length'
       - Re-ordered min/max leafs under path-mtu-discovery
       - Marked 'instance-container/service/ethernet/map-request-source' as
         obsolete
       - deprecated etr-interface-ip by rloc-attributes under
         instance-container/service/ethernet/map-cache/eid-cont /
         instance-container/service/ipv4/map-cache/eid-interface /
         instance-container/service/ipv6/map-cache/eid-interface";
    cisco-semver:module-version "1.0.0";
  }
  revision 2019-01-22 {
    description
      "Added leaf for App-hosting Gigabit Ethernet interface";
  }
  revision 2018-12-04 {
    description
      "Setting default to false for flood access-tunnel";
  }
  revision 2018-11-28 {
    description
      "Add support for instance-service inheritance for publication-
       subscription feature";
  }
  revision 2018-11-07 {
    description
      "Cleanup spelling errors in description statements";
  }
  revision 2018-10-23 {
    description
      "Added support for border convergence";
  }
  revision 2018-08-27 {
    description
      "Add support for publication-subscription feature";
  }
  revision 2018-08-03 {
    description
      "Added leaf node 'proxy' under 'route-import'";
  }
  revision 2018-07-31 {
    description
      "Fixed map-cache away-eid send-map-request CLI";
  }
  revision 2018-07-16 {
    description
      "Added 'mr-use-petr' under instance-id service ipv4
       and removed validations inconsistent with CLI";
  }
  revision 2018-06-22 {
    description
      "Added new leaf 'access-tunnel' in the container 'flood'";
  }
  revision 2018-06-18 {
    description
      "Added fix for validation when instance-id 0 is used
       in extranet";
  }
  revision 2018-04-24 {
    description
      "This revision has changes for extranet internet access
       feature support";
  }
  revision 2018-04-17 {
    description
      "Added two new 'flood' leaves for Ethernet service";
  }
  revision 2018-04-12 {
    description
      "This revision has changes for extranet feature support";
  }
  revision 2018-04-01 {
    description
      "interface vlan lisp mobility <dyn-eid-name> is now a list
       instead of a single leaf";
  }
  revision 2018-03-13 {
    description
      "This revision has changes for ip source-locator knob";
  }
  revision 2018-03-10 {
    description
      "router lisp 0 is now not allowed via lisp-list";
  }
  revision 2018-02-08 {
    description
      "This revision has changes for multisite featurette";
  }
  revision 2018-01-18 {
    description
      "This revision has changes for per-subnet MSMR functionality";
  }
  revision 2017-11-27 {
    description
      "Added Change 25GE name";
  }
  revision 2017-11-14 {
    description
      "This revision has changes for the new 40 and 100GE interface addition";
  }
  revision 2017-09-15 {
    description
      "This revision has changes for the new 2gig interface addition";
  }
  revision 2017-08-16 {
    description
      "This revision has changes for new 5gig and 25gig interfaces addition";
  }
  revision 2017-04-28 {
    description
      "inet:ipv6-prefix changed to ios-types:ipv6-prefix";
  }
  revision 2017-03-22 {
    description
      "add locator default-set command support";
  }
  revision 2017-02-07 {
    description
      "Initial revision";
  }

  grouping router-lisp-inst-service-ip-route-import-database-protocol-grouping {
    container application {
      description
        "Application Protocol";
      uses router-lisp-ip-route-import-database-grouping;
    }
    list bgp {
      description
        "Border Gateway Protocol (BGP)";
      key "id";
      leaf id {
        type ios-types:bgp-as-number-type;
      }
      uses router-lisp-ip-route-import-database-grouping;
    }
    container connected {
      description
        "Connected";
      uses router-lisp-ip-route-import-database-grouping;
    }
    list eigrp {
      description
        "Enhanced Interior Gateway Routing Protocol (EIGRP)";
      key "id";
      leaf id {
        type uint16 {
          range "1..65535";
        }
      }
      uses router-lisp-ip-route-import-database-grouping;
    }
    container isis {
      description
        "ISO IS-IS";
      leaf process-id {
        description
          "Process name";
        type string;
      }
      uses router-lisp-ip-route-import-database-grouping;
    }
    container maximum-prefix {
      description
        "Maximum number of prefixes to pick up from the RIB";
      leaf number {
        type uint32 {
          range "1..4294967295";
        }
      }
      choice threshold-warning {
        case warning-only-case {
          leaf warning-only {
            description
              "Only give a warning message and do not limit entries";
            type empty;
          }
        }
        case threshold-case {
          leaf threshold {
            type uint8 {
              range "1..100";
            }
          }
        }
        case threshold-warning-case {
          leaf threshold1 {
            type uint8 {
              range "1..100";
            }
          }
          leaf warning-only1 {
            description
              "Only give a warning message and do not limit entries";
            type empty;
          }
        }
      }
    }
    container nd {
      description
        "Neighbor Discovery";
      uses router-lisp-ip-route-import-database-grouping;
    }
    container omp {
      if-feature "ios-features:omp";
      description
        "Overlay Management Protocol";
      uses router-lisp-ip-route-import-database-grouping;
    }
    list ospf {
      description
        "Open Shortest Path First (OSPF)";
      key "id";
      leaf id {
        type uint16 {
          range "1..65535";
        }
      }
      uses router-lisp-ip-route-import-database-grouping;
    }
    container static {
      description
        "Static routes";
      uses router-lisp-ip-route-import-database-grouping;
    }
  }

  grouping router-lisp-inst-service-ip-route-import-map-cache-protocol-grouping {
    container application {
      description
        "Application Protocol";
      presence "true";
      uses router-lisp-ip-route-import-map-cache-grouping;
    }
    list bgp {
      description
        "Border Gateway Protocol (BGP)";
      key "id";
      leaf id {
        type ios-types:bgp-as-number-type;
      }
      uses router-lisp-ip-route-import-map-cache-grouping;
    }
    container connected {
      description
        "Connected";
      presence "true";
      uses router-lisp-ip-route-import-map-cache-grouping;
    }
    list eigrp {
      description
        "Enhanced Interior Gateway Routing Protocol (EIGRP)";
      key "id";
      leaf id {
        type uint16 {
          range "1..65535";
        }
      }
      uses router-lisp-ip-route-import-map-cache-grouping;
    }
    container isis {
      description
        "ISO IS-IS";
      leaf id {
        description
          "Process name";
        type string;
      }
      uses router-lisp-ip-route-import-map-cache-grouping;
    }
    container maximum-prefix {
      description
        "Maximum number of prefixes to pick up from the RIB";
      leaf number {
        type uint32 {
          range "1..4294967295";
        }
      }
      choice threshold-warning {
        case warning-only-case {
          leaf warning-only {
            description
              "Only give a warning message and do not limit entries";
            type empty;
          }
        }
        case threshold-case {
          leaf threshold {
            type uint8 {
              range "1..100";
            }
          }
        }
        case threshold-warning-case {
          leaf threshold1 {
            type uint8 {
              range "1..100";
            }
          }
          leaf warning-only1 {
            description
              "Only give a warning message and do not limit entries";
            type empty;
          }
        }
      }
    }
    container nd {
      description
        "Neighbour Discovery";
      presence "true";
      uses router-lisp-ip-route-import-map-cache-grouping;
    }
    list ospf {
      description
        "Open Shortest Path First (OSPF)";
      key "id";
      leaf id {
        type uint16 {
          range "1..65535";
        }
      }
      uses router-lisp-ip-route-import-map-cache-grouping;
    }
    container static {
      description
        "Static routes";
      presence "true";
      uses router-lisp-ip-route-import-map-cache-grouping;
    }
  }

  grouping router-lisp-inst-service-ipv4-route-import-map-cache-protocol-grouping {
    container map-cache {
      description
        "Use RIB routes to define EID address space in map-cache";
      uses router-lisp-inst-service-ip-route-import-map-cache-protocol-grouping;
      container rip {
        description
          "Routing Information Protocol (RIP)";
        uses router-lisp-ip-route-import-map-cache-grouping;
      }
    }
  }

  grouping router-lisp-inst-service-ipv6-route-import-map-cache-protocol-grouping {
    container map-cache {
      description
        "Use RIB routes to define EID address space in map-cache";
      uses router-lisp-inst-service-ip-route-import-map-cache-protocol-grouping;
      list rip {
        description
          "Routing Information Protocol (RIP)";
        key "id";
        leaf id {
          description
            "User selected string identifying this process";
          type string;
        }
        uses router-lisp-ip-route-import-map-cache-grouping;
      }
    }
  }

  grouping router-lisp-inst-service-ipv4-route-import-database-protocol-grouping {
    container database {
      description
        "Use RIB routes to define local EID database entries";
      uses router-lisp-inst-service-ip-route-import-database-protocol-grouping;
      container rip {
        description
          "Routing Information Protocol (RIP)";
        uses router-lisp-ip-route-import-database-grouping;
      }
    }
  }

  grouping router-lisp-inst-service-ipv6-route-import-database-protocol-grouping {
    container database {
      description
        "Use RIB routes to define local EID database entries";
      uses router-lisp-inst-service-ip-route-import-database-protocol-grouping;
      list rip {
        description
          "Routing Information Protocol (RIP)";
        key "id";
        leaf id {
          description
            "User selected string identifying this process";
          type string;
        }
        uses router-lisp-ip-route-import-database-grouping;
      }
    }
  }

  grouping router-lisp-inst-service-ip-route-import-prefix-list-protocol-grouping {
    list prefix-list-proto {
      key "prefix-list protocol";
      leaf prefix-list {
        type string;
      }
      leaf protocol {
        type enumeration {
          enum application;
          enum bgp;
          enum connected;
          enum eigrp;
          enum isis;
          enum maximum-prefix;
          enum nd;
          enum ospf;
          enum static;
          enum rip;
        }
      }
      list bgp-id {
        key "bgp-id";
        when "../protocol = 'bgp'";
        leaf bgp-id {
          type ios-types:bgp-as-number-type;
        }
        leaf route-map {
          type string;
        }
      }
      list eigrp-or-ospf-id {
        when "../protocol = 'eigrp' or ../protocol = 'ospf'";
        key "int16-id";
        leaf int16-id {
          type uint16 {
            range "1..65535";
          }
        }
        leaf route-map {
          type string;
        }
      }
      leaf isis-id {
        when "../protocol = 'isis'";
        type string;
      }
      leaf number {
        when "../protocol = 'maximum-prefix'";
        type uint32 {
          range "1..4294967295";
        }
      }
      leaf threshold {
        when "../protocol = 'maximum-prefix'";
        type uint8 {
          range "1..100";
        }
      }
      leaf warning-only {
        when "../protocol = 'maximum-prefix'";
        type empty;
      }
      leaf route-map {
        when "not(../protocol = 'maximum-prefix')";
        type string;
      }
    }
  }

  grouping router-lisp-inst-service-ipv6-route-import-protocol-grouping {
    uses router-lisp-inst-service-ipv6-route-import-database-protocol-grouping;
    uses router-lisp-inst-service-ipv6-route-import-map-cache-protocol-grouping;
    uses router-lisp-inst-service-ip-route-import-prefix-list-protocol-grouping;
  }

  grouping router-lisp-inst-service-ipv4-route-import-protocol-grouping {
    uses router-lisp-inst-service-ipv4-route-import-database-protocol-grouping;
    uses router-lisp-inst-service-ipv4-route-import-map-cache-protocol-grouping;
    uses router-lisp-inst-service-ip-route-import-prefix-list-protocol-grouping;
  }

  grouping router-lisp-xtr-prefix-list-grouping {
    leaf prefix-list {
      description
        "Associates ITR/ETR with prefix list";
      type string;
    }
  }

  grouping router-lisp-map-server-domain-id-grouping {
    leaf domain-id {
      description
        "Domain-ID associated with map server";
      type uint32 {
        range "1..4294967038";
      }
    }
  }

  grouping router-lisp-itr-grouping {
    container itr {
      description
        "Configures a LISP Ingress Tunnel Router (ITR)";
      list map-resolver {
        description
          "Configures map-resolver address for sending Map-Requests";
        key "ip-addr";
        leaf ip-addr {
          type inet:ip-address;
        }
        uses router-lisp-xtr-prefix-list-grouping;
      }
      leaf nmr-ttl {
        description
          "Override negative map-reply TTL for site EID";
        type uint16 {
          range "1..900";
        }
      }
    }
    container itr-enable {
      leaf itr {
        description
          "Configures a LISP Ingress Tunnel Router (ITR)";
        type empty;
      }
    }
  }

  grouping router-lisp-etr-grouping {
    container etr-enable {
      leaf etr {
        description
          "Configures a LISP Egress Tunnel Router (ETR)";
        type empty;
      }
    }
    container etr {
      description
        "Configures a LISP Egress Tunnel Router (ETR)";
      uses router-lisp-map-server-grouping;
      leaf map-cache-ttl {
        type uint16 {
          range "60..10080";
        }
      }
      container accept-map-request-mapping {
        leaf accept-mappping {
          type empty;
        }
        leaf verify {
          type empty;
        }
      }
    }
  }

  grouping router-lisp-database-mapping-limit-grouping {
    container limit {
      description
        "Configures the maximum size of local EID prefixes database";
      leaf dynamic {
        description
          "Configures the maximum size of dynamic local EID prefixes database";
        type uint32;
      }
      leaf warning-threshold {
        description
          "Send warning message to syslog when the database-mapping dynamic size reaches this percentage of the limit";
        type uint8 {
          range "1..100";
        }
      }
    }
    container proxy {
      description
        "Configure flags specific to proxy database entries";
      leaf check-reachability {
        description
          "Register proxy database entries only after checking for
           presence of more specific entries in local or remote db ";
        type empty;
      }
    }
  }

  grouping router-lisp-map-cache-common-grouping {
    list rloc-attributes {
      key "rloc";
      leaf rloc {
        description
          "IP address of loopback or other ETR interface";
        type inet:ip-address;
      }
      leaf priority {
        description
          "Configures which Locators from a set are preferred";
        mandatory true;
        type uint8 {
          range "0..255";
        }
      }
      leaf weight {
        description
          "Traffic load-spreading among Locators";
        mandatory true;
        type uint8 {
          range "0..100";
        }
      }
    }
    container etr-interface-ip {
      status deprecated;
      description
        "Deprecated by ../rloc-attributes";
      leaf etr-interface-ip-address {
        status deprecated;
        description
          "Deprecated by ../../rloc-attributes/rloc-prefix";
        type inet:ip-address;
      }
      leaf priority {
        status deprecated;
        description
          "Deprecated by ../../rloc-attributes/attributes/priority";
        type uint8 {
          range "0..255";
        }
      }
      leaf weight {
        status deprecated;
        description
          "Deprecated by ../../rloc-attributes/attributes/priority";
        type uint8 {
          range "0..100";
        }
      }
    }
  }

  grouping router-lisp-map-request-source-ipv4-grouping {
    leaf map-request-source {
      description
        "Configures inner header source address in Map-Request message";
      type inet:ipv4-address;
    }
  }

  grouping router-lisp-map-request-source-ipv6-grouping {
    leaf map-request-source {
      description
        "Configures inner header source address in Map-Request message";
      type inet:ipv6-address;
    }
  }

  grouping router-lisp-map-request-source-any-grouping {
    leaf map-request-source {
      description
        "Configures inner header source address in Map-Request message";
      type inet:ip-address;
    }
  }

  grouping router-lisp-map-cache-limit-grouping {
    container map-cache-limit {
      description
        "Configures maximum size of map-cache";
      leaf max-map-cache-entries {
        type uint32 {
          range "0..100000";
        }
      }
      leaf reserve-list {
        description
          "EID-prefixes guaranteed to be stored in map-cache";
        type string;
      }
      leaf warning-threshold {
        description
          "Send warning message to syslog when the map-cache size reaches this percentage of the limit";
        type uint8 {
          range "0..100";
        }
      }
    }
  }

  grouping router-lisp-site-registration-grouping {
    container site-registration {
      description
        "Site registrations configuration for a given instance-id";
      leaf limit {
        description
          "Maximum number of site registrations";
        type uint32 {
          range "1..4294967295";
        }
      }
      leaf warning-threshold {
        description
          "Warning threshold to issue system logging";
        type uint8 {
          range "1..100";
        }
      }
    }
  }

  grouping router-lisp-solicit-map-request-grouping {
    container solicit-map-request {
      description
        "Configure Solicit-Map-Request handling";
      leaf ignore {
        description
          "Ignore SMR bit in incoming Map-Requests";
        type empty;
      }
      leaf max-per-entry {
        description
          "Maximum number of SMRs for addresses under a map-cache entry";
        type uint8 {
          range "1..100";
        }
      }
      leaf suppression-time {
        description
          "How long to suppress repeated SMRs for the same address";
        type uint16 {
          range "1..600";
        }
      }
    }
  }

  grouping router-lisp-registration-history-grouping {
    container registration-history {
      description
        "Map-server (MS) registration history";
      leaf limit {
        description
          "Size of registration history log";
        type uint32 {
          range "0..1000000";
        }
        default "1000";
      }
    }
  }

  grouping router-lisp-service-common-grouping {
    container database-mapping {
      description
        "Address family specific local EID prefixes database configuration";
      uses router-lisp-database-mapping-limit-grouping;
    }
    uses router-lisp-itr-grouping;
    uses router-lisp-etr-grouping;
    uses router-lisp-map-cache-limit-grouping;
    uses router-lisp-registration-history-grouping;
    container map-resolver {
      description
        "Configures a LISP Map Resolver (MR)";
      presence "true";
      container map-request {
        description
          "Map-Request processing options";
        container validate {
          description
            "Validation options";
          container source {
            description
              "Influence which source RLOCs map requests are accepted from";
            container list {
              description
                "Define allowed prefixes using an ip[v6] prefix list";
              leaf ipv4 {
                description
                  "IPv4 prefixes";
                type string;
              }
              leaf ipv6 {
                description
                  "IPv6 prefixes";
                type string;
              }
            }
            container registered {
              description
                "...from RLOCs that register EID-prefixes in the same IID on a co-located MapServer";
              container list {
                description
                  "Define allowed prefixes using an ip[v6] prefix list";
                leaf ipv4 {
                  description
                    "IPv4 prefixes";
                  type string;
                }
                leaf ipv6 {
                  description
                    "IPv6 prefixes";
                  type string;
                }
              }
            }
          }
        }
      }
    }
    container map-server {
      description
        "Configures a LISP Map Server (MS)";
      presence "true";
      container map-register {
        description
          "Map-Register processing options";
        container validate {
          description
            "Validation options";
          container source {
            description
              "RLOC Source IP address";
            leaf allowed-locator {
              description
                "Against sites' allowed-locators policy";
              type empty;
            }
          }
        }
      }
    }
    uses router-lisp-site-registration-grouping;
    uses router-lisp-solicit-map-request-grouping;
  }

  grouping dynamic-eid-detection-grouping {
    container dynamic-eid {
      description
        "Configure dynamic eid options";
      container detection {
        description
          "Configure dynamic eid detection options";
        leaf multiple-addr {
          description
            "Configure to support multiple ip addresses per mac";
          type empty;
        }
        leaf bridged-vm {
          description
            "Configure to support sgt propagation for bridged VMs";
          type empty;
        }
      }
    }
  }

  grouping router-lisp-service-ethernet-grouping {
    container encapsulation {
      description
        "Select encapsulation type for data packets. This node is obsolete";
      status obsolete;
      leaf vxlan {
        description
          "Use VXLAN encapsulation for data packets. This node is obsolete";
        status obsolete;
        type empty;
      }
    }
    container map-cache {
      description
        "Address family specific map cache configuration";
      leaf conservative-allocation {
        description
          "Suppress proactive created map-cache when host moves to another switch";
        type boolean;
        default "false";
      }
      leaf publications {
        description
          "Export publication entries into map cache";
        type empty;
      }
    }
    container enhanced-forwarding-enable {
      leaf enhanced-forwarding {
        description
          "Configure Enhanced Forwarding";
        type boolean;
        default "false";
      }
    }
    uses dynamic-eid-detection-grouping;
    uses router-lisp-map-request-source-any-grouping;
    uses router-lisp-service-common-grouping;
    uses router-lisp-publish-subscribe-grouping;
    uses router-lisp-service-ethernet-import-grouping;
  }

  grouping router-lisp-service-import-publication-grouping {
    container publication {
      description
        "Receive LISP publications";
      list publisher {
        description
          "Import publications from publisher";
        key "ip-addr";
        leaf ip-addr {
          type inet:ip-address;
        }
      }
    }
  }

  grouping router-lisp-inst-service-import-publication-grouping {
    container publication {
      description
        "Receive LISP publications";
      choice publisher-choice {
        container inherit-publisher {
          leaf publisher {
            description
              "Import publications from publisher";
            type boolean;
            default "true";
          }
        }
        list publisher {
          description
            "Import publications from publisher";
          key "ip-addr";
          leaf ip-addr {
            type inet:ip-address;
          }
        }
      }
    }
  }

  grouping router-lisp-service-ip-import-database-grouping {
    container database {
      container site-reg-src {
        description
          "Redistribute LISP internal states as database mapping";
        leaf site-registration-src {
          description
            "Import states from site registrations";
          type empty;
        }
        leaf loc-set {
          description
            "Locator set to use with database mapping entries";
          type string;
        }
      }
      leaf site-registration {
        status deprecated;
        description
          "Import states from site registrations";
        type empty;
      }
      leaf locator-set {
        status deprecated;
        description
          "Locator set to use with created database mapping entries";
        type string;
      }
      container publication {
        description
          "Redistribute LISP publication states as database mapping";
        leaf locator-set {
          must '/ios:native/ios:router/lisp/locator-set[name = current() ] or /ios:native/ios:router/lisp-list/locator-set[name = current() ]' {
            error-message "% Please configure the locator-set before configuring publication";
          }
          description
            "Locator set to use with created database mapping entries";
          type string;
        }
        leaf preserve-priority {
          description
            "Preserve priority from publication to database mapping for registration";
          type empty;
        }
      }
    }
  }

  grouping router-lisp-service-ip-import-prefix-list-grouping {
    container prefix-list-container {
      description
        "Redistribute LISP internal states into LISP prefix-list entries";
      leaf prefix-list {
        description
          "The name of the lisp prefix list";
        type string;
      }
      leaf site-registration {
        description
          "Import states from site registrations";
        type empty;
      }
      leaf publication {
        description
          "Import states from publications";
        type empty;
      }
    }
  }

  grouping router-lisp-service-ethernet-import-publication-grouping {
    container publication {
      description
        "Receive LISP publications";
      list publisher {
        description
          "Import publications from publisher";
        key "ip-addr";
        leaf ip-addr {
          type inet:ip-address;
        }
      }
    }
  }

  grouping router-lisp-service-ethernet-import-grouping {
    container import {
      description
        "Redistribute LISP states internally";
      uses router-lisp-service-ethernet-import-publication-grouping;
    }
  }

  grouping router-lisp-inst-service-ethernet-import-grouping {
    container import {
      description
        "Redistribute LISP states internally";
      uses router-lisp-inst-service-import-publication-grouping;
    }
  }

  grouping router-lisp-service-ip-import-grouping {
    container import {
      description
        "Redistribute LISP states internally";
      uses router-lisp-service-ip-import-database-grouping;
      uses router-lisp-service-import-publication-grouping;
    }
  }

  grouping router-lisp-inst-service-ip-import-grouping {
    container import {
      description
        "Redistribute LISP states internally";
      uses router-lisp-service-ip-import-database-grouping;
      uses router-lisp-service-ip-import-prefix-list-grouping;
      uses router-lisp-inst-service-import-publication-grouping;
    }
  }

  grouping router-lisp-service-ip-grouping {
    uses router-lisp-service-common-grouping;
    uses router-lisp-service-ip-distance-grouping;
    leaf encapsulation {
      description
        "Select encapsulation type for data packets";
      type enumeration {
        enum lisp;
        enum vxlan;
      }
    }
    container mr-use-petr {
      description
        "Configure Map Resolver to include Proxy ETR in negative map reply";
      leaf remote-locator-set {
        description
          "Use the locator-set defined by remote-locator-set";
        must '/ios:native/ios:router/lisp/remote-locator-set[name = current() ] or /ios:native/ios:router/lisp-list/remote-locator-set[name = current() ]' {
          error-message "% Please configure the remote-locator-set before configuring mr-use-petr";
        }
        type string;
      }
    }
    container first-packet-petr {
      description
        "Configure Map Resolver to include First-Packet-Proxy ETR in negative map reply";
      leaf remote-locator-set {
        description
          "Use the locator-set defined by remote-locator-set";
        must '/ios:native/ios:router/lisp/remote-locator-set[name = current() ] or /ios:native/ios:router/lisp-list/remote-locator-set[name = current() ]' {
          error-message "% Please configure the remote-locator-set before configuring first-packet-petr";
        }
        type string;
      }
    }
    container map-cache {
      description
        "Address family specific map cache configuration";
      container away-eids {
        description
          "Map cache configuration for the away table";
        leaf send-map-request {
          description
            "Export away table entries into the map cache with action set to send-map-request";
          type boolean;
          default "true";
        }
      }
      leaf site-registration {
        description
          "Install map cache to map request for site registrations";
        type empty;
      }
      leaf publications {
        description
          "Export publication entries into map cache";
        type empty;
      }
      leaf conservative-allocation {
        description
          "Suppress proactive created map-cache when host moves to another switch";
        type boolean;
        default "false";
      }
    }
    uses router-lisp-map-cache-persistent-grouping;
    uses router-lisp-proxy-grouping;
    uses router-lisp-route-export-grouping;
    uses router-lisp-sgt-grouping;
    uses router-lisp-use-petr-grouping;
    uses router-lisp-use-petr-grouping-deprecated;
    uses router-lisp-publish-subscribe-grouping;
    uses router-lisp-service-ip-import-grouping;
  }

  grouping router-lisp-service-dynamic-eid-grouping {
    container dynamic-eid {
      description
        "configure dynamic-eid parameters";
      leaf dataplane-detection {
        description
          "enable dataplane-based detection of hosts";
        type empty;
      }
    }
  }

  grouping router-lisp-service-ipv4-grouping {
    uses router-lisp-service-ip-grouping;
    uses router-lisp-map-request-source-ipv4-grouping;
    uses router-lisp-service-dynamic-eid-grouping;
  }

  grouping router-lisp-service-ipv6-grouping {
    uses router-lisp-service-ip-grouping;
    uses router-lisp-map-request-source-ipv6-grouping;
  }

  grouping router-lisp-four-key-grouping {
    choice auth-key {
      case uncpwd {
        leaf unc-pwd {
          description
            "The UNENCRYPTED (cleartext) password";
          type string;
        }
      }
      case key0 {
        leaf key-0 {
          description
            "The UNENCRYPTED (cleartext) password";
          type string;
        }
      }
      case key6 {
        leaf key-6 {
          description
            "The ENCRYPTED password";
          type string;
        }
      }
      case key7 {
        leaf key-7 {
          description
            "The ENCRYPTED password";
          type string;
        }
      }
    }
  }

  grouping router-lisp-key-hash-function-grouping {
    leaf hash-function {
      description
        "authentication type";
      type enumeration {
        enum sha1;
        enum sha2;
      }
    }
  }

  grouping router-lisp-password-key-0and6-grouping {
    container key-0 {
      leaf ak-0 {
        description
          "The UNENCRYPTED (cleartext) password";
        type string;
      }
      uses router-lisp-key-hash-function-grouping;
    }
    container key-6 {
      leaf ak-6 {
        description
          "The ENCRYPTED password";
        type string;
      }
      uses router-lisp-key-hash-function-grouping;
    }
  }

  grouping router-lisp-password-key-0and6-with-prefix-list-grouping {
    container key-0 {
      leaf ak-0 {
        description
          "The UNENCRYPTED (cleartext) password";
        type string;
      }
      uses router-lisp-key-hash-function-grouping;
      uses router-lisp-xtr-prefix-list-grouping;
      uses router-lisp-map-server-domain-id-grouping;
    }
    container key-6 {
      leaf ak-6 {
        description
          "The ENCRYPTED password";
        type string;
      }
      uses router-lisp-key-hash-function-grouping;
      uses router-lisp-xtr-prefix-list-grouping;
      uses router-lisp-map-server-domain-id-grouping;
    }
  }

  grouping router-lisp-password-key-7-grouping {
    container key-7 {
      leaf ak-7 {
        description
          "The ENCRYPTED password";
        type string;
      }
      uses router-lisp-key-hash-function-grouping;
      uses router-lisp-map-server-domain-id-grouping;
    }
  }

  grouping router-lisp-password-key-7-with-prefix-list-grouping {
    container key-7 {
      leaf ak-7 {
        description
          "The ENCRYPTED password";
        type string;
      }
      uses router-lisp-key-hash-function-grouping;
      uses router-lisp-xtr-prefix-list-grouping;
      uses router-lisp-map-server-domain-id-grouping;
    }
  }

  grouping router-lisp-password-string-grouping {
    container key-pwd {
      leaf unc-pwd {
        description
          "The UNENCRYPTED (cleartext) password";
        type string;
      }
      uses router-lisp-key-hash-function-grouping;
    }
  }

  grouping router-lisp-password-string-with-prefix-list-grouping {
    container key-pwd {
      leaf unc-pwd {
        description
          "The UNENCRYPTED (cleartext) password";
        type string;
      }
      uses router-lisp-key-hash-function-grouping;
      uses router-lisp-xtr-prefix-list-grouping;
      uses router-lisp-map-server-domain-id-grouping;
    }
  }

  grouping router-lisp-three-key-with-hash-function-grouping {
    choice password {
      case password-string {
        uses router-lisp-password-string-grouping;
      }
      case password-key {
        uses router-lisp-password-key-0and6-grouping;
      }
    }
  }

  grouping router-lisp-four-key-with-hash-function-grouping {
    choice password {
      case password-string {
        uses router-lisp-password-string-grouping;
      }
      case password-key {
        uses router-lisp-password-key-0and6-grouping;
        uses router-lisp-password-key-7-grouping;
      }
    }
  }

  grouping router-lisp-four-key-with-hash-function-and-prefix-list-grouping {
    choice password {
      case password-string {
        uses router-lisp-password-string-with-prefix-list-grouping;
      }
      case password-key {
        uses router-lisp-password-key-0and6-with-prefix-list-grouping;
        uses router-lisp-password-key-7-with-prefix-list-grouping;
      }
    }
  }

  grouping router-lisp-route-export-grouping {
    container route-export {
      description
        "Export routes into RIB from LISP";
      container site-registration-export {
        leaf site-registrations {
          description
            "Export LISP site registrations to RIB";
          type empty;
        }
        uses router-lisp-route-export-options-grouping {
          when 'boolean(./site-registrations)';
        }
      }
      container away-eid-export {
        leaf away-eids {
          description
            "Export LISP away EIDs to RIB";
          type empty;
        }
        uses router-lisp-route-export-options-grouping {
          when 'boolean(./away-eids)';
        }
      }
      container publication-export {
        leaf publications {
          description
            "Export LISP publications to RIB";
          type empty;
        }
        uses router-lisp-route-export-options-grouping {
          when 'boolean(./publications)';
        }
      }
      container destinations-summary-export {
        leaf destinations-summary {
          description
            "Export summary of destinations serviced by LISP to RIB";
          type empty;
        }
        uses router-lisp-route-export-options-grouping {
          when 'boolean(./destinations-summary)';
        }
      }
      leaf site-registrations {
        description
          "Export LISP site registrations to RIB";
        status deprecated;
        type empty;
      }
      leaf away-eids {
        description
          "Export LISP away EIDs to RIB";
        status deprecated;
        type empty;
      }
      leaf publications {
        description
          "Export LISP publications to RIB";
        status deprecated;
        type empty;
      }
    }
  }

  grouping router-lisp-route-export-options-grouping {
    leaf route-tag {
      description
        "RIB route tag";
      type uint32;
    }
  }

  grouping router-lisp-inst-service-route-export-grouping {
    container route-export {
      description
        "Export routes into RIB from LISP";
      choice site-registration-export-choice {
        container inherit-site-registration-export {
          leaf site-registrations {
            description
              "Export LISP site registrations to RIB using inherited
               configuration";
            type boolean;
            default "true";
          }
        }
        container site-registration-export {
          leaf site-registrations {
            description
              "Export LISP site registrations to RIB";
            type empty;
          }
          uses router-lisp-route-export-options-grouping {
            when 'boolean(./site-registrations)';
          }
        }
      }
      choice away-eids-export-choice {
        container inherit-away-eid-export {
          leaf away-eids {
            description
              "Export LISP away EIDs to RIB using inherited configuration";
            type boolean;
            default "true";
          }
        }
        container away-eid-export {
          leaf away-eids {
            description
              "Export LISP away EIDs to RIB";
            type empty;
          }
          uses router-lisp-route-export-options-grouping {
            when 'boolean(./away-eids)';
          }
        }
      }
      choice publications-export-choice {
        container inherit-publication-export {
          leaf publications {
            description
              "Export LISP publications to RIB using inherited configuration";
            type boolean;
            default "true";
          }
        }
        container publication-export {
          leaf publications {
            description
              "Export LISP publications to RIB";
            type empty;
          }
          uses router-lisp-route-export-options-grouping {
            when 'boolean(./publications)';
          }
        }
      }
      choice destinations-summary-export-choice {
        container inherit-destinations-summary-export {
          leaf destinations-summary {
            description
              "Export LISP destinations-summary to RIB using inherited configuration";
            type boolean;
            default "true";
          }
        }
        container destinations-summary-export {
          leaf destinations-summary {
            description
              "Export LISP destinations-summary to RIB";
            type empty;
          }
          uses router-lisp-route-export-options-grouping {
            when 'boolean(./destinations-summary)';
          }
        }
      }
      leaf site-registrations {
        description
          "Export LISP site registrations to RIB";
        status deprecated;
        type empty;
      }
      leaf away-eids {
        description
          "Export LISP away EIDs to RIB";
        status deprecated;
        type empty;
      }
      leaf publications {
        description
          "Export LISP publications to RIB";
        status deprecated;
        type boolean;
      }
    }
  }

  grouping router-lisp-map-cache-persistent-grouping {
    container map-cache-persistent {
      description
        "Dump map-cache onto flash, making it persistent across reboots";
      leaf interval {
        description
          "Interval in minutes of how often the map-cache is saved";
        type uint16 {
          range "1..1440";
        }
      }
    }
  }

  grouping router-lisp-sgt-grouping {
    container sgt-config {
      leaf sgt-enable {
        description
          "Enable security group tag propagation in LISP encapsulated traffic";
        type empty;
      }
      leaf distribution {
        description
          "Enable security group tag distribution via LISP";
        type empty;
      }
    }
    leaf sgt {
      status deprecated;
      description
        "Enable SGT propagation in LISP encapsulated traffic";
      type empty;
    }
  }

  grouping router-lisp-proxy-grouping {
    leaf proxy-etr {
      description
        "Configures a LISP Proxy Engress Tunnel Router (PETR)";
      type empty;
    }
    container proxy-itr {
      description
        "Configures a LISP Proxy Ingress Tunnel Router (PITR)";
      leaf ipv4-addr {
        type inet:ipv4-address;
      }
      leaf ipv6-addr {
        type inet:ipv6-address;
      }
      leaf sgt-policy-native-fwd {
        description
          "Configure policy driven native forwarding";
        type empty;
      }
    }
  }

  grouping router-lisp-use-petr-grouping {
    container use-petr-config {
      choice use-petr-choice {
        list use-petr {
          description
            "Encapsulate to Proxy ETR when matching forward-native entry";
          key "locator-address";
          leaf locator-address {
            type inet:ip-address;
          }
          container priority {
            leaf priority-value {
              description
                "Configures which Locators from a set are preferred";
              type uint8 {
                range "0..255";
              }
            }
            leaf weight {
              description
                "Traffic load-spreading among Locators";
              type uint8 {
                range "0..100";
              }
            }
          }
        }
        container no-use-petr {
          leaf use-petr {
            description
              "Encapsulate to Proxy ETR when matching forward-native entry";
            type boolean;
            default "true";
          }
        }
      }
    }
  }

  grouping router-lisp-use-petr-grouping-deprecated {
    list use-petr {
      description
        "Encapsulate to Proxy ETR when matching forward-native entry";
      status deprecated;
      key "locator-address";
      leaf locator-address {
        status deprecated;
        type inet:ip-address;
      }
      container priority {
        status deprecated;
        leaf priority-value {
          description
            "Configures which Locators from a set are preferred";
          status deprecated;
          type uint8 {
            range "0..255";
          }
        }
        leaf weight {
          description
            "Traffic load-spreading among Locators";
          status deprecated;
          type uint8 {
            range "0..100";
          }
        }
      }
    }
  }

  grouping router-lisp-publish-subscribe-grouping {
    leaf publish-subscribe {
      description
        "Configures Publication Subscription";
      type boolean;
      default "true";
    }
  }

  grouping router-lisp-service-ip-distance-grouping {
    container distance {
      description
        "Administrative distance for RIB route installation";
      leaf alt {
        description
          "LISP routes installed in the ALT table";
        type uint8 {
          range "1..255";
        }
      }
      leaf away {
        description
          "Administrative distance for RIB route installation";
        type uint8 {
          range "1..255";
        }
      }
      leaf dyn-eid {
        description
          "LISP installed routes of type dynamic-EID";
        type uint8 {
          range "1..255";
        }
      }
      leaf site-registrations {
        description
          "LISP installed routes of type site-registrations";
        type uint8 {
          range "1..255";
        }
      }
      leaf publications {
        description
          "LISP installed routes of type publications";
        type uint8 {
          range "1..255";
        }
      }
      leaf destinations-summary {
        description
          "LISP installed routes of type destinations-summary";
        type uint8 {
          range "1..255";
        }
      }
    }
  }

  grouping router-lisp-map-server-grouping {
    list map-server {
      description
        "Configures map server for ETR registration";
      key "ip-addr";
      leaf ip-addr {
        type inet:ip-address;
      }
      container key {
        description
          "Authentication key used with map server";
        uses router-lisp-four-key-with-hash-function-and-prefix-list-grouping;
      }
      leaf proxy-reply {
        description
          "Request Map-Server to send Map-Replies on behalf of site";
        type empty;
      }
    }
  }

  grouping router-lisp-inst-database-mapping-option-grouping {
    container database-mapping-option {
      leaf priority {
        description
          "Configures which Locators from a set are preferred";
        type uint8 {
          range "0..255";
        }
      }
      leaf weight {
        description
          "Traffic load-spreading among Locators";
        type uint8 {
          range "0..100";
        }
      }
      leaf down {
        description
          "Configure this database mapping down";
        type empty;
      }
    }
  }

  grouping router-lisp-inst-database-mapping-service-insertion-grouping {
    container service-insertion {
      description
        "Enable configuration of default-etr database mapping";
      leaf service-id {
        type uint16 {
          range "1..8";
        }
      }
      leaf service-type {
        type enumeration {
          enum firewall;
        }
      }
      leaf locator-set {
        description
          "Use locators defined by locator-set";
        type string;
      }
      leaf default-etr {
        description
          "Enable configuration of default-etr database mapping";
        type empty;
      }
      leaf default-etr-route-map {
        description
          "Configure route-map for default-etr";
        type string;
      }
      leaf service-etr {
        description
          "Enable configuration of service-etr database mapping";
        type empty;
      }
      leaf local {
        description
          "Register only with local MS";
        type empty;
      }
    }
  }

  grouping router-lisp-inst-database-mapping-common-grouping {
    container locator-set-container {
      description
        "Use locators defined by locator-set";
      leaf locator-set {
        description
          "Use locators defined by locator-set";
        type string;
      }
      leaf route-tag {
        description
          "RIB route tag";
        type uint32;
      }
      leaf proxy {
        description
          "Enable configuration of static proxy database mapping";
        type empty;
      }
      leaf default-etr {
        description
          "Enable configuration of default-etr database mapping";
        type empty;
      }
      leaf default-etr-route-map {
        description
          "Configure route-map for default-etr";
        type string;
      }
      leaf local {
        description
          "Register only with local MS";
        type empty;
      }
    }
    list ipv4-addrees {
      description
        "IPv4 Address of loopback or other ETR interface";
      key "address";
      leaf address {
        type inet:ipv4-address;
      }
      uses router-lisp-inst-database-mapping-option-grouping;
    }
    list ipv6-addrees {
      description
        "IPv6 Address of loopback or other ETR interface";
      key "address";
      leaf address {
        type inet:ipv6-address;
      }
      uses router-lisp-inst-database-mapping-option-grouping;
    }
    list IPv4-interface {
      key "name";
      leaf name {
        description
          "Use IPv4 address of interface as locator";
        type string;
      }
      uses router-lisp-inst-database-mapping-option-grouping;
    }
    list IPv6-interface {
      key "name";
      leaf name {
        description
          "Use IPv4 address of interface as locator";
        type string;
      }
      uses router-lisp-inst-database-mapping-option-grouping;
    }
  }

  grouping router-lisp-inst-service-common-grouping {
    uses router-lisp-itr-grouping;
    uses router-lisp-etr-grouping;
    uses router-lisp-map-cache-limit-grouping;
    uses router-lisp-site-registration-grouping;
    uses router-lisp-solicit-map-request-grouping;
    uses router-lisp-registration-history-grouping;
  }

  grouping router-lisp-inst-service-ethernet-grouping {
    container eid-table {
      description
        "Bind an eid-table";
      leaf vlan {
        description
          "VLAN configuration";
        type uint16 {
          range "1..4094";
        }
      }
    }
    container broadcast-underlay {
      description
        "Multicast group to use for underlay";
      leaf ipv4-multicast {
        description
          "IPv4 multicast group address";
        type inet:ipv4-address;
      }
      leaf ipv6-multicast {
        description
          "IPv6 multicast group address";
        type inet:ipv6-address;
      }
    }
    container flood {
      description
        "Control flooding or local intercept of broadcast frames";
      leaf arp-nd {
        description
          "IPv4 ARP / IPv6 ND";
        type empty;
      }
      leaf unknown-unicast {
        description
          "Frames with unknown destination MAC";
        type empty;
      }
      leaf access-tunnel {
        description
          "Broadcast frame flooding toward AP access-tunnel";
        type boolean;
        default "false";
      }
      leaf multicast-address {
        description
          "Multicast Group Address";
        type union {
          type inet:ipv4-address;
          type inet:ipv6-address;
        }
      }
      leaf vlan {
        description
          "Multicast VLAN ID";
        type uint16 {
          range "1..4094";
        }
      }
    }
    container database-mapping {
      description
        "Configures Locator addresses for an ETR";
      list eid-cont {
        description
          "EID-record for RLOC static mapping";
        key "eid-prefix";
        leaf eid-prefix {
          description
            "xxxx.xxxx.xxxx 48 bit mac address";
          type ios-types:cisco-mac-address-type;
        }
        uses router-lisp-inst-database-mapping-common-grouping;
      }
      container mac {
        description
          "L2 EID records";
        presence "true";
        leaf locator-set {
          description
            "Use locators defined by locator-set";
          type string;
        }
      }
      uses router-lisp-database-mapping-limit-grouping;
    }
    uses dynamic-eid-detection-grouping;
    uses router-lisp-inst-service-common-grouping;
    leaf map-request-source {
      status obsolete;
      description
        "Configures inner header source address in Map-Request message";
      type inet:ip-address;
    }
    container map-cache {
      description
        "Use RIB routes to define EID address space in map-cache";
      list eid-cont {
        description
          "EID-record for RLOC static mapping";
        key "eid-prefix";
        leaf eid-prefix {
          description
            "xxxx.xxxx.xxxx 48 bit mac address";
          type ios-types:cisco-mac-address-type;
        }
        uses router-lisp-map-cache-common-grouping;
      }
      leaf conservative-allocation {
        description
          "Suppress proactive created map-cache when host moves to another switch";
        type boolean;
        default "false";
      }
      leaf publications {
        description
          "Export publication entries into map cache";
        type empty;
      }
    }
    container enhanced-forwarding-enable {
      leaf enhanced-forwarding {
        description
          "Configure Enhanced Forwarding";
        type boolean;
        default "false";
      }
    }
    uses router-lisp-inst-service-ethernet-import-grouping;
  }

  grouping router-lisp-inst-service-ip-grouping {
    container eid-table {
      description
        "Bind an eid-table";
      leaf vrf-name {
        type string;
      }
      leaf default {
        type empty;
      }
      leaf vrf {
        type string;
      }
    }
    uses router-lisp-inst-service-common-grouping;
    container alt {
      description
        "LISP Alternative Topology, LISP-ALT";
      list summary-route {
        description
          "Summary route to install into the ALT table";
        key "eid-prefix";
        leaf eid-prefix {
          type union {
            type inet:ipv4-prefix;
            type ios-types:ipv6-prefix;
          }
        }
        leaf route-tag {
          description
            "ALT RIB route tag for EID prefix";
          type uint32 {
            range "0..4294967295";
          }
        }
      }
    }
    leaf alt-vrf {
      description
        "Activate LISP-ALT functionality in VRF";
      status deprecated;
      type string;
    }
    uses router-lisp-service-ip-distance-grouping;
    container mr-use-petr {
      description
        "Configure Map Resolver to include Proxy ETR in negative map reply";
      choice remote-locator-choice {
        container no-remote-locator {
          leaf remote-locator-set {
            type boolean;
          }
        }
        container remote-locator {
          leaf remote-locator-set {
            description
              "Use the locator-set defined by remote-locator-set";
            must '/ios:native/ios:router/lisp/remote-locator-set[name = current() ] or /ios:native/ios:router/lisp-list/remote-locator-set[name = current() ]' {
              error-message "% Please configure the remote-locator-set before configuring mr-use-petr";
            }
            type string;
          }
        }
      }
    }
    container first-packet-petr {
      description
        "Configure Map Resolver to include First-Packet-Proxy ETR in negative map reply";
      choice first-packet-petr-choice {
        case first-packet-petr-disable {
          leaf remote-locator-set {
            description
              "Disable first-packet-petr by adding no option";
            type boolean;
          }
        }
        case first-packet-petr-configure {
          container remote-locator-set-conf {
            leaf remote-locator-set {
              description
                "Use the locator-set defined by remote-locator-set";
              must '/ios:native/ios:router/lisp/remote-locator-set[name = current() ] or /ios:native/ios:router/lisp-list/remote-locator-set[name = current() ]' {
                error-message "% Please configure the remote-locator-set before configuring first-packet-petr";
              }
              type string;
            }
          }
        }
      }
    }
    container map-cache {
      description
        "Address family specific map cache configuration";
      list eid-interface {
        description
          "Configures static EID-to-RLOC mappings for an ITR";
        key "eid-prefix";
        leaf eid-prefix {
          type union {
            type inet:ipv4-prefix;
            type ios-types:ipv6-prefix;
          }
        }
        uses router-lisp-map-cache-common-grouping;
        leaf drop {
          description
            "Drop packets that match this map-cache entry";
          type empty;
        }
        leaf map-request {
          description
            "Send Map-Request for LISP destination EID";
          type empty;
        }
        leaf native-forward {
          description
            "Natively forward packets that match this map-cache entry";
          type empty;
        }
      }
      container away-eids {
        description
          "Map cache configuration for the away table";
        leaf send-map-request {
          description
            "Export away table entries into the map cache with action set to send-map-request";
          type boolean;
          default "true";
        }
      }
      leaf site-registration {
        description
          "Install map cache to map request for site registrations";
        type empty;
      }
      leaf publications {
        description
          "Export publication entries into map cache";
        type boolean;
      }
      leaf conservative-allocation {
        description
          "Suppress proactive created map-cache when host moves to another switch";
        type boolean;
        default "false";
      }
    }
    uses router-lisp-map-cache-persistent-grouping;
    uses router-lisp-proxy-grouping;
    uses router-lisp-inst-service-route-export-grouping;
    uses router-lisp-sgt-grouping;
    uses router-lisp-use-petr-grouping;
    uses router-lisp-use-petr-grouping-deprecated;
    uses router-lisp-inst-service-ip-import-grouping;
  }

  grouping router-lisp-inst-service-ipv4-grouping {
    uses router-lisp-inst-service-ip-grouping;
    container route-import {
      description
        "Import RIB routes by a routing protocol into LISP";
      uses router-lisp-inst-service-ipv4-route-import-protocol-grouping;
    }
    uses router-lisp-map-request-source-ipv4-grouping;
    container database-mapping {
      description
        "Configures Locator addresses for an ETR";
      list eid-cont {
        key "eid-prefix";
        leaf eid-prefix {
          type inet:ipv4-prefix;
        }
        uses router-lisp-inst-database-mapping-service-insertion-grouping;
        uses router-lisp-inst-database-mapping-common-grouping;
        leaf auto-discover-rlocs {
          type empty;
        }
      }
      uses router-lisp-database-mapping-limit-grouping;
    }
  }

  grouping router-lisp-inst-service-ipv6-grouping {
    uses router-lisp-inst-service-ip-grouping;
    container route-import {
      description
        "Import RIB routes by a routing protocol into LISP";
      uses router-lisp-inst-service-ipv6-route-import-protocol-grouping;
    }
    uses router-lisp-map-request-source-ipv6-grouping;
    container database-mapping {
      description
        "Configures Locator addresses for an ETR";
      list eid-cont {
        key "eid-prefix";
        leaf eid-prefix {
          type ios-types:ipv6-prefix;
        }
        uses router-lisp-inst-database-mapping-service-insertion-grouping;
        uses router-lisp-inst-database-mapping-common-grouping;
        leaf auto-discover-rlocs {
          type empty;
        }
      }
      uses router-lisp-database-mapping-limit-grouping;
    }
  }

  grouping router-lisp-inst-grouping {
    container decapsulation {
      description
        "Decapsulation behavior (e.g. filters)";
      container filter {
        description
          "Filters traffic";
        container rloc {
          description
            "Filter based on Routing Locator (RLOC) in packet header";
          container source {
            description
              "Filters traffic based on RLOC source address";
            leaf locator-set {
              description
                "Locator-set Name";
              must '/ios:native/ios:router/ios-lisp:lisp/locator-set[name = current()] or /ios:native/ios:router/ios-lisp:lisp-list/locator-set[name = current()]' {
                error-message "% locator-set used here must be present in the configurations";
              }
              type string;
            }
            leaf member {
              description
                "Members learned from map-server";
              type empty;
            }
          }
        }
      }
    }
    leaf disable-ttl-propagate {
      description
        "Disable ttl propagation";
      type empty;
    }
    list dynamic-eid {
      description
        "Configure a dynamic EID";
      key "name";
      leaf name {
        type string;
      }
      container database-mapping {
        description
          "Configures EID-prefix and locator-set for dynamic-EID";
        choice ip-prefix {
          case ipv4-prefix {
            list ipv4-prefix {
              description
                "IPv4 EID-prefix for dynamic-EID";
              key "eid-prefix";
              leaf eid-prefix {
                type inet:ipv4-prefix;
              }
              leaf locator-set {
                description
                  "Use locators defined by locator-set";
                type string;
              }
              leaf route-tag {
                description
                  "RIB route tag";
                type uint32;
              }
              leaf silent-host-detection {
                description
                  "Register associated silent hosts";
                type empty;
              }
            }
          }
          case ipv6-prefix {
            list ipv6-prefix {
              description
                "IPv6 EID-prefix for dynamic-EID";
              key "eid-prefix";
              leaf eid-prefix {
                type ios-types:ipv6-prefix;
              }
              leaf locator-set {
                description
                  "Use locators defined by locator-set";
                type string;
              }
              leaf route-tag {
                description
                  "RIB route tag";
                type uint32;
              }
              leaf silent-host-detection {
                description
                  "Register associated silent hosts";
                type empty;
              }
            }
          }
        }
      }
      container eid-notify {
        description
          "Configure options for sending/receiving EID-notify";
        container authentication-key {
          description
            "Authentication key used for validating received EID-notify";
          uses router-lisp-four-key-grouping;
        }
        list gateway-key {
          key "gateway-ip";
          leaf gateway-ip {
            type inet:ip-address;
          }
          container key {
            uses router-lisp-three-key-with-hash-function-grouping;
          }
        }
      }
      leaf map-notify-group {
        description
          "Multicast group which to send map-notifies to";
        type inet:ip-address;
      }
      uses router-lisp-map-server-grouping;
    }
    container loc-reach-algorithm {
      description
        "Configure locator reachability algorithm";
      container lsb-reports {
        description
          "Configure data packet LSB report handling";
        leaf do-not-transmit {
          description
            "Force the setting of the encapsulation header L bit to zero";
          type empty;
        }
        leaf ignore {
          description
            "Ignore data packet LSB reports";
          type empty;
        }
      }
      leaf rloc-probing {
        description
          "Probe high priority RLOCs with Map-Requests as last resort";
        type empty;
      }
    }
    container map-server {
      description
        "Map-Server commands";
      container rloc {
        description
          "EID instance RLOC membership";
        container members {
          description
            "EID instance RLOC membership";
          leaf distribute {
            description
              "EID instance RLOC membership distribution";
            type empty;
          }
          container modify-discovered {
            description
              "Modify the EID instance membership that is automaticallydiscovered from ETR registrations";
            leaf operator {
              type enumeration {
                enum add;
                enum override;
              }
            }
            leaf locator-set {
              description
                "Locator set from which to get member RLOC addresses";
              type string;
            }
          }
        }
      }
      container site-registration {
        description
          "Map-server site registration options";
        leaf limit {
          description
            "Maximum number of site registrations as a result of accept-more-specifics";
          type uint32;
        }
        leaf warning-threshold {
          description
            "Warning threshold to issue system logging";
          type uint8 {
            range "1..100";
          }
        }
      }
    }
    container other-xtr-probe {
      description
        "Configure parameters for probing of other xTRs in our site";
      leaf period {
        description
          "Period between probes in seconds";
        type uint16 {
          range "5..900";
        }
      }
    }
    container remote-rloc-probe {
      description
        "Configure parameters for probing of remote RLOCs";
      leaf on-membership-change {
        description
          "Trigger probing upon membership changes for remote RLOC";
        type empty;
      }
      leaf on-route-change {
        description
          "Trigger probing upon routing changes for remote RLOC";
        type empty;
      }
    }
    container service {
      description
        "Configure lisp service type";
      container ipv4 {
        presence "true";
        container default {
          uses router-lisp-inst-service-ipv4-grouping;
        }
        uses router-lisp-inst-service-ipv4-grouping;
      }
      container ipv6 {
        presence "true";
        container default {
          uses router-lisp-inst-service-ipv6-grouping;
        }
        uses router-lisp-inst-service-ipv6-grouping;
      }
      container ethernet {
        presence "true";
        container default {
          uses router-lisp-inst-service-ethernet-grouping;
        }
        uses router-lisp-inst-service-ethernet-grouping;
      }
    }
  }

  grouping router-lisp-ip-route-import-map-cache-grouping {
    container map-cache-container {
      presence "true";
      leaf route-map {
        description
          "Route map for route selection filtering";
        type string;
      }
    }
  }

  grouping router-lisp-ip-route-import-database-grouping {
    container lisp-ip-route-import {
      leaf route-map {
        description
          "Route map for route selection filtering";
        type string;
      }
      leaf route-tag {
        description
          "RIB route tag";
        type uint32;
      }
      leaf locator-set {
        description
          "Locator set to use with created database mapping entries";
        type string;
      }
      leaf proxy {
        description
          "Enable the dynamic import of RIB route as proxy database mapping";
        type empty;
      }
    }
  }

  grouping router-lisp-ddt-authoritative-grouping {
    container delegate {
      description
        "DDT delegation to a child DDT node or map-server";
      choice instance-id-eid-prefix-choice {
        case eid-prefix-case {
          leaf eid-prefix {
            mandatory true;
            type union {
              type inet:ipv4-prefix;
              type ios-types:ipv6-prefix;
            }
          }
        }
        case instance-id-case {
          leaf instance-id {
            description
              "EID instance-ID";
            mandatory true;
            type string;
          }
        }
      }
      leaf to {
        description
          "DDT delegation to a child DDT node or map-server";
        mandatory true;
        type empty;
      }
      leaf ip-address {
        description
          "IPv4/6 Child or map-server node locator address";
        mandatory true;
        type inet:ip-address;
      }
      leaf map-server {
        description
          "Delegation points to a map-server";
        type empty;
      }
    }
    leaf map-server-peer {
      description
        "Peer map-servers that are authoritative for the same EID prefixes";
      type inet:ip-address;
    }
  }

  grouping router-lisp-common-grouping {
    container alt {
      description
        "LISP Alternative Topology, LISP-ALT";
      list summary-route {
        description
          "Summary route to install into the ALT table";
        key "eid-prefix";
        leaf eid-prefix {
          type union {
            type inet:ipv4-prefix;
            type ios-types:ipv6-prefix;
          }
        }
        leaf route-tag {
          description
            "ALT RIB route tag for EID prefix";
          type uint32;
        }
      }
    }
    container control-packet {
      description
        "Configure control packet tx option";
      leaf mtu {
        description
          "Configure control packet MTU";
        type uint32 {
          range "304..10000";
        }
      }
    }
    container ddt {
      description
        "Delegated Database Tree (DDT) mapping system";
      presence "true";
      container authoritative {
        description
          "DDT authoritative prefix";
        list instance-id-eid-prefix-list {
          key "instance-id eid-prefix";
          leaf instance-id {
            description
              "EID instance-ID";
            type uint32;
          }
          leaf eid-prefix {
            type union {
              type inet:ipv4-prefix;
              type ios-types:ipv6-prefix;
            }
          }
          uses router-lisp-ddt-authoritative-grouping;
        }
        list instance-id-list {
          key "instance-id";
          leaf instance-id {
            type string;
          }
          uses router-lisp-ddt-authoritative-grouping;
        }
      }
      leaf cache-limit {
        description
          "DDT resolver cache entry limit";
        type uint32 {
          range "1..100000";
        }
      }
      leaf root {
        description
          "DDT root node";
        type inet:ip-address;
      }
    }
    container decapsulation {
      description
        "Decapsulation behavior (e.g. filters)";
      container filter {
        description
          "Filters traffic";
        container rloc {
          description
            "Filter based on Routing Locator (RLOC) in packet header";
          container source {
            description
              "Filters traffic based on RLOC source address";
            leaf locator-set {
              description
                "Locator-set Name";
              must '/ios:native/ios:router/ios-lisp:lisp/locator-set[name = current()] or /ios:native/ios:router/ios-lisp:lisp-list/locator-set[name = current()]' {
                error-message "% locator-set used here must be present in the configurations";
              }
              type string;
            }
            leaf member {
              description
                "Members learned from map-server";
              type empty;
            }
          }
        }
      }
    }
    leaf disable-ttl-propagate {
      description
        "Disable ttl propagation";
      type empty;
    }
    leaf disable-first-packet-forwarding {
      description
        "Disable first packet forwarding";
      type empty;
    }
    container etr {
      status obsolete;
      description
        "Configures a LISP Egress Tunnel Router (ETR)";
      container map-server {
        status obsolete;
        description
          "Configures map server for ETR registration";
        container source-address-new {
          status obsolete;
          description
            "Configures map server source address";
          uses ios-ifc:interface-obsolete-grouping;
        }
        leaf source-address {
          status obsolete;
          description
            "Configures map server source address";
          type string;
        }
      }
    }
    container ipv4 {
      description
        "IPv4 address family";
      uses router-lisp-ip-grouping;
    }
    container ipv6 {
      description
        "IPv6 address family";
      uses router-lisp-ip-grouping;
    }
    container loc-reach-algorithm {
      description
        "Configure locator reachability algorithm";
      container lsb-reports {
        description
          "Configure data packet LSB report handling";
        leaf do-not-transmit {
          description
            "Force the setting of the encapsulation header L bit to zero";
          type empty;
        }
        leaf ignore {
          description
            "Ignore data packet LSB reports";
          type empty;
        }
      }
      leaf rloc-probing {
        description
          "Probe high priority RLOCs with Map-Requests as last resort";
        type empty;
      }
    }
    container locator-down {
      description
        "Manually set locator status to down";
      leaf address {
        description
          "IPv4/6 Locator address to be set down";
        type inet:ip-address;
      }
      container IPv4-interface-new {
        description
          "Use IPv4 address of interface as locator";
        uses ios-ifc:interface-grouping;
      }
      leaf IPv4-interface {
        status deprecated;
        description
          "Use IPv4 address of interface as locator";
        type string;
      }
      container IPv6-interface-new {
        description
          "Use IPv6 address of interface as locator";
        uses ios-ifc:interface-grouping;
      }
      leaf IPv6-interface {
        status deprecated;
        description
          "Use IPv6 address of interface as locator";
        type string;
      }
    }
    container locator-table {
      description
        "Specify the RLOC table";
      leaf vrf-name {
        type string;
      }
      leaf default {
        description
          "Default VRF";
        type empty;
      }
      leaf vrf {
        description
          "VRF name";
        type string;
      }
    }
    container map-request {
      description
        "Configure map-request handling";
      leaf itr-rlocs {
        description
          "Configure to use the specified RLOC set as ITR RLOC in map-request";
        type string;
      }
    }
    container map-server {
      description
        "Map-Server commands";
      container rloc {
        description
          "EID instance RLOC membership";
        container members {
          description
            "EID instance RLOC membership";
          leaf distribute {
            description
              "EID instance RLOC membership distribution";
            type empty;
          }
          container modify-discovered {
            description
              "Modify the EID instance membership that is automaticallydiscovered from ETR registrations";
            leaf operator {
              type enumeration {
                enum add;
                enum override;
              }
            }
            leaf locator-set {
              description
                "Locator set from which to get member RLOC addresses";
              type string;
            }
          }
        }
      }
      container site-registration {
        description
          "Map-server site registration options";
        leaf limit {
          description
            "Maximum number of site registrations as a result of accept-more-specifics";
          type uint32;
        }
        leaf warning-threshold {
          description
            "Warning threshold to issue system logging";
          type uint8 {
            range "1..100";
          }
        }
      }
      container nmr {
        description
          "Map-server negative map-reply option";
        leaf non-site-ttl {
          description
            "Negative map-reply TTL for non-site EID";
          type uint16 {
            range "1..1440";
          }
        }
      }
      container session {
        description
          "Map-server session";
        leaf passive-open {
          description
            "Open passive TCP sockets to listen for incoming connections";
          type string;
        }
      }
    }
    container platform {
      description
        "Configure platform resource options";
      container resource-usage {
        description
          "Configure resource-usage options";
        leaf local-host {
          description
            "Local host reserved percentage";
          type uint8 {
            range "1..100";
          }
        }
        container maximum-local-hosts {
          description
            "Maximum local hosts";
          leaf l2 {
            description
              "L2 local hosts";
            type uint32;
          }
          leaf l3 {
            description
              "L3 local hosts";
            type uint32;
          }
        }
        leaf warning {
          description
            "warning percentage";
          type uint8 {
            range "1..95";
          }
        }
      }
    }
    container other-xtr-probe {
      description
        "Configure parameters for probing of other xTRs in our site";
      leaf period {
        description
          "Period between probes in seconds";
        type uint16 {
          range "5..900";
        }
      }
    }
    container remote-rloc-probe {
      description
        "Configure parameters for probing of remote RLOCs";
      leaf on-membership-change {
        description
          "Trigger probing upon membership changes for remote RLOC";
        type empty;
      }
      leaf on-route-change {
        description
          "Trigger probing upon routing changes for remote RLOC";
        type empty;
      }
    }
  }

  grouping router-lisp-locator-set-grouping {
    leaf priority {
      description
        "Configures which Locators from a set are preferred";
      type uint8;
    }
    leaf weight {
      description
        "Traffic load-spreading among Locators";
      type uint8 {
        range "0..100";
      }
    }
  }

  grouping router-lisp-locator-set-grouping-deprecated {
    leaf priority {
      status deprecated;
      description
        "Configures which Locators from a set are preferred";
      type uint8;
    }
    leaf weight {
      status deprecated;
      description
        "Traffic load-spreading among Locators";
      type uint8 {
        range "0..100";
      }
    }
  }

  grouping router-lisp-locator-set-grouping-new {
    container affinity {
      choice affinity-opt {
        case id-only {
          leaf affinity-id {
            description
              "Configuration for affinity-id";
            type uint32;
          }
        }
        case id-val {
          container id-val {
            leaf affinity-id {
              description
                "Configuration for affinity-id";
              type uint32;
            }
            leaf y-val {
              description
                "Numeric value for Y dimension";
              type uint32;
            }
          }
        }
      }
    }
    container priority-and-weight {
      description
        "Configures which Locators from a set are preferred";
      leaf priority {
        status deprecated;
        description
          "Configures which Locators from a set are preferred (DEPRECATED)";
        type uint8;
      }
      leaf track-peers {
        description
          "Configures track-peers";
        type empty;
      }
      leaf base-value {
        description
          "Peer RLOC priority base value";
        type uint8;
      }
      leaf decrement {
        when 'boolean(../track-peers)';
        description
          "Peer RLOC tracking decrement";
        type int16 {
          range "-255..-1";
        }
      }
      leaf weight {
        type uint8 {
          range "0..100";
        }
      }
    }
  }

  grouping router-lisp-key-grouping {
    leaf ak-0 {
      description
        "The UNENCRYPTED (cleartext) password";
      type string;
    }
    leaf ak-6 {
      description
        "The ENCRYPTED password";
      type string;
    }
    leaf unc-pwd {
      description
        "The UNENCRYPTED (cleartext) password";
      type string;
    }
  }

  grouping router-lisp-site-inst-id-prefix-grouping {
    list instance-id-cfg {
      description
        "EID instance-ID";
      key "id prefix";
      leaf id {
        type uint32 {
          range "1..16777214";
        }
      }
      leaf prefix {
        type union {
          type inet:ipv4-prefix;
          type ios-types:ipv6-prefix;
        }
      }
      leaf accept-more-specifics {
        description
          "Accept registrations for more specific EID prefixes";
        type empty;
      }
      uses router-lisp-site-publication-summary-only-grouping;
      container route-tag-options {
        leaf route-tag {
          description
            "RIB route tag";
          type uint32 {
            range "0..4294967295";
          }
        }
        leaf accept-more-specifics {
          description
            "Accept registrations for more specific EID prefixes";
          type empty;
        }
      }
    }
    container inst-id-any-mac {
      list instance-id-cfg {
        description
          "EID instance-ID";
        key "id";
        leaf id {
          type uint32 {
            range "1..16777214";
          }
        }
        leaf any-mac {
          description
            "Accept registrations for any L2 EID records";
          type empty;
        }
      }
    }
  }

  grouping router-lisp-site-prefix-grouping-deprecated {
    list prefixes {
      status deprecated;
      key "prefix";
      leaf prefix {
        status deprecated;
        type union {
          type inet:ipv4-prefix;
          type ios-types:ipv6-prefix;
        }
      }
      leaf accept-more-specifics {
        status deprecated;
        description
          "Accept registrations for more specific EID prefixes";
        type empty;
      }
      container route-tag-options {
        status deprecated;
        leaf route-tag {
          status deprecated;
          description
            "RIB route tag";
          type uint32 {
            range "0..4294967295";
          }
        }
        leaf accept-more-specifics {
          status deprecated;
          description
            "Accept registrations for more specific EID prefixes";
          type empty;
        }
      }
      leaf route-tag {
        status deprecated;
        description
          "RIB route tag";
        type uint32 {
          range "0..4294967295";
        }
      }
    }
  }

  grouping router-lisp-site-prefix-grouping {
    list prefixes {
      key "prefix";
      leaf prefix {
        type union {
          type inet:ipv4-prefix;
          type ios-types:ipv6-prefix;
        }
      }
      leaf accept-more-specifics {
        description
          "Accept registrations for more specific EID prefixes";
        type empty;
      }
      uses router-lisp-site-publication-summary-only-grouping;
      container route-tag-options {
        leaf route-tag {
          description
            "RIB route tag";
          type uint32 {
            range "0..4294967295";
          }
        }
        leaf accept-more-specifics {
          description
            "Accept registrations for more specific EID prefixes";
          type empty;
        }
      }
      leaf route-tag {
        status deprecated;
        description
          "RIB route tag";
        type uint32 {
          range "0..4294967295";
        }
      }
    }
  }

  grouping router-lisp-site-common-grouping {
    container authentication-key {
      description
        "Authentication key used by LISP site";
      uses router-lisp-four-key-grouping;
    }
    leaf description {
      description
        "Site description";
      type string;
    }
    container allowed-locator {
      description
        "Locator from LISP site";
      leaf ls-ipv4 {
        description
          "IPv4 locator allowed in registered locator-set";
        type inet:ipv4-address;
      }
      leaf ls-ipv6 {
        description
          "IPv6 locator allowed in registered locator-set";
        type inet:ipv6-address;
      }
      container list {
        description
          "Prefixes allowed in registered locator-set";
        leaf ipv4 {
          description
            "IPv4 prefix-list name";
          type string;
        }
        leaf ipv6 {
          description
            "IPv6 prefix-list name";
          type string;
        }
      }
    }
    list allow-locator-default-etr {
      description
        "Allow default-etr";
      key "instance-id address-family";
      leaf instance-id {
        description
          "EID instance-ID";
        type uint32 {
          range "0..16777214";
        }
      }
      leaf address-family {
        description
          "Accept registrations for ipv4/ipv6";
        type enumeration {
          enum ipv4;
          enum ipv6;
        }
      }
    }
    list allow-locator-service-etr {
      description
        "Allow service-etr";
      key "instance-id address-family";
      leaf instance-id {
        description
          "EID instance-ID";
        type uint32 {
          range "0..16777214";
        }
      }
      leaf address-family {
        description
          "Accept registrations for ipv4/ipv6";
        type enumeration {
          enum ipv4;
          enum ipv6;
        }
      }
    }
    container eid-prefix {
      description
        "Site EID address prefix";
      uses router-lisp-site-prefix-grouping;
      uses router-lisp-site-inst-id-prefix-grouping;
      list instance-id {
        status deprecated;
        description
          "EID instance-ID";
        key "id";
        leaf id {
          status deprecated;
          type uint32 {
            range "1..16777214";
          }
        }
        uses router-lisp-site-prefix-grouping-deprecated;
        leaf any-mac {
          status deprecated;
          description
            "Accept registrations for any L2 EID records";
          type empty;
        }
      }
      leaf any-mac {
        description
          "Accept registrations for any L2 EID records";
        type empty;
      }
    }
    container eid-record {
      description
        "Site EID address prefix";
      uses router-lisp-site-prefix-grouping;
      uses router-lisp-site-inst-id-prefix-grouping;
      list instance-id {
        status deprecated;
        description
          "EID instance-ID";
        key "id";
        leaf id {
          status deprecated;
          type uint32 {
            range "1..16777214";
          }
        }
        uses router-lisp-site-prefix-grouping-deprecated;
        leaf any-mac {
          status deprecated;
          description
            "Accept registrations for any L2 EID records";
          type empty;
        }
      }
      leaf any-mac {
        description
          "Accept registrations for any L2 EID records";
        type empty;
      }
    }
    leaf site-id {
      description
        "Configure a site-id for this site";
      type uint32 {
        range "0..4294967295";
      }
    }
  }

  grouping rouer-lisp-site-grouping {
    list site {
      description
        "Configure a LISP site on a map server (MS)";
      key "sname";
      leaf sname {
        description
          "The site name";
        type string;
      }
      container default {
        status obsolete;
        uses router-lisp-site-common-grouping-obsolete;
      }
      uses router-lisp-site-common-grouping;
    }
  }

  grouping router-lisp-site-publication-summary-only-grouping {
    leaf publication-summary-only {
      description
        "Publish only aggregate summary of EID prefixes";
      type empty;
    }
  }

  grouping router-lisp-extranet-policy-common-group-obsolete {
    list prefixes {
      status obsolete;
      key "prefix";
      leaf prefix {
        status obsolete;
        type union {
          type inet:ipv4-prefix;
          type ios-types:ipv6-prefix;
        }
      }
    }
    leaf ip-any {
      status obsolete;
      description
        "Accept any ipv4/ipv6 address";
      type empty;
    }
  }

  grouping router-lisp-extranet-policy-common-group {
    list prefixes {
      key "prefix";
      leaf prefix {
        type union {
          type inet:ipv4-prefix;
          type ios-types:ipv6-prefix;
        }
      }
    }
    leaf ip-any {
      description
        "Accept any ipv4/ipv6 address";
      type empty;
    }
  }

  grouping router-lisp-extranet-policy-attribute-group-obsolete {
    container map-cache {
      status obsolete;
      description
        "Map-cache configuration";
      leaf extranet-policy {
        status obsolete;
        description
          "Install map cache to map request for extranet policy";
        type empty;
      }
    }
    container route-export {
      status obsolete;
      description
        "Export routes into RIB from LISP";
      leaf extranet-policy {
        status obsolete;
        description
          "Export extranet config policy";
        type empty;
      }
    }
    container distance {
      status obsolete;
      description
        "Administrative distance for RIB route installation";
      leaf extranet-policy {
        status obsolete;
        description
          "LISP installed routes of type extranet-policy";
        type uint32 {
          range "1..255";
        }
      }
    }
  }

  grouping router-lisp-extranet-policy-attribute-group {
    container map-cache {
      description
        "Map-cache configuration";
      leaf extranet-policy {
        description
          "Install map cache to map request for extranet policy";
        type empty;
      }
    }
    container route-export {
      description
        "Export routes into RIB from LISP";
      leaf extranet-policy {
        description
          "Export extranet config policy";
        type empty;
      }
    }
    container distance {
      description
        "Administrative distance for RIB route installation";
      leaf extranet-policy {
        description
          "LISP installed routes of type extranet-policy";
        type uint32 {
          range "1..255";
        }
      }
    }
  }

  grouping router-lisp-extranet-eid-record-provider-group {
    list eid-record-provider {
      description
        "Extranet EID address record for a provider";
      max-elements 1;
      key "instance-id";
      leaf instance-id {
        description
          "EID instance-ID";
        must 'not (/ios:native/ios:router/lisp/extranet/eid-record-subscriber[instance-id = current() ]) and not (/ios:native/ios:router/lisp-list/extranet/eid-record-subscriber[instance-id = current() ])' {
          error-message "% Provider EID group cannot be same as other subscriber EID group";
        }
        type uint32 {
          range "0..16777214";
        }
      }
      container default {
        status obsolete;
        uses router-lisp-extranet-policy-common-group-obsolete;
        uses router-lisp-extranet-policy-attribute-group-obsolete;
      }
      uses router-lisp-extranet-policy-common-group;
      uses router-lisp-extranet-policy-attribute-group;
    }
  }

  grouping router-lisp-extranet-eid-record-subscriber-group {
    list eid-record-subscriber {
      description
        "Extranet EID address record for subscriber";
      key "instance-id";
      leaf instance-id {
        must 'not (../../eid-record-provider[instance-id = current() ])' {
          error-message "% Subscriber instance cannot be same as provider instance";
        }
        must 'not (/ios:native/ios:router/lisp/extranet/eid-record-provider[instance-id = current() ]) and not (/ios:native/ios:router/lisp-list/extranet/eid-record-provider[instance-id = current() ])' {
          error-message "% Subscriber EID group cannot be same as other provider EID group";
        }
        description
          "EID instance-ID";
        type uint32 {
          range "0..16777214";
        }
      }
      container default {
        status obsolete;
        uses router-lisp-extranet-policy-common-group-obsolete;
      }
      uses router-lisp-extranet-policy-common-group;
      container service-insertion {
        leaf service-id {
          type uint16 {
            range "1..8";
          }
        }
        leaf service-type {
          type enumeration {
            enum firewall;
            enum s2s;
          }
        }
      }
    }
  }

  grouping router-lisp-extranet-group {
    list extranet {
      description
        "Configure extranet config policy on a map server (MS)";
      key "ext-name";
      leaf ext-name {
        description
          "The extranet name";
        type string;
      }
      leaf extranet-config-from-transit {
        description
          "Enable extranet config propagation";
        type empty;
      }
      container default {
        status obsolete;
        uses router-lisp-extranet-eid-record-provider-group-obsolete;
        uses router-lisp-extranet-eid-record-subscriber-group-obsolete;
      }
      uses router-lisp-extranet-eid-record-provider-group;
      uses router-lisp-extranet-eid-record-subscriber-group;
    }
  }

  grouping config-lisp-remote-locator-set-grouping {
    list ipv4-address {
      description
        "IPv4 Address of loopback or other Proxy ETR interface";
      key "address";
      leaf address {
        type inet:ipv4-address;
      }
      leaf instance-id {
        description
          "EID instance-ID";
        type uint32 {
          range "0..16777214";
        }
      }
      uses router-lisp-locator-set-grouping;
    }
    list ipv6-address {
      description
        "IPv6 Address of loopback or other Proxy ETR interface";
      key "address";
      leaf address {
        type inet:ipv6-address;
      }
      leaf instance-id {
        description
          "EID instance-ID";
        type uint32 {
          range "0..16777214";
        }
      }
      uses router-lisp-locator-set-grouping;
    }
  }

  grouping config-lisp-main-grouping {
    container service {
      description
        "Configure lisp service type";
      container ipv4 {
        presence "true";
        container default {
          status obsolete;
          uses router-lisp-service-ipv4-grouping-obsolete;
        }
        uses router-lisp-service-ipv4-grouping;
      }
      container ipv6 {
        presence "true";
        container default {
          status obsolete;
          uses router-lisp-service-ipv6-grouping-obsolete;
        }
        uses router-lisp-service-ipv6-grouping;
      }
      container ethernet {
        presence "true";
        container default {
          status obsolete;
          uses router-lisp-service-ethernet-grouping-obsolete;
        }
        uses router-lisp-service-ethernet-grouping;
      }
    }
    leaf disable-extranet-policy-import-to-db {
      description
        "Disable Extranet Policy import to Database";
      type boolean;
      default "false";
    }
    container default-etr {
      description
        "Configuration applied to default-etr registrations";
      leaf disable-metric {
        description
          "Disable getting metric from RIB";
        type empty;
      }
    }
    container encapsulation {
      description
        "Select encapsulation type for data packets";
      leaf vxlan {
        description
          "Use VXLAN encapsulation for data packets";
        type empty;
      }
    }
    uses router-lisp-extranet-group;
    list remote-locator-set {
      description
        "Configure a named remote locator set";
      key "name";
      leaf name {
        type string;
      }
      container default {
        status obsolete;
        uses config-lisp-remote-locator-set-grouping-obsolete;
      }
      uses config-lisp-remote-locator-set-grouping;
    }
    list locator-set {
      description
        "Configure a named locator set";
      key "name";
      leaf name {
        type string;
      }
      leaf auto-discover-rlocs {
        description
          "Auto discover locators registered by other xTRs";
        type empty;
      }
      list IPv4-interface {
        description
          "Use IPv4 address of interface as locator";
        key "name";
        leaf name {
          type string;
        }
        uses router-lisp-locator-set-grouping-new;
        uses router-lisp-locator-set-grouping-deprecated;
      }
      list IPv6-interface {
        description
          "Use IPv6 address of interface as locator";
        key "name";
        leaf name {
          type string;
        }
        uses router-lisp-locator-set-grouping-new;
        uses router-lisp-locator-set-grouping-deprecated;
      }
      list ip-address {
        description
          "Use IPv6 address of interface as locator";
        key "ip";
        leaf ip {
          type inet:ip-address;
        }
        uses router-lisp-locator-set-grouping-new;
        uses router-lisp-locator-set-grouping-deprecated;
      }
    }
    container locator {
      description
        "Locator configuration";
      leaf default-set {
        description
          "Specify a default locator-set";
        type string;
      }
      leaf consistency-check {
        description
          "Log a message if RLOC inconsistency is detected";
        type boolean;
        default "true";
      }
    }
    list locator-scope {
      description
        "Configure a locator scope";
      key "name";
      leaf name {
        type string;
      }
      leaf-list rloc-prefix {
        description
          "RLOC prefix to check against ITR RLOC and ETR RLOC";
        type union {
          type inet:ipv4-prefix;
          type ios-types:ipv6-prefix;
        }
      }
      leaf-list rtr-locator-set {
        description
          "Locator-set of RTR to use in proxy reply for disjoint/cross AF RLOC";
        type string;
      }
    }
    list prefix-list {
      description
        "Configure a named prefix list";
      key "name";
      leaf name {
        type string;
      }
      list ipv4-prefix {
        description
          "IPv4 EID-prefix";
        key "prefix";
        leaf prefix {
          type inet:ipv4-prefix;
        }
      }
      list ipv6-prefix {
        description
          "IPv6 EID-prefix";
        key "prefix";
        leaf prefix {
          type inet:ipv6-prefix;
        }
      }
    }
    container instance-container {
      description
        "EID instance-ID";
      list instance-list {
        key "instance-id";
        leaf instance-id {
          description
            "EID instance-ID";
          type uint32 {
            range "0..16777214";
          }
        }
        container default {
          status obsolete;
          uses router-lisp-inst-grouping-obsolete;
        }
        uses router-lisp-inst-grouping;
      }
    }
    uses router-lisp-common-grouping;
    container eid-table {
      status obsolete;
      description
        "Configure an EID instance for a VRF";
      list instance-list {
        status obsolete;
        key "instance-id";
        leaf instance-id {
          status obsolete;
          description
            "EID instance-ID";
          type uint32 {
            range "0..16777214";
          }
        }
        leaf vrf-name {
          status obsolete;
          type string;
        }
        leaf default {
          status obsolete;
          description
            "Default VRF";
          type empty;
        }
        leaf vrf {
          status obsolete;
          type string;
        }
        list database-mapping {
          status obsolete;
          description
            "Configures Locator addresses for an ETR";
          key "eid-prefix";
          leaf eid-prefix {
            status obsolete;
            type union {
              type inet:ipv4-prefix;
              type ios-types:ipv6-prefix;
            }
          }
          leaf locator-set {
            status obsolete;
            description
              "Use locators defined by locator-set";
            type string;
          }
        }
        list dynamic-eid {
          status obsolete;
          description
            "Configure a dynamic EID";
          key "name";
          leaf name {
            status obsolete;
            type string;
          }
          list database-mapping {
            status obsolete;
            description
              "Configures EID-prefix and locator-set for dynamic-EID";
            key "eid-prefix";
            leaf eid-prefix {
              status obsolete;
              type inet:ipv4-prefix;
            }
            leaf locator-set {
              status obsolete;
              description
                "Use locators defined by locator-set";
              type string;
            }
          }
          container eid-notify {
            status obsolete;
            description
              "Configure options for sending/receiving EID-notify";
            container authentication-key {
              status obsolete;
              description
                "Authentication key used for validating received EID-notify";
              uses router-lisp-key-grouping-obsolete;
            }
            list gateway-key {
              status obsolete;
              key "gateway-ip";
              leaf gateway-ip {
                status obsolete;
                type inet:ip-address;
              }
              uses router-lisp-key-grouping-obsolete;
              leaf hash-function {
                status obsolete;
                description
                  "EID-notify authentication type";
                type enumeration {
                  enum sha1;
                  enum sha2;
                }
              }
            }
          }
          leaf map-notify-group {
            status obsolete;
            description
              "Multicast group which to send map-notifies to";
            type inet:ip-address;
          }
          list map-server {
            status obsolete;
            description
              "Configures map server for ETR registration";
            key "ip";
            leaf ip {
              status obsolete;
              type inet:ip-address;
            }
            container key {
              status obsolete;
              description
                "Authentication key used with map server";
              leaf key-0 {
                status obsolete;
                description
                  "The UNENCRYPTED (cleartext) password";
                type string;
              }
              leaf key-6 {
                status obsolete;
                description
                  "The ENCRYPTED password";
                type string;
              }
              leaf key-7 {
                status obsolete;
                description
                  "The HIDDEN password";
                type string;
              }
              leaf pwd {
                status obsolete;
                description
                  "The UNENCRYPTED (cleartext) password";
                type string;
              }
              leaf hash-function {
                status obsolete;
                description
                  "Map-Register authentication type";
                type enumeration {
                  enum sha1;
                  enum sha2;
                }
              }
            }
            leaf proxy-reply {
              status obsolete;
              description
                "Request Map-Server to send Map-Replies on behalf of site";
              type empty;
            }
          }
        }
        uses router-lisp-common-grouping-obsolete;
        list map-cache {
          status obsolete;
          description
            "Configures static EID-to-RLOC mappings for an ITR";
          key "eid-prefix";
          leaf eid-prefix {
            status obsolete;
            type union {
              type inet:ipv4-prefix;
              type ios-types:ipv6-prefix;
            }
          }
          container etr-interface-ip {
            status obsolete;
            leaf etr-interface-ip-address {
              status obsolete;
              type inet:ip-address;
            }
            leaf priority {
              status obsolete;
              description
                "Configures which Locators from a set are preferred";
              type uint8;
            }
            leaf weight {
              status obsolete;
              description
                "Traffic load-spreading among Locators";
              type uint8 {
                range "0..100";
              }
            }
          }
          leaf drop {
            status obsolete;
            description
              "Drop packets that match this map-cache entry";
            type empty;
          }
          leaf map-request {
            status obsolete;
            description
              "Send Map-Request for LISP destination EID";
            type empty;
          }
          leaf native-forward {
            status obsolete;
            description
              "Natively forward packets that match this map-cache entry";
            type empty;
          }
        }
      }
    }
    container security {
      description
        "Enable default LISP security and authentication in reply is optional";
      presence "true";
      leaf strong {
        description
          "Enable default LISP security and authentication in reply is required";
        type empty;
      }
    }
    uses rouer-lisp-site-grouping;
    leaf site-id {
      description
        "Configure a site-id for this site";
      type uint32;
    }
    container syslog {
      description
        "Configure syslog option";
      container session {
        description
          "Enable session syslog";
        leaf changes {
          description
            "Enable session change syslog";
          type empty;
        }
      }
      leaf verbose {
        description
          "Enable verbose syslog";
        type empty;
      }
    }
    container capability {
      description
        "Configure capability";
      container publish-subscribe {
        description
          "Configure Capability for Publish-Subscribe functionality";
        leaf instance-id {
          description
            "Instance-ID";
          type boolean;
          default "true";
        }
      }
    }
    container fabric {
      description
        "Configure fabric role";
      presence "true";
      leaf border {
        description
          "Configure fabric role as border";
        type empty;
      }
    }
    container redundancy {
      description
        "Configure redundancy";
      leaf sso {
        description
          "Configure redundancy sso";
        type boolean;
        default "true";
      }
    }
    container tcp {
      description
        "Configure TCP options";
      leaf path-mtu-discovery {
        description
          "Configure path mtu discovery";
        type boolean;
        default "true";
      }
      list auth-option {
        description
          "Configure LISP TCP auth-option";
        key "name";
        leaf name {
          type string;
        }
        list peer {
          description
            "Configure TCP-AO peer";
          key "address";
          leaf address {
            type union {
              type inet:ipv4-address;
              type inet:ipv6-address;
              type enumeration {
                enum accept;
              }
            }
          }
        }
      }
    }
    leaf domain-id {
      description
        "Configures Domain-ID of LISP device";
      type uint32 {
        range "1..4294967038";
      }
    }
    leaf multihoming-id {
      description
        "Configures Multihoming-ID of LISP device";
      type uint16 {
        range "1..65535";
      }
    }
    leaf publication-delete-timer {
      description
        "Publication delete timer";
      type uint16 {
        range "3..1440";
      }
      units "minutes";
    }
  }

  grouping config-interface-lisp-grouping {
    container lisp {
      description
        "Locator/ID Separation Protocol";
      leaf extended-subnet-mode {
        description
          "Configures to enable extended subnet mode on the interface";
        type empty;
      }
      container mobility {
        description
          "Configures to allow EID mobility on interface";
        list dynamic-eid {
          key "dynamic-eid-name";
          leaf dynamic-eid-name {
            type string;
          }
          container nbr-proxy-reply {
            description
              "Neighbor proxy reply behavior for dynamic EID group";
            presence "true";
            leaf requests {
              description
                "Send neighbor proxy reply after reaching request threshold";
              type uint8 {
                range "0..5";
              }
            }
          }
        }
        container discover {
          description
            "Configure mobility dynamic EID discover settings";
          leaf arp {
            description
              "Dynamic EID discover through ARP events on this interface";
            type boolean;
          }
        }
        container liveness {
          description
            "Configure mobility liveness settings";
          leaf test {
            description
              "Perform liveness test on dynamic-EID discovered on this interface";
            type boolean;
          }
          leaf ttl {
            description
              "Configures the TTL in the liveness test packet";
            type uint8 {
              range "2..255";
            }
          }
        }
      }
    }
  }

  grouping config-router-lisp-list-grouping {
    list lisp-list {
      description
        "Locator/ID Separation Protocol";
      key "lisp";
      leaf lisp {
        description
          "Locator/ID Separation Protocol";
        type uint16 {
          range "1..65520";
        }
      }
      container default {
        status obsolete;
        uses config-lisp-main-grouping-obsolete;
      }
      uses config-lisp-main-grouping;
    }
  }

  grouping config-router-lisp-grouping {
    container lisp {
      description
        "Locator/ID Separation Protocol";
      presence "true";
      container default {
        status obsolete;
        uses config-lisp-main-grouping-obsolete;
      }
      uses config-lisp-main-grouping;
    }
  }

  grouping config-interface-ip-lisp-grouping {
    container lisp {
      description
        "Locator/ID Separation Protocol";
      container src-locator {
        uses ios:interface-with-dependency-grouping;
      }
      leaf source-locator {
        status deprecated;
        description
          "Deprecated: Please use src-locator";
        type string;
      }
    }
  }

  augment "/ios:native/ios:router" {
    uses config-router-lisp-grouping;
    uses config-router-lisp-list-grouping;
  }

  augment "/ios:native/ios:interface/ios:FastEthernet/ios:ip" {
    uses config-interface-ip-lisp-grouping;
  }

  augment "/ios:native/ios:interface/ios:GigabitEthernet/ios:ip" {
    uses config-interface-ip-lisp-grouping;
  }

  augment "/ios:native/ios:interface/ios:TenGigabitEthernet/ios:ip" {
    uses config-interface-ip-lisp-grouping;
  }

  augment "/ios:native/ios:interface/ios:FiveGigabitEthernet/ios:ip" {
    uses config-interface-ip-lisp-grouping;
  }

  augment "/ios:native/ios:interface/ios:AppGigabitEthernet/ios:ip" {
    uses config-interface-ip-lisp-grouping;
  }

  augment "/ios:native/ios:interface/ios:TwentyFiveGigE/ios:ip" {
    uses config-interface-ip-lisp-grouping;
  }

  augment "/ios:native/ios:interface/ios:TwoGigabitEthernet/ios:ip" {
    uses config-interface-ip-lisp-grouping;
  }

  augment "/ios:native/ios:interface/ios:FortyGigabitEthernet/ios:ip" {
    uses config-interface-ip-lisp-grouping;
  }

  augment "/ios:native/ios:interface/ios:HundredGigE/ios:ip" {
    uses config-interface-ip-lisp-grouping;
  }

  augment "/ios:native/ios:interface/ios:Port-channel/ios:ip" {
    uses config-interface-ip-lisp-grouping;
  }

  augment "/ios:native/ios:interface/ios:Loopback/ios:ip" {
    uses config-interface-ip-lisp-grouping;
  }

  augment "/ios:native/ios:interface/ios:Tunnel/ios:ip" {
    uses config-interface-ip-lisp-grouping;
  }

  augment "/ios:native/ios:interface/ios:FastEthernet" {
    uses config-interface-lisp-grouping;
  }

  augment "/ios:native/ios:interface/ios:GigabitEthernet" {
    uses config-interface-lisp-grouping;
  }

  augment "/ios:native/ios:interface/ios:TenGigabitEthernet" {
    uses config-interface-lisp-grouping;
  }

  augment "/ios:native/ios:interface/ios:FiveGigabitEthernet" {
    uses config-interface-lisp-grouping;
  }

  augment "/ios:native/ios:interface/ios:AppGigabitEthernet" {
    uses config-interface-lisp-grouping;
  }

  augment "/ios:native/ios:interface/ios:TwentyFiveGigE" {
    uses config-interface-lisp-grouping;
  }

  augment "/ios:native/ios:interface/ios:TwoGigabitEthernet" {
    uses config-interface-lisp-grouping;
  }

  augment "/ios:native/ios:interface/ios:FortyGigabitEthernet" {
    uses config-interface-lisp-grouping;
  }

  augment "/ios:native/ios:interface/ios:HundredGigE" {
    uses config-interface-lisp-grouping;
  }

  augment "/ios:native/ios:interface/ios:Port-channel" {
    uses config-interface-lisp-grouping;
  }

  augment "/ios:native/ios:interface/ios:Loopback" {
    uses config-interface-lisp-grouping;
  }

  augment "/ios:native/ios:interface/ios:Tunnel" {
    uses config-interface-lisp-grouping;
  }

  augment "/ios:native/ios:interface/ios:Vlan" {
    uses config-interface-lisp-grouping;
  }

  grouping router-lisp-extranet-group-obsolete {
    list extranet {
      status obsolete;
      description
        "Configure extranet config policy on a map server (MS)";
      key "ext-name";
      leaf ext-name {
        status obsolete;
        description
          "The extranet name";
        type string;
      }
      container default {
        status obsolete;
        uses router-lisp-extranet-eid-record-provider-group-obsolete;
        uses router-lisp-extranet-eid-record-subscriber-group-obsolete;
      }
      uses router-lisp-extranet-eid-record-provider-group-obsolete;
      uses router-lisp-extranet-eid-record-subscriber-group-obsolete;
    }
  }

  grouping router-lisp-extranet-eid-record-subscriber-group-obsolete {
    list eid-record-subscriber {
      status obsolete;
      description
        "Extranet EID address record for subscriber";
      key "instance-id";
      leaf instance-id {
        status obsolete;
        must 'not (../../eid-record-provider[instance-id = current() ])' {
          error-message "% Subscriber instance cannot be same as provider instance";
        }
        must 'not (/ios:native/ios:router/lisp/extranet/eid-record-provider[instance-id = current() ]) and not (/ios:native/ios:router/lisp-list/extranet/eid-record-provider[instance-id = current() ])' {
          error-message "% Subscriber EID group cannot be same as other provider EID group";
        }
        description
          "EID instance-ID";
        type uint32 {
          range "0..16777214";
        }
      }
      container default {
        status obsolete;
        uses router-lisp-extranet-policy-common-group-obsolete;
      }
      uses router-lisp-extranet-policy-common-group-obsolete;
      container service-insertion {
        status obsolete;
        leaf service-id {
          status obsolete;
          type uint16 {
            range "1..8";
          }
        }
        leaf service-type {
          status obsolete;
          type enumeration {
            enum firewall;
            enum s2s;
          }
        }
      }
    }
  }

  grouping router-lisp-extranet-eid-record-provider-group-obsolete {
    list eid-record-provider {
      status obsolete;
      description
        "Extranet EID address record for a provider";
      max-elements 1;
      key "instance-id";
      leaf instance-id {
        status obsolete;
        description
          "EID instance-ID";
        must 'not (/ios:native/ios:router/lisp/extranet/eid-record-subscriber[instance-id = current() ]) and not (/ios:native/ios:router/lisp-list/extranet/eid-record-subscriber[instance-id = current() ])' {
          error-message "% Provider EID group cannot be same as other subscriber EID group";
        }
        type uint32 {
          range "0..16777214";
        }
      }
      container default {
        status obsolete;
        uses router-lisp-extranet-policy-common-group-obsolete;
        uses router-lisp-extranet-policy-attribute-group-obsolete;
      }
      uses router-lisp-extranet-policy-common-group-obsolete;
      uses router-lisp-extranet-policy-attribute-group-obsolete;
    }
  }

  grouping router-lisp-inst-service-ip-route-import-database-protocol-grouping-obsolete {
    container application {
      status obsolete;
      description
        "Application Protocol";
      uses router-lisp-ip-route-import-database-grouping-obsolete;
    }
    list bgp {
      status obsolete;
      description
        "Border Gateway Protocol (BGP)";
      key "id";
      leaf id {
        status obsolete;
        type ios-types:bgp-as-number-type;
      }
      uses router-lisp-ip-route-import-database-grouping-obsolete;
    }
    container connected {
      status obsolete;
      description
        "Connected";
      uses router-lisp-ip-route-import-database-grouping-obsolete;
    }
    list eigrp {
      status obsolete;
      description
        "Enhanced Interior Gateway Routing Protocol (EIGRP)";
      key "id";
      leaf id {
        status obsolete;
        type uint16 {
          range "1..65535";
        }
      }
      uses router-lisp-ip-route-import-database-grouping-obsolete;
    }
    container isis {
      status obsolete;
      description
        "ISO IS-IS";
      leaf process-id {
        status obsolete;
        description
          "Process name";
        type string;
      }
      uses router-lisp-ip-route-import-database-grouping-obsolete;
    }
    container maximum-prefix {
      status obsolete;
      description
        "Maximum number of prefixes to pick up from the RIB";
      leaf number {
        status obsolete;
        type uint32 {
          range "1..4294967295";
        }
      }
      choice threshold-warning {
        status obsolete;
        case warning-only-case {
          status obsolete;
          leaf warning-only {
            status obsolete;
            description
              "Only give a warning message and do not limit entries";
            type empty;
          }
        }
        case threshold-case {
          status obsolete;
          leaf threshold {
            status obsolete;
            type uint8 {
              range "1..100";
            }
          }
        }
        case threshold-warning-case {
          status obsolete;
          leaf threshold1 {
            status obsolete;
            type uint8 {
              range "1..100";
            }
          }
          leaf warning-only1 {
            status obsolete;
            description
              "Only give a warning message and do not limit entries";
            type empty;
          }
        }
      }
    }
    container nd {
      status obsolete;
      description
        "Neighbor Discovery";
      uses router-lisp-ip-route-import-database-grouping-obsolete;
    }
    container omp {
      status obsolete;
      if-feature "ios-features:omp";
      description
        "Overlay Management Protocol";
      uses router-lisp-ip-route-import-database-grouping-obsolete;
    }
    list ospf {
      status obsolete;
      description
        "Open Shortest Path First (OSPF)";
      key "id";
      leaf id {
        status obsolete;
        type uint16 {
          range "1..65535";
        }
      }
      uses router-lisp-ip-route-import-database-grouping-obsolete;
    }
    container static {
      status obsolete;
      description
        "Static routes";
      uses router-lisp-ip-route-import-database-grouping-obsolete;
    }
  }

  grouping router-lisp-inst-service-ip-route-import-map-cache-protocol-grouping-obsolete {
    container application {
      status obsolete;
      description
        "Application Protocol";
      presence "true";
      uses router-lisp-ip-route-import-map-cache-grouping-obsolete;
    }
    list bgp {
      status obsolete;
      description
        "Border Gateway Protocol (BGP)";
      key "id";
      leaf id {
        status obsolete;
        type ios-types:bgp-as-number-type;
      }
      uses router-lisp-ip-route-import-map-cache-grouping-obsolete;
    }
    container connected {
      status obsolete;
      description
        "Connected";
      presence "true";
      uses router-lisp-ip-route-import-map-cache-grouping-obsolete;
    }
    list eigrp {
      status obsolete;
      description
        "Enhanced Interior Gateway Routing Protocol (EIGRP)";
      key "id";
      leaf id {
        status obsolete;
        type uint16 {
          range "1..65535";
        }
      }
      uses router-lisp-ip-route-import-map-cache-grouping-obsolete;
    }
    container isis {
      status obsolete;
      description
        "ISO IS-IS";
      leaf id {
        status obsolete;
        description
          "Process name";
        type string;
      }
      uses router-lisp-ip-route-import-map-cache-grouping-obsolete;
    }
    container maximum-prefix {
      status obsolete;
      description
        "Maximum number of prefixes to pick up from the RIB";
      leaf number {
        status obsolete;
        type uint32 {
          range "1..4294967295";
        }
      }
      choice threshold-warning {
        status obsolete;
        case warning-only-case {
          status obsolete;
          leaf warning-only {
            status obsolete;
            description
              "Only give a warning message and do not limit entries";
            type empty;
          }
        }
        case threshold-case {
          status obsolete;
          leaf threshold {
            status obsolete;
            type uint8 {
              range "1..100";
            }
          }
        }
        case threshold-warning-case {
          status obsolete;
          leaf threshold1 {
            status obsolete;
            type uint8 {
              range "1..100";
            }
          }
          leaf warning-only1 {
            status obsolete;
            description
              "Only give a warning message and do not limit entries";
            type empty;
          }
        }
      }
    }
    container nd {
      status obsolete;
      description
        "Neighbour Discovery";
      presence "true";
      uses router-lisp-ip-route-import-map-cache-grouping-obsolete;
    }
    list ospf {
      status obsolete;
      description
        "Open Shortest Path First (OSPF)";
      key "id";
      leaf id {
        status obsolete;
        type uint16 {
          range "1..65535";
        }
      }
      uses router-lisp-ip-route-import-map-cache-grouping-obsolete;
    }
    container static {
      status obsolete;
      description
        "Static routes";
      presence "true";
      uses router-lisp-ip-route-import-map-cache-grouping-obsolete;
    }
  }

  grouping router-lisp-inst-service-ipv4-route-import-map-cache-protocol-grouping-obsolete {
    container map-cache {
      status obsolete;
      description
        "Use RIB routes to define EID address space in map-cache";
      uses router-lisp-inst-service-ip-route-import-map-cache-protocol-grouping-obsolete;
      container rip {
        status obsolete;
        description
          "Routing Information Protocol (RIP)";
        uses router-lisp-ip-route-import-map-cache-grouping-obsolete;
      }
    }
  }

  grouping router-lisp-inst-service-ipv6-route-import-map-cache-protocol-grouping-obsolete {
    container map-cache {
      status obsolete;
      description
        "Use RIB routes to define EID address space in map-cache";
      uses router-lisp-inst-service-ip-route-import-map-cache-protocol-grouping;
      list rip {
        status obsolete;
        description
          "Routing Information Protocol (RIP)";
        key "id";
        leaf id {
          status obsolete;
          description
            "User selected string identifying this process";
          type string;
        }
        uses router-lisp-ip-route-import-map-cache-grouping-obsolete;
      }
    }
  }

  grouping router-lisp-inst-service-ipv4-route-import-database-protocol-grouping-obsolete {
    container database {
      status obsolete;
      description
        "Use RIB routes to define local EID database entries";
      uses router-lisp-inst-service-ip-route-import-database-protocol-grouping-obsolete;
      container rip {
        status obsolete;
        description
          "Routing Information Protocol (RIP)";
        uses router-lisp-ip-route-import-database-grouping-obsolete;
      }
    }
  }

  grouping router-lisp-inst-service-ipv6-route-import-database-protocol-grouping-obsolete {
    container database {
      status obsolete;
      description
        "Use RIB routes to define local EID database entries";
      uses router-lisp-inst-service-ip-route-import-database-protocol-grouping-obsolete;
      list rip {
        status obsolete;
        description
          "Routing Information Protocol (RIP)";
        key "id";
        leaf id {
          status obsolete;
          description
            "User selected string identifying this process";
          type string;
        }
        uses router-lisp-ip-route-import-database-grouping-obsolete;
      }
    }
  }

  grouping router-lisp-inst-service-ip-route-import-prefix-list-protocol-grouping-obsolete {
    list prefix-list-proto {
      status obsolete;
      key "prefix-list protocol";
      leaf prefix-list {
        status obsolete;
        type string;
      }
      leaf protocol {
        status obsolete;
        type enumeration {
          enum application;
          enum bgp;
          enum connected;
          enum eigrp;
          enum isis;
          enum maximum-prefix;
          enum nd;
          enum ospf;
          enum static;
          enum rip;
        }
      }
      list bgp-id {
        status obsolete;
        key "bgp-id";
        when "../protocol = 'bgp'";
        leaf bgp-id {
          status obsolete;
          type ios-types:bgp-as-number-type;
        }
        leaf route-map {
          status obsolete;
          type string;
        }
      }
      list eigrp-or-ospf-id {
        status obsolete;
        when "../protocol = 'eigrp' or ../protocol = 'ospf'";
        key "int16-id";
        leaf int16-id {
          status obsolete;
          type uint16 {
            range "1..65535";
          }
        }
        leaf route-map {
          status obsolete;
          type string;
        }
      }
      leaf isis-id {
        status obsolete;
        when "../protocol = 'isis'";
        type string;
      }
      leaf number {
        status obsolete;
        when "../protocol = 'maximum-prefix'";
        type uint32 {
          range "1..4294967295";
        }
      }
      leaf threshold {
        status obsolete;
        when "../protocol = 'maximum-prefix'";
        type uint8 {
          range "1..100";
        }
      }
      leaf warning-only {
        status obsolete;
        when "../protocol = 'maximum-prefix'";
        type empty;
      }
      leaf route-map {
        status obsolete;
        when "not(../protocol = 'maximum-prefix')";
        type string;
      }
    }
  }

  grouping router-lisp-inst-service-ipv6-route-import-protocol-grouping-obsolete {
    uses router-lisp-inst-service-ipv6-route-import-database-protocol-grouping-obsolete;
    uses router-lisp-inst-service-ipv6-route-import-map-cache-protocol-grouping-obsolete;
    uses router-lisp-inst-service-ip-route-import-prefix-list-protocol-grouping-obsolete;
  }

  grouping router-lisp-inst-service-ipv4-route-import-protocol-grouping-obsolete {
    uses router-lisp-inst-service-ipv4-route-import-database-protocol-grouping-obsolete;
    uses router-lisp-inst-service-ipv4-route-import-map-cache-protocol-grouping-obsolete;
    uses router-lisp-inst-service-ip-route-import-prefix-list-protocol-grouping-obsolete;
  }

  grouping router-lisp-xtr-prefix-list-grouping-obsolete {
    leaf prefix-list {
      status obsolete;
      description
        "Associates ITR/ETR with prefix list";
      type string;
    }
  }

  grouping router-lisp-map-server-domain-id-grouping-obsolete {
    leaf domain-id {
      status obsolete;
      description
        "Domain-ID associated with map server";
      type uint32 {
        range "1..4294967038";
      }
    }
  }

  grouping router-lisp-itr-grouping-obsolete {
    container itr {
      status obsolete;
      description
        "Configures a LISP Ingress Tunnel Router (ITR)";
      list map-resolver {
        status obsolete;
        description
          "Configures map-resolver address for sending Map-Requests";
        key "ip-addr";
        leaf ip-addr {
          status obsolete;
          type inet:ip-address;
        }
        uses router-lisp-xtr-prefix-list-grouping-obsolete;
      }
      leaf nmr-ttl {
        status obsolete;
        description
          "Override negative map-reply TTL for site EID";
        type uint16 {
          range "1..900";
        }
      }
    }
    container itr-enable {
      status obsolete;
      leaf itr {
        status obsolete;
        description
          "Configures a LISP Ingress Tunnel Router (ITR)";
        type empty;
      }
    }
  }

  grouping router-lisp-etr-grouping-obsolete {
    container etr-enable {
      status obsolete;
      leaf etr {
        status obsolete;
        description
          "Configures a LISP Egress Tunnel Router (ETR)";
        type empty;
      }
    }
    container etr {
      status obsolete;
      description
        "Configures a LISP Egress Tunnel Router (ETR)";
      uses router-lisp-map-server-grouping-obsolete;
      leaf map-cache-ttl {
        status obsolete;
        type uint16 {
          range "60..10080";
        }
      }
      container accept-map-request-mapping {
        status obsolete;
        leaf accept-mappping {
          status obsolete;
          type empty;
        }
        leaf verify {
          status obsolete;
          type empty;
        }
      }
    }
  }

  grouping router-lisp-database-mapping-limit-grouping-obsolete {
    container limit {
      status obsolete;
      description
        "Configures the maximum size of local EID prefixes database";
      leaf dynamic {
        status obsolete;
        description
          "Configures the maximum size of dynamic local EID prefixes database";
        type uint32;
      }
      leaf warning-threshold {
        status obsolete;
        description
          "Send warning message to syslog when the database-mapping dynamic size reaches this percentage of the limit";
        type uint8 {
          range "1..100";
        }
      }
    }
  }

  grouping router-lisp-map-cache-common-grouping-obsolete {
    list rloc-attributes {
      status obsolete;
      key "rloc";
      leaf rloc {
        status obsolete;
        description
          "IP address of loopback or other ETR interface";
        type inet:ip-address;
      }
      leaf priority {
        status obsolete;
        description
          "Configures which Locators from a set are preferred";
        mandatory true;
        type uint8 {
          range "0..255";
        }
      }
      leaf weight {
        status obsolete;
        description
          "Traffic load-spreading among Locators";
        mandatory true;
        type uint8 {
          range "0..100";
        }
      }
    }
    container etr-interface-ip {
      status obsolete;
      description
        "Deprecated by ../rloc-attributes";
      leaf etr-interface-ip-address {
        status obsolete;
        description
          "Deprecated by ../../rloc-attributes/rloc-prefix";
        type inet:ip-address;
      }
      leaf priority {
        status obsolete;
        description
          "Deprecated by ../../rloc-attributes/attributes/priority";
        type uint8 {
          range "0..255";
        }
      }
      leaf weight {
        status obsolete;
        description
          "Deprecated by ../../rloc-attributes/attributes/priority";
        type uint8 {
          range "0..100";
        }
      }
    }
  }

  grouping router-lisp-map-request-source-ipv4-grouping-obsolete {
    leaf map-request-source {
      status obsolete;
      description
        "Configures inner header source address in Map-Request message";
      type inet:ipv4-address;
    }
  }

  grouping router-lisp-map-request-source-ipv6-grouping-obsolete {
    leaf map-request-source {
      status obsolete;
      description
        "Configures inner header source address in Map-Request message";
      type inet:ipv6-address;
    }
  }

  grouping router-lisp-map-request-source-any-grouping-obsolete {
    leaf map-request-source {
      status obsolete;
      description
        "Configures inner header source address in Map-Request message";
      type inet:ip-address;
    }
  }

  grouping router-lisp-map-cache-limit-grouping-obsolete {
    container map-cache-limit {
      status obsolete;
      description
        "Configures maximum size of map-cache";
      leaf max-map-cache-entries {
        status obsolete;
        type uint32 {
          range "0..100000";
        }
      }
      leaf reserve-list {
        status obsolete;
        description
          "EID-prefixes guaranteed to be stored in map-cache";
        type string;
      }
      leaf warning-threshold {
        status obsolete;
        description
          "Send warning message to syslog when the map-cache size reaches this percentage of the limit";
        type uint8 {
          range "0..100";
        }
      }
    }
  }

  grouping router-lisp-site-registration-grouping-obsolete {
    container site-registration {
      status obsolete;
      description
        "Site registrations configuration for a given instance-id";
      leaf limit {
        status obsolete;
        description
          "Maximum number of site registrations";
        type uint32 {
          range "1..4294967295";
        }
      }
      leaf warning-threshold {
        status obsolete;
        description
          "Warning threshold to issue system logging";
        type uint8 {
          range "1..100";
        }
      }
    }
  }

  grouping router-lisp-solicit-map-request-grouping-obsolete {
    container solicit-map-request {
      status obsolete;
      description
        "Configure Solicit-Map-Request handling";
      leaf ignore {
        status obsolete;
        description
          "Ignore SMR bit in incoming Map-Requests";
        type empty;
      }
      leaf max-per-entry {
        status obsolete;
        description
          "Maximum number of SMRs for addresses under a map-cache entry";
        type uint8 {
          range "1..100";
        }
      }
      leaf suppression-time {
        status obsolete;
        description
          "How long to suppress repeated SMRs for the same address";
        type uint16 {
          range "1..600";
        }
      }
    }
  }

  grouping router-lisp-registration-history-grouping-obsolete {
    container registration-history {
      status obsolete;
      description
        "Map-server (MS) registration history";
      leaf limit {
        status obsolete;
        description
          "Size of registration history log";
        type uint32 {
          range "0..1000000";
        }
        default "1000";
      }
    }
  }

  grouping router-lisp-service-common-grouping-obsolete {
    container database-mapping {
      status obsolete;
      description
        "Address family specific local EID prefixes database configuration";
      uses router-lisp-database-mapping-limit-grouping-obsolete;
    }
    uses router-lisp-itr-grouping-obsolete;
    uses router-lisp-etr-grouping-obsolete;
    uses router-lisp-map-cache-limit-grouping-obsolete;
    uses router-lisp-registration-history-grouping-obsolete;
    container map-resolver {
      status obsolete;
      description
        "Configures a LISP Map Resolver (MR)";
      presence "true";
      container map-request {
        status obsolete;
        description
          "Map-Request processing options";
        container validate {
          status obsolete;
          description
            "Validation options";
          container source {
            status obsolete;
            description
              "Influence which source RLOCs map requests are accepted from";
            container list {
              status obsolete;
              description
                "Define allowed prefixes using an ip[v6] prefix list";
              leaf ipv4 {
                status obsolete;
                description
                  "IPv4 prefixes";
                type string;
              }
              leaf ipv6 {
                status obsolete;
                description
                  "IPv6 prefixes";
                type string;
              }
            }
            container registered {
              status obsolete;
              description
                "...from RLOCs that register EID-prefixes in the same IID on a co-located MapServer";
              container list {
                status obsolete;
                description
                  "Define allowed prefixes using an ip[v6] prefix list";
                leaf ipv4 {
                  status obsolete;
                  description
                    "IPv4 prefixes";
                  type string;
                }
                leaf ipv6 {
                  status obsolete;
                  description
                    "IPv6 prefixes";
                  type string;
                }
              }
            }
          }
        }
      }
    }
    container map-server {
      status obsolete;
      description
        "Configures a LISP Map Server (MS)";
      presence "true";
      container map-register {
        status obsolete;
        description
          "Map-Register processing options";
        container validate {
          status obsolete;
          description
            "Validation options";
          container source {
            status obsolete;
            description
              "RLOC Source IP address";
            leaf allowed-locator {
              status obsolete;
              description
                "Against sites' allowed-locators policy";
              type empty;
            }
          }
        }
      }
    }
    uses router-lisp-site-registration-grouping-obsolete;
    uses router-lisp-solicit-map-request-grouping-obsolete;
  }

  grouping dynamic-eid-detection-grouping-obsolete {
    container dynamic-eid {
      status obsolete;
      description
        "Configure dynamic eid options";
      container detection {
        status obsolete;
        description
          "Configure dynamic eid detection options";
        leaf multiple-addr {
          status obsolete;
          description
            "Configure to support multiple ip addresses per mac";
          type empty;
        }
        leaf bridged-vm {
          status obsolete;
          description
            "Configure to support sgt propagation for bridged VMs";
          type empty;
        }
      }
    }
  }

  grouping router-lisp-service-ethernet-grouping-obsolete {
    container encapsulation {
      status obsolete;
      description
        "Select encapsulation type for data packets. This node is obsolete";
      leaf vxlan {
        description
          "Use VXLAN encapsulation for data packets. This node is obsolete";
        status obsolete;
        type empty;
      }
    }
    container map-cache {
      status obsolete;
      description
        "Address family specific map cache configuration";
      leaf conservative-allocation {
        status obsolete;
        description
          "Suppress proactive created map-cache when host moves to another switch";
        type boolean;
        default "false";
      }
      leaf publications {
        status obsolete;
        description
          "Export publication entries into map cache";
        type empty;
      }
    }
    uses dynamic-eid-detection-grouping-obsolete;
    uses router-lisp-map-request-source-any-grouping-obsolete;
    uses router-lisp-service-common-grouping-obsolete;
    uses router-lisp-publish-subscribe-grouping-obsolete;
    uses router-lisp-service-ethernet-import-grouping-obsolete;
  }

  grouping router-lisp-service-import-publication-grouping-obsolete {
    container publication {
      status obsolete;
      description
        "Receive LISP publications";
      list publisher {
        status obsolete;
        description
          "Import publications from publisher";
        key "ip-addr";
        leaf ip-addr {
          status obsolete;
          type inet:ip-address;
        }
      }
    }
  }

  grouping router-lisp-inst-service-import-publication-grouping-obsolete {
    container publication {
      status obsolete;
      description
        "Receive LISP publications";
      choice publisher-choice {
        status obsolete;
        container inherit-publisher {
          status obsolete;
          leaf publisher {
            status obsolete;
            description
              "Import publications from publisher";
            type boolean;
            default "true";
          }
        }
        list publisher {
          status obsolete;
          description
            "Import publications from publisher";
          key "ip-addr";
          leaf ip-addr {
            status obsolete;
            type inet:ip-address;
          }
        }
      }
    }
  }

  grouping router-lisp-service-ip-import-database-grouping-obsolete {
    container database {
      status obsolete;
      container site-reg-src {
        status obsolete;
        description
          "Redistribute LISP internal states as database mapping";
        leaf site-registration-src {
          status obsolete;
          description
            "Import states from site registrations";
          type empty;
        }
        leaf loc-set {
          status obsolete;
          description
            "Locator set to use with database mapping entries";
          type string;
        }
      }
      leaf site-registration {
        status obsolete;
        description
          "Import states from site registrations";
        type empty;
      }
      leaf locator-set {
        status obsolete;
        description
          "Locator set to use with created database mapping entries";
        type string;
      }
      container publication {
        status obsolete;
        description
          "Redistribute LISP publication states as database mapping";
        leaf locator-set {
          status obsolete;
          must '/ios:native/ios:router/lisp/locator-set[name = current() ] or /ios:native/ios:router/lisp-list/locator-set[name = current() ]' {
            error-message "% Please configure the locator-set before configuring publication";
          }
          description
            "Locator set to use with created database mapping entries";
          type string;
        }
      }
    }
  }

  grouping router-lisp-service-ip-import-prefix-list-grouping-obsolete {
    container prefix-list-container {
      status obsolete;
      description
        "Redistribute LISP internal states into LISP prefix-list entries";
      leaf prefix-list {
        status obsolete;
        description
          "The name of the lisp prefix list";
        type string;
      }
      leaf site-registration {
        status obsolete;
        description
          "Import states from site registrations";
        type empty;
      }
      leaf publication {
        status obsolete;
        description
          "Import states from publications";
        type empty;
      }
    }
  }

  grouping router-lisp-service-ethernet-import-publication-grouping-obsolete {
    container publication {
      status obsolete;
      description
        "Receive LISP publications";
      list publisher {
        status obsolete;
        description
          "Import publications from publisher";
        key "ip-addr";
        leaf ip-addr {
          status obsolete;
          type inet:ip-address;
        }
      }
    }
  }

  grouping router-lisp-service-ethernet-import-grouping-obsolete {
    container import {
      status obsolete;
      description
        "Redistribute LISP states internally";
      uses router-lisp-service-ethernet-import-publication-grouping-obsolete;
    }
  }

  grouping router-lisp-inst-service-ethernet-import-grouping-obsolete {
    container import {
      status obsolete;
      description
        "Redistribute LISP states internally";
      uses router-lisp-inst-service-import-publication-grouping-obsolete;
    }
  }

  grouping router-lisp-service-ip-import-grouping-obsolete {
    container import {
      status obsolete;
      description
        "Redistribute LISP states internally";
      uses router-lisp-service-ip-import-database-grouping-obsolete;
      uses router-lisp-service-import-publication-grouping-obsolete;
    }
  }

  grouping router-lisp-inst-service-ip-import-grouping-obsolete {
    container import {
      status obsolete;
      description
        "Redistribute LISP states internally";
      uses router-lisp-service-ip-import-database-grouping-obsolete;
      uses router-lisp-service-ip-import-prefix-list-grouping-obsolete;
      uses router-lisp-inst-service-import-publication-grouping-obsolete;
    }
  }

  grouping router-lisp-service-ip-grouping-obsolete {
    uses router-lisp-service-common-grouping-obsolete;
    uses router-lisp-service-ip-distance-grouping-obsolete;
    leaf encapsulation {
      status obsolete;
      description
        "Select encapsulation type for data packets";
      type enumeration {
        enum lisp;
        enum vxlan;
      }
    }
    container mr-use-petr {
      status obsolete;
      description
        "Configure Map Resolver to include Proxy ETR in negative map reply";
      leaf remote-locator-set {
        status obsolete;
        description
          "Use the locator-set defined by remote-locator-set";
        must '/ios:native/ios:router/lisp/remote-locator-set[name = current() ] or /ios:native/ios:router/lisp-list/remote-locator-set[name = current() ]' {
          error-message "% Please configure the remote-locator-set before configuring mr-use-petr";
        }
        type string;
      }
    }
    container first-packet-petr {
      status obsolete;
      description
        "Configure Map Resolver to include First-Packet-Proxy ETR in negative map reply";
      leaf remote-locator-set {
        status obsolete;
        description
          "Use the locator-set defined by remote-locator-set";
        must '/ios:native/ios:router/lisp/remote-locator-set[name = current() ] or /ios:native/ios:router/lisp-list/remote-locator-set[name = current() ]' {
          error-message "% Please configure the remote-locator-set before configuring first-packet-petr";
        }
        type string;
      }
    }
    container map-cache {
      status obsolete;
      description
        "Address family specific map cache configuration";
      container away-eids {
        status obsolete;
        description
          "Map cache configuration for the away table";
        leaf send-map-request {
          status obsolete;
          description
            "Export away table entries into the map cache with action set to send-map-request";
          type boolean;
          default "true";
        }
      }
      leaf site-registration {
        status obsolete;
        description
          "Install map cache to map request for site registrations";
        type empty;
      }
      leaf publications {
        status obsolete;
        description
          "Export publication entries into map cache";
        type empty;
      }
      leaf conservative-allocation {
        status obsolete;
        description
          "Suppress proactive created map-cache when host moves to another switch";
        type boolean;
        default "false";
      }
    }
    uses router-lisp-map-cache-persistent-grouping-obsolete;
    uses router-lisp-proxy-grouping-obsolete;
    uses router-lisp-route-export-grouping-obsolete;
    uses router-lisp-sgt-grouping-obsolete;
    uses router-lisp-use-petr-grouping-obsolete;
    uses router-lisp-use-petr-grouping-deprecated-obsolete;
    uses router-lisp-publish-subscribe-grouping-obsolete;
    uses router-lisp-service-ip-import-grouping-obsolete;
  }

  grouping router-lisp-service-dynamic-eid-grouping-obsolete {
    container dynamic-eid {
      status obsolete;
      description
        "configure dynamic-eid parameters";
      leaf dataplane-detection {
        status obsolete;
        description
          "enable dataplane-based detection of hosts";
        type empty;
      }
    }
  }

  grouping router-lisp-service-ipv4-grouping-obsolete {
    uses router-lisp-service-ip-grouping-obsolete;
    uses router-lisp-map-request-source-ipv4-grouping-obsolete;
    uses router-lisp-service-dynamic-eid-grouping-obsolete;
  }

  grouping router-lisp-service-ipv6-grouping-obsolete {
    uses router-lisp-service-ip-grouping-obsolete;
    uses router-lisp-map-request-source-ipv6-grouping-obsolete;
  }

  grouping router-lisp-four-key-grouping-obsolete {
    choice auth-key {
      status obsolete;
      case uncpwd {
        status obsolete;
        leaf unc-pwd {
          status obsolete;
          description
            "The UNENCRYPTED (cleartext) password";
          type string;
        }
      }
      case key0 {
        status obsolete;
        leaf key-0 {
          status obsolete;
          description
            "The UNENCRYPTED (cleartext) password";
          type string;
        }
      }
      case key6 {
        status obsolete;
        leaf key-6 {
          status obsolete;
          description
            "The ENCRYPTED password";
          type string;
        }
      }
      case key7 {
        status obsolete;
        leaf key-7 {
          status obsolete;
          description
            "The ENCRYPTED password";
          type string;
        }
      }
    }
  }

  grouping router-lisp-key-hash-function-grouping-obsolete {
    leaf hash-function {
      status obsolete;
      description
        "authentication type";
      type enumeration {
        enum sha1;
        enum sha2;
      }
    }
  }

  grouping router-lisp-password-key-0and6-grouping-obsolete {
    container key-0 {
      status obsolete;
      leaf ak-0 {
        status obsolete;
        description
          "The UNENCRYPTED (cleartext) password";
        type string;
      }
      uses router-lisp-key-hash-function-grouping-obsolete;
    }
    container key-6 {
      status obsolete;
      leaf ak-6 {
        status obsolete;
        description
          "The ENCRYPTED password";
        type string;
      }
      uses router-lisp-key-hash-function-grouping-obsolete;
    }
  }

  grouping router-lisp-password-key-0and6-with-prefix-list-grouping-obsolete {
    container key-0 {
      status obsolete;
      leaf ak-0 {
        status obsolete;
        description
          "The UNENCRYPTED (cleartext) password";
        type string;
      }
      uses router-lisp-key-hash-function-grouping-obsolete;
      uses router-lisp-xtr-prefix-list-grouping-obsolete;
      uses router-lisp-map-server-domain-id-grouping-obsolete;
    }
    container key-6 {
      status obsolete;
      leaf ak-6 {
        status obsolete;
        description
          "The ENCRYPTED password";
        type string;
      }
      uses router-lisp-key-hash-function-grouping-obsolete;
      uses router-lisp-xtr-prefix-list-grouping-obsolete;
      uses router-lisp-map-server-domain-id-grouping-obsolete;
    }
  }

  grouping router-lisp-password-key-7-with-prefix-list-grouping-obsolete {
    container key-7 {
      status obsolete;
      leaf ak-7 {
        status obsolete;
        description
          "The ENCRYPTED password";
        type string;
      }
      uses router-lisp-key-hash-function-grouping-obsolete;
      uses router-lisp-xtr-prefix-list-grouping-obsolete;
      uses router-lisp-map-server-domain-id-grouping-obsolete;
    }
  }

  grouping router-lisp-password-string-grouping-obsolete {
    container key-pwd {
      status obsolete;
      leaf unc-pwd {
        status obsolete;
        description
          "The UNENCRYPTED (cleartext) password";
        type string;
      }
      uses router-lisp-key-hash-function-grouping-obsolete;
    }
  }

  grouping router-lisp-password-string-with-prefix-list-grouping-obsolete {
    container key-pwd {
      status obsolete;
      leaf unc-pwd {
        status obsolete;
        description
          "The UNENCRYPTED (cleartext) password";
        type string;
      }
      uses router-lisp-key-hash-function-grouping-obsolete;
      uses router-lisp-xtr-prefix-list-grouping-obsolete;
      uses router-lisp-map-server-domain-id-grouping-obsolete;
    }
  }

  grouping router-lisp-three-key-with-hash-function-grouping-obsolete {
    choice password {
      status obsolete;
      case password-string {
        status obsolete;
        uses router-lisp-password-string-grouping-obsolete;
      }
      case password-key {
        status obsolete;
        uses router-lisp-password-key-0and6-grouping-obsolete;
      }
    }
  }

  grouping router-lisp-four-key-with-hash-function-and-prefix-list-grouping-obsolete {
    choice password {
      status obsolete;
      case password-string {
        status obsolete;
        uses router-lisp-password-string-with-prefix-list-grouping-obsolete;
      }
      case password-key {
        status obsolete;
        uses router-lisp-password-key-0and6-with-prefix-list-grouping-obsolete;
        uses router-lisp-password-key-7-with-prefix-list-grouping-obsolete;
      }
    }
  }

  grouping router-lisp-route-export-grouping-obsolete {
    container route-export {
      status obsolete;
      description
        "Export routes into RIB from LISP";
      container site-registration-export {
        status obsolete;
        leaf site-registrations {
          status obsolete;
          description
            "Export LISP site registrations to RIB";
          type empty;
        }
        uses router-lisp-route-export-options-grouping-obsolete {
          when 'boolean(./site-registrations)';
        }
      }
      container away-eid-export {
        status obsolete;
        leaf away-eids {
          status obsolete;
          description
            "Export LISP away EIDs to RIB";
          type empty;
        }
        uses router-lisp-route-export-options-grouping-obsolete {
          when 'boolean(./away-eids)';
        }
      }
      container publication-export {
        status obsolete;
        leaf publications {
          status obsolete;
          description
            "Export LISP publications to RIB";
          type empty;
        }
        uses router-lisp-route-export-options-grouping-obsolete {
          when 'boolean(./publications)';
        }
      }
      container destinations-summary-export {
        status obsolete;
        leaf destinations-summary {
          status obsolete;
          description
            "Export summary of destinations serviced by LISP to RIB";
          type empty;
        }
        uses router-lisp-route-export-options-grouping-obsolete {
          when 'boolean(./destinations-summary)';
        }
      }
      leaf site-registrations {
        status obsolete;
        description
          "Export LISP site registrations to RIB";
        type empty;
      }
      leaf away-eids {
        status obsolete;
        description
          "Export LISP away EIDs to RIB";
        type empty;
      }
      leaf publications {
        status obsolete;
        description
          "Export LISP publications to RIB";
        type empty;
      }
    }
  }

  grouping router-lisp-route-export-options-grouping-obsolete {
    leaf route-tag {
      status obsolete;
      description
        "RIB route tag";
      type uint32;
    }
  }

  grouping router-lisp-inst-service-route-export-grouping-obsolete {
    container route-export {
      status obsolete;
      description
        "Export routes into RIB from LISP";
      choice site-registration-export-choice {
        status obsolete;
        container inherit-site-registration-export {
          status obsolete;
          leaf site-registrations {
            status obsolete;
            description
              "Export LISP site registrations to RIB using inherited
               configuration";
            type boolean;
            default "true";
          }
        }
        container site-registration-export {
          status obsolete;
          leaf site-registrations {
            status obsolete;
            description
              "Export LISP site registrations to RIB";
            type empty;
          }
          uses router-lisp-route-export-options-grouping-obsolete {
            when 'boolean(./site-registrations)';
          }
        }
      }
      choice away-eids-export-choice {
        status obsolete;
        container inherit-away-eid-export {
          status obsolete;
          leaf away-eids {
            status obsolete;
            description
              "Export LISP away EIDs to RIB using inherited configuration";
            type boolean;
            default "true";
          }
        }
        container away-eid-export {
          status obsolete;
          leaf away-eids {
            status obsolete;
            description
              "Export LISP away EIDs to RIB";
            type empty;
          }
          uses router-lisp-route-export-options-grouping-obsolete {
            when 'boolean(./away-eids)';
          }
        }
      }
      choice publications-export-choice {
        status obsolete;
        container inherit-publication-export {
          status obsolete;
          leaf publications {
            status obsolete;
            description
              "Export LISP publications to RIB using inherited configuration";
            type boolean;
            default "true";
          }
        }
        container publication-export {
          status obsolete;
          leaf publications {
            status obsolete;
            description
              "Export LISP publications to RIB";
            type empty;
          }
          uses router-lisp-route-export-options-grouping-obsolete {
            when 'boolean(./publications)';
          }
        }
      }
      choice destinations-summary-export-choice {
        status obsolete;
        container inherit-destinations-summary-export {
          status obsolete;
          leaf destinations-summary {
            status obsolete;
            description
              "Export LISP destinations-summary to RIB using inherited configuration";
            type boolean;
            default "true";
          }
        }
        container destinations-summary-export {
          status obsolete;
          leaf destinations-summary {
            status obsolete;
            description
              "Export LISP destinations-summary to RIB";
            type empty;
          }
          uses router-lisp-route-export-options-grouping-obsolete {
            when 'boolean(./destinations-summary)';
          }
        }
      }
      leaf site-registrations {
        status obsolete;
        description
          "Export LISP site registrations to RIB";
        type empty;
      }
      leaf away-eids {
        status obsolete;
        description
          "Export LISP away EIDs to RIB";
        type empty;
      }
      leaf publications {
        status obsolete;
        description
          "Export LISP publications to RIB";
        type boolean;
      }
    }
  }

  grouping router-lisp-map-cache-persistent-grouping-obsolete {
    container map-cache-persistent {
      status obsolete;
      description
        "Dump map-cache onto flash, making it persistent across reboots";
      leaf interval {
        status obsolete;
        description
          "Interval in minutes of how often the map-cache is saved";
        type uint16 {
          range "1..1440";
        }
      }
    }
  }

  grouping router-lisp-sgt-grouping-obsolete {
    container sgt-config {
      status obsolete;
      leaf sgt-enable {
        status obsolete;
        description
          "Enable security group tag propagation in LISP encapsulated traffic";
        type empty;
      }
      leaf distribution {
        status obsolete;
        description
          "Enable security group tag distribution via LISP";
        type empty;
      }
    }
    leaf sgt {
      status obsolete;
      description
        "Enable SGT propagation in LISP encapsulated traffic";
      type empty;
    }
  }

  grouping router-lisp-proxy-grouping-obsolete {
    leaf proxy-etr {
      status obsolete;
      description
        "Configures a LISP Proxy Engress Tunnel Router (PETR)";
      type empty;
    }
    container proxy-itr {
      status obsolete;
      description
        "Configures a LISP Proxy Ingress Tunnel Router (PITR)";
      leaf ipv4-addr {
        status obsolete;
        type inet:ipv4-address;
      }
      leaf ipv6-addr {
        status obsolete;
        type inet:ipv6-address;
      }
      leaf sgt-policy-native-fwd {
        status obsolete;
        description
          "Configure policy driven native forwarding";
        type empty;
      }
    }
  }

  grouping router-lisp-use-petr-grouping-obsolete {
    container use-petr-config {
      status obsolete;
      choice use-petr-choice {
        status obsolete;
        list use-petr {
          status obsolete;
          description
            "Encapsulate to Proxy ETR when matching forward-native entry";
          key "locator-address";
          leaf locator-address {
            status obsolete;
            type inet:ip-address;
          }
          container priority {
            status obsolete;
            leaf priority-value {
              status obsolete;
              description
                "Configures which Locators from a set are preferred";
              type uint8 {
                range "0..255";
              }
            }
            leaf weight {
              status obsolete;
              description
                "Traffic load-spreading among Locators";
              type uint8 {
                range "0..100";
              }
            }
          }
        }
        container no-use-petr {
          status obsolete;
          leaf use-petr {
            status obsolete;
            description
              "Encapsulate to Proxy ETR when matching forward-native entry";
            type boolean;
            default "true";
          }
        }
      }
    }
  }

  grouping router-lisp-use-petr-grouping-deprecated-obsolete {
    list use-petr {
      status obsolete;
      description
        "Encapsulate to Proxy ETR when matching forward-native entry";
      key "locator-address";
      leaf locator-address {
        status obsolete;
        type inet:ip-address;
      }
      container priority {
        status obsolete;
        leaf priority-value {
          status obsolete;
          description
            "Configures which Locators from a set are preferred";
          type uint8 {
            range "0..255";
          }
        }
        leaf weight {
          status obsolete;
          description
            "Traffic load-spreading among Locators";
          type uint8 {
            range "0..100";
          }
        }
      }
    }
  }

  grouping router-lisp-publish-subscribe-grouping-obsolete {
    leaf publish-subscribe {
      status obsolete;
      description
        "Configures Publication Subscription";
      type boolean;
      default "true";
    }
  }

  grouping router-lisp-service-ip-distance-grouping-obsolete {
    container distance {
      status obsolete;
      description
        "Administrative distance for RIB route installation";
      leaf alt {
        status obsolete;
        description
          "LISP routes installed in the ALT table";
        type uint8 {
          range "1..255";
        }
      }
      leaf away {
        status obsolete;
        description
          "Administrative distance for RIB route installation";
        type uint8 {
          range "1..255";
        }
      }
      leaf dyn-eid {
        status obsolete;
        description
          "LISP installed routes of type dynamic-EID";
        type uint8 {
          range "1..255";
        }
      }
      leaf site-registrations {
        status obsolete;
        description
          "LISP installed routes of type site-registrations";
        type uint8 {
          range "1..255";
        }
      }
      leaf publications {
        status obsolete;
        description
          "LISP installed routes of type publications";
        type uint8 {
          range "1..255";
        }
      }
      leaf destinations-summary {
        status obsolete;
        description
          "LISP installed routes of type destinations-summary";
        type uint8 {
          range "1..255";
        }
      }
    }
  }

  grouping router-lisp-map-server-grouping-obsolete {
    list map-server {
      status obsolete;
      description
        "Configures map server for ETR registration";
      key "ip-addr";
      leaf ip-addr {
        status obsolete;
        type inet:ip-address;
      }
      container key {
        status obsolete;
        description
          "Authentication key used with map server";
        uses router-lisp-four-key-with-hash-function-and-prefix-list-grouping-obsolete;
      }
      leaf proxy-reply {
        status obsolete;
        description
          "Request Map-Server to send Map-Replies on behalf of site";
        type empty;
      }
    }
  }

  grouping router-lisp-inst-database-mapping-option-grouping-obsolete {
    container database-mapping-option {
      status obsolete;
      leaf priority {
        status obsolete;
        description
          "Configures which Locators from a set are preferred";
        type uint8 {
          range "0..255";
        }
      }
      leaf weight {
        status obsolete;
        description
          "Traffic load-spreading among Locators";
        type uint8 {
          range "0..100";
        }
      }
      leaf down {
        status obsolete;
        description
          "Configure this database mapping down";
        type empty;
      }
    }
  }

  grouping router-lisp-inst-database-mapping-service-insertion-grouping-obsolete {
    container service-insertion {
      status obsolete;
      description
        "Enable configuration of default-etr database mapping";
      leaf service-id {
        status obsolete;
        type uint16 {
          range "1..8";
        }
      }
      leaf service-type {
        status obsolete;
        type enumeration {
          enum firewall;
        }
      }
      leaf locator-set {
        status obsolete;
        description
          "Use locators defined by locator-set";
        type string;
      }
      leaf default-etr {
        status obsolete;
        description
          "Enable configuration of default-etr database mapping";
        type empty;
      }
      leaf default-etr-route-map {
        status obsolete;
        description
          "Configure route-map for default-etr";
        type string;
      }
      leaf service-etr {
        status obsolete;
        description
          "Enable configuration of service-etr database mapping";
        type empty;
      }
      leaf local {
        status obsolete;
        description
          "Register only with local MS";
        type empty;
      }
    }
  }

  grouping router-lisp-inst-database-mapping-common-grouping-obsolete {
    container locator-set-container {
      status obsolete;
      description
        "Use locators defined by locator-set";
      leaf locator-set {
        status obsolete;
        description
          "Use locators defined by locator-set";
        type string;
      }
      leaf route-tag {
        status obsolete;
        description
          "RIB route tag";
        type uint32;
      }
      leaf proxy {
        status obsolete;
        description
          "Enable configuration of static proxy database mapping";
        type empty;
      }
      leaf default-etr {
        status obsolete;
        description
          "Enable configuration of default-etr database mapping";
        type empty;
      }
      leaf default-etr-route-map {
        status obsolete;
        description
          "Configure route-map for default-etr";
        type string;
      }
      leaf local {
        status obsolete;
        description
          "Register only with local MS";
        type empty;
      }
    }
    list ipv4-addrees {
      status obsolete;
      description
        "IPv4 Address of loopback or other ETR interface";
      key "address";
      leaf address {
        status obsolete;
        type inet:ipv4-address;
      }
      uses router-lisp-inst-database-mapping-option-grouping-obsolete;
    }
    list ipv6-addrees {
      status obsolete;
      description
        "IPv6 Address of loopback or other ETR interface";
      key "address";
      leaf address {
        status obsolete;
        type inet:ipv6-address;
      }
      uses router-lisp-inst-database-mapping-option-grouping-obsolete;
    }
    list IPv4-interface {
      status obsolete;
      key "name";
      leaf name {
        status obsolete;
        description
          "Use IPv4 address of interface as locator";
        type string;
      }
      uses router-lisp-inst-database-mapping-option-grouping-obsolete;
    }
    list IPv6-interface {
      status obsolete;
      key "name";
      leaf name {
        status obsolete;
        description
          "Use IPv4 address of interface as locator";
        type string;
      }
      uses router-lisp-inst-database-mapping-option-grouping-obsolete;
    }
  }

  grouping router-lisp-inst-service-common-grouping-obsolete {
    uses router-lisp-itr-grouping-obsolete;
    uses router-lisp-etr-grouping-obsolete;
    uses router-lisp-map-cache-limit-grouping-obsolete;
    uses router-lisp-site-registration-grouping-obsolete;
    uses router-lisp-solicit-map-request-grouping-obsolete;
    uses router-lisp-registration-history-grouping-obsolete;
  }

  grouping router-lisp-inst-service-ethernet-grouping-obsolete {
    container eid-table {
      status obsolete;
      description
        "Bind an eid-table";
      leaf vlan {
        status obsolete;
        description
          "VLAN configuration";
        type uint16 {
          range "1..4094";
        }
      }
    }
    container broadcast-underlay {
      status obsolete;
      description
        "Multicast group to use for underlay";
      leaf ipv4-multicast {
        status obsolete;
        description
          "IPv4 multicast group address";
        type inet:ipv4-address;
      }
      leaf ipv6-multicast {
        status obsolete;
        description
          "IPv6 multicast group address";
        type inet:ipv6-address;
      }
    }
    container flood {
      status obsolete;
      description
        "Control flooding or local intercept of broadcast frames";
      leaf arp-nd {
        status obsolete;
        description
          "IPv4 ARP / IPv6 ND";
        type empty;
      }
      leaf unknown-unicast {
        status obsolete;
        description
          "Frames with unknown destination MAC";
        type empty;
      }
      leaf access-tunnel {
        status obsolete;
        description
          "Broadcast frame flooding toward AP access-tunnel";
        type boolean;
        default "false";
      }
      leaf multicast-address {
        status obsolete;
        description
          "Multicast Group Address";
        type union {
          type inet:ipv4-address;
          type inet:ipv6-address;
        }
      }
      leaf vlan {
        status obsolete;
        description
          "Multicast VLAN ID";
        type uint16 {
          range "1..4094";
        }
      }
    }
    container database-mapping {
      status obsolete;
      description
        "Configures Locator addresses for an ETR";
      list eid-cont {
        status obsolete;
        description
          "EID-record for RLOC static mapping";
        key "eid-prefix";
        leaf eid-prefix {
          status obsolete;
          description
            "xxxx.xxxx.xxxx 48 bit mac address";
          type ios-types:cisco-mac-address-type;
        }
        uses router-lisp-inst-database-mapping-common-grouping-obsolete;
      }
      container mac {
        status obsolete;
        description
          "L2 EID records";
        presence "true";
        leaf locator-set {
          status obsolete;
          description
            "Use locators defined by locator-set";
          type string;
        }
      }
      uses router-lisp-database-mapping-limit-grouping-obsolete;
    }
    uses dynamic-eid-detection-grouping-obsolete;
    uses router-lisp-inst-service-common-grouping-obsolete;
    leaf map-request-source {
      status obsolete;
      description
        "Configures inner header source address in Map-Request message";
      type inet:ip-address;
    }
    container map-cache {
      status obsolete;
      description
        "Use RIB routes to define EID address space in map-cache";
      list eid-cont {
        status obsolete;
        description
          "EID-record for RLOC static mapping";
        key "eid-prefix";
        leaf eid-prefix {
          status obsolete;
          description
            "xxxx.xxxx.xxxx 48 bit mac address";
          type ios-types:cisco-mac-address-type;
        }
        uses router-lisp-map-cache-common-grouping-obsolete;
      }
      leaf conservative-allocation {
        status obsolete;
        description
          "Suppress proactive created map-cache when host moves to another switch";
        type boolean;
        default "false";
      }
      leaf publications {
        status obsolete;
        description
          "Export publication entries into map cache";
        type empty;
      }
    }
    uses router-lisp-inst-service-ethernet-import-grouping-obsolete;
  }

  grouping router-lisp-inst-service-ip-grouping-obsolete {
    container eid-table {
      status obsolete;
      description
        "Bind an eid-table";
      leaf vrf-name {
        status obsolete;
        type string;
      }
      leaf default {
        status obsolete;
        type empty;
      }
      leaf vrf {
        status obsolete;
        type string;
      }
    }
    uses router-lisp-inst-service-common-grouping-obsolete;
    container alt {
      status obsolete;
      description
        "LISP Alternative Topology, LISP-ALT";
      list summary-route {
        status obsolete;
        description
          "Summary route to install into the ALT table";
        key "eid-prefix";
        leaf eid-prefix {
          status obsolete;
          type union {
            type inet:ipv4-prefix;
            type ios-types:ipv6-prefix;
          }
        }
        leaf route-tag {
          status obsolete;
          description
            "ALT RIB route tag for EID prefix";
          type uint32 {
            range "0..4294967295";
          }
        }
      }
    }
    leaf alt-vrf {
      status obsolete;
      description
        "Activate LISP-ALT functionality in VRF";
      type string;
    }
    uses router-lisp-service-ip-distance-grouping-obsolete;
    container mr-use-petr {
      status obsolete;
      description
        "Configure Map Resolver to include Proxy ETR in negative map reply";
      choice remote-locator-choice {
        status obsolete;
        container no-remote-locator {
          status obsolete;
          leaf remote-locator-set {
            status obsolete;
            type boolean;
          }
        }
        container remote-locator {
          status obsolete;
          leaf remote-locator-set {
            status obsolete;
            description
              "Use the locator-set defined by remote-locator-set";
            must '/ios:native/ios:router/lisp/remote-locator-set[name = current() ] or /ios:native/ios:router/lisp-list/remote-locator-set[name = current() ]' {
              error-message "% Please configure the remote-locator-set before configuring mr-use-petr";
            }
            type string;
          }
        }
      }
    }
    container first-packet-petr {
      status obsolete;
      description
        "Configure Map Resolver to include First-Packet-Proxy ETR in negative map reply";
      choice first-packet-petr-choice {
        status obsolete;
        case first-packet-petr-disable {
          status obsolete;
          leaf remote-locator-set {
            status obsolete;
            description
              "Disable first-packet-petr by adding no option";
            type boolean;
          }
        }
        case first-packet-petr-configure {
          status obsolete;
          container remote-locator-set-conf {
            status obsolete;
            leaf remote-locator-set {
              status obsolete;
              description
                "Use the locator-set defined by remote-locator-set";
              must '/ios:native/ios:router/lisp/remote-locator-set[name = current() ] or /ios:native/ios:router/lisp-list/remote-locator-set[name = current() ]' {
                error-message "% Please configure the remote-locator-set before configuring first-packet-petr";
              }
              type string;
            }
          }
        }
      }
    }
    container map-cache {
      status obsolete;
      description
        "Address family specific map cache configuration";
      list eid-interface {
        status obsolete;
        description
          "Configures static EID-to-RLOC mappings for an ITR";
        key "eid-prefix";
        leaf eid-prefix {
          status obsolete;
          type union {
            type inet:ipv4-prefix;
            type ios-types:ipv6-prefix;
          }
        }
        uses router-lisp-map-cache-common-grouping-obsolete;
        leaf drop {
          status obsolete;
          description
            "Drop packets that match this map-cache entry";
          type empty;
        }
        leaf map-request {
          status obsolete;
          description
            "Send Map-Request for LISP destination EID";
          type empty;
        }
        leaf native-forward {
          status obsolete;
          description
            "Natively forward packets that match this map-cache entry";
          type empty;
        }
      }
      container away-eids {
        status obsolete;
        description
          "Map cache configuration for the away table";
        leaf send-map-request {
          status obsolete;
          description
            "Export away table entries into the map cache with action set to send-map-request";
          type boolean;
          default "true";
        }
      }
      leaf site-registration {
        status obsolete;
        description
          "Install map cache to map request for site registrations";
        type empty;
      }
      leaf publications {
        status obsolete;
        description
          "Export publication entries into map cache";
        type boolean;
      }
      leaf conservative-allocation {
        status obsolete;
        description
          "Suppress proactive created map-cache when host moves to another switch";
        type boolean;
        default "false";
      }
    }
    uses router-lisp-map-cache-persistent-grouping-obsolete;
    uses router-lisp-proxy-grouping-obsolete;
    uses router-lisp-inst-service-route-export-grouping-obsolete;
    uses router-lisp-sgt-grouping-obsolete;
    uses router-lisp-use-petr-grouping-obsolete;
    uses router-lisp-use-petr-grouping-deprecated-obsolete;
    uses router-lisp-inst-service-ip-import-grouping-obsolete;
  }

  grouping router-lisp-inst-service-ipv4-grouping-obsolete {
    uses router-lisp-inst-service-ip-grouping-obsolete;
    container route-import {
      status obsolete;
      description
        "Import RIB routes by a routing protocol into LISP";
      uses router-lisp-inst-service-ipv4-route-import-protocol-grouping-obsolete;
    }
    uses router-lisp-map-request-source-ipv4-grouping-obsolete;
    container database-mapping {
      status obsolete;
      description
        "Configures Locator addresses for an ETR";
      list eid-cont {
        status obsolete;
        key "eid-prefix";
        leaf eid-prefix {
          status obsolete;
          type inet:ipv4-prefix;
        }
        uses router-lisp-inst-database-mapping-service-insertion-grouping-obsolete;
        uses router-lisp-inst-database-mapping-common-grouping-obsolete;
        leaf auto-discover-rlocs {
          status obsolete;
          type empty;
        }
      }
      uses router-lisp-database-mapping-limit-grouping-obsolete;
    }
  }

  grouping router-lisp-inst-service-ipv6-grouping-obsolete {
    uses router-lisp-inst-service-ip-grouping-obsolete;
    container route-import {
      status obsolete;
      description
        "Import RIB routes by a routing protocol into LISP";
      uses router-lisp-inst-service-ipv6-route-import-protocol-grouping-obsolete;
    }
    uses router-lisp-map-request-source-ipv6-grouping-obsolete;
    container database-mapping {
      status obsolete;
      description
        "Configures Locator addresses for an ETR";
      list eid-cont {
        status obsolete;
        key "eid-prefix";
        leaf eid-prefix {
          status obsolete;
          type ios-types:ipv6-prefix;
        }
        uses router-lisp-inst-database-mapping-service-insertion-grouping-obsolete;
        uses router-lisp-inst-database-mapping-common-grouping-obsolete;
        leaf auto-discover-rlocs {
          status obsolete;
          type empty;
        }
      }
      uses router-lisp-database-mapping-limit-grouping-obsolete;
    }
  }

  grouping router-lisp-inst-grouping-obsolete {
    container decapsulation {
      status obsolete;
      description
        "Decapsulation behavior (e.g. filters)";
      container filter {
        status obsolete;
        description
          "Filters traffic";
        container rloc {
          status obsolete;
          description
            "Filter based on Routing Locator (RLOC) in packet header";
          container source {
            status obsolete;
            description
              "Filters traffic based on RLOC source address";
            leaf locator-set {
              status obsolete;
              description
                "Locator-set Name";
              type string;
            }
            leaf member {
              status obsolete;
              description
                "Members learned from map-server";
              type empty;
            }
          }
        }
      }
    }
    leaf disable-ttl-propagate {
      status obsolete;
      description
        "Disable ttl propagation";
      type empty;
    }
    list dynamic-eid {
      status obsolete;
      description
        "Configure a dynamic EID";
      key "name";
      leaf name {
        status obsolete;
        type string;
      }
      container database-mapping {
        status obsolete;
        description
          "Configures EID-prefix and locator-set for dynamic-EID";
        choice ip-prefix {
          status obsolete;
          case ipv4-prefix {
            status obsolete;
            list ipv4-prefix {
              status obsolete;
              description
                "IPv4 EID-prefix for dynamic-EID";
              key "eid-prefix";
              leaf eid-prefix {
                status obsolete;
                type inet:ipv4-prefix;
              }
              leaf locator-set {
                status obsolete;
                description
                  "Use locators defined by locator-set";
                type string;
              }
              leaf route-tag {
                status obsolete;
                description
                  "RIB route tag";
                type uint32;
              }
            }
          }
          case ipv6-prefix {
            status obsolete;
            list ipv6-prefix {
              status obsolete;
              description
                "IPv6 EID-prefix for dynamic-EID";
              key "eid-prefix";
              leaf eid-prefix {
                status obsolete;
                type ios-types:ipv6-prefix;
              }
              leaf locator-set {
                status obsolete;
                description
                  "Use locators defined by locator-set";
                type string;
              }
              leaf route-tag {
                status obsolete;
                description
                  "RIB route tag";
                type uint32;
              }
            }
          }
        }
      }
      container eid-notify {
        status obsolete;
        description
          "Configure options for sending/receiving EID-notify";
        container authentication-key {
          status obsolete;
          description
            "Authentication key used for validating received EID-notify";
          uses router-lisp-four-key-grouping-obsolete;
        }
        list gateway-key {
          status obsolete;
          key "gateway-ip";
          leaf gateway-ip {
            status obsolete;
            type inet:ip-address;
          }
          container key {
            status obsolete;
            uses router-lisp-three-key-with-hash-function-grouping-obsolete;
          }
        }
      }
      leaf map-notify-group {
        status obsolete;
        description
          "Multicast group which to send map-notifies to";
        type inet:ip-address;
      }
      uses router-lisp-map-server-grouping-obsolete;
    }
    container loc-reach-algorithm {
      status obsolete;
      description
        "Configure locator reachability algorithm";
      container lsb-reports {
        status obsolete;
        description
          "Configure data packet LSB report handling";
        leaf do-not-transmit {
          status obsolete;
          description
            "Force the setting of the encapsulation header L bit to zero";
          type empty;
        }
        leaf ignore {
          status obsolete;
          description
            "Ignore data packet LSB reports";
          type empty;
        }
      }
      leaf rloc-probing {
        status obsolete;
        description
          "Probe high priority RLOCs with Map-Requests as last resort";
        type empty;
      }
    }
    container map-server {
      status obsolete;
      description
        "Map-Server commands";
      container rloc {
        status obsolete;
        description
          "EID instance RLOC membership";
        container members {
          status obsolete;
          description
            "EID instance RLOC membership";
          leaf distribute {
            status obsolete;
            description
              "EID instance RLOC membership distribution";
            type empty;
          }
          container modify-discovered {
            status obsolete;
            description
              "Modify the EID instance membership that is automaticallydiscovered from ETR registrations";
            leaf operator {
              status obsolete;
              type enumeration {
                enum add;
                enum override;
              }
            }
            leaf locator-set {
              status obsolete;
              description
                "Locator set from which to get member RLOC addresses";
              type string;
            }
          }
        }
      }
      container site-registration {
        status obsolete;
        description
          "Map-server site registration options";
        leaf limit {
          status obsolete;
          description
            "Maximum number of site registrations as a result of accept-more-specifics";
          type uint32;
        }
        leaf warning-threshold {
          status obsolete;
          description
            "Warning threshold to issue system logging";
          type uint8 {
            range "1..100";
          }
        }
      }
    }
    container other-xtr-probe {
      status obsolete;
      description
        "Configure parameters for probing of other xTRs in our site";
      leaf period {
        status obsolete;
        description
          "Period between probes in seconds";
        type uint16 {
          range "5..900";
        }
      }
    }
    container remote-rloc-probe {
      status obsolete;
      description
        "Configure parameters for probing of remote RLOCs";
      leaf on-membership-change {
        status obsolete;
        description
          "Trigger probing upon membership changes for remote RLOC";
        type empty;
      }
      leaf on-route-change {
        status obsolete;
        description
          "Trigger probing upon routing changes for remote RLOC";
        type empty;
      }
    }
    container service {
      status obsolete;
      description
        "Configure lisp service type";
      container ipv4 {
        status obsolete;
        presence "true";
        container default {
          status obsolete;
          uses router-lisp-inst-service-ipv4-grouping-obsolete;
        }
        uses router-lisp-inst-service-ipv4-grouping-obsolete;
      }
      container ipv6 {
        status obsolete;
        presence "true";
        container default {
          status obsolete;
          uses router-lisp-inst-service-ipv6-grouping-obsolete;
        }
        uses router-lisp-inst-service-ipv6-grouping-obsolete;
      }
      container ethernet {
        status obsolete;
        presence "true";
        container default {
          status obsolete;
          uses router-lisp-inst-service-ethernet-grouping-obsolete;
        }
        uses router-lisp-inst-service-ethernet-grouping-obsolete;
      }
    }
  }

  grouping router-lisp-ip-route-import-map-cache-grouping-obsolete {
    container map-cache-container {
      status obsolete;
      presence "true";
      leaf route-map {
        status obsolete;
        description
          "Route map for route selection filtering";
        type string;
      }
    }
  }

  grouping router-lisp-ip-route-import-database-grouping-obsolete {
    container lisp-ip-route-import {
      status obsolete;
      leaf route-map {
        status obsolete;
        description
          "Route map for route selection filtering";
        type string;
      }
      leaf route-tag {
        status obsolete;
        description
          "RIB route tag";
        type uint32;
      }
      leaf locator-set {
        status obsolete;
        description
          "Locator set to use with created database mapping entries";
        type string;
      }
      leaf proxy {
        status obsolete;
        description
          "Enable the dynamic import of RIB route as proxy database mapping";
        type empty;
      }
    }
  }

  grouping router-lisp-ddt-authoritative-grouping-obsolete {
    container delegate {
      status obsolete;
      description
        "DDT delegation to a child DDT node or map-server";
      choice instance-id-eid-prefix-choice {
        status obsolete;
        case eid-prefix-case {
          status obsolete;
          leaf eid-prefix {
            status obsolete;
            type union {
              type inet:ipv4-prefix;
              type ios-types:ipv6-prefix;
            }
          }
        }
        case instance-id-case {
          status obsolete;
          leaf instance-id {
            status obsolete;
            description
              "EID instance-ID";
            type string;
          }
        }
      }
      leaf to {
        status obsolete;
        description
          "DDT delegation to a child DDT node or map-server";
        type empty;
      }
      leaf ip-address {
        status obsolete;
        description
          "IPv4/6 Child or map-server node locator address";
        type inet:ip-address;
      }
      leaf map-server {
        status obsolete;
        description
          "Delegation points to a map-server";
        type empty;
      }
    }
    leaf map-server-peer {
      status obsolete;
      description
        "Peer map-servers that are authoritative for the same EID prefixes";
      type inet:ip-address;
    }
  }

  grouping router-lisp-ip-grouping {
    leaf alt-vrf {
      status obsolete;
      description
        "Activate LISP-ALT functionality in VRF";
      type string;
    }
    container database-mapping {
      status obsolete;
      description
        "Address family specific local EID prefixes database configuration";
      container limit {
        status obsolete;
        description
          "Configures the maximum size of local EID prefixes database";
        leaf dynamic {
          status obsolete;
          description
            "Configures the maximum size of dynamic local EID prefixes database";
          type uint32;
        }
        leaf warning-threshold {
          status obsolete;
          description
            "Send warning message to syslog when the database-mapping dynamic size reaches this percentage of the limit";
          type uint8;
        }
      }
    }
    container distance {
      status obsolete;
      description
        "Administrative distance for RIB route installation";
      leaf alt {
        status obsolete;
        description
          "LISP routes installed in the ALT table";
        type uint8;
      }
      leaf dyn-eid {
        status obsolete;
        description
          "LISP installed routes of type dynamic-EID";
        type uint8;
      }
      leaf site-registrations {
        status obsolete;
        description
          "LISP installed routes of type site-registrations";
        type uint8;
      }
    }
    container itr {
      status obsolete;
      description
        "Configures a LISP Ingress Tunnel Router (ITR)";
      list map-resolver {
        status obsolete;
        description
          "Configures map-resolver address for sending Map-Requests";
        key "ip-addr";
        leaf ip-addr {
          status obsolete;
          type inet:ip-address;
        }
      }
    }
    container itr-enable {
      status obsolete;
      leaf itr {
        status obsolete;
        description
          "Configures a LISP Ingress Tunnel Router (ITR)";
        type empty;
      }
    }
    container etr {
      status obsolete;
      description
        "Configures a LISP Egress Tunnel Router (ETR)";
      list map-server {
        status obsolete;
        description
          "Configures map server for ETR registration";
        key "ip-addr";
        leaf ip-addr {
          status obsolete;
          type inet:ip-address;
        }
        container key {
          status obsolete;
          description
            "Authentication key used with map server";
          leaf key-0 {
            status obsolete;
            description
              "The UNENCRYPTED (cleartext) password";
            type string;
          }
          leaf key-6 {
            status obsolete;
            description
              "The ENCRYPTED password";
            type string;
          }
          leaf key-7 {
            status obsolete;
            description
              "The HIDDEN password";
            type string;
          }
          leaf pwd {
            status obsolete;
            description
              "The UNENCRYPTED (cleartext) password";
            type string;
          }
        }
        leaf proxy-reply {
          status obsolete;
          description
            "Request Map-Server to send Map-Replies on behalf of site";
          type empty;
        }
      }
    }
    container etr-enable {
      status obsolete;
      leaf etr {
        status obsolete;
        description
          "Configures a LISP Egress Tunnel Router (ETR)";
        type empty;
      }
    }
    container locator {
      description
        "Locator related configuration";
      container reachability {
        description
          "Configuration realted to locator reachability";
        container exclude-default-config {
          description
            "If a remote RLOC is reached via the default route, treat it as unreachable";
          leaf value-none {
            type empty;
          }
          leaf proxy-etr-only {
            description
              "Apply exclude default or minimum mask restriction only for proxy ETR";
            type empty;
          }
        }
        leaf exclude-default {
          status obsolete;
          description
            "If a remote RLOC is reached via the default route, treat it as unreachable";
          type empty;
        }
        container minimum-mask-length-config {
          description
            "Shortest mask prefix to accept when looking up a remote RLOC in the RIB";
          leaf value {
            type uint8;
          }
          leaf proxy-etr-only-config {
            description
              "Apply exclude default or minimum mask restriction only for proxy ETR";
            type empty;
          }
        }
        leaf minimum-mask-length {
          status obsolete;
          description
            "Shortest mask prefix to accept when looking up a remote RLOC in the RIB";
          type uint8 {
            range "0..32";
          }
        }
      }
    }
    container map-cache {
      status obsolete;
      description
        "Address family specific map cache configuration";
      leaf site-registration {
        status obsolete;
        description
          "Install map cache to map request for site registrations";
        type empty;
      }
    }
    container map-cache-limit {
      status obsolete;
      description
        "Configures maximum size of map-cache";
      leaf max-map-cache-entries {
        status obsolete;
        type uint32 {
          range "0..100000";
        }
      }
      leaf reserve-list {
        status obsolete;
        description
          "EID-prefixes guaranteed to be stored in map-cache";
        type string;
      }
      leaf warning-threshold {
        status obsolete;
        description
          "Send warning message to syslog when the map-cache size reaches this percentage of the limit";
        type uint8 {
          range "0..100";
        }
      }
    }
    container map-cache-persistent {
      status obsolete;
      description
        "Dump map-cache onto flash, making it persistent across reboots";
      leaf interval {
        status obsolete;
        description
          "Interval in minutes of how often the map-cache is saved";
        type uint16 {
          range "1..1440";
        }
      }
    }
    leaf map-request-source {
      status obsolete;
      description
        "Configures inner header source address in Map-Request message";
      type inet:ipv4-address;
    }
    container map-resolver {
      status obsolete;
      description
        "Configures a LISP Map Resolver (MR)";
      presence "true";
      container map-request {
        status obsolete;
        description
          "Map-Request processing options";
        container validate {
          status obsolete;
          description
            "Validation options";
          container source {
            status obsolete;
            description
              "Influence which source RLOCs map requests are accepted from";
            leaf list {
              status obsolete;
              description
                "Define allowed prefixes using an ip[v6] prefix list";
              type empty;
            }
            leaf registered {
              status obsolete;
              description
                "...from RLOCs that register EID-prefixes in the same IID on a co-located MapServer";
              type empty;
            }
            leaf ipv4 {
              status obsolete;
              description
                "IPv4 prefixes";
              type string;
            }
            leaf ipv6 {
              status obsolete;
              description
                "IPv6 prefixes";
              type string;
            }
          }
        }
      }
    }
    container map-server {
      status obsolete;
      description
        "Configures a LISP Map Server (MS)";
      presence "true";
      container map-register {
        status obsolete;
        description
          "Map-Register processing options";
        container validate {
          status obsolete;
          description
            "Validation options";
          container source {
            status obsolete;
            description
              "RLOC Source IP address";
            leaf allowed-locator {
              status obsolete;
              description
                "Against sites' allowed-locators policy";
              type empty;
            }
          }
        }
      }
    }
    container path-mtu-discovery {
      description
        "Path MTU discovery";
      presence "true";
      leaf min {
        description
          "Lower bound on the path MTU accepted";
        type uint16 {
          range "68..65535";
        }
      }
      leaf max {
        description
          "Upper bound on the path MTU accepted";
        type uint16 {
          range "68..65535";
        }
      }
    }
    leaf proxy-etr {
      status obsolete;
      description
        "Configures a LISP Proxy Engress Tunnel Router (PETR)";
      type empty;
    }
    leaf-list proxy-itr {
      status obsolete;
      description
        "Configures a LISP Proxy Ingress Tunnel Router (PITR)";
      type inet:ip-address;
    }
    container route-export {
      status obsolete;
      description
        "Export routes into RIB from LISP";
      leaf site-registrations {
        status obsolete;
        description
          "Export LISP site registrations to RIB";
        type empty;
      }
      leaf away-eids {
        status obsolete;
        description
          "Export LISP away EIDs to RIB";
        type empty;
      }
    }
    container route-import {
      status obsolete;
      description
        "Import RIB routes by a routing protocol into LISP";
      container database {
        status obsolete;
        description
          "Use RIB routes to define local EID database entries";
        list bgp {
          status obsolete;
          description
            "Border Gateway Protocol (BGP)";
          key "id";
          leaf id {
            status obsolete;
            type ios-types:bgp-as-number-type;
          }
          uses router-lisp-ip-route-import-database-grouping-obsolete;
        }
        container connected {
          status obsolete;
          description
            "Connected";
          uses router-lisp-ip-route-import-database-grouping-obsolete;
        }
        list eigrp {
          status obsolete;
          description
            "Enhanced Interior Gateway Routing Protocol (EIGRP)";
          key "id";
          leaf id {
            status obsolete;
            type uint16;
          }
          uses router-lisp-ip-route-import-database-grouping-obsolete;
        }
        list isis {
          status obsolete;
          description
            "ISO IS-IS";
          key "id";
          leaf id {
            status obsolete;
            type string;
          }
          uses router-lisp-ip-route-import-database-grouping-obsolete;
        }
        container maximum-prefix {
          status obsolete;
          description
            "Maximum number of prefixes to pick up from the RIB";
          leaf number {
            status obsolete;
            type int32;
          }
          choice threshold-warning {
            status obsolete;
            case warning-only-case {
              status obsolete;
              leaf warning-only {
                status obsolete;
                description
                  "Only give a warning message and do not limit entries";
                type empty;
              }
            }
            case threshold-case {
              status obsolete;
              leaf threshold {
                status obsolete;
                type uint8 {
                  range "1..100";
                }
              }
            }
            case threshold-warning-case {
              status obsolete;
              leaf threshold1 {
                status obsolete;
                type uint8 {
                  range "1..100";
                }
              }
              leaf warning-only1 {
                status obsolete;
                description
                  "Only give a warning message and do not limit entries";
                type empty;
              }
            }
          }
        }
        container omp {
          status obsolete;
          if-feature "ios-features:omp";
          description
            "Overlay Management Protocol";
          uses router-lisp-ip-route-import-database-grouping-obsolete;
        }
        list ospf {
          status obsolete;
          description
            "Open Shortest Path First (OSPF)";
          key "id";
          leaf id {
            status obsolete;
            type uint16;
          }
          uses router-lisp-ip-route-import-database-grouping-obsolete;
        }
        list ospfv3 {
          status obsolete;
          description
            "OSPFv3";
          key "id";
          leaf id {
            status obsolete;
            type uint16;
          }
          uses router-lisp-ip-route-import-database-grouping-obsolete;
        }
        container rip {
          status obsolete;
          description
            "Routing Information Protocol (RIP)";
          uses router-lisp-ip-route-import-database-grouping-obsolete;
        }
        container static {
          status obsolete;
          description
            "Static routes";
          uses router-lisp-ip-route-import-database-grouping-obsolete;
        }
      }
      container map-cache {
        status obsolete;
        description
          "Use RIB routes to define EID address space in map-cache";
        list bgp {
          status obsolete;
          description
            "Border Gateway Protocol (BGP)";
          key "id";
          leaf id {
            status obsolete;
            type ios-types:bgp-as-number-type;
          }
          uses router-lisp-ip-route-import-map-cache-grouping-obsolete;
        }
        container connected {
          status obsolete;
          description
            "Connected";
          presence "true";
          uses router-lisp-ip-route-import-map-cache-grouping-obsolete;
        }
        list eigrp {
          status obsolete;
          description
            "Enhanced Interior Gateway Routing Protocol (EIGRP)";
          key "id";
          leaf id {
            status obsolete;
            type uint16;
          }
          uses router-lisp-ip-route-import-map-cache-grouping-obsolete;
        }
        list isis {
          status obsolete;
          description
            "ISO IS-IS";
          key "id";
          leaf id {
            status obsolete;
            type string;
          }
          uses router-lisp-ip-route-import-map-cache-grouping-obsolete;
        }
        container maximum-prefix {
          status obsolete;
          description
            "Maximum number of prefixes to pick up from the RIB";
          leaf number {
            status obsolete;
            type int32;
          }
          choice threshold-warning {
            status obsolete;
            case warning-only-case {
              status obsolete;
              leaf warning-only {
                status obsolete;
                description
                  "Only give a warning message and do not limit entries";
                type empty;
              }
            }
            case threshold-case {
              status obsolete;
              leaf threshold {
                status obsolete;
                type uint8 {
                  range "1..100";
                }
              }
            }
            case threshold-warning-case {
              status obsolete;
              leaf threshold1 {
                status obsolete;
                type uint8 {
                  range "1..100";
                }
              }
              leaf warning-only1 {
                status obsolete;
                description
                  "Only give a warning message and do not limit entries";
                type empty;
              }
            }
          }
        }
        list ospf {
          status obsolete;
          description
            "Open Shortest Path First (OSPF)";
          key "id";
          leaf id {
            status obsolete;
            type uint16;
          }
          uses router-lisp-ip-route-import-map-cache-grouping-obsolete;
        }
        list ospfv3 {
          status obsolete;
          description
            "OSPFv3";
          key "id";
          leaf id {
            status obsolete;
            type uint16;
          }
          uses router-lisp-ip-route-import-map-cache-grouping-obsolete;
        }
        container rip {
          status obsolete;
          description
            "Routing Information Protocol (RIP)";
          presence "true";
          uses router-lisp-ip-route-import-map-cache-grouping-obsolete;
        }
        container static {
          status obsolete;
          description
            "Static routes";
          presence "true";
          uses router-lisp-ip-route-import-map-cache-grouping-obsolete;
        }
      }
    }
    leaf sgt {
      status obsolete;
      description
        "Enable security group tag propagation in LISP encapsulated traffic";
      type empty;
    }
    container site-registration {
      status obsolete;
      description
        "Site registrations configuration for a given instance-id";
      leaf limit {
        status obsolete;
        description
          "Maximum number of site registrations for a given instance-id";
        type uint32;
      }
      leaf warning-threshold {
        status obsolete;
        description
          "Warning threshold to issue system logging";
        type uint8 {
          range "1..100";
        }
      }
    }
    container solicit-map-request {
      status obsolete;
      description
        "Configure Solicit-Map-Request handling";
      leaf ignore {
        status obsolete;
        description
          "Ignore SMR bit in incoming Map-Requests";
        type empty;
      }
      leaf max-per-entry {
        status obsolete;
        description
          "Maximum number of SMRs for addresses under a map-cache entry";
        type uint8 {
          range "1..100";
        }
      }
      leaf suppression-time {
        status obsolete;
        description
          "How long to suppress repeated SMRs for the same address";
        type uint16 {
          range "1..600";
        }
      }
    }
    container source-locator {
      description
        "Source Locator configuration";
      uses ios-ifc:interface-grouping;
    }
    list use-petr {
      status obsolete;
      description
        "Encapsulate to Proxy ETR when matching forward-native entry";
      key "locator-address";
      leaf locator-address {
        type inet:ip-address;
      }
      leaf priority {
        status obsolete;
        description
          "Configures which Locators from a set are preferred";
        type uint8;
      }
      leaf weight {
        status obsolete;
        description
          "Traffic load-spreading among Locators";
        type uint8 {
          range "0..100";
        }
      }
    }
  }

  grouping router-lisp-ip-grouping-obsolete {
    leaf alt-vrf {
      status obsolete;
      description
        "Activate LISP-ALT functionality in VRF";
      type string;
    }
    container database-mapping {
      status obsolete;
      description
        "Address family specific local EID prefixes database configuration";
      container limit {
        status obsolete;
        description
          "Configures the maximum size of local EID prefixes database";
        leaf dynamic {
          status obsolete;
          description
            "Configures the maximum size of dynamic local EID prefixes database";
          type uint32;
        }
        leaf warning-threshold {
          status obsolete;
          description
            "Send warning message to syslog when the database-mapping dynamic size reaches this percentage of the limit";
          type uint8;
        }
      }
    }
    container distance {
      status obsolete;
      description
        "Administrative distance for RIB route installation";
      leaf alt {
        status obsolete;
        description
          "LISP routes installed in the ALT table";
        type uint8;
      }
      leaf dyn-eid {
        status obsolete;
        description
          "LISP installed routes of type dynamic-EID";
        type uint8;
      }
      leaf site-registrations {
        status obsolete;
        description
          "LISP installed routes of type site-registrations";
        type uint8;
      }
    }
    container itr {
      status obsolete;
      description
        "Configures a LISP Ingress Tunnel Router (ITR)";
      list map-resolver {
        status obsolete;
        description
          "Configures map-resolver address for sending Map-Requests";
        key "ip-addr";
        leaf ip-addr {
          status obsolete;
          type inet:ip-address;
        }
      }
    }
    container itr-enable {
      status obsolete;
      leaf itr {
        status obsolete;
        description
          "Configures a LISP Ingress Tunnel Router (ITR)";
        type empty;
      }
    }
    container etr {
      status obsolete;
      description
        "Configures a LISP Egress Tunnel Router (ETR)";
      list map-server {
        status obsolete;
        description
          "Configures map server for ETR registration";
        key "ip-addr";
        leaf ip-addr {
          status obsolete;
          type inet:ip-address;
        }
        container key {
          status obsolete;
          description
            "Authentication key used with map server";
          leaf key-0 {
            status obsolete;
            description
              "The UNENCRYPTED (cleartext) password";
            type string;
          }
          leaf key-6 {
            status obsolete;
            description
              "The ENCRYPTED password";
            type string;
          }
          leaf key-7 {
            status obsolete;
            description
              "The HIDDEN password";
            type string;
          }
          leaf pwd {
            status obsolete;
            description
              "The UNENCRYPTED (cleartext) password";
            type string;
          }
        }
        leaf proxy-reply {
          status obsolete;
          description
            "Request Map-Server to send Map-Replies on behalf of site";
          type empty;
        }
      }
    }
    container etr-enable {
      status obsolete;
      leaf etr {
        status obsolete;
        description
          "Configures a LISP Egress Tunnel Router (ETR)";
        type empty;
      }
    }
    container locator {
      status obsolete;
      description
        "Locator related configuration";
      container reachability {
        status obsolete;
        description
          "Configuration realted to locator reachability";
        container exclude-default-config {
          status obsolete;
          description
            "If a remote RLOC is reached via the default route, treat it as unreachable";
          leaf value-none {
            status obsolete;
            type empty;
          }
          leaf proxy-etr-only {
            status obsolete;
            description
              "Apply exclude default or minimum mask restriction only for proxy ETR";
            type empty;
          }
        }
        leaf exclude-default {
          status obsolete;
          description
            "If a remote RLOC is reached via the default route, treat it as unreachable";
          type empty;
        }
        container minimum-mask-length-config {
          status obsolete;
          description
            "Shortest mask prefix to accept when looking up a remote RLOC in the RIB";
          leaf value {
            status obsolete;
            type uint8;
          }
          leaf proxy-etr-only-config {
            status obsolete;
            description
              "Apply exclude default or minimum mask restriction only for proxy ETR";
            type empty;
          }
        }
        leaf minimum-mask-length {
          status obsolete;
          description
            "Shortest mask prefix to accept when looking up a remote RLOC in the RIB";
          type uint8 {
            range "0..32";
          }
        }
      }
    }
    container map-cache {
      status obsolete;
      description
        "Address family specific map cache configuration";
      leaf site-registration {
        status obsolete;
        description
          "Install map cache to map request for site registrations";
        type empty;
      }
    }
    container map-cache-limit {
      status obsolete;
      description
        "Configures maximum size of map-cache";
      leaf max-map-cache-entries {
        status obsolete;
        type uint32 {
          range "0..100000";
        }
      }
      leaf reserve-list {
        status obsolete;
        description
          "EID-prefixes guaranteed to be stored in map-cache";
        type string;
      }
      leaf warning-threshold {
        status obsolete;
        description
          "Send warning message to syslog when the map-cache size reaches this percentage of the limit";
        type uint8 {
          range "0..100";
        }
      }
    }
    container map-cache-persistent {
      status obsolete;
      description
        "Dump map-cache onto flash, making it persistent across reboots";
      leaf interval {
        status obsolete;
        description
          "Interval in minutes of how often the map-cache is saved";
        type uint16 {
          range "1..1440";
        }
      }
    }
    leaf map-request-source {
      status obsolete;
      description
        "Configures inner header source address in Map-Request message";
      type inet:ipv4-address;
    }
    container map-resolver {
      status obsolete;
      description
        "Configures a LISP Map Resolver (MR)";
      presence "true";
      container map-request {
        status obsolete;
        description
          "Map-Request processing options";
        container validate {
          status obsolete;
          description
            "Validation options";
          container source {
            status obsolete;
            description
              "Influence which source RLOCs map requests are accepted from";
            leaf list {
              status obsolete;
              description
                "Define allowed prefixes using an ip[v6] prefix list";
              type empty;
            }
            leaf registered {
              status obsolete;
              description
                "...from RLOCs that register EID-prefixes in the same IID on a co-located MapServer";
              type empty;
            }
            leaf ipv4 {
              status obsolete;
              description
                "IPv4 prefixes";
              type string;
            }
            leaf ipv6 {
              status obsolete;
              description
                "IPv6 prefixes";
              type string;
            }
          }
        }
      }
    }
    container map-server {
      status obsolete;
      description
        "Configures a LISP Map Server (MS)";
      presence "true";
      container map-register {
        status obsolete;
        description
          "Map-Register processing options";
        container validate {
          status obsolete;
          description
            "Validation options";
          container source {
            status obsolete;
            description
              "RLOC Source IP address";
            leaf allowed-locator {
              status obsolete;
              description
                "Against sites' allowed-locators policy";
              type empty;
            }
          }
        }
      }
    }
    container path-mtu-discovery {
      status obsolete;
      description
        "Path MTU discovery";
      presence "true";
      leaf min {
        status obsolete;
        description
          "Lower bound on the path MTU accepted";
        type uint16 {
          range "68..65535";
        }
      }
      leaf max {
        status obsolete;
        description
          "Upper bound on the path MTU accepted";
        type uint16 {
          range "68..65535";
        }
      }
    }
    leaf proxy-etr {
      status obsolete;
      description
        "Configures a LISP Proxy Engress Tunnel Router (PETR)";
      type empty;
    }
    leaf-list proxy-itr {
      status obsolete;
      description
        "Configures a LISP Proxy Ingress Tunnel Router (PITR)";
      type inet:ip-address;
    }
    container route-export {
      status obsolete;
      description
        "Export routes into RIB from LISP";
      leaf site-registrations {
        status obsolete;
        description
          "Export LISP site registrations to RIB";
        type empty;
      }
      leaf away-eids {
        status obsolete;
        description
          "Export LISP away EIDs to RIB";
        type empty;
      }
    }
    container route-import {
      status obsolete;
      description
        "Import RIB routes by a routing protocol into LISP";
      container database {
        status obsolete;
        description
          "Use RIB routes to define local EID database entries";
        list bgp {
          status obsolete;
          description
            "Border Gateway Protocol (BGP)";
          key "id";
          leaf id {
            status obsolete;
            type ios-types:bgp-as-number-type;
          }
          uses router-lisp-ip-route-import-database-grouping-obsolete;
        }
        container connected {
          status obsolete;
          description
            "Connected";
          uses router-lisp-ip-route-import-database-grouping-obsolete;
        }
        list eigrp {
          status obsolete;
          description
            "Enhanced Interior Gateway Routing Protocol (EIGRP)";
          key "id";
          leaf id {
            status obsolete;
            type uint16;
          }
          uses router-lisp-ip-route-import-database-grouping-obsolete;
        }
        list isis {
          status obsolete;
          description
            "ISO IS-IS";
          key "id";
          leaf id {
            status obsolete;
            type string;
          }
          uses router-lisp-ip-route-import-database-grouping-obsolete;
        }
        container maximum-prefix {
          status obsolete;
          description
            "Maximum number of prefixes to pick up from the RIB";
          leaf number {
            status obsolete;
            type int32;
          }
          choice threshold-warning {
            status obsolete;
            case warning-only-case {
              status obsolete;
              leaf warning-only {
                status obsolete;
                description
                  "Only give a warning message and do not limit entries";
                type empty;
              }
            }
            case threshold-case {
              status obsolete;
              leaf threshold {
                status obsolete;
                type uint8 {
                  range "1..100";
                }
              }
            }
            case threshold-warning-case {
              status obsolete;
              leaf threshold1 {
                status obsolete;
                type uint8 {
                  range "1..100";
                }
              }
              leaf warning-only1 {
                status obsolete;
                description
                  "Only give a warning message and do not limit entries";
                type empty;
              }
            }
          }
        }
        container omp {
          status obsolete;
          if-feature "ios-features:omp";
          description
            "Overlay Management Protocol";
          uses router-lisp-ip-route-import-database-grouping-obsolete;
        }
        list ospf {
          status obsolete;
          description
            "Open Shortest Path First (OSPF)";
          key "id";
          leaf id {
            status obsolete;
            type uint16;
          }
          uses router-lisp-ip-route-import-database-grouping-obsolete;
        }
        list ospfv3 {
          status obsolete;
          description
            "OSPFv3";
          key "id";
          leaf id {
            status obsolete;
            type uint16;
          }
          uses router-lisp-ip-route-import-database-grouping-obsolete;
        }
        container rip {
          status obsolete;
          description
            "Routing Information Protocol (RIP)";
          uses router-lisp-ip-route-import-database-grouping-obsolete;
        }
        container static {
          status obsolete;
          description
            "Static routes";
          uses router-lisp-ip-route-import-database-grouping-obsolete;
        }
      }
      container map-cache {
        status obsolete;
        description
          "Use RIB routes to define EID address space in map-cache";
        list bgp {
          status obsolete;
          description
            "Border Gateway Protocol (BGP)";
          key "id";
          leaf id {
            status obsolete;
            type ios-types:bgp-as-number-type;
          }
          uses router-lisp-ip-route-import-map-cache-grouping-obsolete;
        }
        container connected {
          status obsolete;
          description
            "Connected";
          presence "true";
          uses router-lisp-ip-route-import-map-cache-grouping-obsolete;
        }
        list eigrp {
          status obsolete;
          description
            "Enhanced Interior Gateway Routing Protocol (EIGRP)";
          key "id";
          leaf id {
            status obsolete;
            type uint16;
          }
          uses router-lisp-ip-route-import-map-cache-grouping-obsolete;
        }
        list isis {
          status obsolete;
          description
            "ISO IS-IS";
          key "id";
          leaf id {
            status obsolete;
            type string;
          }
          uses router-lisp-ip-route-import-map-cache-grouping-obsolete;
        }
        container maximum-prefix {
          status obsolete;
          description
            "Maximum number of prefixes to pick up from the RIB";
          leaf number {
            status obsolete;
            type int32;
          }
          choice threshold-warning {
            status obsolete;
            case warning-only-case {
              status obsolete;
              leaf warning-only {
                status obsolete;
                description
                  "Only give a warning message and do not limit entries";
                type empty;
              }
            }
            case threshold-case {
              status obsolete;
              leaf threshold {
                status obsolete;
                type uint8 {
                  range "1..100";
                }
              }
            }
            case threshold-warning-case {
              status obsolete;
              leaf threshold1 {
                status obsolete;
                type uint8 {
                  range "1..100";
                }
              }
              leaf warning-only1 {
                status obsolete;
                description
                  "Only give a warning message and do not limit entries";
                type empty;
              }
            }
          }
        }
        list ospf {
          status obsolete;
          description
            "Open Shortest Path First (OSPF)";
          key "id";
          leaf id {
            status obsolete;
            type uint16;
          }
          uses router-lisp-ip-route-import-map-cache-grouping-obsolete;
        }
        list ospfv3 {
          status obsolete;
          description
            "OSPFv3";
          key "id";
          leaf id {
            status obsolete;
            type uint16;
          }
          uses router-lisp-ip-route-import-map-cache-grouping-obsolete;
        }
        container rip {
          status obsolete;
          description
            "Routing Information Protocol (RIP)";
          presence "true";
          uses router-lisp-ip-route-import-map-cache-grouping-obsolete;
        }
        container static {
          status obsolete;
          description
            "Static routes";
          presence "true";
          uses router-lisp-ip-route-import-map-cache-grouping-obsolete;
        }
      }
    }
    leaf sgt {
      status obsolete;
      description
        "Enable security group tag propagation in LISP encapsulated traffic";
      type empty;
    }
    container site-registration {
      status obsolete;
      description
        "Site registrations configuration for a given instance-id";
      leaf limit {
        status obsolete;
        description
          "Maximum number of site registrations for a given instance-id";
        type uint32;
      }
      leaf warning-threshold {
        status obsolete;
        description
          "Warning threshold to issue system logging";
        type uint8 {
          range "1..100";
        }
      }
    }
    container solicit-map-request {
      status obsolete;
      description
        "Configure Solicit-Map-Request handling";
      leaf ignore {
        status obsolete;
        description
          "Ignore SMR bit in incoming Map-Requests";
        type empty;
      }
      leaf max-per-entry {
        status obsolete;
        description
          "Maximum number of SMRs for addresses under a map-cache entry";
        type uint8 {
          range "1..100";
        }
      }
      leaf suppression-time {
        status obsolete;
        description
          "How long to suppress repeated SMRs for the same address";
        type uint16 {
          range "1..600";
        }
      }
    }
    container source-locator {
      status obsolete;
      description
        "Source Locator configuration";
      uses ios-ifc:interface-obsolete-grouping;
    }
    list use-petr {
      status obsolete;
      description
        "Encapsulate to Proxy ETR when matching forward-native entry";
      key "locator-address";
      leaf locator-address {
        type inet:ip-address;
      }
      leaf priority {
        status obsolete;
        description
          "Configures which Locators from a set are preferred";
        type uint8;
      }
      leaf weight {
        status obsolete;
        description
          "Traffic load-spreading among Locators";
        type uint8 {
          range "0..100";
        }
      }
    }
  }

  grouping router-lisp-common-grouping-obsolete {
    container alt {
      status obsolete;
      description
        "LISP Alternative Topology, LISP-ALT";
      list summary-route {
        status obsolete;
        description
          "Summary route to install into the ALT table";
        key "eid-prefix";
        leaf eid-prefix {
          status obsolete;
          type union {
            type inet:ipv4-prefix;
            type ios-types:ipv6-prefix;
          }
        }
        leaf route-tag {
          status obsolete;
          description
            "ALT RIB route tag for EID prefix";
          type uint32;
        }
      }
    }
    container control-packet {
      status obsolete;
      description
        "Configure control packet tx option";
      leaf mtu {
        status obsolete;
        description
          "Configure control packet MTU";
        type uint32 {
          range "304..10000";
        }
      }
    }
    container ddt {
      status obsolete;
      description
        "Delegated Database Tree (DDT) mapping system";
      presence "true";
      container authoritative {
        status obsolete;
        description
          "DDT authoritative prefix";
        list instance-id-eid-prefix-list {
          status obsolete;
          key "instance-id eid-prefix";
          leaf instance-id {
            status obsolete;
            description
              "EID instance-ID";
            type uint32;
          }
          leaf eid-prefix {
            status obsolete;
            type union {
              type inet:ipv4-prefix;
              type ios-types:ipv6-prefix;
            }
          }
          uses router-lisp-ddt-authoritative-grouping-obsolete;
        }
        list instance-id-list {
          status obsolete;
          key "instance-id";
          leaf instance-id {
            status obsolete;
            type string;
          }
          uses router-lisp-ddt-authoritative-grouping-obsolete;
        }
      }
      leaf cache-limit {
        status obsolete;
        description
          "DDT resolver cache entry limit";
        type uint32 {
          range "1..100000";
        }
      }
      leaf root {
        status obsolete;
        description
          "DDT root node";
        type inet:ip-address;
      }
    }
    container decapsulation {
      status obsolete;
      description
        "Decapsulation behavior (e.g. filters)";
      container filter {
        status obsolete;
        description
          "Filters traffic";
        container rloc {
          status obsolete;
          description
            "Filter based on Routing Locator (RLOC) in packet header";
          container source {
            status obsolete;
            description
              "Filters traffic based on RLOC source address";
            leaf locator-set {
              status obsolete;
              description
                "Locator-set Name";
              type string;
            }
            leaf member {
              status obsolete;
              description
                "Members learned from map-server";
              type empty;
            }
          }
        }
      }
    }
    leaf disable-ttl-propagate {
      status obsolete;
      description
        "Disable ttl propagation";
      type empty;
    }
    leaf disable-first-packet-forwarding {
      status obsolete;
      description
        "Disable first packet forwarding";
      type empty;
    }
    container etr {
      status obsolete;
      description
        "Configures a LISP Egress Tunnel Router (ETR)";
      container map-server {
        status obsolete;
        description
          "Configures map server for ETR registration";
        container source-address-new {
          status obsolete;
          description
            "Configures map server source address";
          uses ios-ifc:interface-obsolete-grouping;
        }
        leaf source-address {
          status obsolete;
          description
            "Configures map server source address";
          type string;
        }
      }
    }
    container ipv4 {
      status obsolete;
      description
        "IPv4 address family";
      uses router-lisp-ip-grouping-obsolete;
    }
    container ipv6 {
      status obsolete;
      description
        "IPv6 address family";
      uses router-lisp-ip-grouping-obsolete;
    }
    container loc-reach-algorithm {
      status obsolete;
      description
        "Configure locator reachability algorithm";
      container lsb-reports {
        status obsolete;
        description
          "Configure data packet LSB report handling";
        leaf do-not-transmit {
          status obsolete;
          description
            "Force the setting of the encapsulation header L bit to zero";
          type empty;
        }
        leaf ignore {
          status obsolete;
          description
            "Ignore data packet LSB reports";
          type empty;
        }
      }
      leaf rloc-probing {
        status obsolete;
        description
          "Probe high priority RLOCs with Map-Requests as last resort";
        type empty;
      }
    }
    container locator-down {
      status obsolete;
      description
        "Manually set locator status to down";
      leaf address {
        status obsolete;
        description
          "IPv4/6 Locator address to be set down";
        type inet:ip-address;
      }
      container IPv4-interface-new {
        status obsolete;
        description
          "Use IPv4 address of interface as locator";
        uses ios-ifc:interface-obsolete-grouping;
      }
      leaf IPv4-interface {
        status obsolete;
        description
          "Use IPv4 address of interface as locator";
        type string;
      }
      container IPv6-interface-new {
        status obsolete;
        description
          "Use IPv6 address of interface as locator";
        uses ios-ifc:interface-obsolete-grouping;
      }
      leaf IPv6-interface {
        status obsolete;
        description
          "Use IPv6 address of interface as locator";
        type string;
      }
    }
    container locator-table {
      status obsolete;
      description
        "Specify the RLOC table";
      leaf vrf-name {
        status obsolete;
        type string;
      }
      leaf default {
        status obsolete;
        description
          "Default VRF";
        type empty;
      }
      leaf vrf {
        status obsolete;
        description
          "VRF name";
        type string;
      }
    }
    container map-request {
      status obsolete;
      description
        "Configure map-request handling";
      leaf itr-rlocs {
        status obsolete;
        description
          "Configure to use the specified RLOC set as ITR RLOC in map-request";
        type string;
      }
    }
    container map-server {
      status obsolete;
      description
        "Map-Server commands";
      container rloc {
        status obsolete;
        description
          "EID instance RLOC membership";
        container members {
          status obsolete;
          description
            "EID instance RLOC membership";
          leaf distribute {
            status obsolete;
            description
              "EID instance RLOC membership distribution";
            type empty;
          }
          container modify-discovered {
            status obsolete;
            description
              "Modify the EID instance membership that is automaticallydiscovered from ETR registrations";
            leaf operator {
              status obsolete;
              type enumeration {
                enum add;
                enum override;
              }
            }
            leaf locator-set {
              status obsolete;
              description
                "Locator set from which to get member RLOC addresses";
              type string;
            }
          }
        }
      }
      container site-registration {
        status obsolete;
        description
          "Map-server site registration options";
        leaf limit {
          status obsolete;
          description
            "Maximum number of site registrations as a result of accept-more-specifics";
          type uint32;
        }
        leaf warning-threshold {
          status obsolete;
          description
            "Warning threshold to issue system logging";
          type uint8 {
            range "1..100";
          }
        }
      }
      container nmr {
        status obsolete;
        description
          "Map-server negative map-reply option";
        leaf non-site-ttl {
          status obsolete;
          description
            "Negative map-reply TTL for non-site EID";
          type uint16 {
            range "1..1440";
          }
        }
      }
      container session {
        status obsolete;
        description
          "Map-server session";
        leaf passive-open {
          status obsolete;
          description
            "Open passive TCP sockets to listen for incoming connections";
          type string;
        }
      }
    }
    container platform {
      status obsolete;
      description
        "Configure platform resource options";
      container resource-usage {
        status obsolete;
        description
          "Configure resource-usage options";
        leaf local-host {
          status obsolete;
          description
            "Local host reserved percentage";
          type uint8 {
            range "1..100";
          }
        }
        container maximum-local-hosts {
          status obsolete;
          description
            "Maximum local hosts";
          leaf l2 {
            status obsolete;
            description
              "L2 local hosts";
            type uint32;
          }
          leaf l3 {
            status obsolete;
            description
              "L3 local hosts";
            type uint32;
          }
        }
        leaf warning {
          status obsolete;
          description
            "warning percentage";
          type uint8 {
            range "1..95";
          }
        }
      }
    }
    container other-xtr-probe {
      status obsolete;
      description
        "Configure parameters for probing of other xTRs in our site";
      leaf period {
        status obsolete;
        description
          "Period between probes in seconds";
        type uint16 {
          range "5..900";
        }
      }
    }
    container remote-rloc-probe {
      status obsolete;
      description
        "Configure parameters for probing of remote RLOCs";
      leaf on-membership-change {
        status obsolete;
        description
          "Trigger probing upon membership changes for remote RLOC";
        type empty;
      }
      leaf on-route-change {
        status obsolete;
        description
          "Trigger probing upon routing changes for remote RLOC";
        type empty;
      }
    }
  }

  grouping router-lisp-locator-set-grouping-obsolete {
    leaf priority {
      status obsolete;
      description
        "Configures which Locators from a set are preferred";
      type uint8;
    }
    leaf weight {
      status obsolete;
      description
        "Traffic load-spreading among Locators";
      type uint8 {
        range "0..100";
      }
    }
  }

  grouping router-lisp-key-grouping-obsolete {
    leaf ak-0 {
      status obsolete;
      description
        "The UNENCRYPTED (cleartext) password";
      type string;
    }
    leaf ak-6 {
      status obsolete;
      description
        "The ENCRYPTED password";
      type string;
    }
    leaf unc-pwd {
      status obsolete;
      description
        "The UNENCRYPTED (cleartext) password";
      type string;
    }
  }

  grouping router-lisp-site-inst-id-prefix-grouping-obsolete {
    list instance-id-cfg {
      status obsolete;
      description
        "EID instance-ID";
      key "id prefix";
      leaf id {
        status obsolete;
        type uint32 {
          range "1..16777214";
        }
      }
      leaf prefix {
        status obsolete;
        type union {
          type inet:ipv4-prefix;
          type ios-types:ipv6-prefix;
        }
      }
      leaf accept-more-specifics {
        status obsolete;
        description
          "Accept registrations for more specific EID prefixes";
        type empty;
      }
      uses router-lisp-site-publication-summary-only-grouping-obsolete;
      container route-tag-options {
        status obsolete;
        leaf route-tag {
          status obsolete;
          description
            "RIB route tag";
          type uint32 {
            range "0..4294967295";
          }
        }
        leaf accept-more-specifics {
          status obsolete;
          description
            "Accept registrations for more specific EID prefixes";
          type empty;
        }
      }
    }
    container inst-id-any-mac {
      status obsolete;
      list instance-id-cfg {
        status obsolete;
        description
          "EID instance-ID";
        key "id";
        leaf id {
          status obsolete;
          type uint32 {
            range "1..16777214";
          }
        }
        leaf any-mac {
          status obsolete;
          description
            "Accept registrations for any L2 EID records";
          type empty;
        }
      }
    }
  }

  grouping router-lisp-site-common-grouping-obsolete {
    container authentication-key {
      status obsolete;
      description
        "Authentication key used by LISP site";
      uses router-lisp-four-key-grouping-obsolete;
    }
    leaf description {
      status obsolete;
      description
        "Site description";
      type string;
    }
    container allowed-locator {
      status obsolete;
      description
        "Locator from LISP site";
      leaf ls-ipv4 {
        status obsolete;
        description
          "IPv4 locator allowed in registered locator-set";
        type inet:ipv4-address;
      }
      leaf ls-ipv6 {
        status obsolete;
        description
          "IPv6 locator allowed in registered locator-set";
        type inet:ipv6-address;
      }
      container list {
        status obsolete;
        description
          "Prefixes allowed in registered locator-set";
        leaf ipv4 {
          status obsolete;
          description
            "IPv4 prefix-list name";
          type string;
        }
        leaf ipv6 {
          status obsolete;
          description
            "IPv6 prefix-list name";
          type string;
        }
      }
    }
    list allow-locator-default-etr {
      status obsolete;
      description
        "Allow default-etr";
      key "instance-id address-family";
      leaf instance-id {
        description
          "EID instance-ID";
        type uint32 {
          range "0..16777214";
        }
      }
      leaf address-family {
        status obsolete;
        description
          "Accept registrations for ipv4/ipv6";
        type enumeration {
          enum ipv4;
          enum ipv6;
        }
      }
    }
    list allow-locator-service-etr {
      status obsolete;
      description
        "Allow service-etr";
      key "instance-id address-family";
      leaf instance-id {
        status obsolete;
        description
          "EID instance-ID";
        type uint32 {
          range "0..16777214";
        }
      }
      leaf address-family {
        status obsolete;
        description
          "Accept registrations for ipv4/ipv6";
        type enumeration {
          enum ipv4;
          enum ipv6;
        }
      }
    }
    container eid-prefix {
      status obsolete;
      description
        "Site EID address prefix";
      uses router-lisp-site-prefix-grouping-obsolete;
      uses router-lisp-site-inst-id-prefix-grouping-obsolete;
      list instance-id {
        status obsolete;
        description
          "EID instance-ID";
        key "id";
        leaf id {
          status obsolete;
          type uint32 {
            range "1..16777214";
          }
        }
        uses router-lisp-site-prefix-grouping-deprecated-obsolete;
        leaf any-mac {
          status obsolete;
          description
            "Accept registrations for any L2 EID records";
          type empty;
        }
      }
      leaf any-mac {
        status obsolete;
        description
          "Accept registrations for any L2 EID records";
        type empty;
      }
    }
    container eid-record {
      status obsolete;
      description
        "Site EID address prefix";
      uses router-lisp-site-prefix-grouping-obsolete;
      uses router-lisp-site-inst-id-prefix-grouping-obsolete;
      list instance-id {
        status obsolete;
        description
          "EID instance-ID";
        key "id";
        leaf id {
          status obsolete;
          type uint32 {
            range "1..16777214";
          }
        }
        uses router-lisp-site-prefix-grouping-deprecated-obsolete;
        leaf any-mac {
          status obsolete;
          description
            "Accept registrations for any L2 EID records";
          type empty;
        }
      }
      leaf any-mac {
        status obsolete;
        description
          "Accept registrations for any L2 EID records";
        type empty;
      }
    }
    leaf site-id {
      status obsolete;
      description
        "Configure a site-id for this site";
      type uint32 {
        range "0..4294967295";
      }
    }
  }

  grouping rouer-lisp-site-grouping-obsolete {
    list site {
      status obsolete;
      description
        "Configure a LISP site on a map server (MS)";
      key "sname";
      leaf sname {
        status obsolete;
        description
          "The site name";
        type string;
      }
      container default {
        status obsolete;
        uses router-lisp-site-common-grouping-obsolete;
      }
      uses router-lisp-site-common-grouping-obsolete;
    }
  }

  grouping router-lisp-site-publication-summary-only-grouping-obsolete {
    leaf publication-summary-only {
      status obsolete;
      description
        "Publish only aggregate summary of EID prefixes";
      type empty;
    }
  }

  grouping config-lisp-remote-locator-set-grouping-obsolete {
    list ipv4-address {
      status obsolete;
      description
        "IPv4 Address of loopback or other Proxy ETR interface";
      key "address";
      leaf address {
        status obsolete;
        type inet:ipv4-address;
      }
      leaf instance-id {
        status obsolete;
        description
          "EID instance-ID";
        type uint32 {
          range "0..16777214";
        }
      }
      uses router-lisp-locator-set-grouping-obsolete;
    }
    list ipv6-address {
      status obsolete;
      description
        "IPv6 Address of loopback or other Proxy ETR interface";
      key "address";
      leaf address {
        status obsolete;
        type inet:ipv6-address;
      }
      leaf instance-id {
        status obsolete;
        description
          "EID instance-ID";
        type uint32 {
          range "0..16777214";
        }
      }
      uses router-lisp-locator-set-grouping-obsolete;
    }
  }

  grouping config-lisp-main-grouping-obsolete {
    container service {
      status obsolete;
      description
        "Configure lisp service type";
      container ipv4 {
        status obsolete;
        presence "true";
        container default {
          status obsolete;
          uses router-lisp-service-ipv4-grouping-obsolete;
        }
        uses router-lisp-service-ipv4-grouping-obsolete;
      }
      container ipv6 {
        status obsolete;
        presence "true";
        container default {
          status obsolete;
          uses router-lisp-service-ipv6-grouping-obsolete;
        }
        uses router-lisp-service-ipv6-grouping-obsolete;
      }
      container ethernet {
        status obsolete;
        presence "true";
        container default {
          status obsolete;
          uses router-lisp-service-ethernet-grouping-obsolete;
        }
        uses router-lisp-service-ethernet-grouping-obsolete;
      }
    }
    leaf disable-extranet-policy-import-to-db {
      status obsolete;
      description
        "Disable Extranet Policy import to Database";
      type boolean;
      default "false";
    }
    container default-etr {
      status obsolete;
      description
        "Configuration applied to default-etr registrations";
      leaf disable-metric {
        status obsolete;
        description
          "Disable getting metric from RIB";
        type empty;
      }
    }
    container encapsulation {
      status obsolete;
      description
        "Select encapsulation type for data packets";
      leaf vxlan {
        status obsolete;
        description
          "Use VXLAN encapsulation for data packets";
        type empty;
      }
    }
    uses router-lisp-extranet-group-obsolete;
    list remote-locator-set {
      status obsolete;
      description
        "Configure a named remote locator set";
      key "name";
      leaf name {
        status obsolete;
        type string;
      }
      container default {
        status obsolete;
        uses config-lisp-remote-locator-set-grouping-obsolete;
      }
      uses config-lisp-remote-locator-set-grouping-obsolete;
    }
    list locator-set {
      status obsolete;
      description
        "Configure a named locator set";
      key "name";
      leaf name {
        status obsolete;
        type string;
      }
      leaf auto-discover-rlocs {
        status obsolete;
        description
          "Auto discover locators registered by other xTRs";
        type empty;
      }
      list IPv4-interface {
        status obsolete;
        description
          "Use IPv4 address of interface as locator";
        key "name";
        leaf name {
          status obsolete;
          type string;
        }
        uses router-lisp-locator-set-grouping-obsolete;
      }
      list IPv6-interface {
        status obsolete;
        description
          "Use IPv6 address of interface as locator";
        key "name";
        leaf name {
          status obsolete;
          type string;
        }
        uses router-lisp-locator-set-grouping-obsolete;
      }
      list ip-address {
        status obsolete;
        description
          "Use IPv6 address of interface as locator";
        key "ip";
        leaf ip {
          status obsolete;
          type inet:ip-address;
        }
        uses router-lisp-locator-set-grouping-obsolete;
      }
    }
    container locator {
      status obsolete;
      description
        "Locator configuration";
      leaf default-set {
        status obsolete;
        description
          "Specify a default locator-set";
        type string;
      }
      leaf consistency-check {
        status obsolete;
        description
          "Log a message if RLOC inconsistency is detected";
        type boolean;
        default "true";
      }
    }
    list locator-scope {
      status obsolete;
      description
        "Configure a locator scope";
      key "name";
      leaf name {
        status obsolete;
        type string;
      }
      leaf-list rloc-prefix {
        status obsolete;
        description
          "RLOC prefix to check against ITR RLOC and ETR RLOC";
        type union {
          type inet:ipv4-prefix;
          type ios-types:ipv6-prefix;
        }
      }
      leaf-list rtr-locator-set {
        status obsolete;
        description
          "Locator-set of RTR to use in proxy reply for disjoint/cross AF RLOC";
        type string;
      }
    }
    list prefix-list {
      status obsolete;
      description
        "Configure a named prefix list";
      key "name";
      leaf name {
        status obsolete;
        type string;
      }
      list ipv4-prefix {
        status obsolete;
        description
          "IPv4 EID-prefix";
        key "prefix";
        leaf prefix {
          status obsolete;
          type inet:ipv4-prefix;
        }
      }
      list ipv6-prefix {
        status obsolete;
        description
          "IPv6 EID-prefix";
        key "prefix";
        leaf prefix {
          status obsolete;
          type inet:ipv6-prefix;
        }
      }
    }
    container instance-container {
      status obsolete;
      description
        "EID instance-ID";
      list instance-list {
        status obsolete;
        key "instance-id";
        leaf instance-id {
          status obsolete;
          description
            "EID instance-ID";
          type uint32 {
            range "0..16777214";
          }
        }
        container default {
          status obsolete;
          uses router-lisp-inst-grouping-obsolete;
        }
        uses router-lisp-inst-grouping-obsolete;
      }
    }
    uses router-lisp-common-grouping-obsolete;
    container eid-table {
      status obsolete;
      description
        "Configure an EID instance for a VRF";
      list instance-list {
        status obsolete;
        key "instance-id";
        leaf instance-id {
          status obsolete;
          description
            "EID instance-ID";
          type uint32 {
            range "0..16777214";
          }
        }
        leaf vrf-name {
          status obsolete;
          type string;
        }
        leaf default {
          status obsolete;
          description
            "Default VRF";
          type empty;
        }
        leaf vrf {
          status obsolete;
          type string;
        }
        list database-mapping {
          status obsolete;
          description
            "Configures Locator addresses for an ETR";
          key "eid-prefix";
          leaf eid-prefix {
            status obsolete;
            type union {
              type inet:ipv4-prefix;
              type ios-types:ipv6-prefix;
            }
          }
          leaf locator-set {
            status obsolete;
            description
              "Use locators defined by locator-set";
            type string;
          }
        }
        list dynamic-eid {
          status obsolete;
          description
            "Configure a dynamic EID";
          key "name";
          leaf name {
            status obsolete;
            type string;
          }
          list database-mapping {
            status obsolete;
            description
              "Configures EID-prefix and locator-set for dynamic-EID";
            key "eid-prefix";
            leaf eid-prefix {
              status obsolete;
              type inet:ipv4-prefix;
            }
            leaf locator-set {
              status obsolete;
              description
                "Use locators defined by locator-set";
              type string;
            }
          }
          container eid-notify {
            status obsolete;
            description
              "Configure options for sending/receiving EID-notify";
            container authentication-key {
              status obsolete;
              description
                "Authentication key used for validating received EID-notify";
              uses router-lisp-key-grouping-obsolete;
            }
            list gateway-key {
              status obsolete;
              key "gateway-ip";
              leaf gateway-ip {
                status obsolete;
                type inet:ip-address;
              }
              uses router-lisp-key-grouping-obsolete;
              leaf hash-function {
                status obsolete;
                description
                  "EID-notify authentication type";
                type enumeration {
                  enum sha1;
                  enum sha2;
                }
              }
            }
          }
          leaf map-notify-group {
            status obsolete;
            description
              "Multicast group which to send map-notifies to";
            type inet:ip-address;
          }
          list map-server {
            status obsolete;
            description
              "Configures map server for ETR registration";
            key "ip";
            leaf ip {
              status obsolete;
              type inet:ip-address;
            }
            container key {
              status obsolete;
              description
                "Authentication key used with map server";
              leaf key-0 {
                status obsolete;
                description
                  "The UNENCRYPTED (cleartext) password";
                type string;
              }
              leaf key-6 {
                status obsolete;
                description
                  "The ENCRYPTED password";
                type string;
              }
              leaf key-7 {
                status obsolete;
                description
                  "The HIDDEN password";
                type string;
              }
              leaf pwd {
                status obsolete;
                description
                  "The UNENCRYPTED (cleartext) password";
                type string;
              }
              leaf hash-function {
                status obsolete;
                description
                  "Map-Register authentication type";
                type enumeration {
                  enum sha1;
                  enum sha2;
                }
              }
            }
            leaf proxy-reply {
              status obsolete;
              description
                "Request Map-Server to send Map-Replies on behalf of site";
              type empty;
            }
          }
        }
        uses router-lisp-common-grouping-obsolete;
        list map-cache {
          status obsolete;
          description
            "Configures static EID-to-RLOC mappings for an ITR";
          key "eid-prefix";
          leaf eid-prefix {
            status obsolete;
            type union {
              type inet:ipv4-prefix;
              type ios-types:ipv6-prefix;
            }
          }
          container etr-interface-ip {
            status obsolete;
            leaf etr-interface-ip-address {
              status obsolete;
              type inet:ip-address;
            }
            leaf priority {
              status obsolete;
              description
                "Configures which Locators from a set are preferred";
              type uint8;
            }
            leaf weight {
              status obsolete;
              description
                "Traffic load-spreading among Locators";
              type uint8 {
                range "0..100";
              }
            }
          }
          leaf drop {
            status obsolete;
            description
              "Drop packets that match this map-cache entry";
            type empty;
          }
          leaf map-request {
            status obsolete;
            description
              "Send Map-Request for LISP destination EID";
            type empty;
          }
          leaf native-forward {
            status obsolete;
            description
              "Natively forward packets that match this map-cache entry";
            type empty;
          }
        }
      }
    }
    container security {
      status obsolete;
      description
        "Enable default LISP security and authentication in reply is optional";
      presence "true";
      leaf strong {
        status obsolete;
        description
          "Enable default LISP security and authentication in reply is required";
        type empty;
      }
    }
    uses rouer-lisp-site-grouping-obsolete;
    leaf site-id {
      status obsolete;
      description
        "Configure a site-id for this site";
      type uint32;
    }
    container syslog {
      status obsolete;
      description
        "Configure syslog option";
      container session {
        status obsolete;
        description
          "Enable session syslog";
        leaf changes {
          status obsolete;
          description
            "Enable session change syslog";
          type empty;
        }
      }
      leaf verbose {
        status obsolete;
        description
          "Enable verbose syslog";
        type empty;
      }
    }
    container capability {
      status obsolete;
      description
        "Configure capability";
      container publish-subscribe {
        status obsolete;
        description
          "Configure Capability for Publish-Subscribe functionality";
        leaf instance-id {
          status obsolete;
          description
            "Instance-ID";
          type boolean;
          default "true";
        }
      }
    }
    container fabric {
      status obsolete;
      description
        "Configure fabric role";
      presence "true";
      leaf border {
        status obsolete;
        description
          "Configure fabric role as border";
        type empty;
      }
    }
    container redundancy {
      status obsolete;
      description
        "Configure redundancy";
      leaf sso {
        status obsolete;
        description
          "Configure redundancy sso";
        type boolean;
        default "true";
      }
    }
    container tcp {
      status obsolete;
      description
        "Configure TCP options";
      leaf path-mtu-discovery {
        status obsolete;
        description
          "Configure path mtu discovery";
        type boolean;
        default "true";
      }
      list auth-option {
        status obsolete;
        description
          "Configure LISP TCP auth-option";
        key "name";
        leaf name {
          status obsolete;
          type string;
        }
        list peer {
          status obsolete;
          description
            "Configure TCP-AO peer";
          key "address";
          leaf address {
            status obsolete;
            type union {
              type inet:ipv4-address;
              type inet:ipv6-address;
              type enumeration {
                enum accept;
              }
            }
          }
        }
      }
    }
    leaf domain-id {
      status obsolete;
      description
        "Configures Domain-ID of LISP device";
      type uint32 {
        range "1..4294967038";
      }
    }
    leaf multihoming-id {
      status obsolete;
      description
        "Configures Multihoming-ID of LISP device";
      type uint16 {
        range "1..65535";
      }
    }
  }

  grouping router-lisp-site-prefix-grouping-obsolete {
    list prefixes {
      status obsolete;
      key "prefix";
      leaf prefix {
        status obsolete;
        type union {
          type inet:ipv4-prefix;
          type ios-types:ipv6-prefix;
        }
      }
      leaf accept-more-specifics {
        status obsolete;
        description
          "Accept registrations for more specific EID prefixes";
        type empty;
      }
      uses router-lisp-site-publication-summary-only-grouping-obsolete;
      container route-tag-options {
        status obsolete;
        leaf route-tag {
          status obsolete;
          description
            "RIB route tag";
          type uint32 {
            range "0..4294967295";
          }
        }
        leaf accept-more-specifics {
          status obsolete;
          description
            "Accept registrations for more specific EID prefixes";
          type empty;
        }
      }
      leaf route-tag {
        status obsolete;
        description
          "RIB route tag";
        type uint32 {
          range "0..4294967295";
        }
      }
    }
  }

  grouping router-lisp-site-prefix-grouping-deprecated-obsolete {
    list prefixes {
      status obsolete;
      key "prefix";
      leaf prefix {
        status obsolete;
        type union {
          type inet:ipv4-prefix;
          type ios-types:ipv6-prefix;
        }
      }
      leaf accept-more-specifics {
        status obsolete;
        description
          "Accept registrations for more specific EID prefixes";
        type empty;
      }
      container route-tag-options {
        status obsolete;
        leaf route-tag {
          status obsolete;
          description
            "RIB route tag";
          type uint32 {
            range "0..4294967295";
          }
        }
        leaf accept-more-specifics {
          status obsolete;
          description
            "Accept registrations for more specific EID prefixes";
          type empty;
        }
      }
      leaf route-tag {
        status obsolete;
        description
          "RIB route tag";
        type uint32 {
          range "0..4294967295";
        }
      }
    }
  }
}
