module Cisco-IOS-XE-wireless-ap-global-oper {
  yang-version 1.1;
  namespace "http://cisco.com/ns/yang/Cisco-IOS-XE-wireless-ap-global-oper";
  prefix wireless-ap-global-oper;

  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains access point operational data aggregated across wireless processes.
     Copyright (c) 2020-2022 by Cisco Systems, Inc.
     All rights reserved.";

  revision 2022-11-01 {
    description
      "- Added DTLS statistics
       - Added ap location statistics
       - Added AP history data
       - Added AP join count data
       - Added AP join count statistics
       - Added ap join and discovery stats";
    reference
      "1.3.0";
    cisco-semver:module-version "1.3.0";
  }
  revision 2022-07-01 {
    description
      "- Added AP statistics";
    reference
      "1.2.0";
    cisco-semver:module-version "1.2.0";
  }
  revision 2021-07-01 {
    description
      "- Added AP join statistics";
    reference
      "1.1.0";
    cisco-semver:module-version "1.1.0";
  }
  revision 2021-03-01 {
    description
      "Initial revision";
    reference
      "1.0.0";
    cisco-semver:module-version "1.0.0";
  }

  typedef last-failure-phase {
    type enumeration {
      enum ap-con-failure-unknown {
        value 0;
        description
          "Unknown failure";
      }
      enum ap-con-failure-discovery {
        value 1;
        description
          "Failed during discovery phase";
      }
      enum ap-con-failure-dtls {
        value 2;
        description
          "Failed during DTLS phase";
      }
      enum ap-con-failure-join {
        value 3;
        description
          "Failed during join phase";
      }
      enum ap-con-failure-config {
        value 4;
        description
          "Failed during config phase";
      }
      enum ap-con-failure-imgdwnld {
        value 5;
        description
          "Failed during image download phase";
      }
      enum ap-con-failure-run {
        value 6;
        description
          "Failed during run state";
      }
    }
    description
      "Last failure phase of AP connection";
  }

  typedef ap-discovery-failure-reason {
    type enumeration {
      enum disc-fail-none {
        value 0;
        description
          "AP discovery failure none";
      }
      enum disc-fail-req-dec-board-data {
        value 1;
        description
          "Failure decoding board data";
      }
      enum disc-fail-req-dec-rad-info {
        value 2;
        description
          "Failure decoding radio info";
      }
      enum disc-fail-req-dec-wtp-dscrptr {
        value 3;
        description
          "Failure decoding descriptor";
      }
      enum disc-fail-req-max-conc-wtp-dwnlds {
        value 4;
        description
          "Max concurrent downloads reached";
      }
      enum disc-fail-req-high-prity-max-apjoin {
        value 5;
        description
          "Higher priority AP joined after AP max limit";
      }
      enum disc-fail-req-max-wtp-joined {
        value 6;
        description
          "Max AP limit reached";
      }
      enum disc-fail-req-max-conc-wtp-joins {
        value 7;
        description
          "Max concurrent joins reached";
      }
      enum disc-fail-resp-enc-dscrptr {
        value 8;
        description
          "Failure encoding descriptor";
      }
      enum disc-fail-resp-enc-acname {
        value 9;
        description
          "Failure encoding controller name";
      }
      enum disc-fail-resp-enc-ipv4-addr {
        value 10;
        description
          "Failure encoding IPv4 address";
      }
      enum disc-fail-resp-enc-ipv6-addr {
        value 11;
        description
          "Failure encoding IPv6 address";
      }
      enum disc-fail-resp-enc-mwar-payld {
        value 12;
        description
          "Failure encoding mwar type payload";
      }
      enum disc-fail-resp-enc-wtp-rad-info {
        value 13;
        description
          "Failure encoding radio info";
      }
      enum disc-fail-resp-send-fail {
        value 14;
        description
          "Failure sending response";
      }
      enum disc-fail-req-non-wireless-mgmt-intf {
        value 15;
        description
          "Non-wireless management interface";
      }
      enum disc-fail-req-un-reg-license-mgr {
        value 16;
        description
          "Controller not registered with license manager";
      }
    }
    description
      "Enumeration AP discovery failure reason";
  }

  typedef enm-ap-join-failure-reason {
    type enumeration {
      enum jf-none {
        value 0;
        description
          "Default reason code";
      }
      enum jf-reqrej-swver {
        value 1;
        description
          "Failed to decode software version";
      }
      enum jf-reqrej-hwver {
        value 2;
        description
          "Failed to decode hardware version";
      }
      enum jf-reqrej-bootver {
        value 3;
        description
          "Failed to decode boot version";
      }
      enum jf-reqrej-wtpdescrptr {
        value 4;
        description
          "Failed to decode WTP descriptor";
      }
      enum jf-reqrej-unsupportedwtp {
        value 5;
        description
          "Unsupported AP";
      }
      enum jf-reqrej-notfabric {
        value 6;
        description
          "AP is not fabric capable";
      }
      enum jf-reqrej-modelnum {
        value 7;
        description
          "Failed to decode model number";
      }
      enum jf-reqrej-serialnum {
        value 8;
        description
          "Failed to decode serial number";
      }
      enum jf-reqrej-boardid {
        value 9;
        description
          "Failed to decode board ID";
      }
      enum jf-reqrej-boardrev {
        value 10;
        description
          "Failed to decode board revision";
      }
      enum jf-reqrej-basemacaddr {
        value 11;
        description
          "Failed to decode base MAC address";
      }
      enum jf-reqrej-locationdata {
        value 12;
        description
          "Failed to decode location data";
      }
      enum jf-reqrej-wtpname {
        value 13;
        description
          "Failed to decode AP name";
      }
      enum jf-reqrej-wtpipv4addr {
        value 14;
        description
          "Failed to decode IPv4 address";
      }
      enum jf-reqrej-boarddataopt {
        value 15;
        description
          "Failed to decode board data options";
      }
      enum jf-reqrej-invalid-radio {
        value 16;
        description
          "Invalid radio slot ID";
      }
      enum jf-reqrej-maxmsgsize {
        value 17;
        description
          "Failed to decode maximum message size";
      }
      enum jf-reqrej-sessionid {
        value 18;
        description
          "Failed to decode session ID";
      }
      enum jf-resp-wtpradioinfo {
        value 19;
        description
          "Failed to encode radio information";
      }
      enum jf-resp-maxmsglen {
        value 20;
        description
          "Failed to encode maximum message length";
      }
      enum jf-resp-acdscrptr {
        value 21;
        description
          "Failed to encode descriptor";
      }
      enum jf-resp-acname {
        value 22;
        description
          "Failed to encode AC name";
      }
      enum jf-resp-cntrlipv4addr {
        value 23;
        description
          "Failed to encode capwap control ipv4 address";
      }
      enum jf-resp-mwartypepayload {
        value 24;
        description
          "Failed to encode mwar type payload";
      }
      enum jf-resp-authtokenpayload {
        value 25;
        description
          "Failed to encode auth token payload";
      }
      enum jf-resp-dudplite {
        value 26;
        description
          "Failed to encode UDP lite config payload";
      }
      enum jf-delete-progress {
        value 27;
        description
          "AP delete in progress";
      }
      enum jf-resp-respsendf {
        value 28;
        description
          "Failed to send response";
      }
      enum jf-ap-auth-pending {
        value 29;
        description
          "AP auth pending";
      }
      enum jf-reqrej-capwapcapab {
        value 30;
        description
          "Failed to decode CAPWAP capabilities";
      }
      enum jf-dtls-alert-from-peer {
        value 31;
        description
          "DTLS close alert from peer";
      }
      enum jf-internal-error {
        value 32;
        description
          "Internal error";
      }
      enum jf-idb-creation-failed {
        value 33;
        description
          "Capwap IDB creation failed";
      }
      enum jf-resp-cntrlipv6addr {
        value 34;
        description
          "Failed to encode capwap control ipv6 address";
      }
      enum jf-resp-efficientimagedownload {
        value 35;
        description
          "Failed to encode efficient image download";
      }
      enum jf-maxrexmitreached {
        value 36;
        description
          "Maximum retransmissions to AP limit reached";
      }
      enum jf-heartbeattimer {
        value 37;
        description
          "Heart beat timer expired";
      }
      enum jf-hwfailure {
        value 38;
        description
          "Nack received";
      }
      enum jf-ap-auth-failure {
        value 39;
        description
          "AP Auth Failure";
      }
      enum jf-invalid-mtu {
        value 40;
        description
          "Invalid path MTU";
      }
      enum jf-dtls-version {
        value 41;
        description
          "Unexpected DTLS version";
      }
    }
    description
      "Reason for cisco AP join failure";
  }

  typedef enm-ap-config-failure-reason {
    type enumeration {
      enum cf-none {
        value 0;
        description
          "Default failure reason";
      }
      enum cf-reqrej-unknown-ap {
        value 1;
        description
          "Unknown ap";
      }
      enum cf-reqrej-reg-domain-check {
        value 2;
        description
          "Regulatory domain check failed";
      }
      enum cf-req-rej-capwap-data {
        value 3;
        description
          "Capwap data failed";
      }
      enum cf-reqrej-inval-reg-domain {
        value 4;
        description
          "Invalid regulatory domain";
      }
      enum cf-resp-build-fail {
        value 5;
        description
          "Response build failed";
      }
      enum cf-resp-send-fail {
        value 6;
        description
          "Response send failed";
      }
      enum cf-dtls-close-alert {
        value 7;
        description
          "DTLS close alert from the peer";
      }
      enum cf-internal-error {
        value 8;
        description
          "Internal Error";
      }
      enum cf-process-fail {
        value 9;
        description
          "Config Status process failure";
      }
      enum cf-max-rexmit {
        value 10;
        description
          "Max Retransmission to AP";
      }
      enum cf-heartbeat-timer {
        value 11;
        description
          "Heart beat timer expiry";
      }
      enum cf-hw-fail {
        value 12;
        description
          "NACK received";
      }
      enum cf-echo-req-fail {
        value 13;
        description
          "Echo request process failure";
      }
    }
    description
      "AP configuration failure reason code";
  }

  typedef enm-dtls-handshake-failure-reason {
    type enumeration {
      enum dtls-hs-success {
        value 0;
        description
          "No failure";
      }
      enum dtls-hs-err {
        value 1;
        description
          "Handshake error";
      }
      enum dtls-hs-cert-auth {
        value 2;
        description
          "Certificate authorization failed";
      }
      enum dtls-hs-aaa-auth {
        value 3;
        description
          "AAA authorization failed";
      }
      enum dtls-hs-timer-exp {
        value 4;
        description
          "DTLS Timer expired";
      }
      enum dtls-hs-peer-alert {
        value 5;
        description
          "DTLS handshake alert from peer";
      }
      enum dtls-hs-server-shut {
        value 6;
        description
          "DTLS handshake server shutdown";
      }
      enum dtls-hs-config-not-done {
        value 7;
        description
          "DTLS certificate chain not available";
      }
      enum dtls-hs-unsupp-protocol {
        value 8;
        description
          "Unsupported DTLS protocol";
      }
      enum dtls-hs-no-shared-cipher {
        value 9;
        description
          "No shared ciphersuite";
      }
    }
    description
      "AP DTLS handshake failure reason code";
  }

  grouping st-ap-discovery-info {
    description
      "AP discovery stats";
    leaf wtp-mac {
      type yang:mac-address;
      description
        "AP radio MAC address";
    }
    leaf ethernet-mac {
      type yang:mac-address;
      description
        "AP ethernet MAC address";
    }
    leaf ap-ip-address {
      type inet:ip-address;
      description
        "AP IP address";
    }
    leaf num-discovery-req-recvd {
      type uint16;
      description
        "Total number of discovery request received";
    }
    leaf num-succ-disc-resp-sent {
      type uint16;
      description
        "Total number of successful discovery response sent";
    }
    leaf num-err-disc-req {
      type uint16;
      description
        "Total number of errored discovery requests";
    }
    leaf last-disc-failure-type {
      type wireless-ap-global-oper:ap-discovery-failure-reason;
      description
        "Last discovery failure type";
    }
    leaf last-success-disc-time {
      type yang:date-and-time;
      description
        "Last successful discovery attempt time";
    }
    leaf last-failed-disc-time {
      type yang:date-and-time;
      description
        "Last failed discovery attempt time";
    }
  }

  grouping st-ap-join-info {
    description
      "AP join data";
    leaf ap-ip-addr {
      type string;
      description
        "IP address of the AP";
    }
    leaf ap-ethernet-mac {
      type yang:mac-address;
      description
        "AP ethernet MAC address";
    }
    leaf ap-name {
      type string;
      description
        "Name of the AP";
    }
    leaf is-joined {
      type boolean;
      description
        "AP join status";
    }
    leaf num-join-req-recvd {
      type uint16;
      description
        "Total number of join requests received";
    }
    leaf num-config-req-recvd {
      type uint16;
      description
        "Total number of configuration requests received";
    }
    leaf last-join-failure-type {
      type wireless-ap-global-oper:enm-ap-join-failure-reason;
      description
        "Last AP join failure reason";
    }
    leaf last-config-failure-type {
      type wireless-ap-global-oper:enm-ap-config-failure-reason;
      description
        "Last AP config failure reason";
    }
    leaf last-error-type {
      type wireless-ap-global-oper:last-failure-phase;
      description
        "Last failure phase of AP connection";
    }
    leaf last-error-time {
      type yang:date-and-time;
      description
        "Time at which the last join error occurred";
    }
    leaf last-msg-decr-fail-reason {
      type string;
      description
        "Reason for last message decryption failure";
    }
    leaf num-succ-join-resp-sent {
      type uint16;
      description
        "Total number of successful join response sent";
    }
    leaf num-unsucc-join-req-procn {
      type uint16;
      description
        "Total number of unsuccessful join request processed";
    }
    leaf num-succ-conf-resp-sent {
      type uint16;
      description
        "Total number of successful configure response sent";
    }
    leaf num-unsucc-conf-req-procn {
      type uint16;
      description
        "Total number of unsuccessful config request processed";
    }
    leaf last-succ-join-atmpt-time {
      type yang:date-and-time;
      description
        "Last successful join attempt time";
    }
    leaf last-fail-join-atmpt-time {
      type yang:date-and-time;
      description
        "Last join failure time";
    }
    leaf last-succ-conf-atmpt-time {
      type yang:date-and-time;
      description
        "Last successful config attempt time";
    }
    leaf last-fail-conf-atmpt-time {
      type yang:date-and-time;
      description
        "Last failed config attempt time";
    }
  }

  grouping st-dtls-sess-info-list {
    description
      "DTLS phase statistics";
    leaf mac-addr {
      type yang:mac-address;
      description
        "AP MAC address";
    }
    leaf data-dtls-setup-req {
      type uint32;
      description
        "DTLS session requests received";
    }
    leaf data-dtls-success {
      type uint32;
      description
        "Established DTLS session";
    }
    leaf data-dtls-failure {
      type uint32;
      description
        "Unsuccessful DTLS session";
    }
    leaf ctrl-dtls-setup-req {
      type uint32;
      description
        "DTLS session requests received";
    }
    leaf ctrl-dtls-success {
      type uint32;
      description
        "Established Dtls session";
    }
    leaf ctrl-dtls-failure {
      type uint32;
      description
        "Unsuccessful Dtls session";
    }
    leaf data-dtls-failure-type {
      type wireless-ap-global-oper:enm-dtls-handshake-failure-reason;
      description
        "Reason for last unsuccessful DTLS session";
    }
    leaf ctrl-dtls-failure-type {
      type wireless-ap-global-oper:enm-dtls-handshake-failure-reason;
      description
        "Reason for last unsuccessful DTLS session";
    }
    leaf ctrl-dtls-decrypt-err {
      type uint32;
      description
        "SSL decrypt errors";
    }
    leaf ctrl-dtls-anti-replay-err {
      type uint32;
      description
        "SSL anti replay errors";
    }
    leaf data-dtls-decrypt-err {
      type uint32;
      description
        "SSL decrypt errors";
    }
    leaf data-dtls-anti-replay-err {
      type uint32;
      description
        "SSL anti replay errors";
    }
    leaf data-dtls-failure-time {
      type yang:date-and-time;
      description
        "Last unsuccessful data dtls session time";
    }
    leaf data-dtls-success-time {
      type yang:date-and-time;
      description
        "Last successful data dtls session time";
    }
    leaf ctrl-dtls-failure-time {
      type yang:date-and-time;
      description
        "Last unsuccessful control dtls session time";
    }
    leaf ctrl-dtls-success-time {
      type yang:date-and-time;
      description
        "Last successful control dtls session time";
    }
  }

  grouping st-radio-stats {
    description
      "AP radio stats";
    leaf total-radios {
      type uint32;
      description
        "Total number of radios";
    }
    leaf radios-up {
      type uint32;
      description
        "Total number of radios up";
    }
    leaf radios-down {
      type uint32;
      description
        "Total number of radios down";
    }
  }

  grouping ewlc-ap-statistics {
    description
      "AP radio statistics";
    container stats-80211-a-rad {
      description
        "802.11 5 GHz radio stats";
      uses wireless-ap-global-oper:st-radio-stats;
    }
    container stats-80211-bg-rad {
      description
        "802.11 2.4 GHz radio stats";
      uses wireless-ap-global-oper:st-radio-stats;
    }
    container stats-80211-xor-rad {
      description
        "802.11 dual band radio stats";
      uses wireless-ap-global-oper:st-radio-stats;
    }
    container stats-80211-rx-only-rad {
      description
        "802.11 RX radio stats";
      uses wireless-ap-global-oper:st-radio-stats;
    }
    container stats-80211-all-rad {
      description
        "All radio stats";
      uses wireless-ap-global-oper:st-radio-stats;
    }
    container stats-80211bg-clnt-srvg {
      description
        "802.11 2.4 GHz client serving radio stats";
      uses wireless-ap-global-oper:st-radio-stats;
    }
    container stats-80211a-clnt-srvg {
      description
        "802.11 5 GHz client serving radio stats";
      uses wireless-ap-global-oper:st-radio-stats;
    }
    container stats-rad-mon-mode {
      description
        "Monitor radio stats";
      uses wireless-ap-global-oper:st-radio-stats;
    }
    leaf stats-misconfigured-aps {
      type uint32;
      description
        "Total number of misconfigured APs";
    }
    container stats-80211-6ghz-radios {
      description
        "802.11 6 GHz radio stats";
      uses wireless-ap-global-oper:st-radio-stats;
    }
    container stats-80211-6ghz-clnt-srvg {
      description
        "802.11 6 GHz client serving radio stats";
      uses wireless-ap-global-oper:st-radio-stats;
    }
    container dual-band-rad-mon-mode {
      description
        "802.11 dual band monitor radio stats";
      uses wireless-ap-global-oper:st-radio-stats;
    }
    container stats-80211bg-rad-mon-mode {
      description
        "802.11 2.4 GHz monitor radio stats";
      uses wireless-ap-global-oper:st-radio-stats;
    }
    container stats-80211a-rad-mon-mode {
      description
        "802.11 5 GHz monitor radio stats";
      uses wireless-ap-global-oper:st-radio-stats;
    }
    container rad-mon-mode-80211-6ghz {
      description
        "802.11 6 GHz monitor radio stats";
      uses wireless-ap-global-oper:st-radio-stats;
    }
    leaf stats-dtls-lsc-fbk-aps {
      type uint32;
      description
        "Total number of DTLS LSC fallback APs";
    }
    leaf total-high-cpu-reload {
      type uint32;
      description
        "Total number of AP reloads due to high CPU";
    }
    leaf total-high-mem-reload {
      type uint32;
      description
        "Total number of AP reloads due to high memory";
    }
    leaf total-radio-stuck-reset {
      type uint32;
      description
        "Total number of radio stuck resets";
    }
    container dual-band-rad-snfr-mode {
      description
        "802.11 dual band sniffer radio stats";
      uses wireless-ap-global-oper:st-radio-stats;
    }
    container radio-snfr-mode-80211bg {
      description
        "802.11 2.4 GHz sniffer radio stats";
      uses wireless-ap-global-oper:st-radio-stats;
    }
    container radio-snfr-mode-80211a {
      description
        "802.11 5 GHz sniffer radio stats";
      uses wireless-ap-global-oper:st-radio-stats;
    }
    container radio-snfr-mode-80211-6ghz {
      description
        "802.11 6 GHz sniffer radio stats";
      uses wireless-ap-global-oper:st-radio-stats;
    }
    container radio-snfr-mode {
      description
        "All sniffer radio stats";
      uses wireless-ap-global-oper:st-radio-stats;
    }
    container total-80211-xor-5-6ghz-rad {
      description
        "802.11 dual band 5/6 GHz radio stats";
      uses wireless-ap-global-oper:st-radio-stats;
    }
  }

  grouping predownload-stats {
    description
      "AP image predownload statistics";
    leaf num-initiated {
      type uint32;
      description
        "Total number of AP predownload initiated";
    }
    leaf num-in-progress {
      type uint32;
      description
        "Total number of AP predownload in-progress";
    }
    leaf num-complete {
      type uint32;
      description
        "Total number of AP predownload completed";
    }
    leaf num-unsupported {
      type uint32;
      description
        "Total number of AP predownload not supported";
    }
    leaf num-failed {
      type uint32;
      description
        "Total number of AP predownload failed";
    }
    leaf is-predownload-in-progress {
      type boolean;
      description
        "Status of AP image predownload";
    }
    leaf num-total {
      type uint32;
      description
        "Total number of AP connected";
    }
  }

  grouping global-ap-stats {
    description
      "AP aggregated statistics";
    container predownload-stats {
      description
        "AP predownload statistics";
      uses wireless-ap-global-oper:predownload-stats;
    }
    leaf downloads-in-progress {
      type uint32;
      description
        "Total number of APs download in-progress";
    }
    leaf downloads-complete {
      type uint32;
      description
        "Total number of APs download completed";
    }
    container wlc-predownload-stats {
      description
        "Wireless controller predownload statistics";
      uses wireless-ap-global-oper:predownload-stats;
    }
  }

  grouping wlan-client-stats {
    description
      "WLAN client stats";
    leaf wlan-id {
      type uint16;
      description
        "WLAN identifier";
    }
    leaf wlan-profile-name {
      type string;
      description
        "WLAN profile name";
    }
    leaf data-usage {
      type uint64;
      description
        "Data usage";
    }
    leaf total-random-mac-clients {
      type uint32;
      description
        "Total random MAC clients";
    }
    leaf client-curr-state-l2auth {
      type uint32;
      description
        "Total number of clients in L2-authenticating state";
    }
    leaf client-curr-state-mobility {
      type uint32;
      description
        "Total number of clients in mobility state";
    }
    leaf client-curr-state-iplearn {
      type uint32;
      description
        "Total number of clients in iplearn state";
    }
    leaf curr-state-webauth-pending {
      type uint32;
      description
        "Total number of clients in webauth pending state";
    }
    leaf client-curr-state-run {
      type uint32;
      description
        "Total number of clients in run state";
    }
  }

  grouping st-emltd-ap-stats-info {
    description
      "AP join statistics";
    container ap-join-info {
      description
        "AP join information";
      uses wireless-ap-global-oper:st-ap-join-info;
    }
    container ap-discovery-info {
      description
        "AP discovery information";
      uses wireless-ap-global-oper:st-ap-discovery-info;
    }
    container dtls-sess-info {
      description
        "Data and Control DTLS phase statistics";
      uses wireless-ap-global-oper:st-dtls-sess-info-list;
    }
    leaf ap-disconnect-reason {
      type string;
      description
        "Last disconnect reason of AP";
    }
    leaf wtp-mac {
      type yang:mac-address;
      description
        "AP radio MAC address";
    }
    leaf reboot-reason {
      type wireless-types:spam-ap-reboot-reason;
      description
        "Reboot reason from AP";
    }
    leaf disconnect-reason {
      type wireless-types:spam-ap-disconnect-reason;
      description
        "Disconnect reason from AP";
    }
  }

  grouping st-ap-join-count-data {
    description
      "AP join count stats";
    leaf joined-aps-count {
      type uint32;
      description
        "Number of APs joined on wireless LAN controller";
    }
  }

  grouping ewlc-ap-state {
    description
      "AP state data";
    leaf is-ap-joined {
      type boolean;
      description
        "AP joined or not";
    }
    leaf timestamp {
      type yang:date-and-time;
      description
        "AP Joined or first disjoined timestamp";
    }
    leaf last-disconnect-timestamp {
      type yang:date-and-time;
      description
        "Last disconnect timestamp";
    }
    leaf disconnects {
      type uint32;
      description
        "Number of times AP disconnected";
    }
    leaf ap-disconnect-reason-str {
      type string;
      description
        "AP disconnect string";
    }
  }

  grouping st-emltd-all-aps-history {
    description
      "AP history data";
    leaf ap-name {
      type string;
      description
        "AP name";
    }
    leaf ethernet-mac {
      type yang:mac-address;
      description
        "Ethernet MAC address";
    }
    leaf wtp-mac {
      type yang:mac-address;
      description
        "AP WTP mac";
    }
    list ewlc-ap-state-ptr {
      description
        "AP state";
      uses wireless-ap-global-oper:ewlc-ap-state;
    }
  }

  grouping st-emltd-ap-location-stats {
    description
      "AP location stats";
    leaf location {
      type string;
      description
        "AP location name";
    }
    leaf clients-joined {
      type uint64;
      description
        "Number of clients joined";
    }
    leaf clients-on-11a {
      type uint64;
      description
        "Number of clients joined on 11a";
    }
    leaf clients-on-11b {
      type uint64;
      description
        "Number of clients joined on 11b";
    }
    leaf aps-joined {
      type uint64;
      description
        "Number of APs joined";
    }
  }

  container ap-global-oper-data {
    config false;
    description
      "Root container for AP operational data aggregated across wireless processes";
    list ap-history {
      key "ethernet-mac";
      description
        "AP history data";
      uses wireless-ap-global-oper:st-emltd-all-aps-history;
    }
    container ewlc-ap-stats {
      presence "ewlc-ap-stats";
      description
        "AP radio statistics";
      uses wireless-ap-global-oper:ewlc-ap-statistics;
    }
    container ap-img-predownload-stats {
      presence "ap-img-predownload-stats";
      description
        "AP image predownload stats";
      uses wireless-ap-global-oper:global-ap-stats;
    }
    list ap-location-stats {
      key "location";
      description
        "AP location statistics";
      uses wireless-ap-global-oper:st-emltd-ap-location-stats;
    }
    list ap-join-stats {
      key "wtp-mac";
      description
        "AP join statistics";
      uses wireless-ap-global-oper:st-emltd-ap-stats-info;
    }
    list wlan-client-stats {
      key "wlan-id";
      unique "wlan-profile-name";
      description
        "WLAN client stats";
      uses wireless-ap-global-oper:wlan-client-stats {
        refine "wlan-profile-name" {
          mandatory true;
        }
      }
    }
    container emltd-join-count-stat {
      presence "emltd-join-count-stat";
      description
        "AP join count statistics";
      uses wireless-ap-global-oper:st-ap-join-count-data;
    }
  }
}
