module Cisco-IOS-XE-dre-cp-oper {
  yang-version 1.1;
  namespace "http://cisco.com/ns/yang/Cisco-IOS-XE-dre-cp-oper";
  prefix dre-cp-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for dre operational data.
     Copyright (c) 2020, 2022 by Cisco Systems, Inc.
     All rights reserved.";

  revision 2022-11-01 {
    description
      "Update yang-version to 1.1";
    reference
      "1.1.0";
    cisco-semver:module-version "1.1.0";
  }
  revision 2021-03-01 {
    description
      "Initial revision";
    reference
      "1.0.0";
    cisco-semver:module-version "1.0.0";
  }

  grouping appqoe-dre-version-status {
    description
      "DRE version status";
    leaf recommended-version {
      type string;
      description
        "DRE version recommended to run";
    }
    leaf supported-regex {
      type string;
      description
        "DRE version regular expression - describes version support";
    }
    leaf installed-version {
      type string;
      description
        "DRE version currently installed";
    }
    leaf supported {
      type boolean;
      description
        "DRE supported flag - indicates if the installed DRE version is compatible with the supported version";
    }
  }

  container dre-cp-oper-data {
    config false;
    description
      "dre cp operational data";
    container appqoe-dre-version-status {
      presence "appqoe-dre-version-status";
      description
        "DRE version status";
      uses dre-cp-xe-oper:appqoe-dre-version-status;
    }
  }
}
