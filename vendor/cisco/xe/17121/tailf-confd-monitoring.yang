module tailf-confd-monitoring {
  namespace "http://tail-f.com/yang/confd-monitoring";
  prefix tfcm;

  import tailf-common-monitoring {
    prefix tfcg;
    revision-date 2021-09-02;
  }

  organization "Tail-f Systems";

  description
    "This module defines status objects for monitoring of ConfD.

     Copyright 2011-2021 Cisco Systems, Inc.
     All rights reserved.
     Permission is hereby granted to redistribute this file without
     modification.";

  revision 2021-09-09 {
    description
      "Released as part of ConfD-7.6.

       Imported latest tailf-common-monitoring module.";
  }

  revision 2019-10-30 {
    description
      "Released as part of ConfD-7.1.3.";
  }

  revision 2019-04-09 {
    description
      "Released as part of ConfD-7.1.

       Imported latest tailf-common-monitoring module.";
  }

  revision 2018-06-14 {
    description
      "Released as part of ConfD-6.7.

       Imported latest tailf-common-monitoring module.";
  }

  revision 2013-06-14 {
    description
      "Released as part of ConfD-4.3.

       Imported latest tailf-common-monitoring module.";
  }

  revision 2013-03-07 {
    description
      "Released as part of ConfD-4.2.

       Imported latest tailf-common-monitoring module.";
  }

  revision 2012-11-08 {
    description
      "Released as part of ConfD-4.1.

       Imported latest tailf-common-monitoring module.";
  }

  revision 2012-03-08 {
    description
      "Released as part of ConfD-3.9.

       Imported latest tailf-common-monitoring module.";
  }

  revision 2011-12-08 {
    description
      "Released as part of ConfD-3.8.

       Imported latest tailf-common-monitoring module.";
  }

  revision 2011-09-22 {
    description
      "Released as part of ConfD-3.7.";
  }

  container confd-state {
    config false;

    uses tfcg:common-monitoring-objects;
  }

}
