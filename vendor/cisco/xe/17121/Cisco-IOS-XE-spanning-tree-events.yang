module Cisco-IOS-XE-spanning-tree-events {
  yang-version 1.1;
  namespace "http://cisco.com/ns/yang/Cisco-IOS-XE-spanning-tree-events";
  prefix stp-ios-xe-events;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Spanning-Tree event notification.
     Copyright (c) 2023 by Cisco Systems, Inc.
     All rights reserved.";

  revision 2023-07-01 {
    description
      "Initial revision";
    reference
      "1.0.0";
    cisco-semver:module-version "1.0.0";
  }

  typedef stp-port-guard-type {
    type enumeration {
      enum stp-bpduguard {
        value 0;
        description
          "Spanning tree BPDU Guard";
      }
      enum stp-rootguard {
        value 1;
        description
          "Spanning tree Root Guard";
      }
      enum stp-loopguard {
        value 2;
        description
          "Spanning tree Loop Guard";
      }
    }
    description
      "Spanning tree port guard types";
  }

  typedef stp-port-guard-state {
    type enumeration {
      enum stp-guard-activated {
        value 0;
        description
          "The guard is activated on the port";
      }
      enum stp-guard-deactivated {
        value 1;
        description
          "The guard is deactivated on the port";
      }
    }
    description
      "Indicates if the guard is activated or deactivated on the port";
  }

  typedef stp-port-guard-action {
    type enumeration {
      enum stp-action-blocking-port {
        value 0;
        description
          "Port is placed in STP blocking state";
      }
      enum stp-action-unblocking-port {
        value 1;
        description
          "Port is taken out of STP blocking state";
      }
      enum stp-action-disabling-port {
        value 2;
        description
          "Port is placed in disabled state";
      }
      enum stp-action-disabling-vlan {
        value 3;
        description
          "VLAN is placed in disabled state";
      }
    }
    description
      "Indicates the guard action taken by STP on the port";
  }

  grouping stp-interface-guard-event {
    description
      "STP interface guard events";
    leaf if-name {
      type string;
      description
        "Reference to the STP ethernet interface";
    }
    leaf port-num {
      type uint16;
      description
        "The port number of the bridge port";
    }
    leaf guard-type {
      type stp-ios-xe-events:stp-port-guard-type;
      description
        "Interface spanning tree guard type";
    }
    leaf guard-state {
      type stp-ios-xe-events:stp-port-guard-state;
      description
        "Indicates the guard state of the port";
    }
    leaf action {
      type stp-ios-xe-events:stp-port-guard-action;
      description
        "Indicates the action taken by STP on the port";
    }
    choice mac-type-choice {
      description
        "mac type choice";
      case option-enabled {
        leaf client-mac {
          type yang:mac-address;
          description
            "MAC address of the BPDU source";
        }
      }
    }
    choice vlan-type-choice {
      description
        "VLAN type choice";
      case option-enabled {
        leaf vlan-id {
          type uint16;
          description
            "VLAN identifier associated with the port";
        }
      }
    }
    choice instance-type-choice {
      description
        "Instance type choice";
      case option-enabled {
        leaf mst-instance {
          type uint16;
          description
            "MST instance ID";
        }
      }
    }
  }

  notification stp-intf-guard-event {
    description
      "STP interface guard events notification";
    uses stp-ios-xe-events:stp-interface-guard-event;
  }
}
