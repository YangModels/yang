module Cisco-IOS-XE-voice {
  yang-version 1.1;
  namespace "http://cisco.com/ns/yang/Cisco-IOS-XE-voice";
  prefix ios-voice;

  import cisco-semver {
    prefix cisco-semver;
  }
  import Cisco-IOS-XE-native {
    prefix ios;
  }
  import ietf-inet-types {
    prefix inet;
  }
  import Cisco-IOS-XE-types {
    prefix ios-types;
  }
  include Cisco-IOS-XE-voice-register;
  include Cisco-IOS-XE-sip-ua;
  include Cisco-IOS-XE-voice-class;
  include Cisco-IOS-XE-voice-dspfarm;

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Voice Yang model.
     Copyright (c) 2016, 2018-2021 by Cisco Systems, Inc.
     All rights reserved.";

  revision 2022-11-01 {
    description
      "- Update yang-version to 1.1
       - Added voice class tls-cipher
       - Added tls-cipher to tls-profile
       - Added credentials configuration
       - Added package auth config to application
       - Added voice class codec g729br8 and gsmamr-nb
       - Added voice class video codec h261 and mpeg4
       - Added gw-accounting file
       - Added stun in voice service voip";
    cisco-semver:module-version "7.1.0";
  }
  revision 2022-07-01 {
    description
      "- Added sip options-keepalive under dial-peer";
    cisco-semver:module-version "7.0.0";
  }
  revision 2022-03-01 {
    description
      "- Added clid CLI to voice service pots
       - Added cn-san validation for client, bidirectional certificates and
         cn-san hostname list under tls-profile";
    cisco-semver:module-version "6.1.0";
  }
  revision 2021-11-01 {
    description
      "- Added dpg,stun usage,srtp crypto support under voice class
       - Added outbound-proxy, audio forced, block, call-route
         contact-passing, localhost, refer to passing
         to voice service voip - sip
       - Added conn-reuse, min-se,voice iec and voice cause-code config-support
       - Added rtp-port,voice statistics,gateway support
       - Added uc wsapi, uc secure wsapi and http client CLIs
       - Added application services support
       - Added voice class sip-profiles and sip-copylist
       - Added privacy, privacy-policy, requri-passing,
         update-callerid, url passing under voice service voip - sip
       - Added Opus, mp4a-latm, aacld, H263, H263+,
         H264 codec to voice class codec config
       - Added voice class sip-profiles and sip-copylist
       - Added voice class media, voice class sip-hdr-passthrulist and
         voice class sip-event-list config.
       - Added translation-profile CLI under trunk group x
       - Added registrar to sip-ua
       - Added support for voice class uri and e164-pattern-map
         for voice dial-peer
       - Added codecs - g723, g726, g728, clear-channel and isac
       - Added progress_ind, ip qos dscp, max-conn to dial-peer
       - Added anat to voice service voip and dial-peer
       - Added authentication and credentials to voice class tenant
       - Added address-hiding, emergency, silent-discard, asserted-id,
         midcall-signaling, remote-party-id, g729-annexb, redirection,
         set pstn-cause, set sip-status, host-registrar, sip-register configurations
       - Added sip-profiles, privacy, privacy-policy to dial-peer
       - Added provider xsvc and xcdr in  uc wsapi, xsvc in uc secure wsapi
       - Added early media update block,rtcp, media, session under
         voice service voip
       - Added early media update block, answer-address  and rtp payloads
         under dial-peer
       - Added error code override to voice service voip and dial-peer
       - Added call threshold, spike, treatment at global level
       - Added media profile configuration
       - Added media class configuration
       - Added media class configuration to dial-peer
       - Added global media profile, media class configurations
       - Added media-class configurations to dial-peer";
    cisco-semver:module-version "6.0.0";
  }
  revision 2021-07-01 {
    description
      "- Modified noan leaf to handle the no form properly in
         Cisco-IOS-XE-voice-register yang file
       - Editing error-message for leaf destination-pattern
       - Added corlist config support for voice dial-peers
       - Added num-exp and vad config support";
    cisco-semver:module-version "5.1.0";
  }
  revision 2021-03-01 {
    description
      "- Added down and up options to hunt-scheme
       - Added voice class server-group and voice class sip-options-keepalive
       - Added header-passing and rel1xx under voice service voip - sip
       - Changed dial-peer pattern and incoming called pattern";
    cisco-semver:module-version "5.0.0";
  }
  revision 2020-11-01 {
    description
      "- Added support for voip trace
       - Removed mins option from mode border-element license periodicity CLI
       - Changed the range of hours from 1..23 to 8..23";
    cisco-semver:module-version "4.0.0";
  }
  revision 2020-07-01 {
    description
      "- Updated fax and modem configuration
       - Updated sip bind command under dial-peer and global
       - Added voice class tenant
       - Added voice service voip related clis
       - Updated voice service voip configurations
       - Separate DSPFarm into a new module
       - Added dependency of pool configuration on global and max-pool configurations in Cisco-IOS-XE-voice-register yang file
       - Added dial-peer voip restriction for both bind and pass-thru
       - Marked the leaves ls-redundancy , hs-redundancy and version  as Obsolete
       - Removing the CLI dependency of allow-connection sip to sip for media bulk-stats under voice service voip";
    cisco-semver:module-version "3.0.0";
  }
  revision 2020-03-01 {
    description
      "- Added global voice configuration
       - Added trunk group configuration
       - Added the DSPFarm services
       - Added SCCP configuration";
    cisco-semver:module-version "2.1.0";
  }
  revision 2019-11-01 {
    description
      "- Added trunk group config
       - Added statement mandatory for leaves Cisco-IOS-XE-voice-register yang file";
    cisco-semver:module-version "2.0.0";
  }
  revision 2019-07-01 {
    description
      "- Establish semantic version baseline
       - Added voice class codec
       - Added voice service voip commands
       - Added the ip address trusted list option
       - Added dsapp line feature access code command
       - Added voice register mode for SRST
       - Added the dial-peer voice <tag> voip CLIs";
    cisco-semver:module-version "1.0.0";
  }
  revision 2018-10-23 {
    description
      "Added redundancy-group command in voice service voip command";
  }
  revision 2018-09-20 {
    description
      "Add SIP LINE CLI support";
  }
  revision 2017-02-07 {
    description
      "Initial revision";
  }

  typedef dscp-type {
    type union {
      type uint8 {
        range "0..63";
      }
      type enumeration {
        enum af11;
        enum af12;
        enum af13;
        enum af21;
        enum af22;
        enum af23;
        enum af31;
        enum af32;
        enum af33;
        enum af41;
        enum af42;
        enum af43;
        enum cs1;
        enum cs2;
        enum cs3;
        enum cs4;
        enum cs5;
        enum cs6;
        enum cs7;
        enum default;
        enum ef;
      }
    }
  }

  typedef prog-ind-enable-value {
    type enumeration {
      enum 1;
      enum 2;
      enum 8;
    }
  }

  typedef voice-cadence-type {
    type uint16 {
      range "50..10000";
    }
  }

  typedef config-application-service-name {
    type enumeration {
      enum ipsla-responder;
      enum RECAPP;
      enum CALLIndSs_SErviCe;
      enum RetrProxy;
      enum DSPREC;
      enum session;
      enum clid_authen_npw;
      enum app-b-acd-aa;
      enum clid_authen_collect;
      enum app-b-acd;
      enum clid_col_npw_3;
      enum clid_authen;
      enum clid_col_npw_npw;
      enum TOLLFRAUD_APP;
      enum clid_authen_col_npw;
      enum ipsla-testcall;
      enum AFW_THIRD_PARTY_CC;
      enum CTAPP;
      enum fax_hop_on;
      enum dsapp;
    }
  }

  typedef catlife-keepalive-options-type {
    type enumeration {
      enum 30;
      enum 70;
      enum 150;
      enum 310;
      enum 630;
      enum 1270;
      enum 2550;
    }
  }

  typedef config-answer-address {
    type string {
      pattern '(((\[)[(\^)0-9,A-F#*.?+%()-]*(\])|[(\^)0-9,A-F#*.?+%()-]*)*T?(\\$)?)' {
        error-message
          "Incorrect format for Answer Address regular expression pattern,
                   regular expression must be of the form ^[][^0-9,A-F#*.?+%()-]*T?(\\$)?$";
      }
    }
  }

  typedef config-bitrate {
    type uint32 {
      range "16000..128000";
    }
  }

  grouping media-nr-parameter-grouping {
    leaf intensity {
      description
        "noise reduction intensity";
      type uint8 {
        range "0..6";
      }
      default "2";
    }
    leaf noisefloor {
      description
        "min active threshold dB level";
      type int8 {
        range "-58..-20";
      }
      default "-48";
    }
  }

  grouping config-media-mode-grouping {
    container mode {
      choice mode-choice {
        case auto-case {
          leaf auto {
            description
              "Preset ASP sensitivity mode 0. Good tradeoff between ASP speed and false trigger rejection";
            type empty;
          }
        }
        case expert-case {
          container expert {
            description
              "Control of individual ASP sensitivity parameters, recommended for EXPERT debug use only.";
            presence "true";
            leaf holdover {
              description
                "ASP gate holdover time in ms";
              type uint16 {
                range "1..5000";
              }
            }
            leaf min-freq {
              description
                "for exempting low frequencies such as call progress tones";
              type uint16 {
                range "1..3999";
              }
            }
            leaf min-power {
              description
                "minimum power";
              type uint16 {
                range "1..2000";
              }
            }
            container peak-detect {
              description
                "set peak-to-total power ratio";
              leaf num {
                description
                  "numerator of 'peak-tone-energy to total-signal-energy ratio' detection threshold. Recommended value is 6";
                type uint8 {
                  range "1..100";
                }
              }
              leaf denom {
                description
                  "denominator of 'peak-tone-energy to total-signal-energy ratio' detection threshold. Recommended value is 10";
                type uint8 {
                  range "1..100";
                }
              }
            }
            container ramp-step {
              description
                "set ASP trigger ramp step size";
              leaf negative-step {
                description
                  "Decrement stepsize applied to ramp when detect criteria==false";
                type uint8 {
                  range "1..100";
                }
              }
              leaf positive-step {
                description
                  "Positive increment for detect criteria==true";
                type uint8 {
                  range "1..100";
                }
              }
            }
            leaf ramp-threshold {
              description
                "set ASP trigger threshold";
              type uint16 {
                range "1..2000";
              }
            }
            container vb-data-priority {
              description
                "allow fax/modem signals to pass through ASP";
              leaf hertz {
                description
                  "2100 Hz tones will be exempted from ASP suppression";
                type empty;
              }
            }
            leaf watch-freq {
              description
                "user list of frequencies for extra suppression";
              type string;
            }
            leaf watch-window {
              description
                "for watch freq window";
              type uint8 {
                range "1..100";
              }
            }
          }
        }
        case fast-case {
          leaf fast {
            description
              "Preset ASP sensitivity mode 2. Faster detection speed, but higher chance of false triggers";
            type empty;
          }
        }
        case slow-case {
          leaf slow {
            description
              "Preset ASP sensitivity mode 1. Slower detection speed for reduced chance of false triggers";
            type empty;
          }
        }
      }
    }
  }

  grouping config-media-grouping {
    container media {
      description
        "Media Commands";
      list class {
        description
          "media class";
        max-elements 10000;
        key "id";
        leaf id {
          description
            "Media class tag";
          type uint16 {
            range "1..10000";
          }
        }
        leaf description {
          description
            "Media profile specific description";
          type string {
            length "1..64";
          }
        }
        container asp {
          description
            "acoustic shock protection";
          choice media-class-asp-choice {
            case asp-profile-case {
              leaf profile {
                description
                  "select media profile ASP";
                type leafref {
                  path "/ios:native/ios-voice:media/ios-voice:profile/ios-voice:asp-nr/ios-voice:id";
                }
              }
            }
            case asp-parameter-case {
              container parameter {
                description
                  "enter submode to configure parameter";
                presence "true";
                uses config-media-mode-grouping {
                  refine "mode/mode-choice/expert-case/expert";
                }
              }
            }
          }
        }
        container nr {
          description
            "noise reduction";
          choice media-class-nr {
            case nr-profile-case {
              leaf profile {
                description
                  "media profile nr tag";
                type leafref {
                  path "/ios:native/ios-voice:media/ios-voice:profile/ios-voice:asp-nr/ios-voice:id";
                }
              }
            }
            case nr-parameter-case {
              container parameter {
                description
                  "enter submode to configure parameter";
                presence "true";
                uses media-nr-parameter-grouping;
              }
            }
          }
        }
        container police {
          description
            "police specific details";
          leaf profile {
            description
              "select media profile police";
            type leafref {
              path "/ios:native/ios-voice:media/ios-voice:profile/ios-voice:police/ios-voice:id";
            }
          }
        }
        container recorder {
          description
            "recorder specific details";
          choice media-class-recorder {
            container parameter {
              description
                "enter submode to configure parameter";
              presence "true";
              leaf-list media-recording {
                max-elements 5;
                ordered-by user;
                type uint32 {
                  range "1..1073741823";
                }
              }
            }
            container parameter-siprec-mode {
              container parameter {
                description
                  "Enter submode to configure parameter";
                presence "true";
                container siprec {
                  description
                    "INVITE is sent to recording server with application/rs-metadata SDP";
                  presence "true";
                  leaf-list media-recording {
                    description
                      "Set voice class recording parameters";
                    max-elements 5;
                    ordered-by user;
                    type uint32 {
                      range "1..1073741823";
                    }
                  }
                }
              }
            }
            container profile {
              description
                "select media profile recorder";
              leaf tag {
                description
                  "media profile recorder tag";
                type leafref {
                  path "/ios:native/ios-voice:media/ios-voice:profile/ios-voice:recorder/ios-voice:id";
                }
              }
              leaf siprec {
                description
                  "INVITE is sent to recording server with application/rs-metadata SDP";
                type empty;
              }
            }
          }
        }
        container stream-service {
          description
            "stream service specific details";
          leaf profile {
            description
              "select media profile stream-service";
            type leafref {
              path "/ios:native/ios-voice:media/ios-voice:profile/ios-voice:stream-service/ios-voice:id";
            }
          }
        }
        container video {
          description
            "video specific details";
          leaf profile {
            description
              "select media profile video";
            type leafref {
              path "/ios:native/ios-voice:media/ios-voice:profile/ios-voice:video/ios-voice:id";
            }
          }
        }
      }
      container profile {
        description
          "media profile";
        list asp-nr {
          description
            "acoustic shock protection and noise reduction";
          max-elements 10000;
          key "id";
          leaf id {
            description
              "Media profile tag";
            type uint16 {
              range "1..10000";
            }
          }
          leaf asp-nr {
            mandatory true;
            type enumeration {
              enum asp;
              enum nr;
            }
          }
          leaf description {
            description
              "Media profile specific description";
            type string {
              length "1..64";
            }
          }
          uses config-media-mode-grouping {
            when "asp-nr = 'asp'";
            refine "mode/mode-choice/expert-case/expert";
          }
          uses media-nr-parameter-grouping {
            when "asp-nr = 'nr'";
          }
        }
        list police {
          description
            "policing profile";
          max-elements 10000;
          key "id";
          leaf id {
            description
              "Media profile tag";
            type uint16 {
              range "1..10000";
            }
          }
          leaf description {
            description
              "Media profile specific description";
            type string {
              length "1..64";
            }
          }
          container overhead {
            description
              "overhead percentage above negotiated BW";
            leaf audio {
              description
                "Audio overhead percentage";
              type uint16 {
                range "0..50";
              }
            }
            leaf video {
              description
                "Video overhead percentage";
              type uint16 {
                range "0..50";
              }
            }
          }
          container violation {
            description
              "Number of violations before taking configured action";
            leaf count {
              description
                "Number of violations";
              type uint32 {
                range "0..200000";
              }
            }
            leaf action {
              description
                "Action taken after a violation is detected";
              type enumeration {
                enum disconnect;
                enum drop;
                enum ignore;
              }
            }
            leaf no-syslog {
              description
                "Block syslog generation";
              type empty;
            }
          }
        }
        list recorder {
          description
            "recorder profile";
          max-elements 10000;
          key "id";
          leaf id {
            description
              "Media profile tag";
            type uint16 {
              range "1..10000";
            }
          }
          leaf description {
            description
              "Media profile specific description";
            type string {
              length "1..64";
            }
          }
          container media-type {
            description
              "Type of Recording";
            leaf audio {
              description
                "Audio only forking";
              type empty;
            }
          }
          container proxy {
            description
              "Media recording proxy";
            container policy {
              description
                "Proxy policy";
              leaf mandatory {
                description
                  "Set proxy policy mandatory recorder tag";
                type uint32 {
                  range "1..1073741823";
                }
              }
            }
          }
          container media-recording {
            description
              "Set voice class recording parameters";
            choice recording-choice {
              case non-proxy-case {
                leaf-list recording-tags {
                  description
                    "Dial-peer tag to be matched on forked leg(max of 5 dial-peer tags)";
                  max-elements 5;
                  ordered-by user;
                  type uint32 {
                    range "1..1073741823";
                  }
                }
              }
              case proxy-case {
                container proxy {
                  description
                    "Set recording mode to proxy";
                  must '(count(secure/securetags) + count(nonsecuretags)) <= 5' {
                    error-message "A maximum of 5 secure and non-secure dial-peer tags may be configured.";
                  }
                  leaf-list nonsecuretags {
                    description
                      "Dial-peer tags to be matched for non-secure forks (max of 5 including secure forks)";
                    max-elements 5;
                    ordered-by user;
                    type uint32 {
                      range "1..1073741823";
                    }
                  }
                  container secure {
                    description
                      "Set secure proxy mode";
                    leaf-list securetags {
                      description
                        "Dial-peer tags to be matched for secure forks (max of 5 including non-secure forks)";
                      max-elements 5;
                      ordered-by user;
                      type uint32 {
                        range "1..1073741823";
                      }
                    }
                  }
                }
              }
            }
          }
        }
        list stream-service {
          description
            "stream service profile";
          max-elements 10000;
          key "id";
          leaf id {
            description
              "Media profile tag";
            type uint16 {
              range "1..10000";
            }
          }
          leaf description {
            description
              "Media profile specific description";
            type string {
              length "1..64";
            }
          }
          container connection {
            description
              "stream service connection";
            leaf calls-threshold {
              description
                "number of calls per connection";
              type uint8 {
                range "1..20";
              }
            }
            leaf idle-timeout {
              description
                "idle timeout in minutes";
              type uint8 {
                range "1..60";
              }
            }
          }
          container proxy {
            description
              "Websocket Proxy Server";
            choice stream-service-proxy {
              container host {
                description
                  "WebSocket proxy server hostname";
                leaf host-name {
                  description
                    "Specify hostname for proxy server";
                  type string;
                }
                leaf port {
                  description
                    "WebSocket proxy server port";
                  type uint16 {
                    range "0..65535";
                  }
                }
              }
              container ipv4 {
                description
                  "WebSocket proxy server IPV4 address";
                leaf address {
                  description
                    "Specify hostname for proxy server";
                  type inet:ipv4-address;
                }
                leaf port {
                  description
                    "WebSocket proxy server port";
                  type uint16 {
                    range "0..65535";
                  }
                }
              }
            }
          }
          container secure-ciphersuite {
            description
              "Set secure encryption ciphersuite";
            leaf aes-128-cbc-sha {
              description
                "Encryption tls_with_aes-128-cbc-sha2 ciphersuite";
              type empty;
            }
            leaf dhe-rsa-aes-cbc-sha2 {
              description
                "Encryption tls_rsa_with_cbc_sha2 ciphersuite";
              type empty;
            }
            leaf ecdhe-rsa-aes-cbc-sha2 {
              description
                "Encryption tls_rsa_with_aes-cbd-sha2 ciphersuite";
              type empty;
            }
            leaf rsa-aes-cbc-sha2 {
              description
                "Encryption tls_rsa_with_aes_cbc_sha2 ciphersuite";
              type empty;
            }
          }
          leaf source-ip {
            description
              "Local source IP address of the WebSocket connection";
            type inet:ipv4-address;
          }
        }
        list video {
          description
            "video profile";
          max-elements 10000;
          key "id";
          leaf id {
            description
              "Media profile tag";
            type uint16 {
              range "1..10000";
            }
          }
          leaf description {
            description
              "Media profile specific description";
            type string {
              length "1..64";
            }
          }
          leaf h264-packetization-mode {
            description
              "Offer only configured h264 packetization mode(0/1/2)";
            type uint8 {
              range "0..2";
            }
          }
          leaf monitor-ref-frames {
            description
              "Monitor Reference Frames/intra-frames";
            type empty;
          }
          container ref-frame-req {
            description
              "Set intra-frame request parameters";
            presence "true";
            leaf sip-info {
              description
                "intra-frame request using SIP Info message";
              type empty;
            }
            container rtcp {
              description
                "intra-frame request using RTCP";
              presence "true";
              leaf retransmit-interval {
                description
                  "retransmit interval (in msec)";
                type uint16 {
                  range "20..150";
                }
                default "50";
                units "miliseconds";
              }
              leaf retransmit-count {
                description
                  "retransmit count";
                type uint8 {
                  range "0..5";
                }
                default "0";
              }
            }
          }
        }
      }
    }
  }

  grouping progress-ind-options-grouping {
    choice progress-ind-choice {
      default "disable-case";
      case disable-case {
        leaf disable {
          description
            "Disable Progress Indicator for PROG/CONN/CALLPROC";
          type empty;
        }
      }
      case enable-case {
        leaf enable {
          description
            "Enable Progress Indicator for PROG/CONN/CALLPROC";
          type prog-ind-enable-value;
        }
      }
      case strip-case {
        container strip {
          description
            "Strip ANY Progress Indicator for ALERT";
          presence "true";
          leaf-list value {
            description
              "Value for PI (can only be 1, 2 or 8)";
            type prog-ind-enable-value;
          }
        }
      }
    }
  }

  grouping progress-ind-enable-disable-grouping {
    choice progress-ind-choice {
      default "disable-case";
      case disable-case {
        leaf disable {
          description
            "Disable Progress Indicator for PROG/CONN/CALLPROC";
          type empty;
        }
      }
      case enable-case {
        leaf enable {
          description
            "Enable Progress Indicator for PROG/CONN/CALLPROC";
          type prog-ind-enable-value;
        }
      }
    }
  }

  grouping config-voice-translation-profile-grouping {
    container translation-profile {
      description
        "Translation profile";
      leaf incoming {
        description
          "Translation Profile for incoming call leg";
        type leafref {
          path "/ios:native/ios-voice:voice/ios-voice:translation-profile/ios-voice:id";
        }
      }
      leaf outgoing {
        description
          "Translation Profile for outgoing call leg";
        type leafref {
          path "/ios:native/ios-voice:voice/ios-voice:translation-profile/ios-voice:id";
        }
      }
    }
  }

  grouping config-tls-sni-grouping {
    leaf description {
      description
        "Define the description of input options";
      type string {
        length "1..80";
      }
    }
    leaf trustpoint {
      description
        "Define the trustpoint name";
      type string {
        length "1..142";
      }
    }
    leaf client-vtp {
      description
        "Set Client Verification Trustpoint";
      type string {
        length "1..142";
      }
    }
    container cn-san {
      description
        "Certificate CN/SAN options";
      container validate {
        description
          "Enable CN/SAN validation for certificate";
        choice certificate-choice {
          case case-server {
            leaf server-config {
              description
                "Enable CN/SAN validation for server certificate";
              type empty;
            }
          }
          case case-client {
            leaf client {
              description
                "Enable CN/SAN validation for client certificate";
              type empty;
            }
          }
          case case-bidirectional {
            leaf bidirectional {
              description
                "Enable CN/SAN validation for both client and server certificate";
              type empty;
            }
          }
        }
        leaf server {
          status deprecated;
          description
            "Enable CN/SAN validation for server certificate (DEPRECATED)";
          type empty;
        }
      }
      list tag {
        description
          "Specify the tag of CN/SAN hostname/pattern list entry";
        max-elements 10;
        key "id";
        leaf id {
          type uint8 {
            range "1..10";
          }
        }
        leaf cn-san-name {
          description
            "Specify the CN/SAN hostname/pattern, valid values are a FQDN or *.<domain-name>";
          type string {
            length "3..128";
            pattern '((\*\.)?[A-Za-z0-9-]{1,63}\.)+[A-Za-z0-9-]{1,63}' {
              error-message "Valid values are a FQDN or \"*.<domain-name>\"";
            }
          }
        }
      }
    }
    container cipher {
      description
        "Cipher Settings";
      choice cipher-choice {
        case ecdsa-cipher {
          container ecdsa-cipher {
            description
              "Use ECDSA Ciphers";
            presence "true";
            leaf curve-size {
              description
                "Size of Elliptic Curve to use.";
              type enumeration {
                enum 384;
              }
            }
          }
        }
        case strict-cipher {
          leaf strict-cipher {
            description
              "Use only ciphers use by SIP standards";
            type empty;
          }
        }
        case tls-cipher {
          leaf cipher-id {
            description
              "Specify tls-cipher list tag";
            type leafref {
              path "/ios:native/ios-voice:voice/ios-voice:class/ios-voice:tls-cipher/ios-voice:id";
            }
          }
        }
      }
    }
    container sni {
      description
        "TLS Server Name Indication Extension";
      leaf send {
        description
          "Include SNI extension in outbound TLS connections";
        type empty;
      }
    }
  }

  grouping config-srtp-options-grouping {
    choice srtp-choice {
      case fallback-case {
        leaf fallback {
          description
            "Allow Secure calls fallback to non secure";
          type empty;
        }
      }
      case pass-through-case {
        leaf pass-thru {
          description
            "Allow transparent passthru of unsupported crypto suites";
          type empty;
        }
      }
    }
  }

  typedef config-codec-type {
    type enumeration {
      enum g711alaw {
        description
          "G.711 A Law 64000 bps (for E1)";
      }
      enum g711ulaw {
        description
          "G.711 u Law 64000 bps (for T1)";
      }
    }
  }

  grouping config-pass-through-grouping {
    leaf pass-through {
      description
        "Use an audio codec for fax transport";
      type config-codec-type;
    }
  }

  grouping config-fax-protocol-grouping {
    choice protocol-choice {
      case none-case {
        leaf none {
          description
            "Disable fax transport";
          type empty;
        }
      }
      case pass-through-case {
        uses config-pass-through-grouping;
      }
      case t38-case {
        container t38 {
          description
            "Use T.38 protocol";
          presence "true";
          leaf nse {
            description
              "Use Cisco NSEs to signal T.38 mode switch";
            type empty;
          }
          leaf force {
            description
              "Unconditionally use Cisco NSEs to signal T.38 mode switch";
            when '../nse';
            type empty;
          }
          leaf version {
            description
              "T.38 fax version";
            type enumeration {
              enum 0;
              enum 3;
            }
            default "0";
          }
          container redundancy-config {
            leaf ls-redundancy {
              description
                "t38 low speed redundancy";
              type uint8 {
                range "0..5";
              }
              default "0";
            }
            leaf hs-redundancy {
              description
                "t38 high speed redundancy";
              when '../ls-redundancy';
              type uint8 {
                range "0..2";
              }
              default "0";
            }
          }
          container fallback {
            description
              "fax transport to use if T.38 unsupported on far end";
            choice protocol-choice {
              case none-case {
                leaf none {
                  description
                    "No fallback";
                  type empty;
                }
              }
              case pass-through-case {
                uses config-pass-through-grouping;
              }
            }
          }
        }
      }
    }
  }

  grouping config-modem-grouping {
    choice modem-choice {
      case passthrough-case {
        container passthrough {
          description
            "Pass modem traffic via clear channel";
          container nse {
            description
              "Use Named Signaling Events (NSE)";
            choice nse-choice {
              case codec-case {
                leaf codec {
                  description
                    "Codec selections for upspeed";
                  type config-codec-type;
                }
              }
              case payload-type-case {
                container payload-type-conifg {
                  leaf payload-type {
                    description
                      "Payload type value";
                    type uint8 {
                      range "98..117";
                    }
                    default "100";
                  }
                  leaf codec {
                    description
                      "Codec selections for upspeed";
                    type config-codec-type;
                  }
                }
              }
            }
          }
        }
      }
      case relay-case {
        container relay {
          description
            "Relay modem traffic between the gateways";
          choice relay-choice {
            case gateway-xid-case {
              container gateway-xid {
                description
                  "Do XID negotiation between gateways";
                presence "true";
              }
            }
            case nse-case {
              container nse {
                description
                  "Use Named Signaling Events (NSE)";
                choice nse-choice {
                  case codec-case {
                    container codec-gw-controller {
                      leaf codec {
                        description
                          "Codec selections for upspeed";
                        type config-codec-type;
                      }
                      leaf gw-controlled {
                        description
                          "GW Controlled MR";
                        type empty;
                      }
                    }
                  }
                  case payload-type-case {
                    container payload-type-config {
                      leaf payload-type {
                        description
                          "Payload type value";
                        type uint8 {
                          range "98..117";
                        }
                        default "100";
                      }
                      leaf codec {
                        description
                          "Codec selections for upspeed";
                        type config-codec-type;
                      }
                      leaf gw-controlled {
                        description
                          "GW Controlled MR";
                        type empty;
                      }
                    }
                  }
                }
              }
            }
            case sprt-case {
              container sprt {
                description
                  "Configure SPRT (Simple packet relay transport)";
                leaf retries {
                  description
                    "Maximum retries for an SPRT packet";
                  type uint32 {
                    range "6..30";
                  }
                }
              }
            }
            case sse-case {
              container sse {
                description
                  "SSE negotiation parameters for modem relay (Applicable only to SIP)";
                leaf v150mer {
                  description
                    "Enable V 150.1 MER (Applicable only to SIP)";
                  type empty;
                }
              }
            }
          }
        }
      }
    }
  }

  grouping config-port-range-grouping {
    container port-range {
      description
        "Port range";
      leaf min-port {
        description
          "Minimum port number";
        must '. mod 2 = 0' {
          error-message "Minimum port value must be even";
        }
        type uint16 {
          range "8000..48198";
        }
      }
      leaf max-port {
        description
          "Maximum port number";
        must '. mod 2 = 0' {
          error-message "Maximum port value must be even";
        }
        must '../min-port <= .' {
          error-message "Maximum port must be greater than or equal to minimum port";
        }
        type uint16 {
          range "8000..48198";
        }
      }
    }
  }

  grouping config-extended-min-max-range-grouping {
    leaf min-port {
      description
        "Start media address extended port";
      type uint16 {
        range "5500..65498";
      }
    }
    leaf max-port {
      description
        "Stop media address extended port";
      must '../min-port <= .' {
        error-message "Starting port is greater than ending port";
      }
      type uint16 {
        range "5500..65498";
      }
    }
  }

  grouping config-extended-port-range-grouping {
    container port-range-extended {
      container port-range {
        description
          "Media address port range";
        presence "true";
        list port {
          max-elements 10;
          key "min-port max-port";
          uses config-extended-min-max-range-grouping;
        }
      }
    }
  }

  grouping config-uc-wsapi-remote-url {
    list remote-url {
      key "url-index";
      unique "url-string";
      leaf url-index {
        type uint16 {
          range "1..8";
        }
      }
      leaf url-string {
        type string;
      }
    }
    leaf shutdown {
      description
        "shutdown";
      type boolean;
      default "false";
    }
  }

  grouping config-voice-grouping {
    container voice {
      description
        "Global voice configuration";
      leaf vrf {
        description
          "Voice VRF";
        must '/ios:native/ios:vrf/ios:definition[ios:name=current()] or /ios:native/ios:ip/ios:vrf[ios:name=current()]' {
          error-message "VRF must be created 1st, deleted last";
        }
        type string {
          length "1..32";
        }
      }
      container hpi {
        description
          "Host port interface";
        container capture {
          description
            "HPI control message capture";
          leaf buffer {
            description
              "HPI control message capture buffer size";
            type int32 {
              range "880..60000000";
            }
          }
          leaf destination {
            description
              "HPI control message capture data file destination";
            type string {
              pattern '.*';
              length "1..1023";
            }
          }
        }
      }
      container iec {
        description
          "Configure Internal Error Code behavior";
        leaf syslog {
          description
            "Enable syslog reporting";
          type empty;
        }
      }
      leaf cause-code {
        description
          "Sets the internal Q850 cause code mapping";
        type empty;
      }
      container pcm {
        description
          "PCM Capture";
        container capture {
          description
            "PCM control message capture";
          leaf buffer {
            description
              "configure PCM capture buffer number";
            type int32 {
              range "0..200000";
            }
            default "0";
          }
          leaf destination {
            description
              "configure destination target for PCM capture data file";
            type string {
              pattern '.*';
              length "1..1023";
            }
          }
          leaf on-demand-trigger {
            description
              "configure PCM capture user trigger on-demand";
            type empty;
          }
          container user-trigger-string {
            description
              "configure PCM user trigger string";
            leaf trigger-start-string {
              description
                "configure user trigger start string up to 16 characters";
              type string {
                pattern '[0-9#\*]{1,16}';
              }
            }
            leaf trigger-stop-string {
              description
                "configure user trigger stop string up to 16 characters";
              type string {
                pattern '[0-9#\*]{1,16}';
              }
            }
            leaf stream {
              description
                "PCM stream bitmap in hex";
              type string {
                pattern '[1-9A-F][0-9A-F]{0,6}';
              }
            }
            leaf duration {
              description
                "PCM capture duration in second";
              type uint8 {
                range "0..255";
              }
            }
          }
        }
      }
      list translation-rule {
        description
          "Translation Rule configuration commands";
        key "id";
        leaf id {
          type uint32 {
            range "1..1073741823";
          }
        }
        list rule {
          description
            "Translation rule";
          key "id";
          leaf id {
            description
              "Translation rule number";
            type uint8 {
              range "1..100";
            }
          }
          choice rule-choice {
            leaf reject {
              description
                "Call block rule";
              type string {
                pattern '.*';
                length "1..66";
              }
            }
            leaf matching-replacement-pattern {
              description
                "Matching and replacement pattern, i.e., /xxx/ /xxx/";
              type string {
                pattern '.*';
                length "1..133";
              }
            }
          }
        }
      }
      list translation-profile {
        description
          "Translation profile configuration commands";
        key "id";
        leaf id {
          type string {
            length "1..31";
          }
        }
        container translate {
          description
            "Specify numbers that should be translated";
          leaf called {
            description
              "Translation rule for the called-number";
            type leafref {
              path "../../../translation-rule/id";
            }
          }
          leaf calling {
            description
              "Translation rule for the calling-number";
            type leafref {
              path "../../../translation-rule/id";
            }
          }
        }
      }
      container class {
        description
          "Control parameters class";
        uses config-voice-class-tenant-grouping;
        uses config-voice-class-server-group-grouping;
        uses config-voice-class-e164-pattern-map-grouping;
        uses config-voice-class-sip-options-keepalive-grouping;
        uses config-voice-class-uri-grouping;
        uses config-voice-class-dpg-grouping;
        uses config-voice-class-stun-usage-grouping;
        uses config-voice-class-srtp-crypto-grouping;
        uses config-voice-class-sip-profiles-grouping;
        uses config-voice-class-tls-cipher-grouping;
        list custom-cptone {
          description
            "Configuration of customized Call Progress Tones";
          key "id";
          leaf id {
            type string {
              length "1..20";
            }
          }
          list dualtone {
            description
              "Configure call progress dual tones";
            key "id";
            leaf id {
              type enumeration {
                enum busy;
                enum conference;
                enum disconnect;
                enum number-unobtainable;
                enum out-of-service;
                enum reorder;
                enum ringback;
              }
            }
            leaf-list frequency {
              description
                "Configure dual tone frequencies";
              max-elements 2;
              type uint16 {
                range "300..3600";
              }
            }
            container cadence {
              description
                "Configure dual tone cadences";
              leaf first-on-cadence {
                description
                  "First On cadence";
                type voice-cadence-type;
              }
              leaf first-off-cadence {
                description
                  "First Off cadence";
                type voice-cadence-type;
              }
              leaf second-on-cadence {
                description
                  "Second On cadence";
                type voice-cadence-type;
              }
              leaf second-off-cadence {
                description
                  "First Off cadence";
                type voice-cadence-type;
              }
              leaf third-on-cadence {
                description
                  "Third On cadence";
                type voice-cadence-type;
              }
              leaf third-off-cadence {
                description
                  "Third Off cadence";
                type voice-cadence-type;
              }
              leaf fourth-on-cadence {
                description
                  "Fourth On cadence";
                type voice-cadence-type;
              }
              leaf fourth-off-cadence {
                description
                  "Fourth Off cadence";
                type voice-cadence-type;
              }
            }
          }
        }
        list dualtone-detect-params {
          description
            "Dual tone detection parameters";
          key "id";
          leaf id {
            description
              "Voice class dual tone detect parameter tag";
            type uint32 {
              range "1..10000";
            }
          }
          leaf cadence-variation {
            description
              "Cadence variation allowed";
            type uint8 {
              range "0..200";
            }
            default "10";
          }
          leaf freq-max-delay {
            description
              "Timing difference between two frequencies";
            type uint8 {
              range "10..100";
            }
            default "10";
          }
          leaf freq-max-deviation {
            description
              "Maximum frequency deviation allowed for each frequency";
            type uint8 {
              range "10..125";
            }
            default "10";
          }
          leaf freq-max-power {
            description
              "Absolute value of upper limit for tone power per frequency";
            type uint8 {
              range "0..20";
            }
            default "10";
          }
          leaf freq-min-power {
            description
              "Absolute value of lower limit for tone power per frequency";
            type uint8 {
              range "10..35";
            }
            default "30";
          }
          leaf freq-power-twist {
            description
              "The difference between the power of two frequencies";
            type uint8 {
              range "0..15";
            }
            default "6";
          }
        }
        list codec {
          description
            "Set codec global parameters";
          max-elements 10000;
          key "codec-tag";
          leaf codec-tag {
            description
              "Voice class codec tag";
            type uint16 {
              range "1..10000";
            }
          }
          container codec {
            description
              "Set class codec parameters";
            list preference {
              description
                "Set priority order for using this codec";
              max-elements 24;
              key "preference-tag";
              unique "codec-type";
              leaf preference-tag {
                description
                  "Priority order (1 = Highest)";
                type uint8 {
                  range "1..24";
                }
              }
              leaf codec-type {
                type enumeration {
                  enum g711ulaw;
                  enum g711alaw;
                  enum g729r8;
                  enum ilbc;
                  enum g722-64;
                  enum aacld;
                  enum mp4a-latm;
                  enum opus;
                  enum g723ar53;
                  enum g723ar63;
                  enum g723r53;
                  enum g723r63;
                  enum g726r16;
                  enum g726r24;
                  enum g726r32;
                  enum g728;
                  enum clear-channel;
                  enum isac;
                  enum g729br8;
                  enum gsmamr-nb;
                }
              }
              leaf bytes {
                description
                  "Specify number of voice data bytes per frame";
                when "../codec-type = 'g711alaw' or ../codec-type = 'g711ulaw' or ../codec-type = 'g722-64' or ../codec-type = 'clear-channel'";
                type enumeration {
                  enum 80;
                  enum 160;
                  enum 240;
                }
                default "160";
              }
              leaf profile {
                description
                  "Specify the profile tag configured in global codec profile";
                when "../codec-type = 'opus' or ../codec-type = 'mp4a-latm' or ../codec-type = 'aacld'";
                type uint32 {
                  range "1..1000000";
                }
              }
              container fmtp-select-one {
                description
                  "Offer only one format of multi-format codec (first by default";
                when "../codec-type = 'mp4a-latm'";
                presence "true";
                choice rate {
                  case bitrate-case {
                    leaf bitrate {
                      description
                        "Exact match of bitrate value in FMTP paramater";
                      type config-bitrate;
                    }
                  }
                  case max-bitrate-case {
                    leaf max-bitrate {
                      description
                        "Max bitrate allowed";
                      type config-bitrate;
                    }
                  }
                }
              }
              container g729r8-conf {
                when "../codec-type = 'g729r8' or ../codec-type = 'g728' or ../codec-type = 'g729br8'";
                leaf bytes {
                  description
                    "Specify number of voice data bytes per frame";
                  type enumeration {
                    enum 10;
                    enum 20;
                    enum 30;
                    enum 40;
                    enum 50;
                    enum 60;
                    enum 70;
                    enum 80;
                    enum 90;
                    enum 100;
                    enum 110;
                    enum 120;
                    enum 130;
                    enum 140;
                    enum 150;
                    enum 160;
                    enum 170;
                    enum 180;
                    enum 190;
                    enum 200;
                    enum 210;
                    enum 220;
                    enum 230;
                    enum 240;
                  }
                }
              }
              container mode {
                description
                  "Specify mode value (independent or adaptive)";
                when "../codec-type = 'isac'";
                leaf value {
                  type enumeration {
                    enum adaptive;
                    enum independent;
                  }
                }
                container bit-rate {
                  description
                    "Set target bit rate (10 to 32kbps)";
                  leaf value {
                    type uint16 {
                      range "10000..32000";
                    }
                    default "32000";
                  }
                }
                container framesize {
                  description
                    "Set framesize (30ms or 60ms)";
                  leaf value {
                    type enumeration {
                      enum 30 {
                        description
                          "Framesize 30ms";
                      }
                      enum 60 {
                        description
                          "Framesize 60ms";
                      }
                    }
                    default "30";
                  }
                }
                leaf fixed {
                  description
                    "Force fixed framesize (for adaptive mode only)";
                  when "../value = 'adaptive'";
                  type empty;
                }
              }
              container g723-g726-conf {
                when "../codec-type = 'g723ar53' or ../codec-type = 'g723r53' or ../codec-type = 'g726r16'";
                leaf bytes {
                  description
                    "Specify number of voice data bytes per frame";
                  type enumeration {
                    enum 20;
                    enum 40;
                    enum 60;
                    enum 80;
                    enum 100;
                    enum 120;
                    enum 140;
                    enum 160;
                    enum 180;
                    enum 200;
                    enum 220;
                    enum 240;
                  }
                }
              }
              container g723-conf {
                when "../codec-type = 'g723ar63' or ../codec-type = 'g723r63'";
                leaf bytes {
                  description
                    "Specify number of voice data bytes per frame";
                  type enumeration {
                    enum 24;
                    enum 48;
                    enum 72;
                    enum 96;
                    enum 120;
                    enum 144;
                    enum 168;
                    enum 192;
                    enum 216;
                    enum 240;
                  }
                }
              }
              container g726r24-conf {
                when "../codec-type = 'g726r24'";
                leaf bytes {
                  description
                    "Specify number of voice data bytes per frame";
                  type enumeration {
                    enum 30;
                    enum 60;
                    enum 90;
                    enum 120;
                    enum 150;
                    enum 180;
                    enum 210;
                    enum 240;
                  }
                }
              }
              container g726r32-conf {
                when "../codec-type = 'g726r32'";
                leaf bytes {
                  description
                    "Specify number of voice data bytes per frame";
                  type enumeration {
                    enum 40;
                    enum 80;
                    enum 120;
                    enum 160;
                    enum 200;
                    enum 240;
                  }
                }
              }
              container ilbc-conf {
                when "../codec-type = 'ilbc'";
                container mode {
                  description
                    "Specify the value of the mode";
                  choice mode-choice {
                    case twenty-case {
                      container twenty {
                        leaf bytes {
                          description
                            "Specify number of voice data bytes";
                          type enumeration {
                            enum 38;
                            enum 76;
                            enum 114;
                            enum 152;
                            enum 190;
                            enum 228;
                          }
                        }
                      }
                    }
                    case thirty-case {
                      container thirty {
                        leaf bytes {
                          description
                            "Specify number of voice data bytes";
                          type enumeration {
                            enum 50;
                            enum 100;
                            enum 150;
                            enum 200;
                          }
                        }
                      }
                    }
                  }
                }
              }
              container gsmamr-nb-conf {
                when "(../codec-type = 'gsmamr-nb') and
                      (/ios:native/voice/service[type='voip']/allow-connections/sip/to/sip)";
                container encap {
                  description
                    "RTP encapsulation type to be used";
                  leaf rfc3267 {
                    description
                      "RTP encapsulation mentioned in RFC3267(default)";
                    type empty;
                  }
                }
                container frame-format-conf {
                  when '../encap/rfc3267';
                  leaf frame-format {
                    description
                      "Specify the frame format";
                    type enumeration {
                      enum bandwidth-efficient;
                      enum octet-aligned;
                    }
                  }
                  leaf compute-crc {
                    when "../frame-format = 'octet-aligned'";
                    type enumeration {
                      enum crc;
                      enum no-crc;
                    }
                  }
                }
                container modes-conf {
                  leaf modes {
                    description
                      "Specify the supported modes";
                    type int8 {
                      range "0..7";
                    }
                  }
                }
                container packetization-period-conf {
                  leaf packetization-period {
                    description
                      "Specify the packetization period";
                    type enumeration {
                      enum 20;
                    }
                    default "20";
                  }
                }
              }
            }
          }
          container video {
            description
              "Video setup for voice class";
            list codec {
              description
                "Video codec setup";
              key "codec-type";
              leaf codec-type {
                type enumeration {
                  enum h263;
                  enum h263+;
                  enum h264;
                  enum h261;
                  enum mpeg4;
                }
              }
              leaf profile {
                description
                  "Specify the profile tag configured in global codec profile";
                when "../codec-type = 'h263' or ../codec-type = 'h263+' or ../codec-type = 'h264'";
                type uint32 {
                  range "1..1000000";
                }
              }
            }
          }
        }
        uses config-voice-class-media-grouping;
        uses config-voice-class-sip-hdr-passthrulist-grouping;
        uses config-voice-class-sip-event-list-grouping;
        list tls-profile {
          description
            "Associate a tls-profile";
          key "id";
          leaf id {
            type uint16 {
              range "1..10000";
            }
          }
          uses config-tls-sni-grouping;
        }
        list sip-copylist {
          description
            "Configure list of entities to be sent to peer leg";
          max-elements 10000;
          key "id";
          leaf id {
            description
              "Voice class sip-copylist tag";
            type uint32 {
              range "1..10000";
            }
          }
          uses config-sip-copylist-header-grouping;
        }
      }
      list service {
        description
          "Global packet telephony service commands";
        key "type";
        leaf type {
          type enumeration {
            enum pots;
            enum saf;
            enum voatm;
            enum vofr;
            enum voip;
          }
        }
        container clid-pots {
          when "../type = 'pots'";
          container clid {
            description
              "Global setting for caller ID dtmf codes";
            leaf dtmf-codes {
              description
                "3 chars [0-9A-D*#] for start, redirect, end codes";
              type string {
                pattern '[0-9A-D\*#]{3}' {
                  error-message "3 input chars must be in [0-9A-D*#]";
                }
              }
            }
          }
        }
        container stun {
          description
            "STUN configuration commands";
          when "../type = 'voip'";
          presence "true";
          container stun {
            description
              "Stun parameters";
            container flowdata {
              description
                "FlowData parameters";
              container agent-id-config {
                leaf agent-id {
                  description
                    "Set Authorization Agent Id";
                  type uint8;
                }
                leaf boot-count {
                  description
                    "Set boot count";
                  type uint16;
                  default "0";
                }
              }
              container shared-secret-enc {
                description
                  "Set Shared-secret Key";
                leaf encryption {
                  must '../password-string';
                  type enumeration {
                    enum 0 {
                      description
                        "Specifies an UNENCRYPTED shared secret key";
                    }
                    enum 6 {
                      description
                        "Specifies an ENCRYPTED shared secret key";
                    }
                    enum 7 {
                      description
                        "Specifies an ENCRYPTED shared secret key";
                    }
                  }
                }
                leaf password-string {
                  must '../encryption';
                  type string {
                    length "12..162";
                  }
                }
              }
              container shared-secret {
                status deprecated;
                description
                  "Set Shared-secret Key (DEPRECATED)";
                choice shared-secret-choice {
                  status deprecated;
                  case zero-case {
                    status deprecated;
                    leaf zero {
                      status deprecated;
                      description
                        "Specifies an UNENCRYPTED shared secret key (DEPRECATED)";
                      type string {
                        length "12..80";
                      }
                    }
                  }
                  case six-case {
                    status deprecated;
                    leaf six {
                      status deprecated;
                      description
                        "Specifies an ENCRYPTED shared secret key (DEPRECATED)";
                      type string {
                        length "26..162";
                      }
                    }
                  }
                }
              }
              container catlife-config {
                leaf catlife {
                  description
                    "Set how often a new CAT token is generated(default value 1270 = (21 min 10 sec))";
                  type catlife-keepalive-options-type;
                  default "1270";
                }
                leaf keepalive {
                  description
                    "Set how often keepalives are sent (default 30 sec)";
                  must '. <= ../catlife' {
                    error-message "keepalive should be less than or equal to catlife";
                  }
                  type catlife-keepalive-options-type;
                  default "30";
                }
              }
            }
            leaf transaction-timer {
              description
                "Set STUN Transaction Timer";
              type uint16 {
                range "10..50";
              }
              default "10";
            }
          }
        }
        container clid {
          description
            "Caller ID option";
          when "../type = 'voip'";
          leaf network-provided {
            description
              "Set screen ind in oct3a to network-provided for SIP calls";
            type empty;
          }
          container strip {
            description
              "Remove calling party name and number when PI restricted for SIP";
            container pi-restrict {
              description
                "Remove calling party name and number when PI restricted for SIP";
              leaf all {
                description
                  "Remove calling party name and number when PI restricted for SIP";
                type empty;
              }
            }
          }
          container substitute {
            description
              "Sub calling num for missing display name for SIP if PI allows";
            leaf name {
              description
                "Sub calling num for missing display name for SIP if PI allows";
              type empty;
            }
          }
        }
        leaf dtmf-interworking {
          description
            "Dtmf Interworking";
          when "../type = 'voip'";
          type enumeration {
            enum rtp-nte {
              description
                "Digit-begin and digit-end events of RTP NTE packets are sent separately";
            }
            enum standard {
              description
                "RFC compliance RTP NTE packets";
            }
          }
        }
        leaf gcid {
          description
            "Enable Global Call Identification for voip";
          when "../type = 'voip'";
          type empty;
        }
        container notify {
          description
            "send facility indication to application";
          when "../type = 'voip'";
          container redirect {
            description
              "send redirect notification to application for handling";
            leaf ip2ip {
              description
                "send redirect notification to application for ip-to-ip calls";
              type boolean;
              default "true";
            }
            leaf ip2pots {
              description
                "send redirect notification to application for ip-to-pots calls";
              type empty;
            }
          }
        }
        container redirect {
          description
            "voip call redirect";
          when "../type = 'voip'";
          leaf ip2ip {
            description
              "Redirect IP-to-IP calls";
            type empty;
          }
        }
        container rtp-media-loop {
          description
            "Global setting for rtp media loop count";
          when "../type = 'voip'";
          leaf count {
            description
              "specify the max count";
            type uint8 {
              range "6..21";
            }
          }
        }
        container rtp-ssrc {
          description
            "Global setting to handle multiple RTP SSRC's";
          when "../type = 'voip'";
          leaf multiplex {
            description
              "RTCP multiplexing with RTP";
            when "/ios:native/voice/service[type='voip']/allow-connections/sip/to/sip";
            type empty;
          }
        }
        container srtp {
          description
            "Allow Secure calls";
          when "../type = 'voip'";
          presence "true";
          uses config-srtp-options-grouping;
        }
        leaf shutdown {
          description
            "Stop VoIP services gracefully without dropping active calls";
          when "../type = 'voip'";
          type boolean;
          default "false";
        }
        container media-recording {
          description
            "Media recording commands";
          when "../type = 'pots'";
          leaf licenses {
            description
              "Allocate media recording licenses";
            type uint16 {
              range "1..500";
            }
          }
        }
        container allow-connections {
          description
            "Allow call connection types";
          when "../type = 'voip'";
          container sip {
            description
              "from-type sip";
            container to {
              description
                "to";
              leaf sip {
                description
                  "to-type sip";
                type empty;
              }
            }
          }
        }
        container media {
          description
            "Global media setting for voip calls";
          leaf bulk-stats {
            description
              "Retrieve bulk statistics is enabled";
            type empty;
          }
          leaf statistics {
            description
              "Media statistics is enabled";
            when "/ios:native/voice/service[type='voip']/allow-connections/sip/to/sip";
            type empty;
          }
          leaf disable-detailed-stats {
            description
              "Disable detailed stats collection about the calls present";
            type empty;
          }
        }
        container media-address {
          description
            "Voice Media IP Address Range";
          when "../type = 'voip'";
          container range {
            description
              "Address range";
            must 'count(./ipv4) + count(./ipv6) <= 10' {
              error-message "Exceeds maximum number of allowed address ranges";
            }
            list ipv4 {
              key "start-ipv4-address end-ipv4-address";
              leaf start-ipv4-address {
                description
                  "Enter start ip address";
                type inet:ipv4-address;
              }
              leaf end-ipv4-address {
                description
                  "Enter end ip address";
                type inet:ipv4-address;
              }
              uses config-port-range-grouping {
                refine "port-range";
              }
              uses config-extended-port-range-grouping;
            }
            list ipv6 {
              key "start-ipv6-address end-ipv6-address";
              leaf start-ipv6-address {
                description
                  "Start IPv6 address";
                type inet:ipv6-address;
              }
              leaf end-ipv6-address {
                description
                  "End IPv6 address";
                type inet:ipv6-address;
              }
              uses config-port-range-grouping {
                refine "port-range";
              }
              uses config-extended-port-range-grouping;
            }
          }
          list voice-vrf {
            description
              "voice vrf id";
            max-elements 100;
            key "vrfname";
            leaf vrfname {
              description
                "WORD;;VRF name";
              must '/ios:native/ios:vrf/ios:definition[ios:name=current()] or /ios:native/ios:ip/ios:vrf[ios:name=current()]' {
                error-message "VRF must be created 1st, deleted last";
              }
              type string;
            }
            uses config-port-range-grouping {
              refine "port-range";
            }
            uses config-extended-port-range-grouping;
          }
        }
        container rtp-port {
          description
            "Global setting for rtp port range";
          when "../type = 'voip'";
          container range {
            description
              "Port range";
            uses config-port-range-grouping {
              refine "port-range";
            }
            container extended {
              description
                "extended ports";
              uses config-extended-min-max-range-grouping {
                refine "min-port" {
                  must '. mod 2 = 0' {
                    error-message "min_port value must be even";
                  }
                }
                refine "max-port" {
                  must '. mod 2 = 0' {
                    error-message "max_port value must be even";
                  }
                }
              }
            }
          }
        }
        leaf cpa {
          description
            "Enable Call Progress Analysis for voip calls";
          when "../type = 'voip'";
          type boolean;
          default "true";
        }
        container cpa-config {
          when "../cpa = 'true' and ../type = 'voip'";
          container cpa {
            description
              "Enable Call Progress Analysis for voip calls";
            container threshold {
              description
                "Configure cpa thresholds";
              leaf active-signal {
                description
                  "Active signal threshold related to measured noise floor level";
                type enumeration {
                  enum 9db;
                  enum 12db;
                  enum 15db;
                  enum 18db;
                  enum 21db;
                }
                default "15db";
              }
              container noise-level {
                description
                  "Noise floor level limits";
                leaf max {
                  description
                    "Maximum noise floor level";
                  type enumeration {
                    enum -45dBm0;
                    enum -50dBm0;
                    enum -55dBm0;
                    enum -60dBm0;
                  }
                  default "-50dBm0";
                }
                leaf min {
                  description
                    "Minimum noise floor level";
                  type enumeration {
                    enum -55dBm0;
                    enum -60dBm0;
                    enum -65dBm0;
                    enum -70dBm0;
                  }
                  default "-60dBm0";
                }
              }
              container term-tone {
                description
                  "Answering machine terminating tone thresholds";
                leaf min-duration {
                  description
                    "Minimum answering machine terminating tone duration in ms";
                  type uint16 {
                    range "80..2000";
                  }
                  units "miliseconds";
                  default "80";
                }
                leaf min-freq {
                  description
                    "Minimum answering machine terminating tone duration in Hz";
                  type uint16 {
                    range "300..2000";
                  }
                  units "hertz";
                  default "300";
                }
              }
            }
            container timing {
              description
                "Configure cpa timing parameters";
              leaf live-person {
                description
                  "Longest typical greeting time if call is answered by live human";
                type uint16 {
                  range "1..60000";
                }
                units "miliseconds";
                default "2500";
              }
              leaf noise-period {
                description
                  "Amount of time to estimate the noise floor level";
                type uint16 {
                  range "1..60000";
                }
                units "miliseconds";
                default "100";
              }
              leaf silent {
                description
                  "Amount of silent after valid speech to declare a live voice";
                type uint16 {
                  range "1..60000";
                }
                units "miliseconds";
                default "375";
              }
              leaf term-tone {
                description
                  "Amount of time to wait for answering machine terminating tone";
                type uint16 {
                  range "1..60000";
                }
                units "miliseconds";
                default "15000";
              }
              leaf timeout {
                description
                  "Timeout when no active signal present";
                type uint16 {
                  range "1..60000";
                }
                units "miliseconds";
                default "3000";
              }
              leaf valid-speech {
                description
                  "Active speech duration";
                type uint16 {
                  range "1..60000";
                }
                units "miliseconds";
                default "112";
              }
            }
          }
        }
        leaf callmonitor {
          description
            "Call Monitoring";
          when "../type = 'voip'";
          type empty;
        }
        container supplementary-service {
          description
            "Config supplementary service features";
          when "../type = 'voip'";
          container sip {
            description
              "sip supplementary service";
            leaf handle-replaces {
              description
                "Handle INVITE with REPLACES header (SIP-SIP only)";
              type empty;
            }
            leaf moved-temporarily {
              description
                "enable/disable sip moved-temporarily";
              type empty;
            }
            leaf refer {
              description
                "enable/disable sip refer";
              type empty;
            }
          }
          leaf media-renegotiate {
            description
              "Enable/disable Media Renegotiation";
            type empty;
          }
        }
        container sip {
          description
            "SIP configuration commands";
          when "../type = 'voip'";
          presence "true";
          uses config-sip-localhost-grouping;
          uses config-outbound-proxy-grouping;
          uses config-audio-forced-grouping;
          uses config-sdp-block-grouping;
          uses config-call-route-grouping;
          leaf contact-passing {
            description
              "302 contact needs to be passed through for CFWD";
            type empty;
          }
          leaf referto-passing {
            description
              "Refer-To needs to be passed through for transfer";
            type empty;
          }
          container registrar {
            description
              "SIP Registrar config";
            container server {
              description
                "Enable Local SIP Registrar";
              container expires {
                description
                  "Registration Expires time";
                presence "true";
                must './min  <= ./max' {
                  error-message "Max must be greater than min";
                }
                leaf max {
                  description
                    "Default registration max expires time";
                  type uint32 {
                    range "120..86400";
                  }
                  default "3600";
                }
                leaf min {
                  description
                    "Default registration min expires time";
                  type uint16 {
                    range "60..3600";
                  }
                  default "60";
                }
              }
            }
          }
          container call {
            description
              "Global setting to start/stop processing SIP Calls";
            container service {
              description
                "SIP service configuration";
              container stop {
                description
                  "Stop SIP service - Active calls not affected";
                presence "true";
                leaf forced {
                  description
                    "Forced shutdown of SIP service - Active calls will be torn down";
                  type empty;
                }
              }
            }
          }
          container min-se {
            description
              "Min value allowed for SIP Session Timer refresh interval";
            leaf min-se {
              description
                "Min value of Session Expires Header (in seconds)";
              type uint32 {
                range "90..86400";
              }
            }
            leaf session-expires {
              description
                "Value of Session Expires Header (in seconds)";
              must '../min-se <= .' {
                error-message "session-expires value must be greater than or equal to min-se value";
              }
              type uint32 {
                range "90..86400";
              }
            }
          }
          container silent-discard {
            description
              "Configure silent-discard";
            leaf untrusted {
              description
                "Silently Discard the untrusted Request";
              type empty;
            }
          }
          uses config-asserted-id-grouping;
          uses config-midcall-signaling-grouping {
            refine "midcall-signaling/passthru" {
              presence "true";
            }
          }
          uses config-early-offer-grouping {
            when "/ios:native/voice/service[type='voip']/allow-connections/sip/to/sip";
          }
          uses config-asymmetric-grouping;
          container g729 {
            description
              "G729 codec interoperability settings";
            leaf annexb-all {
              description
                "g729b representing g729a and g729b to interop with CCM";
              type empty;
            }
          }
          container session {
            description
              "SIP Voice Protocol session config";
            leaf refresh {
              description
                "Enable SIP session timer";
              type empty;
            }
            uses config-session-transport-grouping;
          }
          uses config-sip-bind-grouping;
          uses pass-thru-grouping;
          leaf header-passing {
            description
              "SIP Headers need to be passed to Applications";
            type empty;
          }
          leaf error-passthru {
            description
              "SIP error response pass-thru functionality";
            type empty;
          }
          uses config-voice-privacy-grouping;
          uses config-voice-privacy-policy-grouping;
          uses config-voice-relxx-grouping;
          uses config-voice-url-grouping;
          leaf requri-passing {
            description
              "Request URI needs to be passed through";
            type empty;
          }
          leaf update-callerid {
            description
              "Enable sending updates for callerid";
            type empty;
          }
          uses config-sip-profiles-grouping;
          leaf anat {
            description
              "Allow alternative network address types IPv4 and IPv6";
            type boolean;
            default "false";
          }
          uses config-error-code-override-grouping;
          uses options-ping-grouping;
          uses early-media-update-grouping;
          uses config-conn-reuse-srtp-nat-grouping;
        }
        container ip {
          description
            "Voice service voip ip setup";
          when "../type = 'voip'";
          container address {
            description
              "Voice service voip ip address setup";
            container trusted {
              description
                "ip address trusted (toll fraud prevention) setup";
              leaf authenticate {
                description
                  "ip address trusted (toll fraud prevention) authenticate control flag";
                type empty;
              }
              leaf call-block {
                description
                  "ip address trusted (toll fraud prevention) call-block";
                type empty;
              }
              container list {
                description
                  "ip address trusted (toll fraud prevention) list setup";
                must 'count(./ipv4/address) + count(./ipv6/address) <= 100' {
                  error-message "Trusted list entries has exceeded the maximum";
                }
                list ipv4 {
                  description
                    "ip address trusted (toll fraud prevention) list entry";
                  max-elements 100;
                  key "address";
                  leaf address {
                    description
                      "IPv4 Address";
                    type inet:ipv4-address;
                  }
                  leaf mask {
                    description
                      "IPv4 Address Mask";
                    type union {
                      type ipv4-mask-pattern;
                      type string {
                        pattern '/([0-9]|[1-2][0-9]|3[0-2])';
                      }
                    }
                  }
                }
                list ipv6 {
                  description
                    "ipv6 address trusted (toll fraud prevention) list entry";
                  max-elements 100;
                  key "address";
                  leaf address {
                    description
                      "IPv6 Prefix";
                    type ios-types:ipv6-prefix;
                  }
                }
              }
            }
          }
        }
        container fax-relay {
          description
            "Global fax relay commands";
          when "../type = 'voip'";
          leaf ans-disable {
            description
              "Allow Ans-am tones to be disabled for SG3 machines to operate at G3 speeds using fax relay";
            type empty;
          }
          leaf ans-treatment {
            description
              "Enable Modem and Fax Answer Tone Treatment";
            type empty;
          }
          leaf sg3-to-g3 {
            description
              "Allow SG3 Fax machines to operate at G3 speeds using fax relay";
            type empty;
          }
        }
        container fax {
          description
            "Global fax commands";
          leaf protocol {
            description
              "The system-wide fax protocol type";
            type enumeration {
              enum cisco;
              enum none;
              enum pass-through;
              enum t38;
            }
          }
          leaf fallback {
            description
              "fax transport to use if T.38 unsupported on far end";
            when "../protocol = 't38'";
            type enumeration {
              enum cisco;
              enum none;
              enum pass-through;
            }
          }
          leaf codec {
            when "../protocol = 'pass-through' or ../fallback = 'pass-through'";
            type enumeration {
              enum g711alaw;
              enum g711ulaw;
            }
          }
          leaf ls-redundancy {
            status obsolete;
            description
              "t38 low speed redundancy";
            when "../protocol = 't38'";
            type uint8 {
              range "0..5";
            }
          }
          leaf hs-redundancy {
            status obsolete;
            description
              "t38 high speed redundancy";
            when "../protocol = 't38'";
            type uint8 {
              range "0..2";
            }
          }
          leaf version {
            status obsolete;
            description
              "t38 fax version";
            when "../protocol = 't38'";
            type enumeration {
              enum 0;
              enum 3;
            }
          }
        }
        container modem {
          description
            "Global modem commands";
          when "../type = 'voip'";
          uses config-modem-grouping;
        }
        leaf redundancy-group {
          description
            "Associate redundancy-group with voice HA";
          type uint8 {
            range "1..2";
          }
        }
        container mode {
          description
            "Global mode setting for voip calls";
          when "../type = 'voip'";
          choice mode-choice {
            case border-element-case {
              container border-element {
                description
                  "Mode setting for Border-Element";
                presence "true";
                container license {
                  description
                    "License setting for Border-Element is deprecated";
                  container periodicity {
                    description
                      "Licence periodicity setting for Border-Element";
                    choice periodicity-choice {
                      case mins-case {
                        leaf mins {
                          status obsolete;
                          description
                            "Periodicity interval in mins";
                          type uint8 {
                            range "1..59";
                          }
                        }
                      }
                      case hours-case {
                        leaf hours {
                          description
                            "Periodicity interval in hours";
                          type uint8 {
                            range "8..23";
                          }
                        }
                      }
                      case days-case {
                        leaf days {
                          description
                            "Periodicity interval in days";
                          type uint8 {
                            range "1..30";
                          }
                        }
                      }
                    }
                  }
                }
              }
            }
          }
        }
        container trace {
          description
            "Voip Trace configuration";
          when "../type = 'voip'";
          presence "true";
          leaf shutdown {
            description
              "Shut Voip Trace debugging";
            type boolean;
            default "false";
          }
          container memory-limit {
            description
              "Set limit based on memory used";
            choice memory-limit-choice {
              default "case-platform";
              case case-platform {
                leaf platform {
                  description
                    "Use 10 percent of available memory";
                  type boolean;
                  default "true";
                  must ". = 'true'" {
                    error-message "Configuring FALSE not allowed";
                  }
                }
              }
              case case-value {
                leaf memory-limit-value {
                  description
                    "Specify maximum memory limit";
                  type uint16 {
                    range "10..1000";
                  }
                  must '. mod 10 = 0' {
                    error-message "Range should be from 10 to 1000, in multiples of 10";
                  }
                  units "Megabytes";
                }
              }
            }
          }
        }
        leaf address-hiding {
          description
            "Address hiding (SIP-SIP)";
          type empty;
        }
        leaf emergency {
          description
            "List of Emergency Numbers";
          type string {
            pattern '[0-9 ]*' {
              error-message "List of numbers separated by ' ' SPACE";
            }
          }
        }
        container rtcp {
          when "../type = 'voip'";
          description
            "Configure RTCP report generation";
          leaf all-pass-through {
            description
              "Pass through all the rtcp in datapath";
            type empty;
          }
          leaf keepalive {
            description
              "Generate RTCP keepalive report";
            type empty;
          }
        }
      }
      container statistics {
        description
          "Voice Statistics";
        container type {
          description
            "Voice statistics aggregation type";
          leaf iec {
            description
              "Internal Error Code";
            type empty;
          }
        }
        container time-range {
          description
            "Time range to collect statistics";
          leaf since-reset {
            description
              "Since-reset aggregation";
            type empty;
          }
        }
      }
      uses config-voice-register-grouping;
    }
  }

  grouping config-voice-card-grouping {
    list voice-card-sb {
      description
        "Configure a specific voice-card";
      key "sb";
      leaf sb {
        type ios-types:slot-bay-type;
      }
      leaf local-bypass {
        description
          "Enable TDM hair pin";
        type boolean;
        default "true";
      }
      container dsp {
        description
          "To configure DSP service dspfarm";
        container services {
          description
            "To configure dsp services on this voice-card";
          leaf dspfarm {
            description
              "To enable dspfarm service on this voice-card";
            type empty;
          }
        }
      }
    }
    list voice-card {
      status obsolete;
      description
        "Configure a specific voice-card (OBSOLETE)";
      key "id";
      leaf id {
        status obsolete;
        type ios-types:slot-bay-type;
      }
      leaf slot {
        status obsolete;
        type uint8 {
          range "0..2";
        }
      }
    }
  }

  grouping config-dtmf-relay-grouping {
    container dtmf-relay {
      description
        "Transport digits across IP link. Enter relay options in order of preference.";
      leaf rtp-nte {
        description
          "RTP Named Telephone Event RFC 2833";
        type empty;
      }
      leaf digit-drop {
        description
          "RTP Named Telephone Event RFC 2833";
        when '../rtp-nte';
        type empty;
      }
      leaf sip-info {
        description
          "Relay via SIP INFO messages";
        type empty;
      }
      leaf sip-kpml {
        description
          "Relay over SIP SUBSCRIBE/NOTIFY";
        type empty;
      }
      leaf sip-notify {
        description
          "Relay via SIP NOTIFY messages";
        type empty;
      }
    }
  }

  grouping config-dial-peer-grouping {
    container dial-peer {
      description
        "Dial Map (Peer) configuration commands";
      list voice {
        description
          "Voice type";
        key "dialpeertag";
        leaf dialpeertag {
          description
            "Voice dial-peer tag";
          type uint32 {
            range "1..1073741823" {
              error-message "Input dial-peer tag is out of range. It should be in range of 1..1073741823";
            }
          }
        }
        leaf type {
          description
            "Dial peer type";
          type enumeration {
            enum pots;
            enum voip;
          }
        }
        leaf description {
          description
            "Dial peer specific description";
          when "../type = 'pots' or ../type = 'voip'";
          type string {
            pattern '.*';
            length "1..64";
          }
        }
        container srtp {
          description
            "Allow Secure calls";
          when "../type = 'voip'";
          presence "true";
          uses config-srtp-options-grouping;
        }
        leaf destination-pattern {
          description
            "A full E.164 telephone number prefix";
          when "../type = 'pots' or ../type = 'voip'";
          type config-e164-pattern;
        }
        leaf direct-inward-dial {
          when "../type = 'pots'";
          description
            "Use Called Number as final call destination";
          type empty;
        }
        container forward-digits {
          description
            "Configure the destination digits forward of this dial-peer";
          when "../type = 'pots'";
          choice fwd-digit-choice {
            leaf num-digits {
              description
                "Number of right-justified dial digits to be forwarded";
              type uint8 {
                range "0..32";
              }
            }
            leaf all {
              description
                "Forward all destination digits";
              type empty;
            }
            container extra {
              description
                "Extra dial digits to be forwarded";
              presence "true";
              leaf inband {
                description
                  "Digits to be forwarded inband";
                type empty;
              }
            }
          }
        }
        container incoming {
          description
            "Incoming called number";
          when "../type = 'pots' or ../type = 'voip'";
          leaf called-number {
            description
              "An incoming called number pattern";
            type config-e164-pattern;
          }
          container called {
            description
              "Configure incoming called e164 map pattern";
            leaf e164-pattern-map {
              description
                "Configure voice class to match destination e164-pattern-map";
              type leafref {
                path "/ios:native/ios-voice:voice/ios-voice:class/ios-voice:e164-pattern-map/ios-voice:id";
              }
            }
          }
          container calling {
            description
              "Configure incoming calling e164 map pattern";
            leaf e164-pattern-map {
              description
                "Configure voice class to match destination e164-pattern-map";
              type leafref {
                path "/ios:native/ios-voice:voice/ios-voice:class/ios-voice:e164-pattern-map/ios-voice:id";
              }
            }
          }
          container uri {
            description
              "Incoming URI class";
            when "../../type = 'voip' and ../../session[protocol='sipv2']";
            leaf from {
              description
                "Match incoming To header";
              type leafref {
                path "/ios:native/ios-voice:voice/ios-voice:class/ios-voice:uri/ios-voice:uri/ios-voice:uritag";
              }
            }
            leaf request {
              description
                "Match incoming Request-URI";
              type leafref {
                path "/ios:native/ios-voice:voice/ios-voice:class/ios-voice:uri/ios-voice:uri/ios-voice:uritag";
              }
            }
            leaf to {
              description
                "Match incoming From header";
              type leafref {
                path "/ios:native/ios-voice:voice/ios-voice:class/ios-voice:uri/ios-voice:uri/ios-voice:uritag";
              }
            }
            leaf via {
              description
                "Match incoming topmost Via header";
              type leafref {
                path "/ios:native/ios-voice:voice/ios-voice:class/ios-voice:uri/ios-voice:uri/ios-voice:uritag";
              }
            }
          }
        }
        container fax-rate-config {
          leaf fax-rate {
            description
              "The fax rate to be attempted in getting to this peer";
            type enumeration {
              enum 12000;
              enum 14400;
              enum 2400;
              enum 4800;
              enum 7200;
              enum 9600;
              enum disable;
              enum voice;
            }
            default "voice";
          }
          leaf bytes {
            when '../fax-rate';
            description
              "Bytes of fax data per frame";
            type uint32 {
              range "0 | 10..255";
            }
            default "0";
          }
        }
        container fax-relay {
          description
            "fax-relay options";
          leaf ans-disable {
            when "../../type = 'voip'";
            description
              "Allow Ans-am tones to be disabled for SG3 machines to operate at G3 speeds using fax relay";
            type empty;
          }
          leaf ans-treatment {
            when "../../type = 'voip'";
            description
              "Enable Modem and Fax Answer Tone Treatment";
            type empty;
          }
          container sg3-to-g3 {
            description
              "Allow SG3 Fax machines to operate at G3 speeds using fax relay";
            presence "true";
            leaf system {
              when "../../../type = 'voip'";
              description
                "Use the system configuration for fax relay sg3-to-g3";
              type empty;
            }
          }
          container ecm {
            when "../../type = 'voip'";
            description
              "ECM mode options for FAX Relay";
            leaf disable {
              description
                "Disables ECM mode for FAX Relay";
              type empty;
            }
          }
        }
        container fax {
          description
            "Configure fax";
          when "../type = 'voip'";
          container protocol {
            description
              "The fax protocol to be attempted in getting to this peer";
            uses config-fax-protocol-grouping;
          }
        }
        container modem {
          description
            "Modem commands through this peer";
          when "../type = 'voip'";
          uses config-modem-grouping;
        }
        container media-recording {
          description
            "Media recording commands";
          when "../type = 'pots'";
          leaf dialpeertag {
            description
              "Recording server dial peer";
            type uint32 {
              range "1..1073741823";
            }
          }
        }
        container pcm-dump {
          description
            "Enable PCM capture stream for this dial-peer";
          container caplog {
            description
              "Enable PCM capture log";
            leaf pcm-stream-bit-map {
              description
                "PCM stream index in hex";
              type string {
                pattern '[1-9A-F][0-9A-F]{0,6}';
              }
            }
            leaf capture-time {
              description
                "PCM capture interval";
              type uint8 {
                range "0..255";
              }
              default "255";
            }
          }
        }
        leaf port {
          description
            "Voice port associated with this peer";
          when "../type = 'pots'";
          type string;
        }
        leaf prefix {
          description
            "The pattern to be appended before the dial num";
          when "../type = 'pots'";
          type string {
            length "1..32";
          }
        }
        leaf shutdown {
          description
            "Change the Admin State of this peer to down";
          when "../type = 'pots' or ../type = 'voip'";
          type boolean;
          default "false";
        }
        uses config-voice-translation-profile-grouping;
        container voice-class {
          description
            "Set Dial-peer voice class control parameters";
          container sip {
            description
              "Set SIP parameters";
            container extension {
              description
                "Configure SIP extension";
              leaf voip_ext {
                when "../../../../type = 'voip'";
                type enumeration {
                  enum system;
                  enum cucm;
                  enum gw-ana;
                }
                default "system";
              }
              leaf pots_ext {
                when "../../../../type = 'pots'";
                type enumeration {
                  enum system;
                  enum gw-ana;
                }
                default "system";
              }
            }
            uses config-sip-bind-grouping {
              when "../../type = 'voip'";
            }
            container options-keepalive {
              description
                "send out-of-dialogue OPTIONS PING to configured proxy/session-target";
              when "../../../type = 'voip'";
              choice keepalive-options {
                case interval-config {
                  uses config-sip-options-keepalive-interval-grouping;
                }
                case profile-config {
                  leaf profile-config {
                    description
                      "Consolidate Options Keepalive profile setup";
                    type leafref {
                      path "/ios:native/ios-voice:voice/ios-voice:class/ios-voice:sip-options-keepalive/ios-voice:id";
                    }
                  }
                }
              }
              leaf profile {
                status deprecated;
                description
                  "Consolidate Options Keepalive profile setup (DEPRECATED)";
                type leafref {
                  path "/ios:native/ios-voice:voice/ios-voice:class/ios-voice:sip-options-keepalive/ios-voice:id";
                }
              }
            }
            uses pass-thru-grouping {
              when "../../type = 'voip'";
            }
            leaf tenant {
              description
                "Set SIP-Tenant parameters";
              when "../../../type = 'voip'";
              type leafref {
                path "/ios:native/ios-voice:voice/ios-voice:class/ios-voice:tenant/ios-voice:id";
              }
            }
            uses config-voice-privacy-grouping;
            uses config-voice-privacy-policy-grouping;
            uses config-asserted-id-grouping {
              when "../../type = 'voip'";
            }
            uses config-midcall-signaling-grouping {
              when "../../type = 'voip'";
            }
            uses config-asymmetric-grouping {
              when "../../type = 'voip'";
            }
            uses config-voice-relxx-grouping {
              when "../../type = 'voip'";
            }
            uses config-early-offer-grouping {
              when "/ios:native/voice/service[type='voip']/allow-connections/sip/to/sip";
            }
            uses config-voice-url-grouping;
            leaf requri-passing {
              description
                "Request URI needs to be passed through";
              type empty;
            }
            leaf anat {
              description
                "Allow alternative network address types IPv4 and IPv6";
              when "../../../type = 'voip'";
              type boolean;
              default "false";
            }
            uses config-error-code-override-grouping {
              when "../../type = 'voip'";
            }
            container profiles {
              container outbound-id {
                leaf id {
                  description
                    "The sip profiles tag number to be linked as global";
                  type leafref {
                    path "/ios:native/ios-voice:voice/ios-voice:class/ios-voice:sip-profiles/ios-voice:id";
                  }
                }
              }
              container sip-profiles-inbound {
                leaf id {
                  description
                    "The sip profiles tag number to be linked as global";
                  type leafref {
                    path "/ios:native/ios-voice:voice/ios-voice:class/ios-voice:sip-profiles/ios-voice:id";
                  }
                }
                leaf inbound {
                  description
                    "Turn on inbound SIP profiles feature";
                  type empty;
                }
              }
            }
            uses early-media-update-grouping {
              when "../../type = 'voip'";
            }
          }
          container codec {
            description
              "Set Global Codec parameters";
            when "../../type = 'voip'";
            leaf codectag {
              type leafref {
                path "../../../../../voice/class/codec/codec-tag";
              }
            }
            leaf offer-all {
              description
                "Offer All the codec configured in this voice-class codec";
              when '../codectag > 0';
              type empty;
            }
          }
          leaf stun-usage {
            description
              "Set stun usage tag";
            when "../../type = 'voip'";
            type leafref {
              path "/ios:native/voice/class/stun-usage/id";
            }
          }
          leaf media {
            description
              "Set media parameters for call";
            when "../../type = 'voip'";
            type leafref {
              path "/ios:native/ios-voice:voice/ios-voice:class/ios-voice:media/ios-voice:media-tag";
            }
          }
        }
        container session {
          description
            "The session [ target | protocol | transport ] for this peer";
          when "../type = 'voip'";
          uses config-session-transport-grouping;
          leaf protocol {
            description
              "The session protocol to be used in getting to this peer";
            type enumeration {
              enum cisco {
                description
                  "Ciso Session Protocol";
              }
              enum sipv2 {
                description
                  "IETF Session Initiation Protocol";
              }
              enum multicast {
                description
                  "Multicast Session Protocol(voice conferencing)";
              }
            }
            default "cisco";
          }
          leaf server-group {
            description
              "Configure voice class server-group";
            when "../../session[protocol='sipv2']";
            type leafref {
              path "/ios:native/ios-voice:voice/ios-voice:class/ios-voice:server-group/ios-voice:id";
            }
          }
          container target {
            description
              "The session target for this peer";
            when "../../session[protocol='sipv2']";
            choice target-choice {
              case address-choice {
                leaf address {
                  description
                    "WORD A string specifying the session target";
                  type string {
                    pattern '(loopback:rtp)|(dns:.*)|(sip-server)|(sip-uri)|(ipv4:[0-9]+\.[0-9]+\.[0-9]+\.[0-9]+(:[0-9]+)?)|(ipv6:\[([0-9A-Fa-f.:])+\](:[0-9]+)?)' {
                      error-message "Must be of the form (loopback:rtp)|(dns:.*)|(sip-server)|(sip-uri)|(ipv4:[0-9]+.[0-9]+.[0-9]+.[0-9]+(:[0-9]+)?) | ((ipv6:[([0-9A-Fa-f.:])+](:[0-9]+)?))";
                    }
                  }
                }
              }
              case dhcp-choice {
                leaf dhcp {
                  description
                    "Provision session target using DHCP";
                  type empty;
                }
              }
              case registrar-choice {
                leaf registrar {
                  description
                    "Provision session target using Registration";
                  type empty;
                }
              }
            }
          }
        }
        leaf huntstop {
          description
            "Stop hunting on Dial-Peers";
          when "../type = 'pots' or ../type = 'voip'";
          type boolean;
          default "false";
        }
        leaf preference {
          description
            "Configure the preference order of this dial-peer";
          type uint16 {
            range "0..10" {
              error-message "Input Number is out of range. Should be 1..10";
            }
          }
        }
        uses config-dtmf-relay-grouping {
          when "type = 'voip' and session[protocol='sipv2']";
        }
        list trunkgroup {
          description
            "trunk groups associated with this peer";
          key "id";
          leaf id {
            description
              "Trunk group ID";
            type string {
              length "1..64";
            }
          }
          leaf trunk-group-preference {
            description
              "trunk group preference value";
            type uint8 {
              range "1..64";
            }
          }
        }
        container signaling {
          description
            "Signaling payload handling";
          when "../type = 'voip'";
          leaf forward {
            description
              "signaling payload forwarding";
            type enumeration {
              enum conditional {
                description
                  "Conditional forwarding of signaling payload";
              }
              enum none {
                description
                  "No forwarding of signaling payload";
              }
              enum rawmsg {
                description
                  "rawmsg except GTD is permitted to be forwarded";
              }
              enum unconditional {
                description
                  "Unconditional forwarding of signaling payload";
              }
            }
          }
        }
        container corlist {
          description
            "set the Class of Restriction lists";
          leaf incoming {
            description
              "set the incoming Class of Restriction lists";
            type leafref {
              path "/ios:native/ios-voice:dial-peer/ios-voice:cor/ios-voice:list/id";
            }
          }
          leaf outgoing {
            description
              "set the outgoing Class of Restriction lists";
            type leafref {
              path "/ios:native/ios-voice:dial-peer/ios-voice:cor/ios-voice:list/id";
            }
          }
        }
        leaf vad {
          description
            "Use vad as necessary option";
          when "../type = 'voip'";
          type boolean;
          default "true";
        }
        container vad-config {
          when "../vad = 'true' and ../type = 'voip'";
          container vad {
            description
              "Use vad as necessary option";
            leaf aggressive {
              description
                "Aggressive vad";
              type empty;
            }
          }
        }
        container destination {
          description
            "Outbound dial-peer match config";
          leaf dpg {
            description
              "Configure voice class dpg";
            type leafref {
              path "/ios:native/voice/class/dpg/id";
            }
          }
          container calling {
            description
              "Match destination calling number";
            leaf e164-pattern-map {
              description
                "Configure voice class to match destination e164-pattern-map";
              type leafref {
                path "/ios:native/ios-voice:voice/ios-voice:class/ios-voice:e164-pattern-map/ios-voice:id";
              }
            }
          }
          leaf e164-pattern-map {
            description
              "Configure voice class to match destination e164-pattern-map";
            when "../../type = 'voip'";
            type leafref {
              path "/ios:native/ios-voice:voice/ios-voice:class/ios-voice:e164-pattern-map/ios-voice:id";
            }
          }
          leaf uri {
            description
              "Configure voice class to match destination URI";
            type leafref {
              path "/ios:native/ios-voice:voice/ios-voice:class/ios-voice:uri/ios-voice:uri/ios-voice:uritag";
            }
          }
          leaf uri-diversion {
            description
              "voice class uri to match sip diversion header";
            when "../../type = 'voip' and ../../session[protocol='sipv2']";
            type leafref {
              path "/ios:native/ios-voice:voice/ios-voice:class/ios-voice:uri/ios-voice:uri/ios-voice:uritag";
            }
          }
          leaf uri-from {
            description
              "voice class uri to match sip from header";
            when "../../type = 'voip' and ../../session[protocol='sipv2']";
            type leafref {
              path "/ios:native/ios-voice:voice/ios-voice:class/ios-voice:uri/ios-voice:uri/ios-voice:uritag";
            }
          }
          leaf uri-to {
            description
              "voice class uri to match sip to header";
            when "../../type = 'voip' and ../../session[protocol='sipv2']";
            type leafref {
              path "/ios:native/ios-voice:voice/ios-voice:class/ios-voice:uri/ios-voice:uri/ios-voice:uritag";
            }
          }
          leaf uri-via {
            description
              "voice class uri to match sip via header";
            when "../../type = 'voip' and ../../session[protocol='sipv2']";
            type leafref {
              path "/ios:native/ios-voice:voice/ios-voice:class/ios-voice:uri/ios-voice:uri/ios-voice:uritag";
            }
          }
        }
        container sip-register-container {
          when "../type = 'pots'";
          choice sip-register-case {
            default "sip-register-case";
            case sip-register-case {
              leaf sip-register {
                description
                  "Enable SIP registrations - enabled by default";
                type boolean;
                default "true";
              }
            }
            case reg-sync-case {
              container reg-sync-container {
                leaf sip-register {
                  description
                    "Enable SIP registrations - enabled by default";
                  type empty;
                }
                leaf-list reg-sync {
                  description
                    "Registration Sync - send REGISTER when registrar up";
                  max-elements 6;
                  type uint32 {
                    range "1..1073741823";
                  }
                }
              }
            }
          }
        }
        container rtp {
          description
            "RTP config";
          when "../type = 'voip'";
          container payload-type {
            description
              "Payload type value";
            leaf cisco-codec-aacld {
              description
                "Cisco codec AACLD";
              must "not (../cisco-codec-ilbc=current()) and
                    not (../cisco-codec-isac=current()) and
                    not (../cisco-codec-mp4a-latm=current()) and
                    not (../cisco-codec-video-h263-plus=current()) and
                    not (../cisco-codec-video-h264=current()) and
                    not (../nse=current()) and not (../nte=current()) and
                    not (../opus=current())" {
                error-message "value is already in use";
              }
              type uint32 {
                range "96..127";
              }
              default "112";
            }
            leaf cisco-codec-ilbc {
              description
                "Cisco codec iLBC";
              must "not (../cisco-codec-aacld=current()) and
                    not (../cisco-codec-isac=current()) and
                    not (../cisco-codec-mp4a-latm=current()) and
                    not (../cisco-codec-video-h263-plus=current()) and
                    not (../cisco-codec-video-h264=current()) and
                    not (../nse=current()) and
                    not (../nte=current()) and
                    not (../opus=current())" {
                error-message "value is already in use";
              }
              type uint32 {
                range "96..127";
              }
              default "116";
            }
            leaf cisco-codec-isac {
              description
                "Cisco codec ISAC";
              must "not (../cisco-codec-ilbc=current()) and
                    not (../cisco-codec-aacld=current()) and
                    not (../cisco-codec-mp4a-latm=current()) and
                    not (../cisco-codec-video-h263-plus=current()) and
                    not (../cisco-codec-video-h264=current()) and
                    not (../nse=current()) and
                    not (../nte=current()) and
                    not (../opus=current())" {
                error-message "value is already in use";
              }
              type uint32 {
                range "96..127";
              }
              default "124";
            }
            leaf cisco-codec-mp4a-latm {
              description
                "Cisco codec MP4A-LATM";
              must "not (../cisco-codec-ilbc=current()) and
                    not (../cisco-codec-isac=current()) and
                    not (../cisco-codec-aacld=current()) and
                    not (../cisco-codec-video-h263-plus=current()) and
                    not (../cisco-codec-video-h264=current()) and
                    not (../nse=current()) and
                    not (../nte=current()) and
                    not (../opus=current())" {
                error-message "value is already in use";
              }
              type uint32 {
                range "96..127";
              }
              default "111";
            }
            leaf cisco-codec-video-h263-plus {
              description
                "RTP video codec H263+ payload type";
              must "not (../cisco-codec-ilbc=current()) and
                    not (../cisco-codec-isac=current()) and
                    not (../cisco-codec-mp4a-latm=current()) and
                    not (../cisco-codec-aacld=current()) and
                    not (../cisco-codec-video-h264=current()) and
                    not (../nse=current()) and
                    not (../nte=current()) and
                    not (../opus=current())" {
                error-message "value is already in use";
              }
              type uint32 {
                range "96..127";
              }
              default "118";
            }
            leaf cisco-codec-video-h264 {
              description
                "RTP video codec H264 payload type";
              must "not (../cisco-codec-ilbc=current()) and
                    not (../cisco-codec-isac=current()) and
                    not (../cisco-codec-mp4a-latm=current()) and
                    not (../cisco-codec-video-h263-plus=current()) and
                    not (../cisco-codec-aacld=current()) and
                    not (../nse=current()) and
                    not (../nte=current()) and
                    not (../opus=current())" {
                error-message "value is already in use";
              }
              type uint32 {
                range "96..127";
              }
              default "119";
            }
            leaf nse {
              description
                "Named Signaling Event";
              must "not (../cisco-codec-ilbc=current()) and
                    not (../cisco-codec-isac=current()) and
                    not (../cisco-codec-mp4a-latm=current()) and
                    not (../cisco-codec-video-h263-plus=current()) and
                    not (../cisco-codec-video-h264=current()) and
                    not (../cisco-codec-aacld=current()) and
                    not (../nte=current()) and
                    not (../opus=current())" {
                error-message "value is already in use";
              }
              type uint32 {
                range "96..127";
              }
              default "100";
            }
            leaf opus {
              description
                "Cisco codec OPUS";
              must "not (../cisco-codec-ilbc=current()) and
                    not (../cisco-codec-isac=current()) and
                    not (../cisco-codec-mp4a-latm=current()) and
                    not (../cisco-codec-video-h263-plus=current()) and
                    not (../cisco-codec-video-h264=current()) and
                    not (../nse=current()) and
                    not (../nte=current()) and
                    not (../cisco-codec-aacld=current())" {
                error-message "value is already in use";
              }
              type uint32 {
                range "96..127";
              }
              default "114";
            }
            leaf nte {
              description
                "Named Telephone Event";
              must "not (../cisco-codec-ilbc=current()) and
                    not (../cisco-codec-isac=current()) and
                    not (../cisco-codec-mp4a-latm=current()) and
                    not (../cisco-codec-video-h263-plus=current()) and
                    not (../cisco-codec-video-h264=current()) and
                    not (../nse=current()) and
                    not (../cisco-codec-aacld=current()) and
                    not (../opus=current())" {
                error-message "value is already in use";
              }
              type uint32 {
                range "96..127";
              }
              default "101";
            }
          }
        }
        container ip {
          description
            "Set ip packet options";
          when "../type = 'voip'";
          container qos {
            description
              "Set ip QoS Parameters";
            container dscp-media {
              leaf dscp {
                description
                  "Specify ip DSCP";
                type dscp-type;
              }
              leaf media {
                description
                  "Apply DSCP to media payload packets";
                type empty;
              }
            }
            container dscp-signaling {
              leaf dscp {
                description
                  "Specify ip DSCP";
                type dscp-type;
              }
              leaf signaling {
                description
                  "Apply DSCP to signaling packets";
                type empty;
              }
            }
            container dscp-video {
              description
                "Specify ip DSCP";
              leaf dscp {
                description
                  "Specify ip DSCP";
                type dscp-type;
              }
              container video {
                description
                  "Apply DSCP to video packets";
                leaf rsvp-none {
                  description
                    "Use this DSCP value if RSVP is not configured";
                  type empty;
                }
              }
            }
          }
        }
        container max-conn {
          description
            "Sets the maximum connections per peer, negation sets to unlimited";
          leaf range {
            description
              "Maximum connections, negation sets to unlimited";
            type uint64 {
              range "1..2147483647";
            }
          }
          leaf exempt-local-media {
            description
              "max-conn value will not be updated for local media calls";
            type empty;
          }
        }
        container progress_ind {
          description
            "Progress Indicator";
          when '../destination-pattern';
          container alert {
            description
              "Set/Strip Progress Indicator for ALERT";
            uses progress-ind-options-grouping;
          }
          container callproc {
            description
              "Set/Strip Progress Indicator for CALLPROC";
            uses progress-ind-options-grouping;
          }
          container connect {
            description
              "Set Progress Indicator for CONNECT";
            uses progress-ind-enable-disable-grouping;
          }
          container progress {
            description
              "Set Progress Indicator for PROGRESS";
            uses progress-ind-enable-disable-grouping;
          }
          container disconnect {
            description
              "Set Progress Indicator for DISCONNECT.";
            leaf disable {
              description
                "Disable Progress Indicator for DISCONNECT";
              type empty;
            }
            leaf enable {
              description
                "Enable Progress Indicator for DISCONNECT";
              type enumeration {
                enum 8;
              }
            }
          }
          container setup {
            description
              "Set Progress Indicator for SETUP";
            leaf disable {
              description
                "Disable Progress Indicator for PROG/CONN/CALLPROC";
              type empty;
            }
            leaf enable {
              description
                "Enable Progress Indicator for PROG/CONN/CALLPROC";
              type enumeration {
                enum 0;
                enum 1;
                enum 3;
              }
            }
          }
        }
        container codec {
          description
            "The codec rate to be attempted in getting to this peer";
          when "../type = 'voip'";
          leaf transparent {
            description
              "Uses the endpoint codec";
            type empty;
          }
        }
        leaf answer-address {
          description
            "The Call Destination Number";
          when "../type = 'pots' or ../type = 'voip'";
          type config-answer-address;
        }
        leaf media-class {
          description
            "Set Dial-peer media class";
          type leafref {
            path "/ios:native/ios-voice:media/ios-voice:class/ios-voice:id";
          }
        }
      }
      container cor {
        description
          "Class of Restriction";
        container custom {
          description
            "Define custom Class of Restriction";
          leaf-list name {
            description
              "name of Class of Restriction";
            max-elements 64;
            type string {
              length "1..32";
            }
          }
        }
        list list {
          description
            "Define List of Class of Restriction";
          max-elements 64;
          key "id";
          leaf id {
            description
              "name of Class of Restriction list";
            type string {
              length "1..32";
              pattern '([0-9,A-Z,a-z-]*T?)' {
                error-message
                  "Incorrect format for dial-peer cor list
                   regular expression must be of the form  [0-9,A-Z,a-z-]*T?";
              }
            }
          }
          leaf-list member {
            description
              "member in COR list";
            max-elements 64;
            type leafref {
              path "/ios:native/ios-voice:dial-peer/ios-voice:cor/ios-voice:custom/ios-voice:name";
            }
          }
        }
      }
    }
  }

  grouping config-num-exp-grouping {
    list num-exp {
      description
        "Dial Map Number Expansion configuration commands";
      max-elements 128;
      key "id";
      leaf id {
        description
          "Dialed Digit Pattern - A Regular Expression String";
        type config-digit-pattern;
      }
      leaf dialled-pattern {
        description
          "Substitution Pattern to Translate Dialed Pattern to E.164";
        type config-digit-pattern;
      }
    }
  }

  grouping config-dsapp-line-grouping {
    container dsapp {
      description
        "Configure Device Service Application";
      leaf line {
        description
          "Configure DSAPP Line";
        type empty;
      }
      container dsappline {
        container line {
          description
            "Configure DSAPP Line";
          container feature {
            description
              "Specify the format of each call feature code";
            container access-code {
              description
                "Specify the format of feature access code";
              presence "true";
              leaf prefix {
                description
                  "Select feature access code prefix string";
                type string {
                  pattern '[\*#]{1,5}';
                }
                default "**";
              }
              container call {
                description
                  "Select call forward feature";
                container forward {
                  description
                    "Select call forward all feature";
                  leaf all {
                    description
                      "Select call forward all feature code";
                    type string {
                      pattern '[0-9\*#]{1,4}';
                    }
                    default "1";
                  }
                  leaf cancel {
                    description
                      "Select call forward cancel feature code";
                    type string {
                      pattern '[0-9\*#]{1,4}';
                    }
                    default "2";
                  }
                }
              }
              container pickup {
                description
                  "Select call pickup feature code";
                leaf local {
                  description
                    "Select pickup local group feature code";
                  type string {
                    pattern '[0-9\*#]{1,4}';
                  }
                  default "5";
                }
                leaf group {
                  description
                    "Select pickup different group feature code";
                  type string {
                    pattern '[0-9\*#]{1,4}';
                  }
                  default "7";
                }
                leaf direct {
                  description
                    "Select pickup extension feature code";
                  type string {
                    pattern '[0-9\*#]{1,4}';
                  }
                  default "6";
                }
              }
              leaf cancel-call-waiting {
                description
                  "Select cancel call waiting feature code";
                type string {
                  pattern '[0-9\*#]{1,4}';
                }
                default "9";
              }
              leaf last-redial {
                description
                  "Select last redial feature code";
                type string {
                  pattern '[0-9\*#]{1,4}';
                }
                default "3";
              }
            }
          }
        }
      }
    }
  }

  grouping config-ccm-manager-grouping {
    container ccm-manager {
      description
        "Call Manager";
      container sipana {
        description
          "Enable Call Manager Application SIP Line Side mode";
        container auto-config {
          description
            "SIP line side auto configuration";
          container local {
            description
              "Specify local interface to use for SIP analog device registration";
            leaf GigabitEthernet {
              description
                "GigabitEthernet IEEE 802.3z";
              type leafref {
                path "/ios:native/ios:interface/ios:GigabitEthernet/ios:name";
              }
            }
          }
        }
      }
      container config {
        description
          "XML download configuration";
        leaf server {
          description
            "set the Call Manager configuration download TFTP server address/name";
          type union {
            type inet:ipv4-address;
            type inet:ipv6-address;
            type inet:domain-name;
          }
        }
      }
    }
  }

  grouping config-trunk-group-grouping {
    container trunk {
      description
        "Global trunk configuration";
      list group {
        description
          "Specify a trunk group";
        key "id";
        leaf id {
          description
            "Trunk group label";
          type string {
            length "1..64";
          }
        }
        container hunt-scheme {
          description
            "The hunt scheme in trunk group";
          presence "true";
          leaf hunt-method {
            description
              "hunt scheme method";
            type enumeration {
              enum least-idle;
              enum least-used;
              enum longest-idle;
              enum random;
              enum round-robin;
              enum sequential;
            }
          }
          leaf precedence-type {
            when "../hunt-method != 'random'";
            description
              "hunt time slot order";
            type enumeration {
              enum both;
              enum even;
              enum odd;
            }
          }
          leaf select-order {
            description
              "Time slot selection order";
            when "../precedence-type and not(../hunt-method = 'least-idle' or
                  ../hunt-method = 'longest-idle')";
            type enumeration {
              enum down;
              enum up;
            }
          }
        }
        leaf max-retry {
          description
            "Maximum number of outgoing call attempts";
          type uint8 {
            range "1..5";
          }
        }
        list max-calls {
          description
            "Maximum number of calls allowed";
          key "call-type direction";
          leaf call-type {
            description
              "Call type";
            type enumeration {
              enum any;
              enum data;
              enum voice;
            }
          }
          leaf direction {
            description
              "Specify direction of calls";
            type enumeration {
              enum in;
              enum out;
            }
          }
          leaf num-call {
            description
              "Specify number of calls allowed";
            type uint16 {
              range "0..1000";
            }
          }
        }
        uses config-voice-translation-profile-grouping;
      }
    }
  }

  grouping config-gateway-grouping {
    container gateway {
      description
        "Gateway";
      presence "true";
      container media-inactivity-criteria {
        description
          "Define voice media inactivity detection method";
        choice media-detection-method {
          case media-all {
            container all {
              description
                "Both RTP and RTCP for silence detection";
              presence "true";
              leaf receive {
                description
                  "Only for the packets received";
                type empty;
              }
            }
          }
          case media-rtcp {
            leaf rtcp {
              description
                "Use RTCP for silence detection";
              type empty;
            }
          }
          case media-rtp {
            container rtp {
              description
                "Use RTP stream for silence detection, this is default";
              presence "true";
              leaf receive {
                description
                  "Only for the packets received";
                type empty;
              }
            }
          }
          case media-rtplib {
            leaf rtplib {
              description
                "Use RTP ( comfort noise = activity) for silence detection";
              type empty;
            }
          }
        }
      }
      container timer {
        description
          "Gateway-wide timers";
        choice media-type {
          case inactive {
            container media-inactive {
              description
                "(dsp based) configure media inactivity timer- available for h323/sip only at this time";
              leaf media-trans-interval {
                description
                  "multiples of RTCP report transmission interval. Value of 5 Recommended";
                type uint16 {
                  range "4..1000";
                }
              }
            }
          }
          case rtcp {
            container receive-rtcp {
              description
                "(non-dsp based) configure media inactivity timer- available for h323/sip only at this time";
              leaf rtcp-trans-interval {
                description
                  "multiples of RTCP report transmission interval. Value of 5 Recommended";
                type uint16 {
                  range "4..1000";
                }
              }
            }
          }
        }
        container receive-rtp {
          description
            "configure absolute RTP receive timer in seconds";
          leaf rtp-timer-interval {
            description
              "RTP timer in seconds. Value of 1200 Recommended";
            type uint32 {
              range "180..86400";
            }
          }
        }
      }
    }
  }

  grouping config-application-grouping {
    container application {
      description
        "Define application";
      list service {
        description
          "Configure standalone application";
        key "service-name";
        leaf service-name {
          description
            "Name of the service/package";
          type config-application-service-name;
        }
        list param {
          description
            "Application parameter (current paramspace implied)";
          key "param-name";
          leaf param-name {
            description
              "Parameter name";
            type string;
          }
          leaf param-value {
            description
              "Value for the parameter";
            type string;
          }
        }
      }
      list package {
        description
          "Configure linkable package";
        key "package-name";
        leaf package-name {
          description
            "Name of the service/package";
          type enumeration {
            enum auth;
          }
        }
        uses config-package-auth-param-grouping;
      }
      container global {
        description
          "Configure global application settings";
        container service {
          description
            "Global services configuration";
          leaf alternate {
            description
              "Define alternate service to use if configured service is unavailable";
            type config-application-service-name;
          }
          leaf default {
            description
              "Define default service for use when none configured via dial-peer";
            type config-application-service-name;
          }
        }
      }
    }
  }

  grouping config-wsapi-secureWsapi-grouping {
    container message-exchange {
      description
        "message exchange";
      leaf max-failures {
        description
          "max failures";
        type uint8 {
          range "1..100";
        }
        default "1";
      }
    }
    leaf response-timeout {
      description
        "response timeout for outbound solicit and notify";
      type uint16 {
        range "1..300";
      }
    }
    leaf source-address {
      description
        "source address in IP address or hostname";
      type string;
    }
    container probing {
      description
        "probing";
      leaf max-failures {
        description
          "max-failures";
        type uint8 {
          range "1..5";
        }
        default "3";
      }
      container interval {
        description
          "interval";
        leaf keepalive {
          description
            "interval during probing keepalive state";
          type uint8 {
            range "1..255";
          }
          default "120";
        }
        leaf negative {
          description
            "interval during probing negative state";
          type uint8 {
            range "1..20";
          }
          default "5";
        }
      }
    }
  }

  grouping config-uc-grouping {
    container uc {
      description
        "Unified Communication";
      container wsapi {
        must 'not(../secure-wsapi)' {
          error-message "Error: remove existing wsapi secure mode configuration first";
        }
        presence "true";
        uses config-wsapi-secureWsapi-grouping;
        container provider {
          description
            "Provider";
          container xcc {
            description
              "wsapi xcc";
            presence "true";
            leaf remote-url {
              description
                "A string URL";
              type string;
            }
            leaf shutdown {
              description
                "shutdown";
              type boolean;
              default "false";
            }
          }
          container xmf {
            description
              "wsapi xmf";
            presence "true";
            list remote-url {
              key "url-index";
              unique "url-string";
              leaf url-index {
                type uint16 {
                  range "1..32";
                }
              }
              leaf url-string {
                type string;
              }
            }
            leaf shutdown {
              description
                "shutdown";
              type boolean;
              default "false";
            }
          }
          container xcdr {
            description
              "wsapi xcdr";
            presence "true";
            uses config-uc-wsapi-remote-url;
          }
          container xsvc {
            description
              "wsapi xsvc";
            presence "true";
            uses config-uc-wsapi-remote-url;
          }
        }
      }
      container secure-wsapi {
        must 'not(../wsapi)' {
          error-message "Error: Remove existing wsapi non-secure mode configuration first";
        }
        presence "true";
        uses config-wsapi-secureWsapi-grouping;
        container provider {
          description
            "Provider";
          container xcc {
            description
              "wsapi xcc";
            presence "true";
            leaf remote-url {
              description
                "A string URL";
              type string {
                pattern 'https://([0-9]+\.[0-9]+\.[0-9]+\.[0-9]+(:[0-9]+)?)/(\S+)' {
                  error-message "invalid url: expected https://<ipv4_address>[:<port>][/<path>]";
                }
              }
            }
            leaf shutdown {
              description
                "shutdown";
              type boolean;
              default "false";
            }
          }
          container xsvc {
            description
              "wsapi xsvc";
            presence "true";
            container remote-url {
              leaf url-index {
                type enumeration {
                  enum 1;
                }
              }
              leaf url-string {
                description
                  "A string URL";
                when "../url-index = '1'";
                type string {
                  pattern 'https://([0-9]+\.[0-9]+\.[0-9]+\.[0-9]+(:[0-9]+)?)/(\S+)' {
                    error-message "invalid url: expected https://<ipv4_address>[:<port>][/<path>]";
                  }
                }
              }
            }
            leaf shutdown {
              description
                "shutdown";
              type boolean;
              default "false";
            }
          }
        }
      }
    }
  }

  grouping config-http-grouping {
    container http {
      description
        "HTTP Config";
      container client {
        description
          "HTTP Client Config";
        container connection {
          description
            "Configure HTTP Client connection";
          container idle {
            description
              "Configure connection idle time allowed";
            leaf timeout {
              description
                "A connection will be closed if it is left idle for this long";
              type uint32 {
                range "1..600";
              }
              default "5";
            }
          }
          leaf persistent {
            description
              "Enable HTTP persistent connections";
            type empty;
          }
          leaf timeout {
            description
              "How long HTTP Client waits for a server connection to establish before giving up";
            type uint16 {
              range "1..60";
            }
          }
        }
      }
    }
  }

  grouping config-codec-profile-grouping {
    container codec {
      description
        "Global codec profile commands";
      list profile {
        description
          "Codec profile configuration";
        max-elements 1000000;
        key "id";
        leaf id {
          description
            "Profile tag for the Codec";
          type uint32 {
            range "1..1000000";
          }
        }
        leaf codec-type {
          description
            "Specify the codec for this profile";
          type enumeration {
            enum aacld;
            enum h263;
            enum h263+;
            enum h264;
            enum mp4a-latm;
            enum opus;
          }
        }
        container clock-rate {
          description
            "Set clock rate for codec";
          when "../codec-type != 'opus'";
          leaf range {
            type uint32 {
              range "0..1000000";
            }
            default "0";
          }
        }
        container fmtp {
          description
            "Set fmtp string for this codec";
          leaf fmtp-string {
            description
              "Format: fmtp:<payload type> <name1>=<val1>;<name2>=<val2>...";
            type string;
          }
        }
      }
    }
  }

  grouping config-call-threshold-grouping {
    container low {
      description
        "the low threshold";
      leaf low-percentage {
        description
          "low threshold in %";
        type uint8 {
          range "1..100";
        }
      }
      container high {
        description
          "the high threshold";
        leaf high-percentage {
          description
            "high threshold in %";
          must '../../low-percentage <= .' {
            error-message "Wrong input: low > high , please reenter:";
          }
          type uint8 {
            range "1..100";
          }
        }
        leaf busyout {
          description
            "busyout the  voice interfaces if out-of-resource";
          type empty;
        }
        leaf treatment {
          description
            "apply out-of-resource to call treatment";
          type empty;
        }
      }
    }
  }

  grouping config-call-parameters-grouping {
    container call {
      description
        "Configure Call parameters";
      container threshold {
        description
          "Configure the threshold for used resources";
        container global {
          description
            "the global resources of this gateway";
          container cpu-5sec {
            description
              "the CPU utilization in the last 5 seconds";
            uses config-call-threshold-grouping;
          }
          container cpu-avg {
            description
              "the average CPU utilization";
            uses config-call-threshold-grouping;
          }
          container io-mem {
            description
              "the IO memory utilization";
            uses config-call-threshold-grouping;
          }
          container proc-mem {
            description
              "the Processor memory utilization";
            uses config-call-threshold-grouping;
          }
          container total-calls {
            description
              "the total number of calls";
            uses config-call-threshold-grouping;
          }
          container total-mem {
            description
              "the total memory utilization";
            uses config-call-threshold-grouping;
          }
        }
        container poll-interval {
          description
            "the poll interval for some resources";
          leaf cpu-avg {
            description
              "the CPU average interval";
            type uint16 {
              range "10..300";
            }
          }
          leaf memory {
            description
              "the memory average polling interval";
            type uint8 {
              range "1..60";
            }
          }
        }
      }
      container spike {
        description
          "Configure the threshold for call spiking";
        leaf incoming-call {
          description
            "Incoming call numbers for spiking threshold";
          type uint32 {
            range "1..2147483647";
          }
        }
        container steps {
          description
            "number of steps for spiking sliding window";
          leaf num-steps {
            description
              "number of steps";
            type uint8 {
              range "3..10";
            }
          }
          leaf size {
            description
              "step size in millisecond";
            type uint8 {
              range "100..250";
            }
          }
        }
      }
      container treatment {
        description
          "Configure the treatment";
        container action {
          description
            "Action to take when call treatment is triggered";
          leaf hairpin {
            description
              "Hairpin";
            type empty;
          }
          leaf playmsg {
            description
              "play the selected message";
            type string;
          }
          leaf reject {
            description
              "Disconnect the call and pass down cause code";
            type empty;
          }
        }
        container cause-code {
          description
            "Select the cause code for disconnection";
          leaf busy {
            description
              "Insert cause code indicating the GW is busy (17)";
            type empty;
          }
          leaf no-QoS {
            description
              "Insert cause code indicating the GW can't provide QOS (49)";
            type empty;
          }
          leaf no-resource {
            description
              "Insert cause code indicating the GW has no resource (47)";
            type empty;
          }
        }
        container isdn-reject {
          description
            "Select the ISDN reject cause-code";
          leaf cause-code {
            description
              "ISDN cause code for rejection";
            type uint8 {
              range "34..47";
            }
          }
        }
        leaf on {
          description
            "toggle deny on/off";
          type empty;
        }
      }
    }
  }

  grouping config-failure-grouping {
    leaf failure {
      description
        "Call failure";
      type uint16 {
        range "400..699";
      }
    }
  }

  grouping config-error-code-override-grouping {
    container error-code-override {
      description
        "Configure sip error code";
      container cac-bandwidth {
        description
          "Status code to be sent for max-bandwidth CAC";
        uses config-failure-grouping;
      }
      container call {
        description
          "Configure call parameters";
        container spike {
          description
            "Status code to be sent for call spiking";
          uses config-failure-grouping;
        }
      }
      container cpu {
        description
          "Status code to be sent for all cpu threshold";
        uses config-failure-grouping;
      }
      container max-conn {
        description
          "Status code to be sent for max-conn threshold";
        uses config-failure-grouping;
      }
      container mem {
        description
          "Status code to be sent for all memory threshold";
        uses config-failure-grouping;
      }
      container options-keepalive {
        description
          "Status code to be sent for options keepalive";
        uses config-failure-grouping;
      }
      container sip-shutdown {
        description
          "Status code to be sent for all SIP Shutdown";
        uses config-failure-grouping;
      }
      container total-calls {
        description
          "Status code to be sent for total call threshold";
        uses config-failure-grouping;
      }
    }
  }

  grouping config-credentials-grouping {
    container credentials {
      description
        "credentials service";
      presence "true";
      leaf trustpoint {
        description
          "define trustpoint for credentials service user";
        type string {
          length "1..142";
        }
      }
      container ip {
        description
          "Define IP address and port for credentials service";
        leaf source-address {
          description
            "Define IP address and port for credentials service";
          type inet:ipv4-address;
        }
        leaf port {
          description
            "Define tcp port for credentials service";
          type uint16 {
            range "2000..9999";
          }
          default "2445";
        }
      }
    }
  }

  grouping config-package-auth-param-grouping {
    container param {
      description
        "Configure param name";
      leaf passwd-prompt {
        description
          "Announcement URL to request password";
        type string;
      }
      leaf passwd {
        description
          "Predefined passwd for authorization";
        type string;
      }
      leaf user-prompt {
        description
          "Announcement URL to request account";
        type string;
      }
      leaf term-digit {
        description
          "Digit for terminating Account/Password digit collection";
        type string;
        default "#";
      }
      leaf abort-digit {
        description
          "Digit for aborting Account/Password digit collection";
        type string;
        default "*";
      }
      leaf max-retries {
        description
          "Attempts to reenter Account/Password";
        type uint16;
        default "0";
      }
      leaf max-digits {
        description
          "MAX collect digits in Account/Password";
        type uint16;
        default "32";
      }
      list param-name {
        description
          "param list";
        key "name";
        leaf name {
          description
            "Parameter name";
          type string;
        }
        leaf value {
          description
            "value";
          type string;
        }
      }
    }
  }

  grouping config-conn-reuse-srtp-nat-grouping {
    leaf conn-reuse {
      description
        "reuse the sip registration tcp connection for the end-point behind a Firewall";
      type empty;
    }
    container srtp {
      description
        "Allow SIP related SRTP options";
      container negotiate {
        description
          "SRTP negotiate options";
        leaf cisco {
          description
            "allow RTP answer to SRTP offer";
          type empty;
        }
      }
    }
    leaf nat {
      description
        "SIP nat global config";
      type enumeration {
        enum force-on {
          description
            "Assume all remote subscribers are behind NAT device";
        }
        enum auto {
          description
            "auto-detect subscriber in a remote subnet is located behind a NAT";
        }
      }
    }
  }

  grouping gw-accounting-primary-secondary-grouping {
    choice file-transfer-choice {
      case ftp-case {
        container ftp {
          description
            "ftp mode of file transfer";
          leaf ftp-server {
            type string;
          }
          leaf username {
            description
              "Username string";
            type string;
          }
          container password {
            leaf encryption {
              type enumeration {
                enum 0;
                enum 6;
                enum 7;
              }
            }
            leaf password-string {
              type string {
                length "4..80";
              }
            }
          }
        }
      }
      case sftp-case {
        container sftp {
          description
            "ftp mode of file transfer";
          leaf sftp-server {
            type string;
          }
          leaf username {
            description
              "Username string";
            type string;
          }
          container password {
            leaf encryption {
              type enumeration {
                enum 0;
                enum 6;
              }
            }
            leaf password-string {
              type string {
                length "4..80";
              }
            }
          }
        }
      }
      case ifs-case {
        leaf ifs {
          description
            "Local file system, i.e.,flash/ mem slot device name such as flash: slot0:";
          type string;
        }
      }
    }
  }

  grouping config-gw-accounting-grouping {
    container gw-accounting {
      description
        "Enable voip gateway accounting.";
      container file {
        description
          "Enable voip file accounting.";
        presence "true";
        container acct-template {
          description
            "Select accounting template";
          choice template-choice {
            case config-name {
              leaf template-name {
                description
                  "Accounting template name";
                type string;
              }
            }
            case define-name {
              leaf callhistory-detail {
                description
                  "To send all voice attributes for accounting.";
                type empty;
              }
            }
          }
        }
        leaf cdr-format {
          description
            "CDR format for file mode of accounting";
          type enumeration {
            enum compact;
            enum detailed;
          }
        }
        container maximum {
          description
            "Specify maximum value of file accounting parameters";
          leaf buffer-size {
            description
              "Specify account buffer size";
            type uint8 {
              range "6..40";
            }
            default "20";
          }
          leaf cdrflush-timer {
            description
              "Specify file mode accounting file cdr flush timer in minutes";
            type uint16 {
              range "1..1435";
            }
            default "60";
          }
          leaf fileclose-timer {
            description
              "Specify file mode accounting file closing timer in minutes";
            type uint16 {
              range "60..1440";
            }
            default "1440";
          }
          leaf filesize {
            description
              "Specify cdr file size";
            type uint16 {
              range "10..10000";
            }
          }
          leaf retry-count {
            description
              "Specify dump file account retry count";
            type uint8 {
              range "1..5";
            }
          }
        }
        container primary {
          description
            "Primary file storage url";
          uses gw-accounting-primary-secondary-grouping;
        }
        container secondary {
          description
            "Secondary file storage url";
          uses gw-accounting-primary-secondary-grouping;
        }
      }
    }
  }

  augment "/ios:native" {
    uses config-sip-ua-grouping;
    uses config-voice-grouping;
    uses config-voice-call-manager-fallback-grouping;
    uses config-voice-card-grouping;
    uses config-dial-peer-grouping;
    uses config-dspfarm-profile-grouping;
    uses config-sccp-grouping;
    uses config-dsapp-line-grouping;
    uses config-ccm-manager-grouping;
    uses config-trunk-group-grouping;
    uses config-num-exp-grouping;
    uses config-gateway-grouping;
    uses config-application-grouping;
    uses config-uc-grouping;
    uses config-http-grouping;
    uses config-codec-profile-grouping;
    uses config-call-parameters-grouping;
    uses config-media-grouping;
    uses config-credentials-grouping;
    uses config-gw-accounting-grouping;
  }

  augment "/ios:native/sip-ua" {
    uses config-registrar-grouping;
    uses config-connection-reuse-grouping;
  }

  augment "/ios:native/voice/class/tenant" {
    uses config-authentication;
    uses config-credentials;
    uses config-error-code-override-grouping;
    uses config-conn-reuse-srtp-nat-grouping;
    uses config-sip-ua-common-grouping;
    container retry {
      description
        "Change default retries for each SIP Method";
      uses config-sip-retry-timers-grouping;
    }
    container timers {
      description
        "SIP Signaling Timers Configuration";
      uses config-sip-signaling-timers-grouping;
    }
  }
}
