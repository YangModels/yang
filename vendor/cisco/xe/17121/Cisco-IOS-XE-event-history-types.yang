module Cisco-IOS-XE-event-history-types {
  yang-version 1.1;
  namespace "http://cisco.com/ns/yang/Cisco-IOS-XE-event-history-types";
  prefix event-history-types;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for event history data types.
     Copyright (c) 2016-2019, 2022 by Cisco Systems, Inc.
     All rights reserved.";

  revision 2022-11-01 {
    description
      "Update yang-version to 1.1";
    reference
      "1.3.0";
    cisco-semver:module-version "1.3.0";
  }
  revision 2019-05-01 {
    description
      "Added semantic version";
    reference
      "1.2.0";
    cisco-semver:module-version "1.2.0";
  }
  revision 2018-11-30 {
    description
      "- Cleaned up spelling errors in descriptions.
       - Introduced event dynamic counters";
    reference
      "1.1.0";
    cisco-semver:module-version "1.1.0";
  }
  revision 2018-03-20 {
    description
      "Initial revision";
    reference
      "1.0.0";
    cisco-semver:module-version "1.0.0";
  }

  grouping event-history-item {
    description
      "Entry of the event history that we want to store in
       order to analyze the current state of the system";
    leaf event {
      type uint32;
      description
        "event";
    }
    leaf state {
      type uint32;
      description
        "state";
    }
    leaf context {
      type uint32;
      description
        "Additional context value that may be occasionally
         used";
    }
    leaf context-str {
      type string;
      description
        "Additional free-form context";
    }
    leaf current-rc {
      type uint32;
      description
        "Return code of the last operation to store";
    }
    leaf count {
      type uint32;
      description
        "Counter of number of occurrences of this event";
    }
    leaf sticky {
      type boolean;
      description
        "Represent whether the event is sticky or not";
    }
    leaf timestamp {
      type yang:date-and-time;
      description
        "Timestamp when the event is recorded";
    }
  }

  grouping event-history {
    description
      "Data structure containing all the state that needs to
       be stored for the object in use";
    list event-history {
      description
        "Event history";
      uses event-history-types:event-history-item;
    }
  }

  grouping dynamic-counter-item {
    description
      "Entry of the dynamic counter array";
    leaf value {
      type uint64;
      description
        "counter value";
    }
    leaf description {
      type string;
      description
        "Human readable description";
    }
  }

  grouping dynamic-counter {
    description
      "Dynamic array of counters";
    list counters {
      description
        "Counter array";
      uses event-history-types:dynamic-counter-item;
    }
  }
}
