module Cisco-IOS-XE-nhrp {
  yang-version 1.1;
  namespace "http://cisco.com/ns/yang/Cisco-IOS-XE-nhrp";
  prefix ios-nhrp;

  import cisco-semver {
    prefix cisco-semver;
  }
  import ietf-inet-types {
    prefix inet;
  }
  import Cisco-IOS-XE-interface-common {
    prefix ios-ifc;
  }
  import Cisco-IOS-XE-types {
    prefix ios-types;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Next Hop Resolution Protocol (NHRP) Yang model.
     Copyright (c) 2016, 2019 by Cisco Systems, Inc.
     All rights reserved.";

  revision 2022-11-01 {
    description
      "- Update yang-version to 1.1";
    cisco-semver:module-version "4.1.0";
  }
  revision 2021-03-01 {
    description
      "- Removed tailf:cli-diff-dependency as it is not supported";
    cisco-semver:module-version "4.0.0";
  }
  revision 2020-03-01 {
    description
      "- Added import configuration under /native/router/nhrp";
    cisco-semver:module-version "3.0.0";
  }
  revision 2019-11-01 {
    description
      "- Added new NHRP config";
    cisco-semver:module-version "2.0.0";
  }
  revision 2019-07-01 {
    description
      "- Establish semantic version baseline
       - Support for all IPV4 and IPV6 NHRP commands under tunnel
       - Augmented Virtual-Template with nhrp";
    cisco-semver:module-version "1.0.0";
  }
  revision 2017-02-07 {
    description
      "Initial revision";
  }

  typedef redist-ospf-external-type {
    type enumeration {
      enum 1;
      enum 2;
    }
  }

  grouping config-interface-nhrp-common-grouping {
    leaf authentication {
      description
        "authentication string";
      type string;
    }
    container bfd {
      description
        "BFD Parameters";
      container notify {
        description
          "Set registration retry count for notification";
        leaf services {
          description
            "Retry counter for Services";
          type union {
            type enumeration {
              enum never;
            }
            type uint8 {
              range "0..10";
            }
          }
        }
        leaf transport {
          description
            "Retry counter for Transport";
          type union {
            type enumeration {
              enum never;
            }
            type uint8 {
              range "0..10";
            }
          }
        }
      }
      leaf strict-mode {
        description
          "Enable BFD in strict mode";
        type empty;
      }
    }
    container cache {
      description
        "NHRP Cache related commands.";
      leaf bgp-sync {
        description
          "Listen to BGP for endpoint creation and deletion.";
        type empty;
      }
      leaf non-authoritative {
        description
          "Mark cache entries non-authoritative";
        type empty;
      }
    }
    leaf connect {
      description
        "NHRP event request id";
      type uint16 {
        range "1..65535";
      }
    }
    leaf holdtime {
      description
        "Number of seconds";
      type uint16 {
        range "1..65535";
      }
    }
    container max-send {
      description
        "Rate limit NHRP traffic";
      list pkt-count {
        key "pkt-count";
        leaf pkt-count {
          description
            "Packet count";
          type uint16 {
            range "1..65535";
          }
        }
        leaf every {
          description
            "Interval in seconds";
          type uint16 {
            range "10..65535";
          }
        }
      }
    }
    container multicast {
      description
        "Multicast Parameters";
      choice batch-size-choice {
        container batch-size-default {
          description
            "Specify the batch size of Multicast replication";
          leaf batch-size {
            description
              "Batch Size";
            type empty;
          }
        }
        container batch-size-value {
          description
            "Specify batch interval to replicate Multicast Packets";
          leaf batch-size {
            description
              "Batch Size";
            type uint16 {
              range "1..65535";
            }
          }
          leaf batch-interval {
            description
              "Interval in milliseconds";
            type uint16 {
              range "1..65535";
            }
          }
        }
      }
    }
    leaf network-id {
      description
        "Network identifier";
      type uint32 {
        range "1..4294967295";
      }
    }
    container path {
      description
        "NHRP path specific configuration";
      container preference {
        description
          "Default preference for cache entries over this path";
        choice path-size-adaptive {
          case path-size-case {
            container pathsize {
              description
                "Default preference";
              leaf path-size {
                description
                  "Path preference (relative)";
                type uint16 {
                  range "1..255";
                }
              }
              leaf adaptive {
                description
                  "Adaptive path preference over this path";
                type empty;
              }
            }
          }
          case adaptive-case {
            leaf adaptive {
              description
                "Adaptive path preference over this path";
              type empty;
            }
          }
        }
      }
    }
    leaf record {
      description
        "Allow NHRP record option";
      type empty;
    }
    container redirect {
      description
        "Enable NHRP redirect traffic indication";
      presence "true";
      leaf timeout {
        description
          "Interval in seconds";
        type uint8 {
          range "2..30";
        }
      }
    }
    container reject {
      description
        "NHRP resolution reject request";
      list reqid {
        key "reqid";
        leaf reqid {
          description
            "reqid value";
          type uint16 {
            range "1..65535";
          }
        }
        leaf rej-secs {
          description
            "Number of seconds";
          type uint16 {
            range "0..65535";
          }
        }
      }
    }
    container responder {
      description
        "Responder interface";
      uses ios-ifc:interface-grouping;
    }
    leaf send-routed {
      description
        "Send NHRP packets via the routed path first";
      type empty;
    }
    container server-only {
      description
        "Disable NHRP requests";
      presence "true";
      leaf non-caching {
        description
          "Do not create NHRP cache entries";
        type empty;
      }
    }
    container shortcut {
      description
        "Enable shortcut switching";
      presence "true";
      leaf virtual-template {
        description
          "Virtual template number";
        type uint16 {
          range "1..4095";
        }
      }
    }
    container trigger-svc {
      description
        "Create NHRP cut-through based on traffic load";
      list kbps {
        key "kbps";
        leaf kbps {
          description
            "Trigger rate in kbps";
          type uint32 {
            range "1..4294967295";
          }
        }
        leaf tear-kbps {
          description
            "Teardown rate in kbps";
          type uint32 {
            range "0..4294967295";
          }
        }
      }
    }
    leaf use {
      description
        "Number of packets to cause NHRP request";
      type uint16 {
        range "1..65535";
      }
    }
  }

  grouping config-interface-ipv4-nhrp-grouping {
    container nhrp-v4 {
      container nhrp {
        description
          "NHRP interface subcommands";
        container attribute {
          description
            "NHRP attribute set";
          container set {
            description
              "attribute set";
            list attr-type {
              key "attr-type";
              leaf attr-type {
                description
                  "attribute type";
                type string;
              }
              leaf attr-val {
                description
                  "attribute value";
                type string;
              }
            }
          }
          leaf group {
            description
              "NHRP group name";
            type string;
          }
        }
        container interest {
          description
            "Specify an access list";
          leaf none {
            description
              "No traffic is interesting.";
            type empty;
          }
          leaf acl-range {
            description
              "IP access list";
            type uint8 {
              range "1..199";
            }
          }
        }
        container registration {
          description
            "Settings for registration packets.";
          leaf delay {
            description
              " Number of seconds to delay registration.";
            type uint8 {
              range "0..10";
            }
          }
          leaf no-unique {
            description
              "Do not set the 'Unique' flag in registration requests.";
            type empty;
          }
          leaf req-def-map {
            description
              "Request default map(s) in registration requests.";
            type empty;
          }
          leaf timeout {
            description
              "Number of seconds";
            type uint16 {
              range "1..65535";
            }
          }
        }
        container map {
          description
            "Map dest IP addresses to NBMA addresses";
          list dest-ipv4 {
            key "dest-ipv4";
            leaf dest-ipv4 {
              description
                "IP address of destination";
              type inet:ipv4-address;
            }
            list nbma-ipv4 {
              key "nbma-ipv4";
              leaf nbma-ipv4 {
                description
                  "IP NBMA address";
                type inet:ipv4-address;
              }
              list ipv4 {
                description
                  "IP NBMA address";
                key "ipv4-address";
                leaf ipv4-address {
                  type inet:ipv4-address;
                }
                leaf preference {
                  description
                    " Preference associated with the map";
                  type uint8 {
                    range "1..255";
                  }
                }
              }
              list ipv6 {
                description
                  "IPv6 NBMA address";
                key "ipv6-address";
                leaf ipv6-address {
                  type inet:ipv6-address;
                }
                leaf preference {
                  description
                    "Preference associated with the map";
                  type uint8 {
                    range "1..255";
                  }
                }
              }
              leaf preference {
                description
                  " Preference associated with the map";
                type uint8 {
                  range "1..255";
                }
              }
            }
            list dest-mask {
              key "dest-mask";
              leaf dest-mask {
                description
                  "IP mask of destination";
                type inet:ipv4-address;
              }
              list ipv4 {
                description
                  "IP NBMA address";
                key "ipv4-address";
                leaf ipv4-address {
                  type inet:ipv4-address;
                }
                leaf preference {
                  description
                    " Preference associated with the map";
                  type uint8 {
                    range "1..255";
                  }
                }
              }
              list ipv6 {
                description
                  "IPv6 NBMA address";
                key "ipv6-address";
                leaf ipv6-address {
                  type inet:ipv6-address;
                }
                leaf preference {
                  description
                    " Preference associated with the map";
                  type uint8 {
                    range "1..255";
                  }
                }
              }
              leaf preference {
                description
                  " Preference associated with the map";
                type uint8 {
                  range "1..255";
                }
              }
            }
            list nbma-ipv6 {
              key "nbma-ipv6";
              leaf nbma-ipv6 {
                description
                  " IPv6 NBMA address";
                type inet:ipv6-address;
              }
              leaf preference {
                description
                  " Preference associated with the map";
                type uint8 {
                  range "1..255";
                }
              }
            }
          }
          container multicast {
            description
              "Use this NBMA mapping for broadcasts/multicasts";
            leaf-list nbma_ipv4 {
              type inet:ipv4-address;
            }
            leaf-list nbma_ipv6 {
              type inet:ipv6-address;
            }
            leaf dynamic {
              description
                "Dynamically learn destinations from client registrations on hub";
              type empty;
            }
          }
        }
        container nhs {
          description
            "Specify a next hop server";
          list ipv4 {
            key "ipv4";
            leaf ipv4 {
              description
                "Protocol IP address of NHS";
              type inet:ipv4-address;
            }
            leaf cluster {
              description
                "NHS cluster number";
              type uint8 {
                range "0..10";
              }
            }
            container nbma {
              description
                "NBMA of NHS";
              list ipv4 {
                key "ipv4";
                leaf ipv4 {
                  description
                    "IPv4 address";
                  type inet:ipv4-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list prior {
                      key "prior";
                      leaf prior {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list pri {
                    key "pri";
                    leaf pri {
                      description
                        "NHS priority, range = 0 to 255, 0 is the highest";
                      type uint8 {
                        range "0..255";
                      }
                    }
                    leaf cluster {
                      description
                        "NHS cluster number";
                      type uint8 {
                        range "0..10";
                      }
                    }
                  }
                }
              }
              list nhs-fqdn {
                key "nhs-fqdn";
                leaf nhs-fqdn {
                  description
                    "NHS FQDN string";
                  type string;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list mc-pri {
                      key "mc-pri";
                      leaf mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list nhs-pri {
                    key "nhs-pri";
                    leaf nhs-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              list ipv6 {
                key "ipv6";
                leaf ipv6 {
                  description
                    "IPv6 address";
                  type inet:ipv6-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list mc-pri {
                      key "mc-pri";
                      leaf mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list mc-prior {
                    key "mc-prior";
                    leaf mc-prior {
                      description
                        "NHS priority, range = 0 to 255, 0 is the highest";
                      type uint8 {
                        range "0..255";
                      }
                    }
                    leaf cluster {
                      description
                        "NHS cluster number";
                      type uint8 {
                        range "0..10";
                      }
                    }
                  }
                }
              }
            }
            container priority {
              description
                "NHS priority, don't specify for default priority";
              list pri-range {
                key "pri-range";
                leaf pri-range {
                  description
                    "NHS priority, range = 0 to 255, 0 is the highest";
                  type uint8 {
                    range "0..255";
                  }
                }
                leaf cluster {
                  description
                    "NHS cluster number";
                  type uint8 {
                    range "0..10";
                  }
                }
              }
            }
          }
          container cluster {
            description
              "NHS Redundancy cluster configurations";
            list clus-num {
              key "clus-num";
              leaf clus-num {
                description
                  "NHS cluster number";
                type uint8 {
                  range "0..10";
                }
              }
              leaf max-connections {
                description
                  "Max-connections value";
                type uint8 {
                  range "0..255";
                }
              }
            }
          }
          container dynamic {
            description
              "NHS protocol address dynamically learnt";
            container nbma {
              description
                "NBMA of NHS";
              list ipv4 {
                description
                  "NBMA of NHS";
                key "ipv4";
                leaf ipv4 {
                  description
                    "IPv4 address";
                  type inet:ipv4-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list dyn-pri {
                      key "dyn-pri";
                      leaf dyn-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list n-prior {
                    key "n-prior";
                    leaf n-prior {
                      description
                        "NHS priority, range = 0 to 255, 0 is the highest";
                      type uint8 {
                        range "0..255";
                      }
                    }
                    leaf cluster {
                      description
                        "NHS cluster number";
                      type uint8 {
                        range "0..10";
                      }
                    }
                  }
                }
              }
              list dyn-fqdn {
                key "dyn-fqdn";
                leaf dyn-fqdn {
                  description
                    "NHS FQDN string";
                  type string;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list dyn-mc-pri {
                      key "dyn-mc-pri";
                      leaf dyn-mc-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list dp {
                    key "dp";
                    leaf dp {
                      description
                        "NHS priority, range = 0 to 255, 0 is the highest";
                      type uint8 {
                        range "0..255";
                      }
                    }
                    leaf cluster {
                      description
                        "NHS cluster number";
                      type uint8 {
                        range "0..10";
                      }
                    }
                  }
                }
              }
              list ipv6 {
                key "ipv6";
                leaf ipv6 {
                  description
                    "IPv6 address";
                  type inet:ipv6-address;
                }
                leaf cluster {
                  description
                    "NHS cluster number";
                  type uint8 {
                    range "0..10";
                  }
                }
                container multicast {
                  description
                    "Use this NBMA mapping for broadcasts/multicasts";
                  presence "true";
                  leaf cluster {
                    description
                      "NHS cluster number";
                    type uint8 {
                      range "0..10";
                    }
                  }
                  container priority {
                    description
                      "NHS priority, don't specify for default priority";
                    list v6-pri {
                      key "v6-pri";
                      leaf v6-pri {
                        description
                          "NHS priority, range = 0 to 255, 0 is the highest";
                        type uint8 {
                          range "0..255";
                        }
                      }
                      leaf cluster {
                        description
                          "NHS cluster number";
                        type uint8 {
                          range "0..10";
                        }
                      }
                    }
                  }
                }
                container priority {
                  description
                    "NHS priority, don't specify for default priority";
                  list v6-pri2 {
                    key "v6-pri2";
                    leaf v6-pri2 {
                      description
                        "NHS priority, range = 0 to 255, 0 is the highest";
                      type uint8 {
                        range "0..255";
                      }
                    }
                    leaf cluster {
                      description
                        "NHS cluster number";
                      type uint8 {
                        range "0..10";
                      }
                    }
                  }
                }
              }
            }
          }
          leaf fallback {
            description
              "NHS Redundancy Fallback time, 0 -60 seconds";
            type uint8 {
              range "0..60";
            }
          }
        }
        container summary-map {
          description
            "Summary IP address";
          list dest-ipv4 {
            key "dest-ipv4";
            leaf dest-ipv4 {
              description
                "IP address";
              type inet:ipv4-address;
            }
            list dest-mask {
              key "dest-mask";
              leaf dest-mask {
                description
                  "mask destination";
                type inet:ipv4-address;
              }
              list nbma-ipv4 {
                key "nbma-ipv4";
                leaf nbma-ipv4 {
                  description
                    "IP NBMA address";
                  type inet:ipv4-address;
                }
                uses summary-map-grouping;
                container multicast {
                  description
                    "Use this NBMA mapping for broadcasts/multicasts";
                  presence "true";
                  uses summary-map-grouping;
                }
                container preference {
                  description
                    "Preference associated with the map";
                  list pri-range {
                    key "pri-range";
                    leaf pri-range {
                      description
                        "NHS priority, range = 1 to 255, 0 is the highest";
                      type uint8 {
                        range "1..255";
                      }
                    }
                    uses summary-map-grouping;
                    container multicast {
                      description
                        "Use this NBMA mapping for broadcasts/multicasts";
                      presence "true";
                      uses summary-map-grouping;
                    }
                  }
                  uses summary-map-grouping;
                  container multicast {
                    description
                      "Use this NBMA mapping for broadcasts/multicasts";
                    presence "true";
                    uses summary-map-grouping;
                  }
                }
              }
              list nbma-ipv6 {
                key "nbma-ipv6";
                leaf nbma-ipv6 {
                  description
                    "IPv6 NBMA address";
                  type inet:ipv6-address;
                }
                uses summary-map-grouping;
                container multicast {
                  description
                    "Use this NBMA mapping for broadcasts/multicasts";
                  presence "true";
                  uses summary-map-grouping;
                }
                container preference {
                  description
                    "Preference associated with the map";
                  list pri-range {
                    key "pri-range";
                    leaf pri-range {
                      description
                        "NHS priority, range = 1 to 255, 0 is the highest";
                      type uint8 {
                        range "1..255";
                      }
                    }
                    uses summary-map-grouping;
                    container multicast {
                      description
                        "Use this NBMA mapping for broadcasts/multicasts";
                      presence "true";
                      uses summary-map-grouping;
                    }
                  }
                  uses summary-map-grouping;
                  container multicast {
                    description
                      "Use this NBMA mapping for broadcasts/multicasts";
                    presence "true";
                    uses summary-map-grouping;
                  }
                }
              }
              leaf resolve {
                description
                  "Resolve mapping information for this summary";
                type empty;
              }
            }
          }
          list length-ipv4 {
            key "prefix";
            leaf prefix {
              description
                "IP address/<length> of destination, eg:24.6.0.0/16";
              type inet:ipv4-prefix;
            }
            list nbma-ipv4 {
              key "nbma-ipv4";
              leaf nbma-ipv4 {
                description
                  "IP NBMA address";
                type inet:ipv4-address;
              }
              uses summary-map-grouping;
              container multicast {
                description
                  "Use this NBMA mapping for broadcasts/multicasts";
                presence "true";
                uses summary-map-grouping;
              }
              container preference {
                description
                  "Preference associated with the map";
                list pri-range {
                  key "pri-range";
                  leaf pri-range {
                    description
                      "NHS priority, range = 1 to 255, 0 is the highest";
                    type uint8 {
                      range "1..255";
                    }
                  }
                  uses summary-map-grouping;
                  container multicast {
                    description
                      "Use this NBMA mapping for broadcasts/multicasts";
                    presence "true";
                    uses summary-map-grouping;
                  }
                }
                uses summary-map-grouping;
                container multicast {
                  description
                    "Use this NBMA mapping for broadcasts/multicasts";
                  presence "true";
                  uses summary-map-grouping;
                }
              }
            }
            list nbma-ipv6 {
              key "nbma-ipv6";
              leaf nbma-ipv6 {
                description
                  "IPv6 NBMA address";
                type inet:ipv6-address;
              }
              uses summary-map-grouping;
              container multicast {
                description
                  "Use this NBMA mapping for broadcasts/multicasts";
                presence "true";
                uses summary-map-grouping;
              }
              container preference {
                description
                  "Preference associated with the map";
                list pri-range {
                  key "pri-range";
                  leaf pri-range {
                    description
                      "NHS priority, range = 1 to 255, 0 is the highest";
                    type uint8 {
                      range "1..255";
                    }
                  }
                  uses summary-map-grouping;
                  container multicast {
                    description
                      "Use this NBMA mapping for broadcasts/multicasts";
                    presence "true";
                    uses summary-map-grouping;
                  }
                }
                uses summary-map-grouping;
                container multicast {
                  description
                    "Use this NBMA mapping for broadcasts/multicasts";
                  presence "true";
                  uses summary-map-grouping;
                }
              }
            }
            leaf resolve {
              description
                "Resolve mapping information for this summary";
              type empty;
            }
          }
        }
        uses config-interface-nhrp-common-grouping;
      }
    }
  }

  grouping config-interface-ipv6-nhrp-grouping {
    container nhrp {
      description
        "NHRP interface subcommands";
      container attribute {
        description
          "NHRP attribute set";
        container set {
          description
            "attribute set";
          list attr-type {
            key "attr-type";
            leaf attr-type {
              description
                "attribute type";
              type string;
            }
            leaf attr-val {
              description
                "attribute value";
              type string;
            }
          }
        }
      }
      container interest {
        description
          "Specify an access list";
        leaf none {
          description
            "No traffic is interesting.";
          type empty;
        }
        leaf acl-range {
          description
            "IP access list";
          type string;
        }
      }
      container map {
        description
          "Map dest IP addresses to NBMA addresses";
        list ipv6_nn {
          key "ipv6_nn";
          leaf ipv6_nn {
            description
              "IP prefix <network>/<length>";
            type ios-types:ipv6-prefix;
          }
          list ipv4 {
            description
              "IP NBMA address";
            key "ipv4-address";
            leaf ipv4-address {
              description
                "IPv4 NBMA address";
              type inet:ipv4-address;
            }
            leaf preference {
              description
                " Preference associated with the map";
              type uint8 {
                range "1..255";
              }
            }
          }
          list ipv6 {
            description
              "IPv6 NBMA address";
            key "ipv6-address";
            leaf ipv6-address {
              description
                "IPv6 NBMA address";
              type inet:ipv6-address;
            }
            leaf preference {
              description
                "Preference associated with the map";
              type uint8 {
                range "1..255";
              }
            }
          }
        }
      }
      container nhs {
        description
          "Specify a next hop server";
        list ipv6 {
          key "ipv6";
          leaf ipv6 {
            description
              "Protocol IP address of NHS";
            type inet:ipv6-address;
          }
          leaf cluster {
            description
              "NHS cluster number";
            type uint8 {
              range "0..10";
            }
          }
          container nbma {
            description
              "NBMA of NHS";
            list ipv4 {
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list prior {
                    key "prior";
                    leaf prior {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list pri {
                  key "pri";
                  leaf pri {
                    description
                      "NHS priority, range = 0 to 255, 0 is the highest";
                    type uint8 {
                      range "0..255";
                    }
                  }
                  leaf cluster {
                    description
                      "NHS cluster number";
                    type uint8 {
                      range "0..10";
                    }
                  }
                }
              }
            }
            list nhs-fqdn {
              key "nhs-fqdn";
              leaf nhs-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list nhs-pri {
                  key "nhs-pri";
                  leaf nhs-pri {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list mc-prior {
                  key "mc-prior";
                  leaf mc-prior {
                    description
                      "NHS priority, range = 0 to 255, 0 is the highest";
                    type uint8 {
                      range "0..255";
                    }
                  }
                  leaf cluster {
                    description
                      "NHS cluster number";
                    type uint8 {
                      range "0..10";
                    }
                  }
                }
              }
            }
          }
          container priority {
            description
              "NHS priority, don't specify for default priority";
            list pri-range {
              key "pri-range";
              leaf pri-range {
                description
                  "NHS priority, range = 0 to 255, 0 is the highest";
                type uint8 {
                  range "0..255";
                }
              }
              leaf cluster {
                description
                  "NHS cluster number";
                type uint8 {
                  range "0..10";
                }
              }
            }
          }
        }
        container cluster {
          description
            "NHS Redundancy cluster configurations";
          list clus-num {
            key "clus-num";
            leaf clus-num {
              description
                "NHS cluster number";
              type uint8 {
                range "0..10";
              }
            }
            leaf max-connections {
              description
                "Max-connections value";
              type uint8 {
                range "0..255";
              }
            }
          }
        }
        container dynamic {
          description
            "NHS protocol address dynamically learnt";
          container nbma {
            description
              "NBMA of NHS";
            list ipv4 {
              description
                "NBMA of NHS";
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-pri {
                    key "dyn-pri";
                    leaf dyn-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list n-prior {
                  key "n-prior";
                  leaf n-prior {
                    description
                      "NHS priority, range = 0 to 255, 0 is the highest";
                    type uint8 {
                      range "0..255";
                    }
                  }
                  leaf cluster {
                    description
                      "NHS cluster number";
                    type uint8 {
                      range "0..10";
                    }
                  }
                }
              }
            }
            list dyn-fqdn {
              key "dyn-fqdn";
              leaf dyn-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-mc-pri {
                    key "dyn-mc-pri";
                    leaf dyn-mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list dp {
                  key "dp";
                  leaf dp {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list v6-pri {
                    key "v6-pri";
                    leaf v6-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list v6-pri2 {
                  key "v6-pri2";
                  leaf v6-pri2 {
                    description
                      "NHS priority, range = 0 to 255, 0 is the highest";
                    type uint8 {
                      range "0..255";
                    }
                  }
                  leaf cluster {
                    description
                      "NHS cluster number";
                    type uint8 {
                      range "0..10";
                    }
                  }
                }
              }
            }
          }
        }
        leaf fallback {
          description
            "NHS Redundancy Fallback time, 0 -60 seconds";
          type uint8 {
            range "0..60";
          }
        }
      }
      container registration {
        description
          "Settings for registration packets.";
        leaf delay {
          description
            " Number of seconds to delay registration.";
          type uint8 {
            range "0..10";
          }
        }
        leaf no-unique {
          description
            "Do not set the 'Unique' flag in registration requests.";
          type empty;
        }
        leaf timeout {
          description
            "Number of seconds";
          type uint16 {
            range "1..65535";
          }
        }
      }
      container summary-map {
        description
          "Summary IP address";
        list ipv6-nn {
          key "ipv6-nn";
          leaf ipv6-nn {
            description
              "IP prefix <network>/<length>";
            type ios-types:ipv6-prefix;
          }
          list nbma-ipv4 {
            key "nbma-ipv4";
            leaf nbma-ipv4 {
              description
                "IP NBMA address";
              type inet:ipv4-address;
            }
            container preference {
              description
                "Preference associated with the map";
              list pri-range {
                key "pri-range";
                leaf pri-range {
                  description
                    "NHS priority, range = 1 to 255, 0 is the highest";
                  type uint8 {
                    range "1..255";
                  }
                }
                uses summary-map-grouping;
                container multicast {
                  description
                    "Use this NBMA mapping for broadcasts/multicasts";
                  presence "true";
                  uses summary-map-grouping;
                }
              }
              uses summary-map-grouping;
              container multicast {
                description
                  "Use this NBMA mapping for broadcasts/multicasts";
                presence "true";
                uses summary-map-grouping;
              }
            }
          }
          list nbma-ipv6 {
            key "nbma-ipv6";
            leaf nbma-ipv6 {
              description
                "IPv6 NBMA address";
              type inet:ipv6-address;
            }
            container preference {
              description
                "Preference associated with the map";
              list pri-range {
                key "pri-range";
                leaf pri-range {
                  description
                    "NHS priority, range = 1 to 255, 0 is the highest";
                  type uint8 {
                    range "1..255";
                  }
                }
                uses summary-map-grouping;
                container multicast {
                  description
                    "Use this NBMA mapping for broadcasts/multicasts";
                  presence "true";
                  uses summary-map-grouping;
                }
              }
              uses summary-map-grouping;
              container multicast {
                description
                  "Use this NBMA mapping for broadcasts/multicasts";
                presence "true";
                uses summary-map-grouping;
              }
            }
          }
          leaf resolve {
            description
              "Resolve mapping information for this summary";
            type empty;
          }
        }
      }
      uses config-interface-nhrp-common-grouping;
    }
  }

  grouping config-tunnel-if-state-grouping {
    container if-state-tunnel {
      container if-state {
        description
          "Allow applications to control interface state";
        leaf nhrp {
          description
            "Allow NHRP to control interface state";
          type empty;
        }
        leaf track {
          description
            "Track an object";
          type uint16 {
            range "1..1000";
          }
        }
      }
    }
  }

  grouping config-interface-tunn-grouping {
    container nhrp-tunn {
      container nhrp {
        description
          "NHRP Interface commands";
        container attribute {
          description
            "NHRP attribute";
          leaf group {
            description
              "NHRP group name";
            type string;
          }
        }
        container event-publisher {
          description
            "Enable NHRP smart spoke feature";
          leaf max-event-timeout {
            description
              "Number of seconds";
            type uint8 {
              range "1..22";
            }
          }
        }
        leaf group {
          description
            "group name string";
          type string;
        }
        container map {
          description
            "Map group name to QoS service policy";
          container group {
            description
              "NHRP group mapping";
            list nhrp-name {
              key "nhrp-name";
              leaf nhrp-name {
                description
                  "NHRP group name";
                type string;
              }
              container service-policy {
                description
                  "QoS service-policy";
                leaf output {
                  description
                    "QoS policy-map name";
                  type string;
                }
              }
            }
          }
        }
        leaf route-watch {
          description
            "Enable NHRP route watch";
          type empty;
        }
      }
    }
  }

  grouping summary-map-grouping {
    container match {
      description
        "Use this NBMA mapping based on match criteria";
      container attribute {
        description
          "Select map based on a user defined attribute";
        list attr-type {
          key "attr-type";
          leaf attr-type {
            description
              "attribute type";
            type string;
          }
          leaf attr-val {
            description
              "attribute value";
            type string;
          }
        }
      }
      leaf geo-location {
        description
          "Select map based on geographical location";
        type string;
      }
      leaf group {
        description
          "Select map based on group";
        type string;
      }
      leaf topo-location {
        description
          "Select map based on topological location";
        type string;
      }
    }
  }

  grouping config-global-nhrp-grouping {
    container nhrp {
      description
        "NHRP global commands";
      when '/ios:native/ios:service/ios:internal';
      container G-Ach {
        description
          " Generic Associated Channel ";
        leaf type {
          description
            "G-ACh type";
          type uint32 {
            range "0..32767";
          }
        }
      }
      container multicast {
        description
          "NHRP multicast related commands";
        container queue {
          description
            " Incoming multicast packet queue ";
          leaf size {
            description
              "Size of the queue";
            type uint32 {
              range "512..10240";
            }
          }
          leaf threshold {
            description
              "Threshold beyond which non-locally generated packets are dropped";
            type uint32 {
              range "0..10240";
            }
          }
        }
      }
    }
  }

  grouping config-interface-nhrp-grouping-obsolete {
    container nhrp {
      description
        "NHRP interface subcommands";
      status obsolete;
      container attribute {
        description
          "NHRP attribute set";
        status obsolete;
        container set {
          description
            "attribute set";
          status obsolete;
          list attr-type {
            status obsolete;
            key "attr-type";
            leaf attr-type {
              status obsolete;
              description
                "attribute type";
              type string;
            }
            leaf attr-val {
              status obsolete;
              description
                "attribute value";
              type string;
            }
          }
        }
      }
      leaf authentication {
        status obsolete;
        description
          "authentication string";
        type string;
      }
      container cache {
        status obsolete;
        description
          "NHRP Cache related commands.";
        leaf non-authoritative {
          status obsolete;
          description
            "Mark cache entries non-authoritative";
          type empty;
        }
      }
      leaf connect {
        status obsolete;
        description
          "NHRP event request id";
        type uint16 {
          range "1..65535";
        }
      }
      leaf group {
        status obsolete;
        type string;
      }
      leaf holdtime {
        status obsolete;
        description
          "Number of seconds";
        type uint16 {
          range "1..65535";
        }
      }
      container interest {
        status obsolete;
        description
          "Specify an access list";
        leaf acl-range {
          status obsolete;
          description
            "IP access list";
          type uint8 {
            range "1..199";
          }
        }
        leaf none {
          status obsolete;
          description
            "No traffic is interesting.";
          type empty;
        }
      }
      container map {
        status obsolete;
        description
          "Map dest IP addresses to NBMA addresses";
        list dest-ipv4 {
          status obsolete;
          key "dest-ipv4";
          leaf dest-ipv4 {
            status obsolete;
            description
              "IP address of destination";
            type inet:ipv4-address;
          }
          list nbma-ipv4 {
            status obsolete;
            key "nbma-ipv4";
            leaf nbma-ipv4 {
              status obsolete;
              description
                "IP NBMA address";
              type inet:ipv4-address;
            }
            leaf ipv4 {
              status obsolete;
              type inet:ipv4-address;
            }
            leaf ipv6 {
              status obsolete;
              type inet:ipv6-address;
            }
          }
          list dest-mask {
            status obsolete;
            key "dest-mask";
            leaf dest-mask {
              status obsolete;
              description
                "IP mask of destination";
              type inet:ipv4-address;
            }
            leaf ipv4 {
              status obsolete;
              type inet:ipv4-address;
            }
            leaf ipv6 {
              status obsolete;
              type inet:ipv6-address;
            }
          }
          leaf nbma-ipv6 {
            status obsolete;
            type inet:ipv6-address;
          }
        }
        container multicast {
          status obsolete;
          description
            "Use this NBMA mapping for broadcasts/multicasts";
          leaf-list nbma_ipv4 {
            status obsolete;
            type inet:ipv4-address;
          }
          leaf-list nbma_ipv6 {
            status obsolete;
            type inet:ipv6-address;
          }
          leaf dynamic {
            status obsolete;
            description
              "Dynamically learn destinations from client registrations on hub";
            type empty;
          }
        }
        list group {
          status obsolete;
          key "name";
          leaf name {
            status obsolete;
            type string;
          }
          container service-policy {
            status obsolete;
            leaf output {
              status obsolete;
              description
                "Policy";
              type string;
            }
          }
        }
      }
      container max-send {
        status obsolete;
        description
          "Rate limit NHRP traffic";
        list pkt-count {
          status obsolete;
          key "pkt-count";
          leaf pkt-count {
            status obsolete;
            description
              "Packet count";
            type uint16 {
              range "1..65535";
            }
          }
          leaf every {
            status obsolete;
            description
              "Interval in seconds";
            type uint16 {
              range "10..65535";
            }
          }
        }
      }
      leaf network-id {
        status obsolete;
        description
          "Network identifier";
        type uint32 {
          range "1..4294967295";
        }
      }
      container nhs {
        status obsolete;
        description
          "Specify a next hop server";
        list ipv4 {
          status obsolete;
          key "ipv4";
          leaf ipv4 {
            status obsolete;
            description
              "Protocol IP address of NHS";
            type inet:ipv4-address;
          }
          leaf cluster {
            status obsolete;
            description
              "NHS cluster number";
            type uint8 {
              range "0..10";
            }
          }
          container nbma {
            status obsolete;
            description
              "NBMA of NHS";
            list ipv4 {
              status obsolete;
              key "ipv4";
              leaf ipv4 {
                status obsolete;
                description
                  "IPv4 address";
                type inet:ipv4-address;
              }
              leaf cluster {
                status obsolete;
                description
                  "NHS cluster number";
                type uint8 {
                  range "0..10";
                }
              }
              container multicast {
                status obsolete;
                description
                  "Use this NBMA mapping for broadcasts/multicasts";
                presence "true";
                leaf cluster {
                  status obsolete;
                  description
                    "NHS cluster number";
                  type uint8 {
                    range "0..10";
                  }
                }
                container priority {
                  status obsolete;
                  description
                    "NHS priority, don't specify for default priority";
                  list prior {
                    status obsolete;
                    key "prior";
                    leaf prior {
                      status obsolete;
                      description
                        "NHS priority, range = 0 to 255, 0 is the highest";
                      type uint8 {
                        range "0..255";
                      }
                    }
                    leaf cluster {
                      status obsolete;
                      description
                        "NHS cluster number";
                      type uint8 {
                        range "0..10";
                      }
                    }
                  }
                }
              }
              container priority {
                status obsolete;
                description
                  "NHS priority, don't specify for default priority";
                list pri {
                  status obsolete;
                  key "pri";
                  leaf pri {
                    status obsolete;
                    description
                      "NHS priority, range = 0 to 255, 0 is the highest";
                    type uint8 {
                      range "0..255";
                    }
                  }
                  leaf cluster {
                    status obsolete;
                    description
                      "NHS cluster number";
                    type uint8 {
                      range "0..10";
                    }
                  }
                }
              }
            }
            list nhs-fqdn {
              status obsolete;
              key "nhs-fqdn";
              leaf nhs-fqdn {
                status obsolete;
                description
                  "NHS FQDN string";
                type string;
              }
              leaf cluster {
                status obsolete;
                description
                  "NHS cluster number";
                type uint8 {
                  range "0..10";
                }
              }
              container multicast {
                status obsolete;
                description
                  "Use this NBMA mapping for broadcasts/multicasts";
                presence "true";
                leaf cluster {
                  status obsolete;
                  description
                    "NHS cluster number";
                  type uint8 {
                    range "0..10";
                  }
                }
                container priority {
                  status obsolete;
                  description
                    "NHS priority, don't specify for default priority";
                  list mc-pri {
                    status obsolete;
                    key "mc-pri";
                    leaf mc-pri {
                      status obsolete;
                      description
                        "NHS priority, range = 0 to 255, 0 is the highest";
                      type uint8 {
                        range "0..255";
                      }
                    }
                    leaf cluster {
                      status obsolete;
                      description
                        "NHS cluster number";
                      type uint8 {
                        range "0..10";
                      }
                    }
                  }
                }
              }
              container priority {
                status obsolete;
                description
                  "NHS priority, don't specify for default priority";
                list nhs-pri {
                  status obsolete;
                  key "nhs-pri";
                  leaf nhs-pri {
                    status obsolete;
                    description
                      "NHS priority, range = 0 to 255, 0 is the highest";
                    type uint8 {
                      range "0..255";
                    }
                  }
                  leaf cluster {
                    status obsolete;
                    description
                      "NHS cluster number";
                    type uint8 {
                      range "0..10";
                    }
                  }
                }
              }
            }
            list ipv6 {
              status obsolete;
              key "ipv6";
              leaf ipv6 {
                status obsolete;
                description
                  "IPv6 address";
                type inet:ipv6-address;
              }
              leaf cluster {
                status obsolete;
                description
                  "NHS cluster number";
                type uint8 {
                  range "0..10";
                }
              }
              container multicast {
                status obsolete;
                description
                  "Use this NBMA mapping for broadcasts/multicasts";
                presence "true";
                leaf cluster {
                  status obsolete;
                  description
                    "NHS cluster number";
                  type uint8 {
                    range "0..10";
                  }
                }
                container priority {
                  status obsolete;
                  description
                    "NHS priority, don't specify for default priority";
                  list mc-pri {
                    status obsolete;
                    key "mc-pri";
                    leaf mc-pri {
                      status obsolete;
                      description
                        "NHS priority, range = 0 to 255, 0 is the highest";
                      type uint8 {
                        range "0..255";
                      }
                    }
                    leaf cluster {
                      status obsolete;
                      description
                        "NHS cluster number";
                      type uint8 {
                        range "0..10";
                      }
                    }
                  }
                }
              }
              container priority {
                status obsolete;
                description
                  "NHS priority, don't specify for default priority";
                list mc-prior {
                  status obsolete;
                  key "mc-prior";
                  leaf mc-prior {
                    status obsolete;
                    description
                      "NHS priority, range = 0 to 255, 0 is the highest";
                    type uint8 {
                      range "0..255";
                    }
                  }
                  leaf cluster {
                    status obsolete;
                    description
                      "NHS cluster number";
                    type uint8 {
                      range "0..10";
                    }
                  }
                }
              }
            }
          }
          container priority {
            status obsolete;
            description
              "NHS priority, don't specify for default priority";
            list pri-range {
              status obsolete;
              key "pri-range";
              leaf pri-range {
                status obsolete;
                description
                  "NHS priority, range = 0 to 255, 0 is the highest";
                type uint8 {
                  range "0..255";
                }
              }
              leaf cluster {
                status obsolete;
                description
                  "NHS cluster number";
                type uint8 {
                  range "0..10";
                }
              }
            }
          }
        }
        container cluster {
          status obsolete;
          description
            "NHS Redundancy cluster configurations";
          list clus-num {
            status obsolete;
            key "clus-num";
            leaf clus-num {
              status obsolete;
              description
                "NHS cluster number";
              type uint8 {
                range "0..10";
              }
            }
            leaf max-connections {
              status obsolete;
              description
                "Max-connections value";
              type uint8 {
                range "0..255";
              }
            }
          }
        }
        container dynamic {
          status obsolete;
          description
            "NHS protocol address dynamically learnt";
          container nbma {
            status obsolete;
            description
              "NBMA of NHS";
            list ipv4 {
              status obsolete;
              description
                "NBMA of NHS";
              key "ipv4";
              leaf ipv4 {
                status obsolete;
                description
                  "IPv4 address";
                type inet:ipv4-address;
              }
              leaf cluster {
                status obsolete;
                description
                  "NHS cluster number";
                type uint8 {
                  range "0..10";
                }
              }
              container multicast {
                status obsolete;
                description
                  "Use this NBMA mapping for broadcasts/multicasts";
                presence "true";
                leaf cluster {
                  status obsolete;
                  description
                    "NHS cluster number";
                  type uint8 {
                    range "0..10";
                  }
                }
                container priority {
                  status obsolete;
                  description
                    "NHS priority, don't specify for default priority";
                  list dyn-pri {
                    status obsolete;
                    key "dyn-pri";
                    leaf dyn-pri {
                      status obsolete;
                      description
                        "NHS priority, range = 0 to 255, 0 is the highest";
                      type uint8 {
                        range "0..255";
                      }
                    }
                    leaf cluster {
                      status obsolete;
                      description
                        "NHS cluster number";
                      type uint8 {
                        range "0..10";
                      }
                    }
                  }
                }
              }
              container priority {
                status obsolete;
                description
                  "NHS priority, don't specify for default priority";
                list n-prior {
                  status obsolete;
                  key "n-prior";
                  leaf n-prior {
                    status obsolete;
                    description
                      "NHS priority, range = 0 to 255, 0 is the highest";
                    type uint8 {
                      range "0..255";
                    }
                  }
                  leaf cluster {
                    status obsolete;
                    description
                      "NHS cluster number";
                    type uint8 {
                      range "0..10";
                    }
                  }
                }
              }
            }
            list dyn-fqdn {
              status obsolete;
              key "dyn-fqdn";
              leaf dyn-fqdn {
                status obsolete;
                description
                  "NHS FQDN string";
                type string;
              }
              leaf cluster {
                status obsolete;
                description
                  "NHS cluster number";
                type uint8 {
                  range "0..10";
                }
              }
              container multicast {
                status obsolete;
                description
                  "Use this NBMA mapping for broadcasts/multicasts";
                presence "true";
                leaf cluster {
                  status obsolete;
                  description
                    "NHS cluster number";
                  type uint8 {
                    range "0..10";
                  }
                }
                container priority {
                  status obsolete;
                  description
                    "NHS priority, don't specify for default priority";
                  list dyn-mc-pri {
                    status obsolete;
                    key "dyn-mc-pri";
                    leaf dyn-mc-pri {
                      status obsolete;
                      description
                        "NHS priority, range = 0 to 255, 0 is the highest";
                      type uint8 {
                        range "0..255";
                      }
                    }
                    leaf cluster {
                      status obsolete;
                      description
                        "NHS cluster number";
                      type uint8 {
                        range "0..10";
                      }
                    }
                  }
                }
              }
              container priority {
                status obsolete;
                description
                  "NHS priority, don't specify for default priority";
                list dp {
                  status obsolete;
                  key "dp";
                  leaf dp {
                    status obsolete;
                    description
                      "NHS priority, range = 0 to 255, 0 is the highest";
                    type uint8 {
                      range "0..255";
                    }
                  }
                  leaf cluster {
                    status obsolete;
                    description
                      "NHS cluster number";
                    type uint8 {
                      range "0..10";
                    }
                  }
                }
              }
            }
            list ipv6 {
              status obsolete;
              key "ipv6";
              leaf ipv6 {
                status obsolete;
                description
                  "IPv6 address";
                type inet:ipv6-address;
              }
              leaf cluster {
                status obsolete;
                description
                  "NHS cluster number";
                type uint8 {
                  range "0..10";
                }
              }
              container multicast {
                status obsolete;
                description
                  "Use this NBMA mapping for broadcasts/multicasts";
                presence "true";
                leaf cluster {
                  status obsolete;
                  description
                    "NHS cluster number";
                  type uint8 {
                    range "0..10";
                  }
                }
                container priority {
                  status obsolete;
                  description
                    "NHS priority, don't specify for default priority";
                  list v6-pri {
                    status obsolete;
                    key "v6-pri";
                    leaf v6-pri {
                      status obsolete;
                      description
                        "NHS priority, range = 0 to 255, 0 is the highest";
                      type uint8 {
                        range "0..255";
                      }
                    }
                    leaf cluster {
                      status obsolete;
                      description
                        "NHS cluster number";
                      type uint8 {
                        range "0..10";
                      }
                    }
                  }
                }
              }
              container priority {
                status obsolete;
                description
                  "NHS priority, don't specify for default priority";
                list v6-pri2 {
                  status obsolete;
                  key "v6-pri2";
                  leaf v6-pri2 {
                    status obsolete;
                    description
                      "NHS priority, range = 0 to 255, 0 is the highest";
                    type uint8 {
                      range "0..255";
                    }
                  }
                  leaf cluster {
                    status obsolete;
                    description
                      "NHS cluster number";
                    type uint8 {
                      range "0..10";
                    }
                  }
                }
              }
            }
          }
        }
        leaf fallback {
          status obsolete;
          description
            "NHS Redundancy Fallback time, 0 -60 seconds";
          type uint8 {
            range "0..60";
          }
        }
      }
      leaf record {
        status obsolete;
        description
          "Allow NHRP record option";
        type empty;
      }
      container redirect {
        status obsolete;
        description
          "Enable NHRP redirect traffic indication";
        presence "true";
        leaf timeout {
          status obsolete;
          description
            "Interval in seconds";
          type uint8 {
            range "2..30";
          }
        }
      }
      container registration {
        status obsolete;
        description
          "Settings for registration packets.";
        leaf no-unique {
          status obsolete;
          description
            "Do not set the 'Unique' flag in registration requests.";
          type empty;
        }
        leaf timeout {
          status obsolete;
          description
            "Number of seconds";
          type uint16 {
            range "1..65535";
          }
        }
      }
      container reject {
        status obsolete;
        description
          "NHRP resolution reject request";
        list reqid {
          status obsolete;
          key "reqid";
          leaf reqid {
            status obsolete;
            description
              "reqid value";
            type uint16 {
              range "1..65535";
            }
          }
          leaf rej-secs {
            status obsolete;
            description
              "Number of seconds";
            type uint16 {
              range "0..65535";
            }
          }
        }
      }
      container responder {
        status obsolete;
        description
          "Responder interface";
        leaf res-int {
          status obsolete;
          description
            "Virtual ACR interface";
          type string;
        }
        leaf Analysis-Module {
          status obsolete;
          description
            "Analysis-Module interface number";
          type uint8;
        }
        leaf Fcpa {
          status obsolete;
          description
            "Fcpa interface number";
          type uint8;
        }
        leaf SBC {
          status obsolete;
          description
            "SBC interface number";
          type uint32 {
            range "0..2147483647";
          }
        }
        leaf SONET_ACR {
          status obsolete;
          description
            "SONET_ACR interface number";
          type uint8;
        }
        leaf TB-controller {
          status obsolete;
          description
            "Telecom-Bus Clock Controller";
          type string;
        }
        leaf Service-Engine {
          status obsolete;
          description
            "Service-Engine interface number";
          type uint8;
        }
        leaf Tunnel {
          status obsolete;
          description
            "Tunnel interface number";
          type uint32 {
            range "0..2147483647";
          }
        }
        leaf Tunnel-tp {
          status obsolete;
          description
            "Tunnel-tp interface number";
          type uint16 {
            range "0..65535";
          }
        }
        leaf VPN {
          status obsolete;
          description
            "VPN interface number";
          type uint32 {
            range "0..2147483647";
          }
        }
        leaf Virtual-TokenRing {
          status obsolete;
          description
            "Virtual-TokenRing interface number";
          type uint32 {
            range "0..2147483647";
          }
        }
        leaf VirtualPortGroup {
          status obsolete;
          description
            "VirtualPortGroup interface number";
          type uint8 {
            range "0..31";
          }
        }
        leaf Vlan {
          status obsolete;
          description
            "Vlan interface number";
          type uint16 {
            range "1..4095";
          }
        }
        leaf ucse {
          status obsolete;
          description
            "ucse interface number";
          type uint8;
        }
        leaf vasileft {
          status obsolete;
          description
            "vasileft interface number";
          type uint16 {
            range "1..2000";
          }
        }
        leaf vasiright {
          status obsolete;
          description
            "vasiright interface number";
          type uint16 {
            range "1..2000";
          }
        }
      }
      container server-only {
        status obsolete;
        description
          "Disable NHRP requests";
        presence "true";
        leaf non-caching {
          status obsolete;
          description
            "Do not create NHRP cache entries";
          type empty;
        }
      }
      container shortcut {
        status obsolete;
        description
          "Enable shortcut switching";
        presence "true";
        leaf virtual-template {
          status obsolete;
          description
            "Virtual template number";
          type uint16 {
            range "1..4095";
          }
        }
      }
      container trigger-svc {
        status obsolete;
        description
          "Create NHRP cut-through based on traffic load";
        list kbps {
          status obsolete;
          key "kbps";
          leaf kbps {
            status obsolete;
            description
              "Trigger rate in kbps";
            type uint32 {
              range "1..4294967295";
            }
          }
          leaf tear-kbps {
            status obsolete;
            description
              "Teardown rate in kbps";
            type uint32 {
              range "0..4294967295";
            }
          }
        }
      }
      leaf use {
        status obsolete;
        description
          "Number of packets to cause NHRP request";
        type uint16 {
          range "1..65535";
        }
      }
    }
  }

  grouping config-router-nhrp-grouping {
    leaf default-metric {
      description
        "Set metric of redistributed routes";
      type uint32 {
        range "1 ..4294967295";
      }
    }
    container distance {
      description
        "Define an administrative distance";
      list admin-distance {
        key "distance";
        leaf distance {
          description
            "Set route administrative distance";
          type uint8 {
            range "1..255";
          }
        }
        leaf ipv4-address {
          description
            "IP Source address";
          type inet:ipv4-address;
        }
        leaf wildcard {
          description
            "Wildcard bits";
          type inet:ipv4-address;
        }
        leaf access-list {
          description
            "Standard Access List";
          type ios-types:std-acl-type;
        }
      }
    }
    container distribute-list {
      description
        "Filter entries in eigrp updates";
      container access-list {
        list access-list-direction {
          key "direction";
          leaf ex-access-list {
            description
              "IP expanded access list number";
            type ios-types:exp-acl-type;
          }
          leaf direction {
            description
              "Filter service updates";
            must '(not (../../../ios-nhrp:prefix-list/ios-nhrp:prefix-list-direction[ios-nhrp:direction=current()]))' {
              error-message "distribute-list prefix already exists";
            }
            must '(not (../../../ios-nhrp:gateway/ios-nhrp:gateway-direction[ios-nhrp:direction=current()]))' {
              error-message "distribute-list gateway already exists";
            }
            must '(not (../../../ios-nhrp:route-map/ios-nhrp:route-map-direction[ios-nhrp:direction=current()]))' {
              error-message "distribute-list route-map already exists";
            }
            type enumeration {
              enum in;
              enum out;
            }
          }
        }
        list access-list-direction-interface {
          key "direction";
          leaf ex-access-list {
            description
              "IP expanded access list number";
            type ios-types:exp-acl-type;
          }
          leaf direction {
            description
              "Filter service updates";
            type enumeration {
              enum in;
              enum out;
            }
          }
          container interface {
            description
              "Interface name";
            uses ios-ifc:interface-grouping;
          }
        }
      }
      container gateway {
        description
          "Filtering incoming address updates based on gateway";
        list gateway-direction {
          key "direction";
          leaf gateway {
            description
              "Name of an IP prefix-list";
            type string;
          }
          leaf direction {
            description
              "Filter service updates";
            must '(not (../../../ios-nhrp:access-list/ios-nhrp:access-list-direction[ios-nhrp:direction=current()]))' {
              error-message "distribute-list acess-list already exists";
            }
            must '(not (../../../ios-nhrp:prefix-list/ios-nhrp:prefix-list-direction[ios-nhrp:direction=current()]))' {
              error-message "distribute-list prefix already exists";
            }
            must '(not (../../../ios-nhrp:route-map/ios-nhrp:route-map-direction[ios-nhrp:direction=current()]))' {
              error-message "distribute-list route-map already exists";
            }
            type enumeration {
              enum in;
              enum out;
            }
          }
        }
        list gateway-direction-interface {
          key "direction";
          leaf gateway {
            description
              "Name of an IP prefix-list";
            type string;
          }
          leaf direction {
            description
              "Filter service updates";
            type enumeration {
              enum in;
              enum out;
            }
          }
          container interface {
            description
              "Interface name";
            uses ios-ifc:interface-grouping;
          }
        }
      }
      container prefix-list {
        description
          "Filter prefixes in address updates";
        list prefix-list-direction {
          key "direction";
          leaf prefix-list {
            description
              "Name of an IP prefix-list";
            type string;
          }
          leaf gateway {
            description
              "Filtering incoming address updates based on gateway";
            type string;
          }
          leaf direction {
            description
              "Filter service updates";
            must '(not (../../../ios-nhrp:access-list/ios-nhrp:access-list-direction[ios-nhrp:direction=current()]))' {
              error-message "distribute-list acess-list already exists";
            }
            must '(not (../../../ios-nhrp:gateway/ios-nhrp:gateway-direction[ios-nhrp:direction=current()]))' {
              error-message "distribute-list gateway already exists";
            }
            must '(not (../../../ios-nhrp:route-map/ios-nhrp:route-map-direction[ios-nhrp:direction=current()]))' {
              error-message "distribute-list route-map already exists";
            }
            type enumeration {
              enum in;
              enum out;
            }
          }
        }
        list prefix-list-direction-interface {
          key "direction";
          leaf prefix-list {
            description
              "Name of an IP prefix-list";
            type string;
          }
          leaf gateway {
            description
              "Filtering incoming address updates based on gateway";
            type string;
          }
          leaf direction {
            description
              "Filter service updates";
            type enumeration {
              enum in;
              enum out;
            }
          }
          container interface {
            description
              "Interface name";
            uses ios-ifc:interface-grouping;
          }
        }
      }
      container route-map {
        list route-map-direction {
          description
            "Filter prefixes based on the route-map";
          key "direction";
          leaf route-map-name {
            description
              "route-map name";
            type string;
          }
          leaf direction {
            description
              "Filter service updates";
            must '(not (../../../ios-nhrp:access-list/ios-nhrp:access-list-direction[ios-nhrp:direction=current()]))' {
              error-message "distribute-list acess-list already exists";
            }
            must '(not (../../../ios-nhrp:prefix-list/ios-nhrp:prefix-list-direction[ios-nhrp:direction=current()]))' {
              error-message "distribute-list prefix already exists";
            }
            must '(not (../../../ios-nhrp:gateway/ios-nhrp:gateway-direction[ios-nhrp:direction=current()]))' {
              error-message "distribute-list gateway already exists";
            }
            type enumeration {
              enum in;
              enum out;
            }
          }
        }
        list route-map-direction-interface {
          description
            "Filter prefixes based on the route-map";
          key "direction";
          leaf route-map-name {
            description
              "route-map name";
            type string;
          }
          leaf direction {
            description
              "Filter service updates";
            type enumeration {
              enum in;
              enum out;
            }
          }
          container interface {
            description
              "Interface name";
            uses ios-ifc:interface-grouping;
          }
        }
      }
    }
    leaf maximum-paths {
      description
        "Forward packets over multiple paths";
      type uint32 {
        range "1 .. 32";
      }
    }
    container neighbor {
      description
        "Specify a neighbor router";
      container nhs {
        description
          "Publish routes to Next Hop Servers";
        container Tunnel {
          description
            "Tunnel interface";
          leaf number {
            description
              "Tunnel interface number";
            type uint32 {
              range "1 .. 2147483647";
            }
          }
        }
      }
    }
    container network {
      description
        "Enable routing on an IP network";
      list address-wildcard {
        key "ipv4-address wildcard";
        leaf ipv4-address {
          description
            "Network number";
          type inet:ipv4-address;
        }
        leaf wildcard {
          description
            "EIGRP wild card bits";
          type inet:ipv4-address;
        }
        leaf passive {
          type empty;
        }
      }
      list address {
        key "ipv4-address";
        leaf ipv4-address {
          description
            "Network number";
          type inet:ipv4-address;
        }
        leaf passive {
          type empty;
        }
      }
    }
    container redistribute {
      description
        "Redistribute information from another routing protocol";
      uses nhrp-redistribute-top-grouping;
      container maximum-prefix {
        description
          "Maximum number of prefixes redistributed to protocol";
        leaf number {
          type uint32 {
            range "1 .. 4294967295";
          }
        }
        container threshold-warning-only-container {
          leaf threshold {
            type uint32 {
              range "1 .. 100";
            }
          }
          leaf warning-only {
            description
              "Only give warning message when limit is exceeded";
            type empty;
          }
        }
      }
      container vrf {
        description
          "Specify a source VRF";
        list non-global-vrf {
          key "name";
          leaf name {
            must '/ios:native/ios:vrf/ios:definition[ios:name=current()] or /ios:native/ios:ip/ios:vrf[ios:name=current()]' {
              error-message "VRF must be created 1st, deleted last";
            }
            type string;
          }
          uses nhrp-redistribute-top-grouping;
        }
        container global {
          description
            "global VRF";
          uses nhrp-redistribute-top-grouping;
        }
      }
    }
    grouping nhrp-redistribute-top-grouping {
      list application {
        description
          "Application";
        key "name";
        leaf name {
          type string;
        }
        uses nhrp-redistribute-grouping;
      }
      list bgp {
        description
          "Border Gateway Protocol (BGP)";
        key "as-number";
        uses nhrp-redistribute-bgp-grouping;
      }
      container connected {
        description
          "Connected";
        presence "Connected";
        uses nhrp-redistribute-grouping;
      }
      list eigrp {
        description
          "Enhanced Interior Gateway Routing Protocol (EIGRP)";
        key "as-number";
        uses nhrp-redistribute-bgp-grouping;
      }
      container isis {
        presence "ISO IS-IS";
        description
          "ISO IS-IS";
        choice isis-level-routes-isis-area-choice {
          leaf isis-level-routes {
            type enumeration {
              enum level-1;
              enum level-2;
              enum level-1-2;
            }
          }
          list isis-area {
            key "name";
            leaf name {
              type string;
            }
            leaf isis-level-routes {
              type enumeration {
                enum level-1;
                enum level-2;
                enum level-1-2;
              }
            }
            uses nhrp-redistribute-grouping;
          }
        }
        uses nhrp-redistribute-grouping;
      }
      container iso-igrp {
        description
          "IGRP for OSI networks";
        presence "IGRP for OSI networks";
        choice area-tag-route-map-choice {
          container area-tag-route-map-container {
            leaf area-tag {
              type string;
            }
            leaf route-map {
              description
                "Route map reference";
              type string;
            }
          }
          leaf route-map {
            description
              "Route map reference";
            type string;
          }
        }
        container iso-igrp-container {
          uses nhrp-iso-igrp-redistribute-grouping;
        }
      }
      container lisp {
        description
          "Locator ID Separation Protocol (LISP)";
        uses nhrp-redistribute-grouping;
      }
      container mobile {
        description
          "Mobile routes";
        presence "Mobile routes";
        uses nhrp-redistribute-grouping;
      }
      container odr {
        description
          "On Demand stub Routes";
        presence "On Demand stub Routes";
        uses nhrp-redistribute-grouping;
      }
      container omp {
        if-feature "ios-features:omp";
        description
          "Overlay Management Protocol (OMP)";
        presence "omp";
        uses nhrp-redistribute-grouping;
      }
      container nat-route {
        if-feature "ios-features:sdwan";
        description
          "NAT Route";
        leaf dia {
          description
            "Redistribute NAT Direct Internet Access routes";
          type empty;
        }
        leaf outside {
          description
            "Redistribute NAT outside routes";
          type empty;
        }
        uses nhrp-redistribute-grouping;
      }
      list ospf {
        description
          "Open Shortest Path First (OSPF)";
        key "id";
        leaf id {
          type uint32 {
            range "1 .. 65535";
          }
        }
        uses nhrp-redistribute-top-match-grouping;
        uses nhrp-redistribute-match-grouping;
        leaf vrf {
          description
            "VPN Routing/Forwarding Instance";
          must '/ios:native/ios:vrf/ios:definition[ios:name=current()] or /ios:native/ios:ip/ios:vrf[ios:name=current()]' {
            error-message "VRF must be created 1st, deleted last";
          }
          type string;
        }
      }
      list ospfv3 {
        description
          "OSPFv3";
        key "id";
        leaf id {
          type uint32 {
            range "1 .. 65535";
          }
        }
        uses nhrp-redistribute-top-match-grouping;
        uses nhrp-redistribute-match-grouping;
      }
      list rip {
        description
          "Routing Information Protocol (RIP)";
        key "id";
        leaf id {
          description
            "User selected string identifying this rip process";
          type string;
        }
        uses nhrp-redistribute-grouping;
      }
      container static {
        description
          "Static routes";
        presence "Static routes";
        uses nhrp-redistribute-grouping;
      }
    }

    grouping nhrp-redistribute-bgp-grouping {
      leaf as-number {
        type ios-types:bgp-as-number-type;
      }
      uses nhrp-redistribute-grouping;
    }

    grouping nhrp-redistribute-grouping {
      container redist-options {
        uses nhrp-iso-igrp-redistribute-grouping;
        leaf route-map {
          description
            "Route map reference";
          type string;
        }
      }
    }

    grouping nhrp-iso-igrp-redistribute-grouping {
      leaf metric {
        description
          "Metric for redistributed routes";
        type uint32;
      }
      leaf tag {
        description
          "Set tag for routes redistributed into OSPF";
        type uint32 {
          range "0 .. 4294967295";
        }
      }
    }

    grouping nhrp-redistribute-top-match-grouping {
      container match {
        description
          "Redistribution of OSPF routes";
        container internal {
          presence "Redistribute OSPF internal routes";
          description
            "Redistribute OSPF internal routes";
          uses nhrp-redistribute-match-grouping;
        }
        container external {
          description
            "Redistribute OSPF external routes";
          presence "Redistribute OSPF external routes";
          leaf external-routes {
            type redist-ospf-external-type;
          }
          uses nhrp-redistribute-match-grouping;
        }
        container nssa-external {
          description
            "Redistribute OSPF NSSA external routes";
          presence "Redistribute OSPF NSSA external routes";
          leaf nssa-external-routes {
            type redist-ospf-external-type;
          }
          uses nhrp-redistribute-match-grouping;
        }
      }
    }

    grouping nhrp-redistribute-match-grouping {
      leaf metric {
        description
          "Metric for redistributed routes";
        type uint32;
      }
      leaf metric-type {
        description
          "OSPF/IS-IS exterior metric type for redistributed routes";
        type enumeration {
          enum 1;
          enum 2;
        }
      }
      leaf nssa-only {
        description
          "Limit redistributed routes to NSSA areas";
        type empty;
      }
      leaf subnets {
        description
          "Consider subnets for redistribution into OSPF";
        type empty;
      }
      leaf route-map {
        description
          "Route map reference";
        type string;
      }
      leaf tag {
        description
          "Set tag for routes redistributed into OSPF";
        type uint32 {
          range "0 .. 4294967295";
        }
      }
    }

    container summary-prefix {
      description
        "Configure IP address summaries";
      list ipv4 {
        key "ipv4";
        leaf ipv4 {
          description
            "IP summary address";
          type inet:ipv4-address;
        }
        leaf mask {
          description
            "Summary mask";
          type inet:ipv4-address;
        }
      }
      container prefix-value {
        leaf prefix {
          description
            "IP prefix <network>/<length>, e.g., 35.0.0.0/8";
          type inet:ipv4-prefix;
        }
        leaf tag {
          description
            "Set tag";
          type uint32 {
            range "0..4294967295";
          }
        }
      }
    }
    container summary-address {
      description
        "Configure IP address summaries";
      list ipv4 {
        key "ipv4";
        leaf ipv4 {
          description
            "IP summary address";
          type inet:ipv4-address;
        }
        leaf mask {
          description
            "Summary mask";
          type inet:ipv4-address;
        }
      }
      container prefix-value {
        leaf prefix {
          description
            "IP prefix <network>/<length>, e.g., 35.0.0.0/8";
          type inet:ipv4-prefix;
        }
        leaf tag {
          description
            "Set tag";
          type uint32 {
            range "0..4294967295";
          }
        }
      }
    }
    container traffic-share {
      description
        "How to compute traffic share over alternate paths";
      container min {
        description
          "All traffic shared among min metric paths";
        leaf across-interfaces {
          description
            "Use different interfaces for equal-cost paths";
          type empty;
        }
      }
    }
  }

  grouping config-nhrp-router-grouping {
    list nhrp {
      description
        "Next Hop Resolution Protocol (NHRP)";
      key "id";
      leaf id {
        description
          "Process ID";
        type uint16 {
          range "1..65535";
        }
      }
      container address-family {
        description
          "Enter Address Family command mode";
        container vrf-ipv4 {
          container ipv4 {
            description
              "Address family";
            leaf unicast {
              type empty;
            }
            list vrf {
              key "name";
              leaf name {
                type string;
                must '/ios:native/ios:vrf/ios:definition[ios:name=current()]/ios:rd or /ios:native/ios:ip/ios:vrf[ios:name=current()]/ios:rd' {
                  error-message "VRF must be created 1st, deleted last";
                }
              }
              uses config-router-nhrp-grouping;
            }
          }
        }
        container vrf-ipv6 {
          container ipv6 {
            description
              "Address family";
            leaf unicast {
              type empty;
            }
            list vrf {
              key "name";
              leaf name {
                type string;
                must '/ios:native/ios:vrf/ios:definition[ios:name=current()]/ios:rd or /ios:native/ios:ip/ios:vrf[ios:name=current()]/ios:rd' {
                  error-message "VRF must be created 1st, deleted last";
                }
              }
              uses config-router-nhrp-grouping;
            }
          }
        }
        container ipv4 {
          description
            "Address family";
          list vrf {
            key "name";
            leaf name {
              type string;
              must '/ios:native/ios:vrf/ios:definition[ios:name=current()]/ios:rd or /ios:native/ios:ip/ios:vrf[ios:name=current()]/ios:rd' {
                error-message "ipv4 VRF must be created 1st, deleted last";
              }
            }
            uses config-router-nhrp-grouping;
          }
        }
        container ipv6 {
          description
            "Address family";
          list vrf {
            key "name";
            leaf name {
              type string;
              must '/ios:native/ios:vrf/ios:definition[ios:name=current()]/ios:rd or /ios:native/ios:ip/ios:vrf[ios:name=current()]/ios:rd' {
                error-message "VRF must be created 1st, deleted last";
              }
            }
            uses config-router-nhrp-grouping;
          }
        }
        container vpnv4 {
          description
            "Address family";
          container unicast {
            list vrf {
              key "name";
              leaf name {
                type string;
                must '/ios:native/ios:vrf/ios:definition[ios:name=current()]/ios:rd or /ios:native/ios:ip/ios:vrf[ios:name=current()]/ios:rd' {
                  error-message "VRF must be created 1st, deleted last";
                }
              }
            }
          }
          container import {
            description
              "importing bgp protocol";
            container bgp {
              description
                "bgp protocol importing";
              leaf number {
                description
                  "bgp number";
                type uint32 {
                  range "1..4294967295";
                }
              }
              leaf route-map {
                description
                  "Filter prefixes based on the route-map";
                when '/ios:native/ios:service/ios:internal';
                type string;
              }
            }
          }
        }
        container vpv4 {
          description
            "Address family";
          status obsolete;
          leaf unicast {
            status obsolete;
            type empty;
          }
          list vrf {
            status obsolete;
            key "name";
            leaf name {
              status obsolete;
              type string;
              must '/ios:native/ios:vrf/ios:definition[ios:name=current()]/ios:rd or /ios:native/ios:ip/ios:vrf[ios:name=current()]/ios:rd' {
                error-message "To delete vrf/rd, bgp/address-family/vrf needs to be deleted 1st";
              }
            }
            uses config-router-nhrp-grouping;
          }
          container import {
            description
              "importing bgp protocol";
            status obsolete;
            container bgp {
              description
                "bgp protocol importing";
              status obsolete;
              leaf number {
                description
                  "bgp number";
                status obsolete;
                type uint32 {
                  range "1..65535";
                }
              }
              leaf route-map {
                description
                  "Filter prefixes based on the route-map";
                status obsolete;
                type string;
              }
            }
          }
          uses config-router-nhrp-grouping;
        }
        container vpnv6 {
          description
            "Address family";
          leaf unicast {
            type empty;
          }
          list vrf {
            key "name";
            leaf name {
              type string;
              must '/ios:native/ios:vrf/ios:definition[ios:name=current()]/ios:rd or /ios:native/ios:ip/ios:vrf[ios:name=current()]/ios:rd' {
                error-message "VRF must be created 1st, deleted last";
              }
            }
            uses config-router-nhrp-grouping;
          }
        }
      }
      uses config-router-nhrp-grouping;
    }
  }

  grouping config-llp-nhrp-grouping {
    container llp {
      description
        "NHRP multicast map for link layer protocols";
      container nhrp {
        description
          "NHRP interface subcommands";
        container map {
          description
            "Map dest IP addresses to NBMA addresses";
          container multicast {
            description
              "Use this NBMA mapping for broadcasts/multicasts";
            list ipv4 {
              description
                "IP NBMA address";
              key "ipv4-address";
              leaf ipv4-address {
                type inet:ipv4-address;
              }
            }
            list ipv6 {
              description
                "IPv6 NBMA address";
              key "ipv6-address";
              leaf ipv6-address {
                type inet:ipv6-address;
              }
            }
            leaf dynamic {
              description
                "Dynamically learn destinations from client registrations on hub";
              type empty;
            }
          }
        }
      }
    }
  }

  augment "/ios:native/ios:interface/ios:Tunnel/ios:ip" {
    uses config-interface-nhrp-grouping-obsolete;
  }

  augment "/ios:native/ios:interface/ios:Tunnel/ios:ip" {
    uses config-interface-ipv4-nhrp-grouping;
  }

  augment "/ios:native/ios:interface/ios:Virtual-Template/ios:ip" {
    when "/ios:native/ios:interface/ios:Virtual-Template/ios:type = 'tunnel'";
    uses config-interface-ipv4-nhrp-grouping;
  }

  augment "/ios:native/ios:interface/ios:Tunnel" {
    uses config-llp-nhrp-grouping;
  }

  augment "/ios:native/ios:interface/ios:Tunnel/ios:ipv6" {
    uses config-interface-ipv6-nhrp-grouping;
  }

  augment "/ios:native/ios:interface/ios:Virtual-Template/ios:ipv6" {
    when "/ios:native/ios:interface/ios:Virtual-Template/ios:type = 'tunnel'";
    uses config-interface-ipv6-nhrp-grouping;
  }

  augment "/ios:native/ios:interface/ios:Tunnel" {
    uses config-interface-tunn-grouping;
  }

  augment "/ios:native/ios:interface/ios:Virtual-Template" {
    when "/ios:native/ios:interface/ios:Virtual-Template/ios:type = 'tunnel'";
    uses config-interface-tunn-grouping;
  }

  augment "/ios:native/ios:interface/ios:Tunnel" {
    uses config-tunnel-if-state-grouping;
  }

  augment "/ios:native/ios:interface/ios:Virtual-Template" {
    uses config-tunnel-if-state-grouping;
  }

  augment "/ios:native" {
    uses config-global-nhrp-grouping;
  }

  augment "/ios:native/ios:router" {
    uses config-nhrp-router-grouping;
  }
}
