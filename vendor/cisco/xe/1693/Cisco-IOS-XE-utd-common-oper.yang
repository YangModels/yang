module Cisco-IOS-XE-utd-common-oper {
  yang-version 1;
  namespace "http://cisco.com/ns/yang/Cisco-IOS-XE-utd-common-oper";
  prefix utd-common-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     common for all UTD operational data.
     Copyright (c) 2018 by Cisco Systems, Inc.
     All rights reserved.";

  revision 2018-04-04 {
    description
      "Initial revision";
    reference "1.0.0";
  }

  typedef utd-update-status-val {
    type enumeration {
      enum "utd-update-status-unknown" {
        value 0;
        description
          "Unified Threat Defense (UTD) update status is unknown";
      }
      enum "utd-update-status-success" {
        value 1;
        description
          "Unified Threat Defense (UTD) update successful";
      }
      enum "utd-update-status-failure" {
        value 2;
        description
          "Unified Threat Defense (UTD) update failed";
      }
      enum "utd-update-status-no-update" {
        value 3;
        description
          "Unified Threat Defense (UTD) update attemped but not required";
      }
    }
    description
      "Unified Threat Defense (UTD) update status";
  }
}
