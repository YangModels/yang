module Cisco-IOS-XE-atm {
  namespace "http://cisco.com/ns/yang/Cisco-IOS-XE-atm";
  prefix ios-atm;

  import ietf-inet-types {
    prefix inet;
  }


  import Cisco-IOS-XE-l2vpn {
    prefix ios-l2vpn;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native ATM Interfaces Yang model.
     Copyright (c) 2016 by Cisco Systems, Inc.
     All rights reserved.";

  // =========================================================================
  // REVISION
  // =========================================================================
  revision 2018-03-28 {
    description 
        "Enhancements for configuring PVCs under ATM";
  }

  revision 2017-02-07 {
    description
      "Initial revision";
  }


  grouping config-interface-atm-grouping {
    container ip {
      description
        "IP address";
      leaf address {
        type inet:ipv4-address;
      }
      leaf split-horizon{
        type empty;
      }
    }
    container atm {
      description
        "ATM";
      leaf bandwidth {
        description
          "ATM bandwith";
        type enumeration {
          enum "dynamic";
        }
      }
      leaf enable-ilmi-trap {
        description
          "Enable-ilmi-trap";
        type boolean;
      }
      leaf ilmi-keepalive{
            type empty;
      }
      leaf route-bridged{
             type enumeration{
                 enum "ip";
                 enum "ipv6";
             }
       }

      list pvp {
        description
          "PVP";
        key "pvp-number";
        leaf pvp-number {
          description
            "PVP number";
          type uint16;
        }
        leaf l2transport {
          type empty;
        }
        uses ios-l2vpn:config-interface-efp-xconnect-grouping;
      }
    }
    leaf load-interval {
      description
        "Load interval";
      type uint32;
    }
    leaf cdp {
         type enumeration{
             enum "enable";
         }
     }

    list cem {
      description
        "CEM";
      key "number";
      leaf number {
        type uint32;
      }
      uses ios-l2vpn:config-interface-efp-xconnect-grouping;
    }
    list pvc {
      description
        "PVC";
      key "local-vpi-vci";
      leaf local-vpi-vci {
        description
          "Vpi and vci";
        type string;
      }
      leaf remote-vpi-vci {
        description
          "Vpi and vci";
        type string;
      }
      leaf l2transport {
        type empty;
      }
      leaf ubr {
        description
          "UBR";
        type uint32;
      }
      container ubrplus{
        leaf PCR{
            type uint32;
        }
        leaf MCR{
            type uint32;
        }
      }
      leaf cbr{
         description
             "CBR";
         type uint32;
       }
       leaf vbr{
         description
             "VBR";
         type uint32;
       }
       leaf vbr-rt{
         type uint32;
       }
       leaf vbr-nrt{
         type uint32;
       }
       container oam-pvc{
         presence true;
         leaf loopback-frequency{
             type uint32{
                 range 0..600;
             }
         }
         leaf manage{
             type empty;
         }
 
       }
       container service-policy{
            leaf input {
                description
                "Assign policy-map to the input of an interface";
                type string;
            }
            leaf output {
                description
                "Assign policy-map to the output of an interface";
                type string;
            }
        }

       container encapsulation{
         container aal5autoppp{
         leaf Virtual-Template{
             type uint32;
         }
       }
       container aal5ciscoppp{
         leaf Virtual-Template{
             type uint32;
         }
       }
       container aal5mux{
         container ppp{
             leaf Virtual-Template{
                 type uint32;
             }
             leaf dialer{
                 type empty;
             }
         }
       }
       leaf aal5nlpid{
         type empty;
       }
       leaf aal5snap{
         type empty;
       }
 
       }
      uses ios-l2vpn:config-interface-efp-xconnect-grouping;
    }
  }

  grouping config-acr-grouping {
    //unused /native/acr
    list acr { 
      description
        "ACR";
      key "number";
      leaf number {
        type uint8;
      }
      leaf type {
        type enumeration {
          enum "CH-OC3";
        }
      }
    }
  }

  /////////////////////////////////////////////////////////
  // native / interface
  /////////////////////////////////////////////////////////
  augment "/ios:native/ios:interface/ios:ATM" {
    uses config-interface-atm-grouping;
  }

  augment "/ios:native/ios:interface/ios:ATM-subinterface/ios:ATM" {
    uses config-interface-atm-grouping;
  }

  augment "/ios:native/ios:interface/ios:ATM-ACR" {
    uses config-interface-atm-grouping;
  }

  augment "/ios:native/ios:interface/ios:ATM-ACRsubinterface/ios:ATM-ACR" {
    uses config-interface-atm-grouping;
  }

  augment "/ios:native/ios:interface/ios:CEM" {
    uses config-interface-atm-grouping;
  }

  augment "/ios:native/ios:interface/ios:CEM-ACR" {
    uses config-interface-atm-grouping;
  }
}
