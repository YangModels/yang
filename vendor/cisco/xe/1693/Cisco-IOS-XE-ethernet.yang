module Cisco-IOS-XE-ethernet {
  namespace "http://cisco.com/ns/yang/Cisco-IOS-XE-ethernet";
  prefix ios-eth;


  import Cisco-IOS-XE-native {
    prefix ios;
  }

  import Cisco-IOS-XE-types {
    prefix ios-types;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Ethernet Interfaces Yang model.
     Copyright (c) 2016-2018 by Cisco Systems, Inc.
     All rights reserved.";

  // =========================================================================
  // REVISION
  // =========================================================================
  revision 2018-07-25 {
    description
      "Remove the must constraints on interface auto-negotiation and speed";
  }
  revision 2018-07-18 {
    description
      "Validate interface auto-negotiation is not enabled when setting speed";
  }
  revision 2018-04-09 {
    description
      "Add dependency for bridge-domain";
  }
  revision 2018-03-08 {
    description
      "allow speed change under interface";
  }
  revision 2018-03-06 {
    description
      "add dependency between speed and duplex";
  }
  revision 2018-02-22 {
    description
      "add encapsulation priority-tagged without parameter support";
  }
  revision 2018-02-02 {
    description
      "Add model for port-channel mlacp";
  }
  revision 2018-01-15 {
    description
      "Added dot1ad nni support ";
  }
  revision 2018-01-04 {
     description
       "Change ethernet lmi ce-vlan map vlan range";
  }
  revision 2017-11-27 {
     description
       "Added Change 25GE name";
  }
  revision 2017-09-21 {
    description
      "Added interface macsec without option";
  }
  revision 2017-09-20 {
    description
      "Added interface macsec";
  }
  revision 2017-09-14 {
    description
      "This revision has changes for new 2gig interface addition";
  }
  revision 2017-08-21 {
    description
      "Augment HundredGigE interface with ethernet grouping";
  }
  revision 2017-08-16 {
    description
      "This revision has changes for new 5gig and 25gig interfaces addition";
  }
  revision 2017-08-10 {
    description 
      "Add BDI interface";
  }
  revision 2017-07-25 {
    description 
      "Modification to fix model under service instance *";
  }
  revision 2017-07-18 {
    description
      "Consolidate modeling for interface lacp";
  }
  revision 2017-02-07 {
    description
      "Initial revision";
  }


  grouping interface-ethernet-carrier-delay-grouping {
    choice delay-choice {
      leaf seconds {
        type uint8 {
          range "0..60";
        }
      }
      leaf msec {
        description
          "delay specified in milliseconds";
        type uint16 {
          range "0..1000";
        }
      }
    }
  }

  grouping config-interface-efp-l2protocol-grouping {
    leaf-list protocol {
      type enumeration {
        enum "R4";
        enum "R5";
        enum "R6";
        enum "R8";
        enum "R9";
        enum "RA";
        enum "RB";
        enum "RC";
        enum "RD";
        enum "RF";
        enum "cdp";
        enum "dtp";
        enum "elmi";
        enum "esmc";
        enum "lacp";
        enum "lldp";
        enum "loam";
        enum "pagp";
        enum "ptppd";
        enum "stp";
        enum "udld";
        enum "vtp";
      }
    }
  }

  // interface * / lacp  (except Port-channel interfaces)
  grouping config-interface-ethernet-member-link-lacp-grouping {
    container lacp {
        description
          "LACP interface subcommands";
      leaf port-priority {
        description
          "LACP priority on this interface ";
        type uint32;
      }
      leaf rate {
        description
          "Rate at which the LACP packets are requested to be ingressed to this interface";
        type enumeration {
          enum "fast";
          enum "normal";
        }
      }
    }
  }

  // interface Port-channel / lacp
  grouping config-interface-port-channel-lacp-grouping {
    container lacp {
        description
          "LACP Port Channel interface subcommands";
      leaf failover {
        description
          "Link failover options";
        type enumeration {
          enum "brute-force";
          enum "non-revertive";
        }
      }
      leaf fast-switchover {
        description
          "Enable LACP fast switchover on this port channel";
        type empty;
      }
      leaf max-bundle {
        description
          "LACP maximum number of ports to bundle in this port channel";
        type uint8;
      }
      leaf min-bundle {
        description
          "LACP minimum number of ports to bundle in this port channel";
        type uint8;
      }
    }
  }

  // interface Port-channel / mlacp
  grouping config-interface-port-channel-mlacp-grouping {
    container mlacp {
      description
        "mLACP Port Channel interface subcommands";
      container interchassis {
        description
          "mLACP Interchassis commands";
        leaf group {
          description
            "Interchassis Group";
          type uint32 {
            range "1..4294967295";
          }
        }
      }
    }
  }

  grouping config-interface-ethernet-grouping {
    // interface * / carrier-delay
    container carrier-delay {
      description
        "Specify delay for interface transitions";
      uses interface-ethernet-carrier-delay-grouping;
      container down {
        description
          "Carrier Down Transitions";
        uses interface-ethernet-carrier-delay-grouping;
      }
      container up {
        description
          "Carrier Up Transitions";
        uses interface-ethernet-carrier-delay-grouping;
      }
    }

    // interface * / channel-group
    container channel-group {
      description
        "Add this interface to an Etherchannel group";
      leaf number {
        type uint16 {
          range "1..512";
        }
      }

      leaf mode {
        description
          "Etherchannel Mode of the interface";
        type enumeration {
          enum "active";
          enum "auto";
          enum "desirable";
          enum "on";
          enum "passive";
        }
      }

      leaf non-silent {
        description
          "Start negotiation only after data packets received";
        type empty;
      }

      leaf link {
        description
          "Assign a link identifier used for load-balancing";
        type uint8 {
          range "1..4";
        }
      }

      leaf auto {
        description
          "LACP auto";
        type empty;
      }
    }

    // interface * / channel-protocol
    leaf channel-protocol {
      description
        "Select the channel protocol (LACP, PAgP)";
      type enumeration {
        enum "lacp";
        enum "pagp";
      }
    }

    // interface * / ethernet
    container ethernet {
      description
        "Ethernet interface parameters";
      container oam {
        description
          "To enable Ethernet Link OAM";
        presence "true";
        container link-monitor {
          description
            "Ethernet OAM Link Monitor";
          container frame {
            description
              "Errored frames in a period measured by time";
            container threshold {
              description
                "Errored frame threshold";
              container high {
                description
                  "High Threshold";
                leaf thresh {
                  description
                    "Set the high errored frame threshold in number of frames";
                  type uint16 {
                    range "1..65535";
                  }
                }
                leaf none {
                  description
                    "Disable high threshold";
                  type empty;
                }
              }
              leaf low {
                description
                  "Set the low errored frame threshold in number of frames";
                type uint16 {
                  range "0..65535";
                }
              }
            }
            leaf window {
              description
                "Set window size in multiple of 100 milliseconds (will be rounded off to second)";
              type uint16 {
                range "10..600";
              }
            }
          }

          container frame-period {
            description
              "Errored frames in a period measured by number of frames";
            container threshold {
              description
                "Errored frame-period threshold";
              container high {
                description
                  "High Threshold";
                leaf f-thresh {
                  description
                    "Set the high errored frame-period threshold in number of frames";
                  type uint16 {
                    range "1..65535";
                  }
                }
                leaf none {
                  description
                    "Disable high threshold";
                  type empty;
                }
              }
              leaf low {
                description
                  "Set the low errored frame-period threshold in number of frames";
                type uint16 {
                  range "0..65535";
                }
              }
            }
            leaf window {
              description
                "Set window size in number of 10000 frames";
              type uint16 {
                range "1..65535";
              }
            }
          }

          container frame-seconds {
            description
              "Errored frame seconds in a period";
            container threshold {
              description
                "Errored frame-seconds threshold";
              container high {
                description
                  "High Threshold";
                leaf e-thresh {
                  description
                    "Set the high errored frame-seconds threshold in number of seconds";
                  type uint16 {
                    range "1..900";
                  }
                }
                leaf none {
                  description
                    "Disable high threshold";
                  type empty;
                }
              }
              leaf low {
                description
                  "Set the low errored frame-seconds threshold in number of seconds";
                type uint16 {
                  range "1..900";
                }
              }
            }
            leaf window {
              description
                "Set window size in multiple of 100 milliseconds (will be rounded off to second)";
              type uint16 {
                range "100..9000";
              }
            }
          }

          container high-threshold {
            description
              "Additional high threshold configuration";
            container action {
              description
                "Specifiy an action when the high threshold is crossed";
              leaf error-disable-interface {
                description
                  "Error-disable the interface";
                type empty;
              }
            }
          }
          leaf on {
            description
              "Enable link monitoring on the interface";
            type empty;
          }
          container receive-crc {
            description
              "Received frames with CRC errors in a period";
            container threshold {
              description
                "Errored frame-seconds threshold";
              container high {
                description
                  "High Threshold";
                leaf crc-thresh {
                  description
                    "Set the high received crc error threshold in number of frames";
                  type uint16 {
                    range "1..65535";
                  }
                }
                leaf none {
                  description
                    "Disable high threshold";
                  type empty;
                }
              }
              leaf low {
                description
                  "Set the low received crc error threshold in number of frames";
                type uint16 {
                  range "0..65535";
                }
              }
            }
            leaf window {
              description
                "Set window size in multiple of 100 milliseconds (will be rounded off to second)";
              type uint16 {
                range "10..1800";
              }
            }
          }
          leaf supported {
            description
              "Support link monitoring on the interface";
            type empty;
          }
          container symbol-period {
            description
              "Errored symbols in a period";
            container threshold {
              description
                "Error symbol-period threshold";
              container high {
                description
                  "High Threshold";
                leaf err-thresh {
                  description
                    "Set the high error symbol-period threshold in number of symbols";
                  type uint16 {
                    range "1..65535";
                  }
                }
                leaf none {
                  description
                    "Disable high threshold";
                  type empty;
                }
              }
              leaf low {
                description
                  "Set the low error symbol-period threshold in number of symbols";
                type uint16 {
                  range "0..65535";
                }
              }
            }
            leaf window {
              description
                "Set window size in number of 1048576 symbols";
              type uint16 {
                range "1..65535";
              }
            }
          }
        }
        leaf max-rate {
          type uint8 {
            range "1..10";
          }
        }
        leaf min-rate {
          type uint8 {
            range "1..10";
          }
        }
        leaf mode {
          type enumeration {
            enum "active";
            enum "passive";
          }
        }

        container remote-failure {
          description
            "Ethernet OAM remote failure indication";
          container critical-event {
            description
              "Critical event";
            container action {
              description
                "Specifiy an action when a remote failure is detected";
              leaf error-disable-interface {
                description
                  "Error-disable the interface";
                type empty;
              }
            }
          }
          container dying-gasp {
            description
              "Dying gasp";
            container action {
              description
                "Specifiy an action when a remote failure is detected";
              presence "true";
              leaf error-disable-interface {
                description
                  "Error-disable the interface";
                type empty;
              }
            }
          }
          container link-fault {
            description
              "Link fault";
            container action {
              description
                "Specifiy an action when a remote failure is detected";
              presence "true";
              leaf error-disable-interface {
                description
                  "Error-disable the interface";
                type empty;
              }
            }
          }
        }

        container remote-loopback {
          description
            "Ethernet OAM Remote Loopback";
          leaf supported {
            description
              "Support remote loopback functionality";
            type empty;
          }
          leaf timeout {
            description
              "Set timeout value in number of seconds";
            type uint8 {
              range "1..10";
            }
          }
        }
        leaf timeout {
          type uint8 {
            range "2..30";
          }
        }
      }

      container dot1ad {
        description
          "ethernet dot1ad port";
        choice dot1ad-choice {
          leaf nni {
            description
              "dot1ad nni port";
            type empty;
          }

          container uni {
            description
              "dot1ad uni";
            choice uni-choice {
              leaf c-port {
                description
                  "dot1ad uni customer bridge port";
                type empty;
              }
              leaf s-port {
                description
                  "dot1ad uni s bridge port";
                type empty;
              }
            }
          }//uni
       }
      }//dot1ad
    }


    // interface * / eapol 
    container eapol {
      description
        "eapol";
      container destination-address {
        description
          "Configure destination MAC address";
        leaf broadcast-address {
          description
            "Configure broadcast MAC address";
          type empty;
        }
      }
    }

    // interface * / synchronous
    container synchronous {
      description
        "Synchronous";
      leaf mode {
        description
          "Mode";
        type empty;
      }
    }

    // interface * / speed
    container speed {
      description
        "Configure speed operation";
      choice speed-choice {
        leaf auto {
          description
            "Enable AUTO speed configuration";
          type empty;
        }
        leaf value-10 {
          description
            "10 Mbps operation";
          type empty;
        }
        leaf value-100 {
          description
            "100 Mbps operation";
          type empty;
        }
        leaf value-1000 {
          description
            "1000 Mbps operation";
          type empty;
        }
        leaf value-10000 {
          description
            "10000 Mbps operation";
          type empty;
        }
        leaf nonegotiate {
          type empty;
        }
      }
    }
    // interface * / duplex
    leaf duplex {
      description
        "Configure duplex operation.";
      type enumeration {
        enum "auto" {
        }
        enum "full" {
        }
        enum "half" {
        }
      }
    }

    // interface * / negotiation
    container negotiation {
      description
        "Select autonegotiation mode";
      leaf auto {
        description
          "Enable link autonegotiation";
        type boolean;
      }
    }

    // interface * plim
    container plim {
      description
        "Configure features on the PLIM";
      container ethernet {
        description
          "Configure features on the ethernet interface";
        container vlan {
          description
            "vlan specific features";
          container filter {
            description
              "Configure VLAN filtering";
            leaf disable {
              description
                "Configure the interface to accept all VLAN traffic";
              type empty;
            }
          }
        }
      }

      container qos {
        description
          "QoS on the PLIM";
        container input {
          description
            "Configure PLIM QoS at the input of an interface";
          container queue {
            description
              "Queue number";
            choice priority {
              case low {
                container zero {
                  description
                    "Low priority queue";
                  container pause {
                    description
                      "Pause Frame generation and threshold";
                    leaf enable {
                      description
                        "Enable pause-frame generation";
                      type boolean;
                    }
                    leaf threshold {
                      description
                        "Threshold as a percent of queue limit for pause frame generation";
                      type uint8 {
                        range "0..99";
                      }
                    }
                  }
                }
              }
              case high {
                container strict-priority {
                  description
                    "High priority queue";
                  container pause {
                    description
                      "Pause Frame generation and threshold";
                    leaf enable {
                      description
                        "Enable pause-frame generation";
                      type boolean;
                    }
                    leaf threshold {
                      description
                        "Threshold as a percent of queue limit for pause frame generation";
                      type uint8 {
                        range "0..99";
                      }
                    }
                  }
                }
              }
            }
          }
        }
      }
    }

    // interface * / pppoe
    container pppoe {
      description
        "pppoe interface subcommands";
      container enable {
        description
          "Enable pppoe";
        presence "true";
        leaf group {
          description
            "attach a BBA group";
          type union {
            type string;
            type enumeration {
              enum "global";
            }
          }
        }
      }
      leaf max-sessions {
        description
          "Maximum PPPOE sessions";
        type uint16 {
          range "1..4085";
        }
      }
    }

    // interface * / service instance * ethernet
    container service {
      description
        "Configure Ether Service";
      list instance {
        description
          "Configure Ether Service Instance";
        // interface overlay aslo has service, but not ethernet-grouping
        key "id";
        leaf id {
          type uint32;
        }
        leaf trunk {
          description
            "Trunk Service Instance";
          type empty;
        }
        leaf GigabitEthernet {
          description
            "Configure an GigabitEthernet Instance";
          type empty;
        }
        leaf ethernet {
          description
            "Configure an Ethernet Instance";
          type empty;
        }
        leaf ethernet-evc-name {
          type string;
        }
        // interface * / service instance * ethernet / description
        leaf description {
          description
            "Service instance specific description";
          type string {
            length "0..240";
          }
        }
        // interface * / service instance * ethernet / evc-name
        leaf evc-name {
          type string {
            length "1..100";
          }
        }
        // interface * / service instance * ethernet / encapsulation
        container encapsulation {
          description
            "Configure ethernet frame match criteria";
          leaf default {
            description
              "catch-all unconfigured encapsulation";
            type empty;
          }
          container dot1ad {
            description
              "802.1ad - Provider Bridges";
            leaf-list id {
              type union {
                type uint16 {
                  range "1..4094";
                }
                type enumeration {
                  enum "any";
                }
                type string;
              }
            }
            leaf-list cos {
              description
                "CoS value to use for CFM packets";
              type uint8 {
                range "0..7";
              }
            }
            leaf-list dot1q {
              description
                "Second tag (dot1q)";
              type union {
                type uint16 {
                  range "1..4094";
                }
                type enumeration {
                  enum "any";
                }
                type string;
              }
            }
            container cos2 {
              leaf-list cos {
                description
                  "CoS value to use for CFM packets";
                type uint8 {
                  range "0..7";
                }
              }
            }
            leaf-list etype {
              description
                "payload ethertype after Vlan Field";
              type enumeration {
                enum "ipv4";
                enum "ipv6";
                enum "pppoe-all";
                enum "pppoe-discovery";
                enum "pppoe-session";
              }
            }
            leaf exact {
              description
                "payload Ethertype does not include 802.1q/802.1ad Tags.";
              type empty;
            }
          }
          container dot1q {
            description
              "IEEE 802.1Q Virtual LAN or S-VLAN";
            leaf-list id {
              type union {
                type uint16 {
                  range "1..4094";
                }
                type enumeration {
                  enum "any";
                }
                type string;
              }
            }
            leaf-list cos {
              description
                "cos Vlan";
              type uint8 {
                range "0..7";
              }
            }
            leaf-list second-dot1q {
              description
                "inner 802.1Q Virtual LAN or C-VLAN";
              type union {
                type uint16 {
                  range "1..4094";
                }
                type enumeration {
                  enum "any";
                }
                type string;
              }
            }
            container cos2 {
              leaf-list cos {
                description
                  "cos Vlan";
                type uint8 {
                  range "0..7";
                }
              }
            }
            leaf-list etype {
              description
                "payload ethertype after Vlan Field";
              type enumeration {
                enum "ipv4";
                enum "ipv6";
                enum "pppoe-all";
                enum "pppoe-discovery";
                enum "pppoe-session";
              }
            }
            leaf exact {
              description
                "payload Ethertype does not include 802.1q/802.1ad Tags.";
              type empty;
            }
            leaf vlan-type {
              description
                "Vlan Protocol Type";
              type enumeration {
                enum "0x88A8";
                enum "0x9100";
                enum "0x9200";
              }
            }
          }
          container priority-tagged {
            description
              "Priority tagged EFP";
            presence "true";
            container cos-container {
              leaf-list cos {
                description
                  "cos Vlan";
                type uint8 {
                  range "0..7";
                }
              }
            }
            leaf-list etype {
              description
                "payload ethertype after Vlan Field";
              type enumeration {
                enum "ipv4";
                enum "ipv6";
                enum "pppoe-all";
                enum "pppoe-discovery";
                enum "pppoe-session";
              }
            }
          }
          container untagged {
            description
              "Untagged encapsulation";
            presence "true";
          }
        }
        // interface * / service instance * ethernet / ip
        container ip {
          description
            "Interface Internet Protocol config commands";
          container acl {
            leaf access-group {
              description
                "Specify access control for packets";
              type ios-types:exp-acl-type;
            }
            leaf in {
              description
                "inbound packets";
              type empty;
            }
            leaf out {
              description
                "outbound packets";
              type empty;
            }
          }
          container dhcp {
            description
              "DHCP";
            container relay {
              description
                "DHCP relay";
              container information {
                description
                  "DHCP relay information";
                container option {
                  description
                    "DHCP relay information option";
                  leaf subscriber-id {
                    description
                      "DHCP relay information option subscriber-id";
                    type string;
                  }
                }
              }
            }
          }
          container verify {
            description
              "verify";
            leaf source {
              description
                "source address";
              type empty;
            }
            leaf vlan {
              description
                "vlan specification";
              type empty;
            }
            leaf dhcp-snooping {
              description
                "snooping enable vlan";
              type empty;
            }
            leaf port-security {
              description
                "port security";
              type empty;
            }
          }
        }
        // interface * / service instance * ethernet / ipv6
        container ipv6 {
          description
            "IPv6 interface subcommands";
          leaf traffic-filter {
            description
              "Access control list for packets";
            type string;
          }
          leaf in {
            description
              "inbound packets";
            type empty;
          }
          leaf out {
            description
              "outbound packets";
            type empty;
          }
        }
        // interface * / service instance * ethernet / rewrite
        container rewrite {
          description
            "Configure ethernet rewrite criteria";
          container ingress {
            description
              "Ingress Rewrite";
            container tag {
              description
                "Configure Rewrite Tag";
              container pop {
                description
                  "Pop the tag";
                leaf way {
                  type enumeration {
                    enum "1";
                    enum "2";
                  }
                }
                leaf mode {
                  type enumeration {
                    enum "symmetric";
                  }
                }
              }
              container push {
                description
                  "Rewrite Operation of push";
                leaf dot1q {
                  description
                    "Push dot1q tag";
                  type uint16 {
                    range "1..4094";
                  }
                }
                leaf mode {
                  type enumeration {
                    enum "symmetric";
                  }
                }
              }
              container translate {
                description
                  "Translate Tag";
                container t1-to-1 {
                  description
                    "Translate 1-to-1";
                  leaf dot1q {
                    description
                      "Ethertype dot1q of the translation";
                    type uint16 {
                      range "1..4094";
                    }
                  }
                  leaf mode {
                    type enumeration {
                      enum "symmetric";
                    }
                  }
                }
                container t1-to-2 {
                  description
                    "Translate 1-to-2";
                  leaf dot1q {
                    description
                      "Translate ethertype of dot1q";
                    type uint16 {
                      range "1..4094";
                    }
                  }
                  leaf second-dot1q {
                    description
                      "Second dot1q tag";
                    type uint16 {
                      range "1..4094";
                    }
                  }
                  leaf mode {
                    type enumeration {
                      enum "symmetric";
                    }
                  }
                }
                container t2-to-1 {
                  description
                    "Translate 2-to-1";
                  leaf dot1q {
                    description
                      "Ethertype dot1q of the translation";
                    type uint16 {
                      range "1..4094";
                    }
                  }
                  leaf mode {
                    type enumeration {
                      enum "symmetric";
                    }
                  }
                }
                container t2-to-2 {
                  description
                    "Translate 2-to-2";
                  leaf dot1q {
                    description
                      "Translate ethertype of dot1q";
                    type uint16 {
                      range "1..4094";
                    }
                  }
                  leaf second-dot1q {
                    description
                      "Second dot1q tag";
                    type uint16 {
                      range "1..4094";
                    }
                  }
                  leaf mode {
                    type enumeration {
                      enum "symmetric";
                    }
                  }
                }
              }
            }
          }
        }
        // interface * / service instance * ethernet / group
        leaf group {
          type uint32;
        }
        // interface * / service instance * ethernet / errdisable
        container errdisable {
          description
            "Configure error disable";
          container recovery {
            description
              "enable auto recovery";
            container cause {
              description
                "error disable cause";
              leaf mac-security {
                description
                  "mac-security violation";
                type uint32 {
                  range "30..86400";
                }
              }
            }
          }
        }
        // interface * / service instance * ethernet / ethernet
        container ethernet-container {
           //in order not to collide with submode ethernet
          container ethernet {
            description
              "ethernet";
            container lmi {
              description
                "Configure ether lmi parameters";
              container ce-vlan {
                description
                  "Configure ether lmi customer vlans";
                container map {
                  description
                    "Configure ether lmi ce-vlan/evc map";
                  choice map-choice {
                    leaf any {
                      description
                        "For all VLANS [1-4094,untagged]";
                      type empty;
                    }
                    leaf default {
                      description
                        "Default EFP";
                      type empty;
                    }
                    leaf untagged {
                      description
                        "Untagged frames";
                      type empty;
                    }
                    leaf vlan-range {
                      type string {
                        pattern "(\\d+(.*-.*\\d+)?)(,.*\\d+(.*-.*\\d+)?)*(,.*untagged)?";
                      }
                    }
                  }
                }
              }
            }
            container loopback {
              description
                "Ethernet Dataplane Loopback";
              container permit {
                description
                  "Allow data plane loopback to be activated";
                leaf external {
                  description
                    "Allow to loopback the traffic from the wire";
                  type empty;
                }
                leaf internal {
                  description
                    "Allow to loopback the traffic from the relay";
                  type empty;
                }
              }
            }
          }
        }
        // interface * / service instance * ethernet / snmp
        container snmp {
          description
            "Modify SNMP service instance parameters";
          container trap {
            description
              "Allow a specific SNMP trap";
            leaf link-status {
              description
                "Allow SNMP LINKUP and LINKDOWN traps";
              type empty;
            }
          }
          container ifindex {
            description
              "Persist ifindex for the service instance";
            leaf persist {
              description
                "Enable/Disable ifIndex persistence";
              type empty;
            }
          }
        }
        // interface * / service instance * ethernet / bridge-domain
        container bridge-domain {
          description
            "Bridge-domain";
          leaf bridge-id {
            must "../../encapsulation/default or ../../encapsulation/dot1ad/id or ../../encapsulation/dot1q/id"
                 + " or ../../encapsulation/priority-tagged or ../../encapsulation/untagged" {
              error-message "bridge-domain depends on encapsulation configuration";
            }
            type uint16;
          }
          container split-horizon {
            description
              "Configure this port as a member of a split horizon group";
            leaf group {
              description
                "Split-horizon group";
              type uint8 {
                range "0..13";
              }
            }
          }
          leaf from-encapsulation {
            description
              "from-encapsulation";
            type empty;
          }
        }
        // interface * / service instance * ethernet / mac
        container mac {
          description
            "Commands for MAC Address-based features";
          container security {
            description
              "MAC Security commands";
            presence "true";
            container maximum {
              description
                "Configure an upper bound";
              leaf addresses {
                description
                  "Maximum addresses that can be learnt on this service instance";
                type uint16 {
                  range "1..1000";
                }
              }
            }
            leaf violation {
              description
                "Configure the response when a MAC security policy is violated";
              type enumeration {
                enum "protect";
                enum "restrict";
              }
            }
          }
          list access-group {
            description
              "Specify access control for packets";
            key "acl-name";
            leaf acl-name {
              description
                "ACL name";
              type "string";
            }
            leaf in {
              description
                "Apply to ingress";
              type empty;
            }
            leaf out {
              description
                "Apply to Egress";
              type empty;
            }
          }
        }
        // interface * / service instance * ethernet / service-policy
        container service-policy {
          description
            "Attach a policy-map to an EFP";
          list input {
            description
              "service policy input";
            key "name";
            leaf name {
              type string;
            }
          }
          list output {
            description
              "service policy output";
            key "name";
            leaf name {
              type string;
            }
          }
        }

        // interface * / service instance * ethernet / shutdown
        leaf shutdown {
          description
            "Take the Service Instance out of Service";
          type empty;
        }

        // interface * / service instance * ethernet / cfm
        container cfm {
          description
            "Ethernet CFM EFP subcommands";
          container encapsulation {
            description
              "Configure CFM ethernet frame encapsulation";
            container dot1ad {
              description
                "802.1ad - Provider Bridges";
              leaf vlan-id {
                type uint16 {
                  range "1..4094";
                }
              }
              leaf cos {
                description
                  "CoS value to use for CFM packets";
                type uint8 {
                  range "0..7";
                }
              }
              leaf dot1q {
                description
                  "Second tag (dot1q)";
                type uint16 {
                  range "1..4094";
                }
              }
            }
            container dot1q {
              description
                "IEEE 802.1Q Virtual LAN or S-VLAN";
              leaf vlan-id {
                type uint16 {
                  range "1..4094";
                }
              }
              leaf cos {
                description
                  "CoS value to use for CFM packets";
                type uint8 {
                  range "0..7";
                }
              }
              leaf second-dot1q {
                description
                  "inner 802.1Q Virtual LAN or C-VLAN";
                type uint16 {
                  range "1..4094";
                }
              }
            }
          }

          container mep {
            description
              "Maintenance End Point";
            leaf domain {
              description
                "Configure a domain for this mep";
              type string;
            }
            leaf mpid {
              description
                "Maintenance End Point Identifier";
              type uint16 {
                range "1..8191";
              }
            }
          }

          container mip {
            description
              "Maintenance Intermediate Point";
            leaf level {
              description
                "Maintenance Level";
              type uint8;
            }
          }
        }

        // interface * / service instance * ethernet / l2protocol
        container l2protocol {
          description
            "Configure l2 control protocol processing";
          container discard {
            description 
              "discard L2 control protocol packets as data";
            presence "true";
            uses config-interface-efp-l2protocol-grouping;
          }
          container peer {
            description
              "peer L2 control protocol packets as data";
            presence "true";
            uses config-interface-efp-l2protocol-grouping;
          }
          container forward {
            description
              "forward L2 control protocol packets as data";
            presence "true";
            uses config-interface-efp-l2protocol-grouping;
          }
          container tunnel {
            description
              "tunnel L2 control protocol packets as data";
            presence "true";
            uses config-interface-efp-l2protocol-grouping;
          }
        }
      }
    }
  } // config-interface-ethernet-grouping

  grouping config-ethernet-grouping {
    list evc {
      if-feature ios-features:eth-evc;
      description
        "define an Ethernet virtual connection (EVC)";
      key "name";
      leaf name {
        type string {
          length "1..100";
        }
      }
    }
    // ethernet lmi
    container lmi {
      description
        "Local Management Interface";
      leaf ce {
        description
          "Ethernet LMI Customer Edge";
        type empty;
      }
      leaf global {
        description
          "Ethernet LMI is enabled on all supported Interfaces";
        type empty;
      }
    }
    // ethernet cfm
    container cfm {
      description
        "Connectivity Fault Management";
      container ais {
        description
          "AIS Maintenance Condition";
        container link-status {
          description
            "8023ah SMEP or link state up/down";
          container global {
            description
              "8023ah SMEP or link state state up/down AIS global configuration";
            presence "true";
            container cfm-Mode__config-ais-link-cfm {
              leaf disable {
                description
                  "Disable AIS transmission";
                type empty;
              }
              leaf level {
                description
                  "Maintenance Level";
                type uint8 {
                  range "0..7";
                }
              }
              container period {
                description
                  "AIS Transmission period";
                leaf tp-1 {
                  type empty;
                }
                leaf tp-60 {
                  description
                    "Seconds";
                  type empty;
                }
              }
            }
          }
        }
      }
      container alarm {
        description
          "CFM Alarm";
        leaf delay {
          description
            "msec (default 2500 msec)";
          type uint16 {
            range "2500..10000";
          }
        }
        container notification {
          description
            "CFM alarm notification";
          leaf all {
            description
              "Report all defects: DefRDI, DefMACStatus, DefRemote, DefError, DefXcon";
            type empty;
          }
          leaf error-xcon {
            description
              "Report only: DefError and DefXcon";
            type empty;
          }
          leaf mac-remote-error-xcon {
            description
              "Report only: DefMACStatus, DefRemote, DefError and DefXcon (default)";
            type empty;
          }
          leaf none {
            description
              "No defects to be reported";
            type empty;
          }
          leaf remote-error-xcon {
            description
              "Report only: DefRemote, DefError and DefXcon";
            type empty;
          }
          leaf xcon {
            description
              "Report only: DefXcon";
            type empty;
          }
        }
        leaf packet {
          description
            "max DefError and DefXcon packets";
          type uint16 {
            range "1..65535";
          }
        }
        leaf reset {
          description
            "msec (default 10000 msec)";
          type uint16 {
            range "2500..10000";
          }
        }
      }
      leaf ieee {
        description
          "CFM IEEE enable";
        type empty;
      }
      leaf global {
        description
          "CFM global enable";
        type empty;
      }
      list domain {
        description
          "Configure a domain";
        key "name";
        leaf name {
          type string;
        }
        leaf level {
          description
            "Maintenance Level";
          type uint8;
        }
        list service {
          description
            "Maintenance Association within Domain";
          key "name";
          leaf name {
            type string;
          }
          leaf evc {
            if-feature ios-features:eth-evc;
            description
              "Specify EVC";
            type string;
          }

          leaf vlan {
            description
              "VLAN id";
            type uint16 {
              range "1..4094";
            }
          }
          container continuity-check {
            description
              "Enable Continuity Check for Maintenance Association";
            presence "true";
          }
        }
      }
      container logging {
        description
          "Enable CFM syslog messages";
        presence "true";
        leaf ais {
          description
            "AIS logging";
          type empty;
        }
        container alarm {
          description
            "Alarm logging";
          leaf cisco {
            description
              "Cisco MIB syslogs";
            type empty;
          }
          leaf ieee {
            description
              "IEEE MIB syslogs";
            type empty;
          }
        }
      }
      container mep {
        description
          "Maintenance End Point";
        container crosscheck {
          description
            "Cross Check remote MEPs";
          leaf start-delay {
            description
              "seconds (30 seconds default)";
            type uint16 {
              range "1..65535";
            }
          }
        }
      }
      container mip {
        description
          "CFM MIP commands";
        container auto-create {
          description
            "CFM MIP auto creation";
          container level {
            description
              "Maintenance Level";
            list mef-num {
              key "mef-num";
              leaf mef-num {
                description
                  "maintenance level number";
                type uint8 {
                  range "0..7";
                }
              }
              leaf evc {
                description
                  "EVC name";
                type string;
              }
              leaf vlan {
                description
                  "VLAN id";
                type uint16 {
                  range "1..4094";
                }
              }
            }
          }
        }
        leaf filter {
          description
            "CFM MIP filter";
          type empty;
        }
      }
      container traceroute {
        description
          "CFM Traceroute";
        container cache {
          description
            "CFM Traceroute Cache";
          presence "true";
          leaf hold-time {
            description
              "minutes (default 100)";
            type uint16 {
              range "1..65535";
            }
          }
          leaf size {
            description
              "Number of cached lines (default 100)";
            type uint16 {
              range "1..4095";
            }
          }
        }
      }
    }
  }

  grouping config-port-channel-grouping {
    //  hash-distribution  Hash Distribution method
    // port-channel auto
    leaf auto {
      description
        "LACP auto for the system";
      type empty;
    }
    // port-channel load-balance
    container load-balance {
      description
        "Load Balancing method";
      leaf load-balance {
        type enumeration {
          enum "dst-ip";
          enum "dst-mac";
          enum "dst-mixed-ip-port";
          enum "dst-port";
          enum "mpls";
          enum "src-dst-ip";
          enum "src-dst-mac";
          enum "src-dst-mixed-ip-port";
          enum "src-dst-port";
          enum "src-ip";
          enum "src-mac";
          enum "src-mixed-ip-port";
          enum "src-port";
        }
      }
      //extended
     container extended {
       description
         "Extended Load Balance Methods";
       presence true;
       leaf-list extended {
         type enumeration {
           enum "dst-ip";
           enum "dst-mac";
           enum "dst-port";
           enum "ipv6-label";
           enum "l3-proto";
           enum "src-ip";
           enum "src-mac";
           enum "src-port";
         }
       }
     }
    }
    container load-balancing {
      description "Load Balance method";
        leaf vlan-manual {
          description "Manual Traffic Distribution based on VLAN id";
          type empty;
        }
    }
    // per-module per-module configuration
  }

  grouping config-interface-macsec-grouping {
    leaf  macsec {
      description
        "Enable macsec on the interface";
      type empty;
    }
    container macsec-option {
      description
        "Enable macsec on the interface";
      container macsec {
        leaf dot1q-in-clear {
          description
            "Dot1q in Clear option";
          type enumeration {
            enum "1";
          }
        }
        container replay-protection {
          description
            "Set replay-protection";
          leaf window-size {
            description
              "Set replay window-size";
            type uint32;
          }
        }
      }
    }
  }

  /////////////////////////////////////////////////////////
  // native / esmc
  /////////////////////////////////////////////////////////
  grouping config-esmc-grouping {
    container esmc {
      description
        "Ethernet Synchronization Messaging Channel";
      leaf process {
        description
          "process";
        type empty;
      }
    }
  }

  /////////////////////////////////////////////////////////
  // native / esmc
  /////////////////////////////////////////////////////////
  augment "/ios:native" {
     uses config-esmc-grouping {
       if-feature ios-features:esmc;
     }
  }

  /////////////////////////////////////////////////////////
  // native / ethernet
  /////////////////////////////////////////////////////////
  augment "/ios:native/ios:ethernet" {
     uses config-ethernet-grouping;
  }

  /////////////////////////////////////////////////////////
  // native / port-channel
  /////////////////////////////////////////////////////////
  augment "/ios:native/ios:port-channel" {
    uses config-port-channel-grouping;
  }

  /////////////////////////////////////////////////////////
  // native / interface
  /////////////////////////////////////////////////////////
  augment "/ios:native/ios:interface/ios:FastEthernet" {
    uses config-interface-ethernet-grouping;
    uses config-interface-ethernet-member-link-lacp-grouping;
    uses config-interface-macsec-grouping {
      if-feature ios-features:macsec;
    }
  }

  augment "/ios:native/ios:interface/ios:GigabitEthernet" {
    uses config-interface-ethernet-grouping;
    uses config-interface-ethernet-member-link-lacp-grouping;
    uses config-interface-macsec-grouping {
      if-feature ios-features:macsec;
    }
  }

  augment "/ios:native/ios:interface/ios:TwoGigabitEthernet" {
    uses config-interface-ethernet-grouping;
    uses config-interface-ethernet-member-link-lacp-grouping;
    uses config-interface-macsec-grouping {
      if-feature ios-features:macsec;
    }
  }

  augment "/ios:native/ios:interface/ios:FiveGigabitEthernet" {
    uses config-interface-ethernet-grouping;
    uses config-interface-ethernet-member-link-lacp-grouping;
    uses config-interface-macsec-grouping {
      if-feature ios-features:macsec;
    }
  }

  augment "/ios:native/ios:interface/ios:TenGigabitEthernet" {
    uses config-interface-ethernet-grouping;
    uses config-interface-ethernet-member-link-lacp-grouping;
    uses config-interface-macsec-grouping {
      if-feature ios-features:macsec;
    }
  }

  augment "/ios:native/ios:interface/ios:TwentyFiveGigE" {
    uses config-interface-ethernet-grouping;
    uses config-interface-ethernet-member-link-lacp-grouping;
    uses config-interface-macsec-grouping {
      if-feature ios-features:macsec;
    }
  }

  augment "/ios:native/ios:interface/ios:FortyGigabitEthernet" {
    uses config-interface-ethernet-grouping;
    uses config-interface-ethernet-member-link-lacp-grouping;
    uses config-interface-macsec-grouping {
      if-feature ios-features:macsec;
    }
  }

  augment "/ios:native/ios:interface/ios:HundredGigE" {
    uses config-interface-ethernet-grouping;
    uses config-interface-macsec-grouping {
      if-feature ios-features:macsec;
    }
  }

  augment "/ios:native/ios:interface/ios:Port-channel" {
    uses config-interface-ethernet-grouping;
    uses config-interface-port-channel-lacp-grouping;
    uses config-interface-port-channel-mlacp-grouping;
  }

  augment "/ios:native/ios:interface/ios:Port-channel-subinterface/ios:Port-channel" {
    uses config-interface-ethernet-grouping;
  }

  augment "/ios:native/ios:interface/ios:VirtualPortGroup" {
    uses config-interface-ethernet-grouping;
    uses config-interface-ethernet-member-link-lacp-grouping;
  }

  augment "/ios:native/ios:interface/ios:Virtual-Template" {
    uses config-interface-ethernet-grouping;
    uses config-interface-ethernet-member-link-lacp-grouping;
  }

  augment "/ios:native/ios:interface/ios:BDI" {
    uses config-interface-ethernet-grouping;
  }
  augment "/ios:native/ios:interface/ios:Vlan" {
    uses config-interface-ethernet-grouping;
  }
}
