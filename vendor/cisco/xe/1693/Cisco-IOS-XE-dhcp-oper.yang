module Cisco-IOS-XE-dhcp-oper {
  yang-version 1;
  namespace "http://cisco.com/ns/yang/Cisco-IOS-XE-dhcp-oper";
  prefix dhcp-ios-xe-oper;

  import ietf-inet-types {
    prefix inet;
  }
  import ietf-yang-types {
    prefix yang;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for DHCP Server and Client operational data.
     Copyright (c) 2017-2018 by Cisco Systems, Inc.
     All rights reserved.";

  revision 2018-02-13 {
    description
      "dns name changes.";
    reference "2.0.0";
  }
  revision 2017-11-01 {
    description
      "Initial revision";
    reference "1.0.0";
  }

  typedef dhcp-server-binding-state {
    type enumeration {
      enum "dhcp-server-binding-state-selecting" {
        value 0;
        description
          "Server state is in Selecting mode";
      }
      enum "dhcp-server-binding-state-active" {
        value 1;
        description
          "Server state Active new address provided";
      }
      enum "dhcp-server-binding-state-terminated" {
        value 2;
        description
          "Server terminated the connection with a client";
      }
      enum "dhcp-server-binding-state-unknown" {
        value 3;
        description
          "Server state unknown";
      }
    }
    description
      "DHCP server binding states ";
  }

  typedef dhcp-server-binding-type {
    type enumeration {
      enum "dhcp-server-binding-type-manual" {
        value 0;
        description
          "Server binding Type Manual";
      }
      enum "dhcp-server-binding-type-static" {
        value 1;
        description
          "Sever binding type Static";
      }
      enum "dhcp-server-binding-type-relay" {
        value 2;
        description
          "Server binding type relay";
      }
      enum "dhcp-server-binding-type-automatic" {
        value 3;
        description
          "Server binding type automatic";
      }
      enum "dhcp-server-binding-type-odap" {
        value 4;
        description
          "Server binding Type ODAP";
      }
      enum "dhcp-server-binding-type-from-aaa" {
        value 5;
        description
          "Sever binding type from AAA";
      }
      enum "dhcp-server-binding-type-remembered" {
        value 6;
        description
          "Server binding type remembered";
      }
    }
    description
      "DHCP server binding type";
  }

  typedef dhcp-client-state {
    type enumeration {
      enum "dhcp-client-state-temp-from-client" {
        value 0;
        description
          "Client state address/sync from other client";
      }
      enum "dhcp-client-state-temp-from-sync" {
        value 1;
        description
          "Client state Sync";
      }
      enum "dhcp-client-state-initial" {
        value 2;
        description
          "Client state Initialing";
      }
      enum "dhcp-client-state-selecting" {
        value 3;
        description
          "Client state Selecting";
      }
      enum "dhcp-client-state-requesting" {
        value 4;
        description
          "Client state Requesting";
      }
      enum "dhcp-client-state-bound" {
        value 5;
        description
          "Client state bound";
      }
      enum "dhcp-client-state-rebinding" {
        value 6;
        description
          "Client state rebinding";
      }
      enum "dhcp-client-state-renewing" {
        value 7;
        description
          "Client state renewing";
      }
      enum "dhcp-client-state-holdtime" {
        value 8;
        description
          "Client state holdtime";
      }
      enum "dhcp-client-state-ddns-wait" {
        value 9;
        description
          "Client state DDNS wait";
      }
      enum "dhcp-client-state-releasing" {
        value 10;
        description
          "Client state releasing";
      }
      enum "dhcp-client-state-purging" {
        value 11;
        description
          "Client state purging";
      }
      enum "dhcp-client-state-leasequery" {
        value 12;
        description
          "Client state leasequery";
      }
      enum "dhcp-client-state-unknown" {
        value 13;
        description
          "Client state unknown";
      }
    }
    description
      "DHCP Client state";
  }

  typedef dhcp-expiry-option {
    type enumeration {
      enum "dhcp-expiration-time" {
        value 0;
        description
          "Expiration option time";
      }
      enum "dhcp-expiration-infinite" {
        value 1;
        description
          "Expiration option infinite";
      }
    }
    description
      "DHCP expiration option ";
  }

  typedef dhcp-client-id-type {
    type enumeration {
      enum "dhcp-htype-ethernet" {
        value 0;
        description
          "DHCP Client hardware type Ethernet";
      }
      enum "dhcp-htype-ieee802" {
        value 1;
        description
          "DHCP Client hardware type 802";
      }
      enum "dhcp-htype-rfclimit" {
        value 2;
        description
          "DHCP Client hardware type RFCLIMIT";
      }
      enum "dhcp-htype-clientid" {
        value 3;
        description
          "DHCP Client hardware type CLIENTID";
      }
    }
    description
      "DHCP Client id hardware types ";
  }

  grouping dhcp-expiry {
    description
      "Type describes whether it is time or never";
    choice expiration-time-choice {
      description
        "Choice of the expiration time";
      case dhcp-expiration-time {
        leaf time {
          type yang:date-and-time;
          description
            "Date and time of expiry ";
        }
      }
      case dhcp-expiration-infinite {
        leaf infinite {
          type empty;
          description
            "Expiry time infinite";
        }
      }
    }
  }

  grouping dhcpv4-server-key {
    description
      "Key for DHCP Server infomation table";
    leaf pool-name {
      type string;
      description
        "Server Pool name from where the Client 
         ip is provided";
    }
    leaf client-ip {
      type inet:ip-address;
      description
        "ipaddress released for a speicfic Client 
         from Server";
    }
    leaf vrf-name {
      type string;
      description
        "Query based on the vrfname speicfic to that
         pool and Client ip address as key";
    }
  }

  grouping dhcpv4-server-oper {
    description
      "DHCP Server data for binding";
    leaf client-id-type {
      type dhcp-ios-xe-oper:dhcp-client-id-type;
      description
        "Client identification Hardware types";
    }
    leaf client-id {
      type string;
      description
        "Client identification can be based on Hardware types/Mac";
    }
    container expiration {
      description
        "Expiration time infomation";
      uses dhcp-ios-xe-oper:dhcp-expiry;
    }
    leaf type {
      type dhcp-ios-xe-oper:dhcp-server-binding-type;
      description
        "Server binding type.";
    }
    leaf state {
      type dhcp-ios-xe-oper:dhcp-server-binding-state;
      description
        "Server binding states";
    }
    leaf interface {
      type string;
      description
        "interface name of the pool";
    }
  }

  grouping dhcpv4-client-key {
    description
      "Key for DHCP Server infomation table";
    leaf if-name {
      type string;
      description
        "Interface infomation where dhcp Client is configured";
    }
    leaf client-addr {
      type inet:ip-address;
      description
        "Client_addr address Allocated from Server";
    }
    leaf vrf-name {
      type string;
      description
        "Vrfname infomation related to Client";
    }
  }

  grouping dhcpv4-client-oper {
    description
      "DHCP Client data for binding";
    leaf state {
      type dhcp-ios-xe-oper:dhcp-client-state;
      description
        "DHCP Client States ";
    }
    leaf lease-server-addr {
      type inet:ip-address;
      description
        "IP address of Server from where we got IP";
    }
    leaf gateway-addr {
      type inet:ip-address;
      description
        "Gateway Address we got from Server";
    }
    leaf lease-time {
      type uint32;
      description
        "Total Lease Time in Seconds";
    }
    container lease-expiry {
      description
        "Lease Expiry time for the IP address we got";
      uses dhcp-ios-xe-oper:dhcp-expiry;
    }
    leaf lease-remaining {
      type uint32;
      description
        "Lease remaining time for the IP address";
    }
    leaf dns-address {
      type inet:ip-address;
      description
        "First DNS address";
    }
    leaf dns-address-secondary {
      type inet:ip-address;
      description
        "Secondary DNS address";
    }
    leaf subnet-mask {
      type inet:ip-address;
      description
        "Subnet mask address";
    }
  }

  container dhcp-oper-data {
    config false;
    description
      "Operational state of DHCP";
    list dhcpv4-server-oper {
      key "pool-name client-ip vrf-name";
      description
        "List of DHCP server bidning";
      uses dhcp-ios-xe-oper:dhcpv4-server-key;
      uses dhcp-ios-xe-oper:dhcpv4-server-oper;
    }
    list dhcpv4-client-oper {
      key "if-name client-addr vrf-name";
      description
        "List of DHCP clients";
      uses dhcp-ios-xe-oper:dhcpv4-client-key;
      uses dhcp-ios-xe-oper:dhcpv4-client-oper;
    }
  }
}
