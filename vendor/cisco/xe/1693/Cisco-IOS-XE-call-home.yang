module Cisco-IOS-XE-call-home {
  namespace "http://cisco.com/ns/yang/Cisco-IOS-XE-call-home";
  prefix ios-ch;


  import Cisco-IOS-XE-native {
    prefix ios;
  }

  import Cisco-IOS-XE-types {
    prefix ios-types;
  }

  import Cisco-IOS-XE-interface-common {
    prefix ios-ifc;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Call Home Yang Model.
     Copyright (c) 2016, 2018 by Cisco Systems, Inc.
     All rights reserved.";

  // =========================================================================
  // REVISION
  // =========================================================================
  revision 2018-10-11 {
    description
      "add anonymous-reporting-only and server-identity-check";
  }

  revision 2017-02-07 {
    description
      "Initial revision";
  }

  grouping call-home-profile-periodic-grouping {
    container periodic {
      choice periodic-choice {
        description
          "Periodic call-home message";
        container daily {
          description
            "Daily call-home message";
          leaf begin-time{
            description
              "Begin time";
            type ios-types:hhmm-type;
          }
        }
        container monthly {
          description
            "Monthly call-home message";
          leaf date {
            description
                "Day of month";
            type uint8 {
              range "1..31";
            }
          }
          leaf begin-time {
            description
              "Begin time";
            type ios-types:hhmm-type;
          }
        }
        container weekly {
          description
            "Weekly call-home message";
          leaf day {
            description
              "Day of the week";
            type ios-types:weekday-type;
          }
          leaf begin-time{
            description
              "Begin time";
            type ios-types:hhmm-type;
          }
        }
      }
    }
  }

  grouping cfg-call-home-profile-grouping {
    leaf active {
      description
        "Activate the current profile";
      type boolean;
    }
    leaf anonymous-reporting-only {
      description
        "Enable call-home anonymous reporting only";
      type empty;
    }
    container destination {
      description
        "Message destination related configuration";
      leaf transport-method {
        description
          "To specify transport method for this profile";
        type enumeration {
          enum "http";
          enum "email";
        }
      }
      container address {
        description
          "To add destination address to this profile";
        leaf email {
          description
            "Use email address";
          type string;
        }
        leaf http {
          description
            "To add http address to this profile";
          type string;
        }
      }
    }
    container subscribe-to-alert-group {
      description
        "Subscribe to alert-group";
      container diagnostic {
        description
          "diagnostic info";
        presence true;
        leaf severity {
          description
            "Severity";
          type enumeration {
            enum "catastrophic";
            enum "critical";
            enum "debugging";
            enum "disaster";
            enum "fatal";
            enum "major";
            enum "minor";
            enum "normal";
            enum "notification";
            enum "warning";
          }
        }
      }
      container environment {
        description
          "environmental info";
        presence true;
        leaf severity {
          description
            "Severity";
          type enumeration {
            enum "catastrophic";
            enum "critical";
            enum "debugging";
            enum "disaster";
            enum "fatal";
            enum "major";
            enum "minor";
            enum "normal";
            enum "notification";
            enum "warning";
          }
        }
      }
      container inventory {
        description
          "inventory info";
        presence true;
        uses call-home-profile-periodic-grouping;
      }
      container syslog {
        description
          "syslog info";
        presence true;
        list severity {
          description "severity";
          key value;
          leaf value {
            type enumeration {
              enum "catastrophic";
              enum "critical";
              enum "debugging";
              enum "disaster";
              enum "fatal";
              enum "major";
              enum "minor";
              enum "normal";
              enum "notification";
              enum "warning";
            }
          }
          leaf pattern{
            description
              "Syslog message pattern";
            type string;
          }
        }
      }
      container configuration {
        description
          "configuration info";
        presence true;
        uses call-home-profile-periodic-grouping;
      }
    }
  }

  grouping config-call-home-grouping {
    leaf contact-email-addr {
      description
        "Use email address";
      type string;
    }
    container source-interface {
      description
        "Source interface name to send call-home messages using email";
      uses ios-ifc:interface-grouping;
    }
    container http {
      description
        "Set parameters for http transport method";
      container secure {
        description
          "Specify secure settings for http transport method";
        leaf server-identity-check {
          description
            "check server identity";
          type boolean;
          default true;
        }
      }
    }

    container http-proxy {
      description
        "Specify proxy server for http request";
      list proxy-servers {
        key "proxy-server";
        leaf proxy-server {
          description
            "Http proxy server";
          type string;
        }
        leaf port {
          description
            "http proxy server port number";
          type uint16 {
            range "1..65535";
          }
        }
      }
    }
    list profile {
      description
        "Enter call-home profile configuration mode";
      key profile-name;
      leaf profile-name {
        type string;
      }
      uses cfg-call-home-profile-grouping;
    }
  }

  /////////////////////////////////////////////////////////
  // native / call-home
  /////////////////////////////////////////////////////////
  augment "/ios:native/ios:call-home" {
    uses config-call-home-grouping;
  }
}
