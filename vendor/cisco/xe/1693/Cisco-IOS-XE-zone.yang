module Cisco-IOS-XE-zone {
  namespace "http://cisco.com/ns/yang/Cisco-IOS-XE-zone";
  prefix ios-zone;


  import Cisco-IOS-XE-native {
    prefix ios;
  }

  import Cisco-IOS-XE-policy {
    prefix ios-policy;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Zone Interfaces Yang model.
     Copyright (c) 2016-2018 by Cisco Systems, Inc.
     All rights reserved.";

  // =========================================================================
  // REVISION
  // =========================================================================
  revision 2018-06-12 {
    description
      "Further restrict zone and zone-pair string lengths";
  }

  revision 2018-05-14 {
    description
      "Limit string lengths for threat-defense features";
  }

  revision 2018-04-28 {
    description
      "Add leaf-refs to other models to fix depencencies";
  }

  revision 2018-02-22 {
    description
      "Add threat-defense support for Ethernet interfaces";
  }

  revision 2017-11-27 {
    description
      "Added Change 25GE name";
  }

  revision 2017-09-15 {
    description
      "This revision has changes for new 2gig interface addition";
  }

  revision 2017-08-16 {
    description
      "This revision has changes for new 5gig and 25gig interfaces addition";
  }

  revision 2017-02-07 {
    description
      "Initial revision";
  }

  grouping config-interface-zone-member-grouping {
    // interface * / zone-member
    container zone-member {
      description
        "Apply zone name";
      leaf security {
        description
          "Security zone";
        type string {
          length "1..64";
        }
      }
    }
  }

  grouping config-zone-grouping {
    list security {
      description
        "Security zone";
      key "id";
      leaf id {
        type string {
          length "1..64";
        }
      }
      leaf description {
        description
          "Zone description";
        type string {
          length "1..200";
        }
      }
      leaf protection {
        description
          "config sync cookie protection against sync flood";
        type string {
          length "1..256";
        }
      }
    }
  }

  grouping config-zone-pair-grouping {
    description
      "Zone pair command";
    list security {
      description
        "Zone-pair name";
      key "id";
      leaf id {
        type string {
          length "1..128";
        }
      }
      leaf source {
        description
          "Source zone";
        type string {
          length "1..64";
        }
      }
      leaf destination {
        description
          "Destination zone";
        type string {
          length "1..64";
        }
      }
      leaf description {
        description
          "Zone description";
        type string {
          length "1..200";
        }
      }
      container service-policy {
        description
          "Configure Zone Pair Service Policy";
        container type {
          description
            "Service Policy type";
          leaf inspect {
            description
              "Configure Zone Pair Service Policy type inspect";
            type string {
              length "1..512";
            }
          }
        }
      }
    }
  }

  /////////////////////////////////////////////////////////
  // native / zone
  /////////////////////////////////////////////////////////
  augment "/ios:native/ios:zone" {
    uses config-zone-grouping;
  }

  /////////////////////////////////////////////////////////
  // native / zone-pair
  /////////////////////////////////////////////////////////
  augment "/ios:native/ios:zone-pair" {
    uses config-zone-pair-grouping;
  }

  /////////////////////////////////////////////////////////
  // native / interface *
  /////////////////////////////////////////////////////////
  augment "/ios:native/ios:interface/ios:Ethernet" {
    uses config-interface-zone-member-grouping;
  }

  augment "/ios:native/ios:interface/ios:FastEthernet" {
    uses config-interface-zone-member-grouping;
  }

  augment "/ios:native/ios:interface/ios:GigabitEthernet" {
    uses config-interface-zone-member-grouping;
  }

  augment "/ios:native/ios:interface/ios:TenGigabitEthernet" {
    uses config-interface-zone-member-grouping;
  }

  augment "/ios:native/ios:interface/ios:FiveGigabitEthernet" {
    uses config-interface-zone-member-grouping;
  }

  augment "/ios:native/ios:interface/ios:TwentyFiveGigE" {
    uses config-interface-zone-member-grouping;
  }

  augment "/ios:native/ios:interface/ios:FortyGigabitEthernet" {
    uses config-interface-zone-member-grouping;
  }

  augment "/ios:native/ios:interface/ios:HundredGigE" {
    uses config-interface-zone-member-grouping;
  }

  augment "/ios:native/ios:interface/ios:LISP" {
    uses config-interface-zone-member-grouping;
  }

  augment "/ios:native/ios:interface/ios:TwoGigabitEthernet" {
    uses config-interface-zone-member-grouping;
  }

  augment "/ios:native/ios:interface/ios:Loopback" {
    uses config-interface-zone-member-grouping;
  }

  augment "/ios:native/ios:interface/ios:Tunnel" {
    uses config-interface-zone-member-grouping;
  }

  augment "/ios:native/ios:interface/ios:Virtual-Template" {
    uses config-interface-zone-member-grouping;
  }

  augment "/ios:native/ios:interface/ios:Vlan" {
    uses config-interface-zone-member-grouping;
  }

  augment "/ios:native/ios:interface/ios:vasileft" {
    uses config-interface-zone-member-grouping;
  }

  augment "/ios:native/ios:interface/ios:vasiright" {
    uses config-interface-zone-member-grouping;
  }
}
