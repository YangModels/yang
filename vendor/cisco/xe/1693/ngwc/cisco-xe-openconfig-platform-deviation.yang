module cisco-xe-openconfig-platform-deviation {
  // namespace
  namespace "http://cisco.com/ns/yang/cisco-xe-openconfig-platform-deviation";

  prefix oc-platform-devs;

  import openconfig-platform {
    prefix oc-platform;
  }

  import openconfig-platform-transceiver {
    prefix oc-transceiver;
  }

  import openconfig-platform-port {
    prefix oc-port;
  }

  import cisco-xe-openconfig-platform-ext {
    prefix oc-platform-ext;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-platform module.";

  // =========================================================================
  // REVISION
  // =========================================================================

  revision 2018-01-25 {
    description
      "Deviated unsupported leaves for oc-port and oc-transceiver in NGWC";
  }

  revision 2017-09-01 {
    description
      "Hided avg/min/max temperature because we do not support in NGWC";
  }

  revision 2017-03-21 {
    description
      "Initial Revision";

    reference
      "RFC 6020: YANG - A Data Modeling Language for the
       Network Configuration Protocol (NETCONF)";
  }

  // =========================================================================
  // DEVIATION
  // =========================================================================

  deviation "/oc-platform:components/oc-platform:component" +
            "/oc-platform:properties/oc-platform:property" +
            "/oc-platform:name" {
      deviate replace {
        type string;
      }
      description
        "platform is oper only in Cisco XE device.";
  }

  deviation "/oc-platform:components/oc-platform:component" +
            "/oc-platform:subcomponents/oc-platform:subcomponent" +
            "/oc-platform:name" {
      deviate replace {
        type string;
      }
      description
        "platform is oper only in Cisco XE device.";
  }

  deviation "/oc-platform:components/oc-platform:component" +
            "/oc-platform:subcomponents/oc-platform:subcomponent" +
            "/oc-platform:state/oc-platform:name" {
      deviate replace {
        type string;
      }
      description
        "platform is oper only in Cisco XE device.";
  }

  deviation "/oc-platform:components/oc-platform:component" +
            "/oc-platform:name" {
      deviate replace {
        type string;
      }
      description
        "platform is oper only in Cisco XE device.";
  }

  deviation "/oc-platform:components/oc-platform:component" +
            "/oc-platform:properties/oc-platform:property" +
            "/oc-platform:config" {
      deviate not-supported;
      description
        "platform is oper only in Cisco XE device.";
  }

  deviation "/oc-platform:components/oc-platform:component" +
            "/oc-platform:subcomponents/oc-platform:subcomponent" +
            "/oc-platform:config" {
      deviate not-supported;
      description
        "platform is oper only in Cisco XE device.";
  }

  deviation "/oc-platform:components/oc-platform:component" +
            "/oc-platform:config" {
      deviate not-supported;
      description
        "platform is oper only in Cisco XE device.";
  }

  deviation "/oc-platform:components/oc-platform:component" +
            "/oc-platform:properties/oc-platform:property" +
            "/oc-platform:name" {
      deviate replace {
        config false;
      }
      description
        "platform is oper only in Cisco XE device.";
  }

  deviation "/oc-platform:components/oc-platform:component" +
            "/oc-platform:subcomponents/oc-platform:subcomponent" +
            "/oc-platform:name" {
      deviate replace {
        config false;
      }
      description
        "platform is oper only in Cisco XE device.";
  }

  deviation "/oc-platform:components/oc-platform:component" +
            "/oc-platform:properties" {
      deviate replace {
        config false;
      }
      description
        "platform is oper only in Cisco XE device.";
  }

  deviation "/oc-platform:components/oc-platform:component" +
            "/oc-platform:properties/oc-platform:property" {
      deviate replace {
        config false;
      }
      description
        "platform is oper only in Cisco XE device.";
  }

  deviation "/oc-platform:components/oc-platform:component" +
            "/oc-platform:subcomponents" {
      deviate replace {
        config false;
      }
      description
        "platform is oper only in Cisco XE device.";
  }

  deviation "/oc-platform:components/oc-platform:component" +
            "/oc-platform:subcomponents/oc-platform:subcomponent" {
      deviate replace {
        config false;
      }
      description
        "platform is oper only in Cisco XE device.";
  }

  deviation "/oc-platform:components/oc-platform:component" +
            "/oc-platform:state/oc-platform:temperature/oc-platform:avg" {
      deviate not-supported;
  }

  deviation "/oc-platform:components/oc-platform:component" +
            "/oc-platform:state/oc-platform:temperature/oc-platform:min" {
      deviate not-supported;
  }

  deviation "/oc-platform:components/oc-platform:component" +
            "/oc-platform:state/oc-platform:temperature/oc-platform:max" {
      deviate not-supported;
  }

  // =========================================================================
  // Transceiver part
  // =========================================================================

  deviation "/oc-platform:components/oc-platform:component" +
            "/oc-transceiver:transceiver/oc-transceiver:config" {
      deviate not-supported;
  }

  deviation "/oc-platform:components/oc-platform:component" +
            "/oc-transceiver:transceiver/oc-transceiver:state" +
            "/oc-transceiver:fault-condition" {
      deviate not-supported;
  }
 
  deviation "/oc-platform:components/oc-platform:component" +
            "/oc-transceiver:transceiver/oc-transceiver:state" +
            "/oc-transceiver:vendor-rev" {
      deviate replace {
        type string;
      }
  }

  deviation "/oc-platform:components/oc-platform:component" +
            "/oc-transceiver:transceiver/oc-transceiver:state" +
            "/oc-transceiver:date-code" {
      deviate replace {
        type string;
      }
  }

  deviation "/oc-platform:components/oc-platform:component" +
            "/oc-transceiver:transceiver/oc-transceiver:state" +
            "/oc-transceiver:output-power/oc-transceiver:avg" {
      deviate not-supported;
  }

  deviation "/oc-platform:components/oc-platform:component" +
            "/oc-transceiver:transceiver/oc-transceiver:state" +
            "/oc-transceiver:output-power/oc-transceiver:min" {
      deviate not-supported;
  }

  deviation "/oc-platform:components/oc-platform:component" +
            "/oc-transceiver:transceiver/oc-transceiver:state" +
            "/oc-transceiver:output-power/oc-transceiver:max" {
      deviate not-supported;
  }

  deviation "/oc-platform:components/oc-platform:component" +
            "/oc-transceiver:transceiver/oc-transceiver:state" +
            "/oc-transceiver:input-power/oc-transceiver:avg" {
      deviate not-supported;
  }

  deviation "/oc-platform:components/oc-platform:component" +
            "/oc-transceiver:transceiver/oc-transceiver:state" +
            "/oc-transceiver:input-power/oc-transceiver:min" {
      deviate not-supported;
  }

  deviation "/oc-platform:components/oc-platform:component" +
            "/oc-transceiver:transceiver/oc-transceiver:state" +
            "/oc-transceiver:input-power/oc-transceiver:max" {
      deviate not-supported;
  }

  deviation "/oc-platform:components/oc-platform:component" +
            "/oc-transceiver:transceiver/oc-transceiver:state" +
            "/oc-transceiver:laser-bias-current/oc-transceiver:avg" {
      deviate not-supported;
  }

  deviation "/oc-platform:components/oc-platform:component" +
            "/oc-transceiver:transceiver/oc-transceiver:state" +
            "/oc-transceiver:laser-bias-current/oc-transceiver:min" {
      deviate not-supported;
  }

  deviation "/oc-platform:components/oc-platform:component" +
            "/oc-transceiver:transceiver/oc-transceiver:state" +
            "/oc-transceiver:laser-bias-current/oc-transceiver:max" {
      deviate not-supported;
  }

  deviation "/oc-platform:components/oc-platform:component" +
            "/oc-transceiver:transceiver/oc-transceiver:physical-channels" +
            "/oc-transceiver:channel/oc-transceiver:index" {
      deviate replace {
        type uint16;
        config false;
      }
  }

  deviation "/oc-platform:components/oc-platform:component" +
            "/oc-transceiver:transceiver/oc-transceiver:physical-channels" +
            "/oc-transceiver:channel/oc-transceiver:config" {
      deviate not-supported;
  }

  deviation "/oc-platform:components/oc-platform:component" +
            "/oc-transceiver:transceiver/oc-transceiver:physical-channels" +
            "/oc-transceiver:channel/oc-transceiver:state" +
            "/oc-transceiver:description" {
      deviate not-supported;
  }

  deviation "/oc-platform:components/oc-platform:component" +
            "/oc-transceiver:transceiver/oc-transceiver:physical-channels" +
            "/oc-transceiver:channel/oc-transceiver:state" +
            "/oc-transceiver:target-output-power" {
      deviate not-supported;
  }

  deviation "/oc-platform:components/oc-platform:component" +
            "/oc-transceiver:transceiver/oc-transceiver:physical-channels" +
            "/oc-transceiver:channel/oc-transceiver:state" +
            "/oc-transceiver:tx-laser" {
      deviate not-supported;
  }

  deviation "/oc-platform:components/oc-platform:component" +
            "/oc-transceiver:transceiver/oc-transceiver:physical-channels" +
            "/oc-transceiver:channel/oc-transceiver:state" +
            "/oc-transceiver:output-frequency" {
      deviate not-supported;
  }

  deviation "/oc-platform:components/oc-platform:component" +
            "/oc-transceiver:transceiver/oc-transceiver:physical-channels" +
            "/oc-transceiver:channel/oc-transceiver:state" +
            "/oc-transceiver:input-power/oc-transceiver:avg" {
      deviate not-supported;
  }

  deviation "/oc-platform:components/oc-platform:component" +
            "/oc-transceiver:transceiver/oc-transceiver:physical-channels" +
            "/oc-transceiver:channel/oc-transceiver:state" +
            "/oc-transceiver:input-power/oc-transceiver:min" {
      deviate not-supported;
  }

  deviation "/oc-platform:components/oc-platform:component" +
            "/oc-transceiver:transceiver/oc-transceiver:physical-channels" +
            "/oc-transceiver:channel/oc-transceiver:state" +
            "/oc-transceiver:input-power/oc-transceiver:max" {
      deviate not-supported;
  }

  deviation "/oc-platform:components/oc-platform:component" +
            "/oc-transceiver:transceiver/oc-transceiver:physical-channels" +
            "/oc-transceiver:channel/oc-transceiver:state" +
            "/oc-transceiver:output-power/oc-transceiver:avg" {
      deviate not-supported;
  }

  deviation "/oc-platform:components/oc-platform:component" +
            "/oc-transceiver:transceiver/oc-transceiver:physical-channels" +
            "/oc-transceiver:channel/oc-transceiver:state" +
            "/oc-transceiver:output-power/oc-transceiver:min" {
      deviate not-supported;
  }

  deviation "/oc-platform:components/oc-platform:component" +
            "/oc-transceiver:transceiver/oc-transceiver:physical-channels" +
            "/oc-transceiver:channel/oc-transceiver:state" +
            "/oc-transceiver:output-power/oc-transceiver:max" {
      deviate not-supported;
  }

  deviation "/oc-platform:components/oc-platform:component" +
            "/oc-transceiver:transceiver/oc-transceiver:physical-channels" +
            "/oc-transceiver:channel/oc-transceiver:state" +
            "/oc-transceiver:laser-bias-current/oc-transceiver:avg" {
      deviate not-supported;
  }

  deviation "/oc-platform:components/oc-platform:component" +
            "/oc-transceiver:transceiver/oc-transceiver:physical-channels" +
            "/oc-transceiver:channel/oc-transceiver:state" +
            "/oc-transceiver:laser-bias-current/oc-transceiver:min" {
      deviate not-supported;
  }

  deviation "/oc-platform:components/oc-platform:component" +
            "/oc-transceiver:transceiver/oc-transceiver:physical-channels" +
            "/oc-transceiver:channel/oc-transceiver:state" +
            "/oc-transceiver:laser-bias-current/oc-transceiver:max" {
      deviate not-supported;
  }

  // =========================================================================
  // Breakout port part
  // =========================================================================

  deviation "/oc-platform:components/oc-platform:component" +
            "/oc-port:breakout-mode/oc-port:config" {
      deviate not-supported;
  }
}
