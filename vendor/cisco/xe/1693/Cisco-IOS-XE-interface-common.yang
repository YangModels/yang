module Cisco-IOS-XE-interface-common {
  namespace "http://cisco.com/ns/yang/Cisco-IOS-XE-interface-common";
  prefix ios-ifc;


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Interfaces Common Yang model.
     Copyright (c) 2016-2018 by Cisco Systems, Inc.
     All rights reserved.";

  // =========================================================================
  // REVISION
  // =========================================================================
  revision 2018-02-08 {
     description
       "Add a type of Interface: Ethernet";
  }
  revision 2017-11-27 {
     description
       "Added Change 25GE name";
  }

  revision 2017-11-13 {
    description
      "Added leafs for FortyGigabitEthernet and HundredGigE interfaces";
  }
  revision 2017-09-15 {
    description
      "This revison has changes for the new 2gig interface addition";
  }
  revision 2017-08-16 {
    description
      "This revision has changes for new 5gig and 25gig interfaces addition";
  }

  revision 2017-03-04 {
    description
      "Changed LISP key type to string to support OC mapping";
  }

  revision 2017-02-07 {
    description
      "Initial revision";
  }

  grouping interface-grouping {
    choice interface-choice {
      leaf AppNav-Compress {
        description
          "Service-Context Virtual Interface Compress";
        type uint16;
      }

      leaf AppNav-UnCompress {
        description
          "Service-Context Virtual Interface UnCompress";
        type uint16;
      }

      leaf ATM {
        description
          "ATM interface";
        type string; 
      }

      container ATM-subinterface {
        leaf ATM {
          type string; 
        }
      }

      leaf ATM-ACR {
        description
          "ATM-ACR interface";
        type string {
          pattern "[0-9]";
        }
      }

      container ATM-ACRsubinterface {
        leaf ATM-ACR {
          type string {
            pattern "[0-9]\\.([0-9]/){3}[0-9]";
          }
        }
      }

      leaf BDI {
        description
          "Bridge-Domain interface";
        type string;
      }

      leaf CEM {
        description
          "CEM interface";
        type string {
          pattern "([0-9]/){2}[0-9]";
        }
      }

      leaf CEM-ACR {
        description
          "CEM-ACR interface";
        type uint8 {
          range "0..255";
        }
      }

      leaf Embedded-Service-Engine {
        description
          "cisco embedded service engine module";
        type string;
      }

      leaf Ethernet {
        description
          "IEEE 802.3";
        type string;
      }

      leaf FastEthernet {
        description
          "FastEthernet IEEE 802.3";
        type string;
      }

      leaf GigabitEthernet {
        description
          "GigabitEthernet IEEE 802.3z";
        type string;
      }

      leaf FiveGigabitEthernet {
        description
          "Five GigabitEthernet ";
        type string;
      }

      leaf TwentyFiveGigE {
        description
          "Twenty Five GigabitEthernet ";
        type string;
      }

      leaf TwoGigabitEthernet {
        description
          "Two GigabitEthernet ";
        type string;
      }

      leaf FortyGigabitEthernet {
        description
          "Forty GigabitEthernet ";
        type string;
      }

      leaf HundredGigE {
        description
          "Hundred GigabitEthernet";
        type string;
      }

      leaf LISP {
        description
          "Locator/ID Separation Protocol Virtual Interface";
          type string;
//CHANGE        type uint16 {
//          range "0..65520";
//        }
      }

      // Lspsubvif   LSP virtual Sub-Interface
      container LISP-subinterface {
        description
          "Locator/ID Separation Protocol Virtual Interface";
        leaf LISP {
          type string {
              pattern "[0-9]*(. ?[1-9][0-9]*)*";
          }
        }
      }

      leaf Loopback {
        description
          "Loopback interface";
        type uint32;
      }

      leaf Multilink {
        description
          "Multilink-group interface";
        type uint16;
      }

      leaf nve {
        description
          "Network virtualization endpoint interface";
        type uint16;
      }

      leaf overlay {
        description
          "Overlay interface";
        type uint16;
      }

      leaf Port-channel {
        description
          "Ethernet Channel of interfaces";
        type uint32;
      }

      container Port-channel-subinterface {
        leaf Port-channel {
          type string;
        }
      }

      leaf pseudowire {
        description
          "Pseudowire Interface";
        type uint32;
      }

      leaf SM {
        description
          "SM Interface";
        type string;
      }

      leaf Cellular {
        description
          "Cellular Interface";
        type string;
      }

      leaf Serial {
        description
          "Serial interface";
        type string;
      }

      leaf TenGigabitEthernet {
        description
          "Ten Gigabit Ethernet";
        type string;
      }

      leaf Tunnel {
        description
          "Tunnel interface";
        type uint32;
      }

      leaf Virtual-Template {
        description
          "Virtual Template interface";
        type uint16;
      }

      leaf Vlan {
        description
          "Iosxr Vlans";
        type uint16;
      }

      leaf VirtualPortGroup {
        description
          "Virtual Port Group";
        type uint16;
      }

      leaf vasileft {
        description
          "vasileft";
        type uint16;
      }

      leaf vasiright {
        description
          "vasiright";
        type uint16;
      }
    }
  }// interface-grouping - all interface lists collected

  grouping passive-interface-grouping {
    container passive-interface {
      description
        "Suppress routing updates on an interface";
      choice passive-interface-choice {
        leaf default {
          description
            "Suppress routing updates on all interfaces";
          type empty;
        }
        leaf interface {
          type string;
        }
      }
    }
    container disable {
      when "../passive-interface/default";
      list passive-interface {
        key "interface";
        leaf interface {
          type string;
        }
      }
    }
  }
}
