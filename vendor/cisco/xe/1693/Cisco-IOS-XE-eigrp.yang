module Cisco-IOS-XE-eigrp {
  namespace "http://cisco.com/ns/yang/Cisco-IOS-XE-eigrp";
  prefix ios-eigrp;

  import ietf-inet-types {
    prefix inet;
  }


  import Cisco-IOS-XE-types {
    prefix ios-types;
  }

  import Cisco-IOS-XE-interface-common {
    prefix ios-ifc;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native EIGRP Yang model.
     Copyright (c) 2016-2017 by Cisco Systems, Inc.
     All rights reserved.";

  // =========================================================================
  // REVISION
  // =========================================================================
  revision 2018-06-28 {
    description
      "added must constraints for deleting vrf";
  }
  revision 2017-09-21 {
    description 
      "fix the regression issue that a cli is splitted";
  }

  revision 2017-08-22 {
    description 
      "Allow to set autonomous-system under address-family ipv4 vrf";
  }

  revision 2017-08-01 {
    description 
      "Fix passive interface data model";
  }

  revision 2017-06-27 {
    description 
      "NED extension for IWAN 2.x - router eigrp";
  }

  revision 2017-02-07 {
    description
      "Initial revision";
  }

  grouping ipv6-router-distribute-list-grouping {
    container distribute-list {
      description
        "Filter networks in routing updates";
      list prefix-list {
        description
          "Filter connections based on an IPv6 prefix-list";
        key "name";
        leaf name {
          type string;
        }
        leaf in {
          description
            "Filter incoming routing updates";
          type empty;
        }
        leaf out {
          description
            "Filter outgoing routing updates";
          type empty;
        }
      }
    }
  }

  // Router eigrp topology base grouping
  grouping eigrp-topology-base-grouping {
    container topology {
      description
        "Topology configuration mode";
      container base {
        description
          "Base Topology";
        presence true;
        container distance {
          description
            "Define an administrative distance";
          container eigrp {
            description
              "EIGRP-IPV6 distance";
            list distance-list {
              key "internal-route";
              leaf internal-route {
                description
                  "Distance for internal routes";
                type uint8 {
                  range "1..255";
                }
              }
              leaf external-route {
                description
                  "Distance for external routes";
                type uint8 {
                  range "1..255";
                }
              }
            }
          }
        }
        container distribute-list {
          description
            "Filter entries in eigrp updates";
          list prefix-list {
            description
              "Filter prefixes in address updates";
            key "prefix-list";
            leaf prefix-list {
            description
              "Name of an IP prefix-list";
              type string;
            }
            leaf gateway {
              description
                "Filtering incoming address updates based on gateway";
              type empty;
            }
            leaf in {
              description
                "Filter incoming service updates";
              type empty;
            }
            leaf out {
              description
                "Filter outgoing service updates";
              type empty;
            }
          }
          list route-map {
            description
              "Filter prefixes based on the route-map";
            key "name";
            leaf name {
              type string;
            }
            leaf in {
              description
                "Filter incoming service updates";
              type string;
            }
            leaf out {
              description
                "Filter outgoing service updates";
              type string;
            }
          }
        }
        container redistribute {
          description
            "Redistribute IPv6 prefixes from another routing protocol";
          container eigrp {
            description
              "Enhanced Interior Gateway Routing Protocol (EIGRP)";
            list as-list {
              key "autonomous-system";
              leaf autonomous-system {
                description
                  "Autonomous system number";
                type uint16 {
                  range "1..65535";
                }
              }
            }
          }
          container ospf {
            description
              "Open Shortest Path First (OSPFv3)";  
            list pid-list {
              key "process-id";
              leaf process-id {
                description
                  "Process ID";
                type uint16 {
                  range "1..65535";
                }
              }
            }
          }
          leaf connected {
            description
              "Connected Routes";
            type empty;
          }
          container static {
            description
              "Static Routes";
            presence true;
          }
        }
        list summary-metric {
          description 
            "Specify summary to apply metric/filtering";
          key "ipv4-addr-slash-prefix-len";
          leaf ipv4-addr-slash-prefix-len {
            description 
              "Summary <network>/<length>, e.g., 192.168.0.0/16";
            type inet:ipv4-prefix;
          }
          container metric {
            leaf bandwidth-metric {
              description 
                "Bandwidth metric in Kbits per second";
              type uint32 {
                range "1..4294967295";
              }
            }
            leaf delay-metric {
              description
                "delay metric in 10 microsecond units";
              type uint32 {
                range "1..4294967295";
              }
            }
            leaf reliability-metric {
              description 
                "reliability metric where 255 is 100% reliable";
              type uint8 {
                range "0..255";
              }
            }
            leaf effective-bandwidth-metric {
              description 
                "Effective bandwidth metric (Loading) where 255 is 100% loaded";
              type uint8 {
                range "0..255";                                           
              }
            }
            leaf mtu {
              description 
                "MTU of the path";
              type uint16 {
                range "1..65535";                                         
              }
            }
          }
          leaf distance {
            description 
              "Set administrative distance for summary route";
            type uint8 {
              range "1..255";
            }
          }
        }
      }
    }
  }

  // router eigrp address-family
  grouping eigrp-address-family-grouping {
    list af-interface {
      description
        "Enter Address Family interface configuration";
      key "name";
      leaf name {
        type string;
      }
      leaf bandwidth-percent {
        description
          "Set percentage of bandwidth percentage limit";
        type uint32 {
          range "1..999999";
        }
      }
      leaf hello-interval {
        description
          "Configures hello interval";
        type uint16;
      }
      leaf hold-time {
        description
          "Configures hold time";
        type uint16;
      }
      leaf passive-interface {
        description
          "Suppress address updates on an interface";
        type boolean;
      }
      leaf split-horizon {
        description
          "Perform split horizon";
        type boolean;
      }
      container stub-site {
        description
          "Stub-Site";
          leaf wan-interface {
            description 
              "Wan Interface";
            type empty;  
          }
      }
      container authentication {
        description
          "authentication subcommands";
        container mode {
          description
            "authentication mode";
          leaf md5 {
            description
              "Keyed message digest";
            type empty;
          }
          container hmac-sha-256 {
            description
              "HMAC-SHA-256 Authentication";
            leaf auth-type {
              type uint8;
            }
            leaf auth-key {
              type string;
            }
          }
        }
        leaf key-chain {
          description
            "key-chain";
          type string;
        }
      }
      container summary-address {
        leaf address {
          type inet:ipv4-address;
        }
        leaf mask {
          type inet:ipv4-address;
        }
      }
    }
    container set-as-in-submode {
      leaf autonomous-system {
        description
        "Specify Address-Family Autonomous System Number?";
          type uint16;
      }
    }
    leaf auto-summary {
      description
        "Enable automatic network number summarization";
        type empty;
    }
    container bfd {
      description
        "BFD configuration commands";
      leaf all-interfaces {
        description
          "Enable BFD on all interfaces";
          type empty;
      }
      container interface {
        description
          "Enable BFD on specific interface";
        uses ios-ifc:interface-grouping;
      }
    }
    container default-information {
      description
        "Control distribution of default information";
      container in {
        description
          "Accept input default routing information";
        presence "true";
        leaf sa-num {
          description
            "A standard expanded IP access list number";
          type uint16 {
            range "1300..1999";
          }
        }
        leaf sa-name {
          description
            "Standard Access-list name";
          type string;
        }
      }
      container out {
        description
          "Accept output default routing information";
        presence "true";
        leaf sa-out-num {
          description
            "A standard expanded IP access list number";
          type uint16 {
            range "1300..1999";
          }
        }
        leaf sa-out-name {
          description
            "Standard Access-list name";
          type string;
        }
      }
    }
    container default-metric {
      description
        "Set metric of redistributed routes";
      list dm-rdr {
        key "dm-rdr";
        leaf dm-rdr {
          description
            "Bandwidth in Kbits per second";
          type uint32 {
            range "1..4294967295";
          }
        }
        list dm-rdr0 {
          key "dm-rdr0";
          leaf dm-rdr0 {
            description
              "delay metric in 10 microsecond units";
            type uint32 {
              range "0..4294967295";
            }
          }
          leaf dm-rdr-pct {
            description
              "Reliability metric where 255 is 100% reliable";
            type uint8 {
              range "0..255";
            }
          }
        }
      }
    }
    container distance {
      description
        "Define an administrative distance";
      list rad-dis {
        key "rad-dis";
        leaf rad-dis {
          description
            "Set route administrative distance";
          type uint8 {
            range "1..255";
          }
        }
        list ipv4 {
          key "ipv4";
          leaf ipv4 {
            description
              "IP Source address";
            type inet:ipv4-address;
          }
          leaf ipv40 {
            description
              "Wildcard bits";
            type inet:ipv4-address;
          }
        }
      }
      container eigrp {
        description
          "Set distance for internal and external routes";
        list di-rt {
          key "di-rt";
          leaf di-rt {
            description
              "Distance for internal routes";
            type uint8 {
              range "1..255";
            }
          }
          leaf di-rt0 {
            description
              "Distance for external routes";
            type uint8 {
              range "1..255";
            }
          }
        }
      }
    }
    container distribute-list {
      description
        "Filter entries in eigrp updates";
      list eig-filt {
        key "eig-filt";
        leaf eig-filt {
          description
            "IP expanded access list number";
          type ios-types:exp-acl-type;
        }
        container in {
          description
            "Filter incoming service updates";
          presence "true";
          leaf-list interface_name {
            description
              "Interface name";
            type string;
          }
        }
        container out {
          description
            "Filter outgoing service updates";
          presence "true";
          leaf-list interface_name {
            description
              "Interface name";
            type string;
          }
        }
      }
      container gateway {
        description
          "Filtering incoming address updates based on gateway";
        list gw-list {
          key "gw-list";
          leaf gw-list {
            description
              "Name of an IP prefix-list";
            type string;
          }
          leaf in {
            description
              "Filter incoming service updates";
            type empty;
          }
          leaf out {
            description
              "Filter outgoing service updates";
            type empty;
          }
        }
      }
      container prefix {
        description
          "Filter prefixes in address updates";
        list pl-name {
          key "pl-name";
          leaf pl-name {
            description
              "Name of an IP prefix-list";
            type string;
          }
          leaf gateway {
            description
              "Filtering incoming address updates based on gateway";
            type empty;
          }
          leaf in {
            description
              "Filter incoming service updates";
            type empty;
          }
          leaf out {
            description
              "Filter outgoing service updates";
            type empty;
          }
        }
      }
      container route-map {
        description
          "Filter prefixes based on the route-map";
        list rmap-name {
          key "rmap-name";
          leaf rmap-name {
            description
              "route-map name";
            type string;
          }
          leaf in {
            description
              "Filter incoming service updates";
            type empty;
          }
          leaf out {
            description
              "Filter outgoing service updates";
            type empty;
          }
        }
      }
    }
    container eigrp {
      description
        "EIGRP Address Family specific commands";
      leaf router-id {
        description
          "router id for this EIGRP process";
        type inet:ipv4-address;
      }
      container stub {
        description
          "Set address-family in stubbed mode";
        presence "true";
        leaf connected {
          description
            "Do advertise connected routes";
          type empty;
        }
        leaf summary {
          description
            "Do advertise summary routes";
          type empty;
        }
        leaf redistributed {
          description
            "Do advertise redistributed routes";
          type empty;
        }
        leaf leak-map {
          description
            "Allow dynamic prefixes based on the leak-map";
          type string;
        }
        leaf receive-only {
          description
            "Set receive only neighbor";
          type empty;
        }
        leaf static {
          description
            "Do advertise static routes";
          type empty;
        }
      }
      leaf stub-site {
        description
          "ASN:nn, Dotted-Decimal:nn or 4BASN:nn  Stub-Site ID in aa:nn format";
        type string;   
      }
    }
    leaf maximum-paths {
      description
        "Number of paths";
      type uint8 {
        range "1..32";
      }
    }
    container metric {
      description
        "Modify metrics and parameters for advertisement";
      leaf maximum-hops {
        description
          "Hop count";
        type uint8 {
          range "1..255";
        }
      }
      leaf weights {
        description
          "Type (Only TOS 0 supported)";
        type uint8 {
          range "0..8";
        }
     }
    }
    container neighbor {
      description
        "Specify a neighbor router";
      list ipv4 {
        key "ipv4";
        leaf ipv4 {
          description
            "Neighbor address";
          type inet:ipv4-address;
        }
        container interface {
          description
            "Specify interface for global address";
          uses ios-ifc:interface-grouping;
        }
      }
    }
    list network {
      description
        "Enable routing on an IP network";
      key number;
      leaf number {
        description
          "Network number";
        type inet:ipv4-address;
      }
      leaf wild-card {
        description
          "EIGRP wild card bits";
        type inet:ipv4-address;
      }
    }
    leaf nsf {
      description
        "Non-stop forwarding";
      type empty;
    }
    container offset-list {
      description
        "Add or subtract offset from EIGRP metrics";
      list nsr-list {
        key "nsr-list";
        leaf nsr-list {
          description
            "Access list of networks to apply offset (extended range)";
          type uint16 {
            range "1300..1999";
          }
        }
        leaf in {
          description
            "Perform offset on incoming updates";
          type empty;
        }
        leaf out {
          description
            "Perform offset on outgoing updates";
          type empty;
        }
      }
      list ol-acl {
        key "ol-acl";
        leaf ol-acl {
          description
            "Access-list name";
          type string;
        }
        leaf in {
          description
            "Perform offset on incoming updates";
          type empty;
        }
        leaf out {
          description
            "Perform offset on outgoing updates";
          type empty;
        }
      }
    }
    container redistribute {
      description
        "Redistribute IPv4 routes from another routing protocol";
      list bgp {
        description
          "Border Gateway Protocol (BGP)";
        key "rdr-as";
        leaf rdr-as {
          description
            "Autonomous system number";
          type ios-types:bgp-as-number-type;
        }
        container metric {
          description
            "Metric for redistributed routes";
          leaf bandwith {
            description
              "Bandwidth metric in Kbits per second";
            type uint32 {
              range "1..4294967295";
            }
          }
          leaf delay {
            description
              "EIGRP delay metric, in 10 microsecond units";
            type uint32 {
              range "0..4294967295";
            }
          }
          leaf reliability {
            description
              "EIGRP reliability metric where 255 is 100% reliable";
            type uint8 {
              range "0..255";
            }
          }
          leaf Effective {
            description
              "EIGRP Effective bandwidth metric (Loading) where 255 is 100% loaded";
            type uint8 {
              range "1..255";
            }
          }
          leaf mtu {
            description
              "EIGRP MTU of the path";
            type uint16 {
              range "1..65535";
            }
          }
        }
        leaf route-map {
          description
            "Route map reference";
          type string;
        }
        leaf rd-LESSER_1_PERIOD_0-XX_PERIOD_YY_GREATER_ {
          description
            "Autonomous system number";
          type empty;
        }
      }
      container connected {
        description
          "Connected";
        presence "true";
        leaf metric {
          description
            "Metric for redistributed routes";
          type empty;
        }
        leaf route-map {
          description
            "Route map reference";
          type empty;
        }
      }
      leaf eigrp {
        description
          "Autonomous system number";
        type uint16 {
          range "1..65535";
        }
      }
      container isis {
        description
          "ISO IS-IS";
        presence "true";
        leaf is-tag {
          description
            "ISO routing area tag";
          type string;
        }
        leaf level-1 {
          description
            "IS-IS level-1 routes only";
          type empty;
        }
        leaf level-1-2 {
          description
            "IS-IS level-1 and level-2 routes";
          type empty;
        }
        leaf level-2 {
          description
            "IS-IS level-2 routes only";
          type empty;
        }
        leaf metric {
          description
            "Metric for redistributed routes";
          type empty;
        }
        leaf route-map {
          description
            "Route map reference";
          type empty;
        }
      }
      container lisp {
        description
          "Locator ID Separation Protocol (LISP)";
        presence "true";
        leaf metric {
          description
            "Metric for redistributed routes";
          type empty;
        }
        leaf route-map {
          description
            "Route map reference";
          type empty;
        }
      }
      container mobile {
        description
          "Mobile routes";
        presence "true";
        leaf metric {
          description
            "Metric for redistributed routes";
          type empty;
        }
        leaf route-map {
          description
            "Route map reference";
          type empty;
        }
      }
      container odr {
        description
          "On Demand stub Routes";
        presence "true";
        leaf metric {
          description
            "Metric for redistributed routes";
          type empty;
        }
        leaf route-map {
          description
            "Route map reference";
          type empty;
        }
      }
      leaf ospf {
        description
          "Process ID";
        type uint16 {
          range "1..65535";
        }
      }
      container rip {
        description
          "Routing Information Protocol (RIP)";
        presence "true";
        leaf metric {
          description
            "Metric for redistributed routes";
          type empty;
        }
        leaf route-map {
          description
            "Route map reference";
          type empty;
        }
      }
      container static {
        description
          "Static routes";
        presence "true";
        leaf metric {
          description
            "Metric for redistributed routes";
          type empty;
        }
        leaf route-map {
          description
            "Route map reference";
          type empty;
        }
      }
      container vrf {
        description
          "Specify a source virtual routing/forwarding instance";
        leaf name {
          description
            "Virtual Routing/Forwarding instance name";
          type string;
        }
        leaf global {
          description
            "global VRF";
          type empty;
        }
      }
    }
    leaf shutdown {
      description
        "Shutdown this instance of EIGRP";
      type empty;
    }
    container summary-metric {
      description
        "Specify summary to apply metric/filtering";
      list ipv4 {
        key "ipv4";
        leaf ipv4 {
          description
            "Summary to configure static metric";
          type inet:ipv4-address;
        }
        leaf mask {
          description
            "Network mask";
          type inet:ipv4-address;
        }
      }
      leaf A_PERIOD_B_PERIOD_C_PERIOD_D_SLASH_nn {
        description
          "Summary <network>/<length>, e.g., 192.168.0.0/16";
        type empty;
      }
    }
    container timers {
      description
        "Adjust routing timers";
      container active-time {
        description
          "time limit for active state";
        leaf atimer {
          description
            "active state time limit in minutes";
          type uint16 {
            range "1..65535";
          }
        }
        leaf disabled {
          description
            "disable time limit for active state";
          type empty;
        }
      }
      container graceful-restart {
        description
          "EIGRP Graceful Restart timer";
        leaf purge-time {
          description
            "EIGRP stale route purge time";
          type empty;
        }
      }
      container nsf {
        description
          "EIGRP NSF timer";
        leaf converge {
          description
            "EIGRP time limit for convergence after switchover";
          type empty;
        }
        leaf signal {
          description
            "EIGRP time limit for signaling NSF restart";
          type empty;
        }
      }
    }
    container traffic-share {
      description
        "How to compute traffic share over alternate paths";
      leaf balanced {
        description
          "Share inversely proportional to metric";
        type empty;
      }
      container min {
        description
          "All traffic shared among min metric paths";
        leaf across-interfaces {
          description
            "Use different interfaces for equal-cost paths";
          type empty;
        }
      }
    }
    leaf variance {
      description
        "Metric variance multiplier";
      type uint8 {
        range "1..128";
      }
    }
  }

  grouping config-router-eigrp-grouping {
    list eigrp { //69666
      description
        "Enhanced Interior Gateway Routing Protocol (EIGRP)";
      key "id";
      leaf id {
        description
          "Autonomous System ID";
        type union {
          type uint16 {
            range "1..65535";
          }
          type string;
        }
      }

      container passive-interface {
        description "Suppress routing updates on an interface";
        leaf interface {
          description "interface name";
          type string;
        }
        leaf Tunnel {
          description "Tunnel interface number";
          type uint32 {
            range "0..2147483647";
          }
        }
        leaf Vlan {
          description "Vlan interface number";
          type uint16 {
             range "1..4094";
          }
        }
        leaf default {
          description "Suppress routing updates on all interfaces";
          type empty;
        }
      }

      list address-family {
        description
          "Enter Address Family command mode";
        key "type";
        leaf type {
          type enumeration {
            enum "ipv4";
            enum "ipv6";
          }
        }

        list af-ip-list {
          description
            "Address family IPv4/IPv6";
          key "unicast-multicast";
          leaf unicast-multicast {
            type enumeration {
              enum "unicast";
              enum "multicast";
            }
          }
          leaf autonomous-system {
            description
              "Specify Address-Family Autonomous System Number";
            type uint16 {
              range "1..65535";
            }
          }
          uses eigrp-address-family-grouping;
          uses eigrp-topology-base-grouping;
        }

        list af-ip-vrf-list {
          description
            "Address family IPv4/IPv6 VRF";
          key "vrf";
          leaf vrf {
	    must "/ios:native/ios:vrf/ios:definition[ios:name=current()] or /ios:native/ios:ip/ios:vrf[ios:name=current()]" {
	      error-message "VRF must be created 1st, deleted last";
            }
            type string;
          }
          leaf unicast-multicast {
            type enumeration {
              enum "unicast";
              enum "multicast";
            }
          }
          leaf autonomous-system {
            description
            "Specify Address-Family Autonomous System Number?";
            type uint16;
          }
          uses eigrp-address-family-grouping;
          uses eigrp-topology-base-grouping;
        }
      }
      uses eigrp-address-family-grouping;
    }
  }

  grouping config-router-ipv6-eigrp-grouping {
    container default-metric {
      description
        "Set metric of redistributed routes";
      leaf dm-rdr {
        description
          "Bandwidth in Kbits per second";
        type uint32 {
          range "1..4294967295";
        }
      }
      leaf dm-rdr0 {
        description
          "delay metric in 10 microsecond units";
        type uint32 {
          range "0..4294967295";
        }
      }
      leaf dm-rdr-pct {
        description
          "Reliability metric where 255 is 100% reliable";
        type uint8 {
          range "0..255";
        }
      }
      leaf effective-bandwith-metric {
        description
          "Effective bandwidth metric (Loading) where 255 is 100% loaded";
        type uint8;
      }
      leaf mtu {
        description
          "Maximum Transmission Unit metric of the path ";
        type uint16;
      }
    }
    container distance {
      description
        "Define an administrative distance";
      container eigrp {
        description
          "EIGRP-IPV6 distance";
        leaf internal-route {
          description
            "Distance for internal routes";
          type uint8;
        }
        leaf external-route {
          description
            "Distance for external routes";
          type uint8;
        }
      }
    }
    uses ipv6-router-distribute-list-grouping;
    container eigrp {
      description
        "EIGRP specific commands";
      leaf router-id {
        description
          "router id for this EIGRP process";
        type inet:ipv4-address;
      }
    }
    list passive-interface {
      description
        "Suppress routing updates on an interface";
      key "name";
      leaf name {
        type union {
          type string;
          type enumeration {
            enum "default";
          }
        }
      }
    }
  }

  grouping config-route-tag-grouping {
      container list {
        list rt-name {
          key "rt-name";
          leaf rt-name {
            type string;
          }
          container deny {
            list ipv4 {
              key "ipv4";
              leaf ipv4 {
                type inet:ipv4-address;
              }
              leaf mask {
                type inet:ipv4-address;
              }
            }
          }
          container permit {
            list ipv4 {
              key "ipv4";
              leaf ipv4 {
                type inet:ipv4-address;
              }
              leaf mask {
                type inet:ipv4-address;
              }
            }
          }
          container seq {
            list seq-num {
              key "seq-num";
              leaf seq-num {
                type uint32 {
                  range "1..4294967294";
                }
              }
              container deny {
                leaf ipv4 {
                  type inet:ipv4-address;
                }
                leaf mask {
                  type inet:ipv4-address;
                }
              }
              container permit {
                leaf ipv4 {
                  type inet:ipv4-address;
                }
                leaf mask {
                  type inet:ipv4-address;
                }
              }
            }
          }
        }
      }
      container notation {
        leaf dotted-decimal {
          type empty;
        }
      }
  }

  /////////////////////////////////////////////////////////
  // native / router / eigrp
  /////////////////////////////////////////////////////////
  augment "/ios:native/ios:router" {
    uses config-router-eigrp-grouping;
  }

  /////////////////////////////////////////////////////////
  // native / ipv6 / router / eigrp
  /////////////////////////////////////////////////////////
  augment "/ios:native/ios:ipv6/ios:router/ios:eigrp" {
    uses config-router-ipv6-eigrp-grouping;
  }

  /////////////////////////////////////////////////////////
  // native / route-tag
  /////////////////////////////////////////////////////////
  augment "/ios:native/ios:route-tag" {
    uses config-route-tag-grouping;
  }
}
