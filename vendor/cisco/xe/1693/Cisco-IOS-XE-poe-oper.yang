module Cisco-IOS-XE-poe-oper {
  yang-version 1;
  namespace "http://cisco.com/ns/yang/Cisco-IOS-XE-poe-oper";
  prefix poe-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring power over ethernet feature in a Network Element.
     Copyright (c) 2016-2018 by Cisco Systems, Inc.
     All rights reserved.";

  revision 2018-02-04 {
    description
      "Initial revision";
    reference "1.0.0";
  }

  typedef ilpower-pd-class {
    type enumeration {
      enum "poe-null" {
        value 0;
        description
          "List of POE interfaces, keyed by interface name";
      }
      enum "poe-unknown" {
        value 1;
        description
          "Power class unknown";
      }
      enum "poe-cisco" {
        value 2;
        description
          "Power class cisco";
      }
      enum "poe-ieee0" {
        value 3;
        description
          "IEEE power class 0";
      }
      enum "poe-ieee1" {
        value 4;
        description
          "IEEE power class 1";
      }
      enum "poe-ieee2" {
        value 5;
        description
          "IEEE power class 2";
      }
      enum "poe-ieee3" {
        value 6;
        description
          "IEEE power class 3";
      }
      enum "poe-ieee4" {
        value 7;
        description
          "IEEE power class 4";
      }
      enum "poe-ieee5" {
        value 8;
        description
          "IEEE power class 5";
      }
      enum "poe-ieee-unknown-class" {
        value 9;
        description
          "IEEE power class unknown";
      }
    }
    description
      "Name of the power class";
  }

  grouping poe-ethernet {
    description
      "POE ethernet grouping";
    leaf intf-name {
      type string;
      description
        "Name of the POE interface";
    }
    leaf poe-intf-enabled {
      type boolean;
      description
        "POE interface admin state";
    }
    leaf power-used {
      type decimal64 {
        fraction-digits 2;
      }
      description
        "Power used by PD device";
    }
    leaf pd-class {
      type poe-ios-xe-oper:ilpower-pd-class;
      description
        "Class of the PD device";
    }
  }

  container poe-oper-data {
    config false;
    description
      "Informaton about POEs";
    list poe-port {
      key "intf-name";
      description
        "List of POE interfaces, keyed by interface name";
      uses poe-ios-xe-oper:poe-ethernet;
    }
  }
}
