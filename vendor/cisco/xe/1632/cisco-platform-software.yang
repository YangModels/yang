module cisco-platform-software {

     yang-version 1;

     namespace "urn:cisco:params:xml:ns:yang:cisco-platform-software";
     prefix platform-software;


     organization
    "Cisco Systems, Inc.";

   contact
    " Cisco Systems, Inc.
    Customer Service

    Postal: 170 W Tasman Drive
    San Jose, CA 95134

    Tel: +1 1800 553-NETS

    E-mail: cs-yang@cisco.com";
    
    description
       "This module contains a collection of YANG definitions for
        monitoring the platform software in a Network Element.";
    
    reference "TODO";
    
    revision 2015-07-09 {
    description "added platform-software-interface-RP-active-brief-Forwarding"; 
  }

    revision 2015-05-20 {
    description "Proposed";  
  }

container cisco-platform-software {
    config false;
  
	container platform-software-status-control-process {
		description
			"Contents of the show platform software status control process cli.";
	
                list control-process {
                        key "name";
                        description
                                "Control process";

                leaf name {
                        type string;
                        description
                                "Name of the control process";
                }
 
		leaf status {
			type string;
        	description
        		"Status of the control processer";
		}
		
		leaf updated {
			type uint64;
			description
				"Number of seconds since the data has been updated.";
		}
		
		container load-average-stats {
			description
				"Statistics on the load average.";
				
			leaf load-average-status {
				type string;
        	}
        	
        	list minutes {
        		key "number";
        		description
        			"Load average statistics based on a time frame";
        		
        		leaf number {
        			type uint64;
        			description
        				"The number of minutes the average was calculated on.";
        		}
        		
        		leaf average {
        			type string;
        			description
        				"Format: Decimal with 2 fraction digits";
        		}

                	container status {

                	leaf condition {
                        	type string;
                        	description
                                	"Need description";
                	}

                	leaf threshold-status {
                        	type string;
                        	description
                                	"Need description";
                	}

                	leaf threshold-value {
                        	type string;
                        	description
                                	"Format: Decimal with 2 fraction digits";
                	}

                	}        		
        		
        	}
        	
		}
		
		container memory-stats {
			description
				"The statistics on the memory";
				
    		leaf memory-status {
    			type string;
    			description
    				"The status of the memory";
    		}
    		
    		leaf total {
    			type uint64;
    			description
    				"The total number of memory in kb";
    		}
    		
    		leaf used-number {
    			type uint64;
    			description
    				"The number of memory being used in kb";
    		}
    		
    		leaf used-percent {
    			type uint64;
    			description
    				"The percentage of memory being used";
    		}
    		
    		leaf free-number {
    			type uint64;
    			description
    				"The number of free memory in kb";
    		}
    		
    		leaf free-percent {
    			type uint64;
    			description
    				"The percentage of free memory";
    		}
    	
                leaf available-number {
                        type uint64;
                        description
                                "The number of available memory in kb";
                }

                leaf available-percent {
                        type uint64;
                        description
                                "The percentage of available memory";
                }

    		leaf committed-number {
    			type uint64;
    			description
    				"The number of committed memory in kb";
    		}
    		
    		leaf committed-percent {
    			type uint8;
    			description
    				"The percentage of comitted memory";
    		}
    		
                container status {

    		leaf condition {
    			type string;
    			description
    				"Need description";
    		}
    		
    		leaf threshold-status {
    			type string;
    			description
    				"Need description";
    		}

                leaf threshold-value-percent {
                        type uint64;
                        description
                                "Need description";
		}

                }

                }
		
		container per-core-stats {
			description
				"Statistics on each core";
		
			list core {
				key "name";
				description
					"A Core";
					
	    		leaf name {
	    			type string;
	    			description
	    				"The name of the core";
	    		}
	    		
	    		leaf user {
	    			type string;
	    			description
	    				"The percentage of utilization by user
                                         Format: Decimal with 2 fraction digits";
	    		}
	    		
	    		leaf system {
	    			type string;
	    			description
	    				"The percentage of utilization by the system
                                         Format: Decimal with 2 fraction digits";
	    		}
	    		
	    		leaf nice {
	    			type string;
	    			description
	    				"The percentage of utilization by nice
                                         Format: Decimal with 2 fraction digits";
	    		}
	    		
	    		leaf idle {
	    			type string;
	    			description
	    				"The percentage that is idle
                                         Format: Decimal with 2 fraction digits";
	    		}
	    		
	    		leaf irq {
	    			type string;
	    			description
	    				"The percentage of utilizaion by irq
                                         Format: Decimal with 2 fraction digits";
	    		}
	    		
	    		leaf sirq {
	    			type string;
	    			description
	    				"The percentage of utilizaion by sirq
                                         Format: Decimal with 2 fraction digits";
	    		}
	    		
	    		leaf io-wait {
	    			type string;
	    			description
	    				"The percentage of utilization by IOwait
                                         Format: Decimal with 2 fraction digits";
	    		}
				
			}
		
		}
      	
                } 

	}

    container platform-software-interface-rp-active-brief-forwarding  {
        description
            "DESCRIPTION NEEDED";
        
        list interface-xos {
            key "name";
            description
                "DESCRIPTION NEEDED";
        
            leaf name {
                type string;
                description
                    "DESCRPITION NEEDED";
            }
            
            leaf id {
                type uint64;
                description
                    "DESCRPITION NEEDED";
            }
            
            leaf qfp-id {
                type uint64;
                description
                    "DESCRPITION NEEDED";
            }
            
        }
        
    }

}

}
