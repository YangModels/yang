module cisco-process-cpu {

    yang-version 1;

    namespace "urn:cisco:params:xml:ns:yang:cisco-process-cpu";
    prefix pcpu;


    organization
        "Cisco Systems, Inc.";

    contact
        " Cisco Systems, Inc.
          Customer Service

          Postal: 170 W Tasman Drive
          San Jose, CA 95134

          Tel: +1 1800 553-NETS

          E-mail: cs-yang@cisco.com";
    
    description
        "This module contains a collection of YANG definitions for
         monitoring CPU usage of processes in a Network Element.";

    reference "TODO";

    revision 2015-04-09 {
        description "Proposed";
    }

    container cpu-usage {
        config false;

        container cpu-utilization {
	    config false;
	    description
	        "Data nodes for Total CPU Utilizations Statistics.";

	    leaf five-seconds {
		type uint8;
		units "percent";
		description "Busy percentage in last 5-seconds";
	    }

	    leaf five-seconds-intr {
		type uint8;
		units "percent";
		description "Interrupt busy percentage in last 5-seconds";
	    }

	    leaf one-minute {
		type uint8;
		units "percent";
	        description "Busy percentage in last one minute";
	    }

	    leaf five-minutes {
		type uint8;
		units "percent";
		description "Busy percentage in last five minutes";
	    }
	}

        container process-cpu-usage {
	    config false;
	    description
	        "Data nodes for System wide Process CPU usage Statistics.";

	    list process {
	        key "pid name";

		description
		    "The list of software processes on the device.";

		leaf pid {
		    type uint32;
		    description
		        "Process-ID of the process.";
		}

		leaf name {
		    type string;
		    description
			"The name of the process.";
		}

		leaf tty {
		    type uint16;
		    description
			"TTY bound to by the process.";
		}

                leaf total-run-time {
                    type uint64;
                    units "milli-seconds";
                    description "Total Run-time of this process (mSec)";
                }

                leaf invocation-count {
                    type uint32;
                    description "Total number of invocations";
		}

		leaf avg-run-time {
		    type uint64;
		    units "micro-seconds";
		    description "Average Run-time of this process (uSec)";
		}

		leaf five-seconds {
		    type decimal64 {
		        fraction-digits 2;
		    }
                    units "percent";
		    description "Busy percentage in last 5-seconds";
	        }

                leaf one-minute {
		    type decimal64 {
			fraction-digits 2;
		    }
		    units "percent";
		    description "Busy percentage in last one minute";
		}

		leaf five-minutes {
		    type decimal64 {
			fraction-digits 2;
		    }
		    units "percent";
		    description "Busy percentage in last five minutes";
		}
	    }
	}
    }

}
