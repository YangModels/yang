module cisco-virtual-service {

    yang-version 1;

    namespace "urn:cisco:params:xml:ns:yang:cisco-virtual-service";
    prefix vservice;

    organization
        "Cisco Systems, Inc.";

    contact
        " Cisco Systems, Inc. Customer Service Postal: 170 W Tasman Drive
        San Jose, CA 95134 Tel: +1 1800 553-NETS E-mail: cs-yang@cisco.com";

    description
        "This module contains a collection of YANG definitions for monitoring
        virtual services in a Network Element.";

    reference "TODO";

    revision 2016-04-19 {
        description "Merged three root containers into one";
    }

    revision 2015-04-09 {
        description "Proposed";
    }

    container virtual-services {
        config false;
        description
                "Names and Status of virtual services on the device";

        list virtual-service {
            key "name";
            description
            	"A virtual service.";

            leaf name {
                type string;
                description
                	"The name of the virtual service.";
            }

            container details {
                description 
                    "Details of the virtual service.";

            leaf state {
                type string;
                description
                	"State of the virtual service.";
            }

            container package-information {
                description
                	"Details of the package for the virtual-service.";

                leaf name {
                    type string;
                    description
                    	"Name of the package for the virtual-service.";
                }

                leaf path {
                    type string;
                    description
                    	"Path to the package.";
                }

                container application {
                    description
                    	"Details of the application.";

                    leaf name {
                        type string;
                        description
                        	"Name of the application.";
                    }

                    leaf installed-version {
                        type string;
                        description
                        	"Version of the application.";
                    }

                    leaf description {
                        type string;
                        description
                        	"Description of the application.";
                    }
                }

                container signing {
                    description
                    	"Details of the key signing.";

                    leaf key-type {
                        type string;
                        description
                        	"The Type of the signed key.";
                    }

                    leaf method {
                        type string;
                        description
                        	"The method the key was signed.";
                    }
                }

                container licensing {
                    description
                    	"Details about the license.";

                    leaf name {
                        type string;
                        description
                        	"The name of the license.";
                    }

                    leaf version {
                        type string;
                        description
                        	"The version of the license.";
                    }
                }
            }

            container detailed-guest-status {
                description
                	"Details on the guest status.";

                container processes {
                    description
                            "All the processes.";
                

                    list process {
                        key "name";
                        description
                                "A proccess.";
                        
                        leaf name {
                            type string;
                            description
                                    "Name of the proccess.";
                        }

                        leaf status {
                            type string;
                            description
                                    "Status of the proccess.";
                        }

                        leaf pid {
                            type string;
                            description
                                    "Process ID.";
                        }

                        leaf uptime {
                            type string;
                            description
                                    "Up time of the proccess.";
                        }

                        leaf memory {
                            type string;
                            description
                                    "Memory of the proccess.";
                        }
                    }
                }
            }

            leaf activated-profile-name {
                type string;
                description
                	"The activated profile name.";
            }

            container resource-reservation {
                description
                	"Details of the resources reserved for this virtual service.";

                leaf disk {
                    type uint64;
                    description
                    	"The amount of reserverd disk space in MB.";
                }

                leaf memory {
                    type uint64;
                    description
                    	"The amount of reserved memory in MB.";
                }

                leaf cpu {
                    type uint64;
                    description 
                    	"The percentage of reserved cpu.";
                }
            }

            container attached-devices {
                description
                	"Details for the devices attached to this virtual service.";

                list attached-device {
                    key "name";
                    description
                    	"List of attached devices.";

                    leaf name {
                        type string;
                        description
                        	"The name of the attached device.";
                    }

                    leaf type {
                        type string;
                        description
                        	"The type of the attached device.";
                    }

                    leaf alias {
                        type string;
                        mandatory false;
                        description
                        	"The alias for the attached device.";
                    }
                }
            }

            container network-interfaces {
                description
                	"Details for the network interfaces.";

                list network-interface {
                    key "mac-address";
                    description
                    	"Details for a network interface.";

                    leaf mac-address {
                        type string;
                        description
                        	"The MAC address for the network interface.";
                    }

                    // Possible better Yang/PAL with better output
                    leaf attached-interface {
                        type string;
                        description
                        	"Name of the the attached interface";
                    }
                }
            }

            // Possible better Yang/PAL with better output
            leaf guest-interface {
                type string;
                description
                	"The name of a guest interface.";
            }

            // Possible better Yang/PAL with better output
            container guest-routes {
                description
                	"Routes for the guest interface.";

                list guest-route {
                    key "route";
                    description
                    	"List of guest routes for a guest interface.";

                    leaf route {
                        type string;
                        description
                        	"A guest route for a guest interface.";
                    }
                }
            }

            container resource-admission {
                description
                	"Resources being allocated for the virtual-service.";

                leaf state {
                    type string;
                    description
                    	"Thes status the of the resource allocation.";
                }
                leaf disk-space {
                    type string;
                    description
                    	"The amount of disk space being allocated for the virtual-service.";
                }

                leaf memory {
                    type string;
                    description
                    	"The amount of memory being allocated for the virtual-service.";
                }

                leaf cpu {
                    type uint64;
                    description
                    	"The percentage of cpu being allocated for the virtual-service";
                }

                leaf vcpus {
                    type string;
                    description
                    	"The amount of VCPUs being allocated for the virtual-service.";
                }
            }
        }

        container utilization {
            description
            	"Utilization of device resources for a virtual-service.";

            leaf name {
                type string;
                description
                	"The name of the virtual service.";
            }
            container cpu-util {
                description
                	"Details on the CPU utilization for the virtual-service.";

                leaf requested-application-util {
                    type uint64;
                    description
                    	"Percentage of requested CPU utilization by the virtual-service.";
                }

                leaf actual-application-util {
                    type uint64;
                    description
                    	"Percetnage of CPU actual utilization for the virtual-service.";
                }

                leaf cpu-state {
                    type string;
                    description
                    	"The state of the CPU utilization for the virtual-service.";
                }
            }

            container memory-util {
                description
                	"Details on the memory usage for the virtual-service.";

                leaf memory-allocation {
                    type string;
                    description
                    	"Amount of memory being allocated for the virtual-service in KB.";
                }

                leaf memory-used {
                    type string;
                    description
                    	"Amount of memory being used for the virtual-service in KB.";
                }
            }

            container network-util-list {
                description
                	"list of the network utilizations for the virtual-service.";

                list network-util {
                    key "name";
                    description
                    	"Details on a network utilization for the virtual-service.";

                    leaf name {
                        type string;
                        description
                        	"The name of the network that is being used for the virtual-service.";
                    }

                    leaf alias {
                        type string;
                        description
                        	"The alias of the network that is being used for the virtual-service.";
                    }

                    leaf rx-packets {
                        type uint64;
                        // for the virtual-service or the network?
                        description
                        	"The number of rx packets being utilized for the virtual-service.";
                    }

                    leaf rx-bytes {
                        type uint64;
                        description
                        	"The number of rx bytes being utilized for the virtual-service.";
                    }

                    leaf rx-errors {
                        type uint64;
                        description
                        	"The number of rx errors.";
                    }

                    leaf tx-packets {
                        type uint64;
                        description
                        	"The number of tx packets being utilized for the virtual-service.";
                    }

                    leaf tx-bytes {
                        type uint64;
                        description
                        	"The number of tx bytes being utilized for the virtual-service.";
                    }

                    leaf tx-errors {
                        type uint64;
                        description
                        	"The number of tx errors.";
                    }
                }
            }

            container storage-util-list {
                description
                	"List of the storage utilizations for the virtual-service.";

                list storage-util {
                    key "name";
                    description
                    	"Details on a storage utilization for the virtual-service.";

                    leaf name {
                        type string;
                        description
                        	"The name of the storage process being used for the virtual-service.";
                    }

                    leaf alias {
                        type string;
                        description
                        	"The alias of the storage process being used for the virtual-service.";
                    }

                    leaf rd-bytes {
                        type uint64;
                        // for the virtual-service or the storage process?
                        description
                        	"The number of RD bytes being used for the virtual-service.";
                    }

                    leaf rd-requests {
                        type uint64;
                        description
                        	"The number of rd requests being used for the virtual-service.";
                    }

                    leaf errors {
                        type uint64;
                        description
                        	"The name of errors on the storage process.";
                    }

                    leaf wr-bytes {
                        type uint64;
                        description
                        	"The number of WR bytes for the virtual-service.";
                    }

                    leaf wr-requests {
                        type uint64;
                        description
                        	"The number of WR requests for the virtual-service.";
                    }

                    leaf capacity {
                        type uint64;
                        description
                        	"The storage capactity in 1K blocks.";
                    }

                    leaf available {
                        type string;
                        description
                        	"The available storage in 1K blocks.";
                    }

                    leaf used {
                        type uint64;
                        description
                        	"The number of 1K blocks being used.";
                    }

                    leaf usage {
                        type string;
                        description
                        	"The percetage of storage capactiy being used.";
                    }
                }
            }
        }
    }

    }
}
