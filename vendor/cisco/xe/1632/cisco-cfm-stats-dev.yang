module cisco-cfm-stats-dev {
  namespace "urn:cisco:params:xml:ns:yang:cisco-cfm-stats-dev";
  prefix cfmstats-dev;

  import cisco-cfm-stats {
    prefix cfm;
  }

  organization "Cisco Systems, Inc.";
  contact
    "Cisco Systems, Inc.
     Customer Service

     Postal: 170 W Tasman Drive
     San Jose, CA 95134

     Tel: +1 1800 553-NETS

     E-mail: cs-yang@cisco.com";
  description
    "This YANG module is a deviation to 'cisco-cfm-stats'
     for making last clearing time a string";

  revision 2015-05-27 {
    description
      "Proposed";
    reference "TODO";
  }
    deviation "/cfm:cfm-statistics/cfm:mep/cfm:last-cleared" {
        description
            "Modifies the usage of yang:date-and-time in ietf-routing
             temporarily to string so that Router's time notation is 
             passed as it is without conversion to yang:date-and-time format.";

        deviate replace {
            type string;
        }

    }

} // --end module
