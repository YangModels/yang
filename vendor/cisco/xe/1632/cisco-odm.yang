module cisco-odm {
  namespace "http://cisco.com/yang/cisco-odm";
  prefix codm;

  import cisco-self-mgmt {
    prefix cisco-sfm;
  }
 
  import tailf-common {
    prefix tailf;
  }

  description
    "Copyright (c) 2016 by Cisco Systems, Inc."+
    "All rights reserved.";

  revision "2016-05-16" {
    description "Add augment statement";
  }

  revision "2016-05-04" {
    description "Add tail-f annotation to boolean leaves";
  }

  revision 2016-03-30 {
    description
      "Update description with copyright notice.";
  }

  revision "2015-06-19" {
    description "initial commit";
  }

  augment "/cisco-sfm:netconf-yang" {     
  container cisco-odm {
    leaf polling-enable {
      tailf:cli-boolean-no;
      type boolean;
      default false;
    }
    leaf on-demand-default-time {
      type uint32 {
        range "500..max";
      }
      default 30000;
    }
    leaf on-demand-enable {
      tailf:cli-boolean-no;
      type boolean;
      default false;
    }
    list actions {
      key action-name;
      leaf action-name {
        type string;
      }
      leaf polling-interval {
        type uint32 {
          range "1..max";
	}
        default 120000;
      }
      leaf mode {
        type enumeration {
          enum poll;
          enum on-demand;
          enum none;
	}
        default poll;
      }
      leaf cdb-xpath {
         type string;
      }
    }
  }
  }
}
