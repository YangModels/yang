/*
 * Generated by confdc --mib2yang-std
 * Source: mgmt/dmi/model/common/mib-source/CISCO-VOICE-DNIS-MIB.mib
 */
/*
 * This YANG module has been generated by smidump 0.5.0:
 *
 *      smidump -f yang CISCO-VOICE-DNIS-MIB
 *
 * Do not edit. Edit the source file instead!
 */

module CISCO-VOICE-DNIS-MIB {

  namespace "urn:ietf:params:xml:ns:yang:smiv2:CISCO-VOICE-DNIS-MIB";
  prefix CISCO-VOICE-DNIS-MIB;

  import SNMPv2-TC {
    prefix "snmpv2-tc";
  }

  import ietf-yang-smiv2 {
    prefix "smiv2";
  }

  organization
   "Cisco Systems, Inc.";

  contact
   "       Cisco Systems
    Customer Service
    
    Postal: 170 W. Tasman Drive
    San Jose, CA  95134
    USA
    
    Tel: +1 800 553-NETS
    
    E-mail: cs-voice@cisco.com";

  description
   "The MIB module provides management support for Dialer
    Number Information Service (DNIS) mapping.  A DNIS
    entry is associated with a Voice XML (VXML) page to
    provide audio play back features. Multiple DNIS
    entries can be grouped together to form a DNIS
    mapping with a unique map name.
    
    *** ABBREVIATIONS, ACRONYMS, AND SYMBOLS ***
    
    DNIS - Dialer Number Information Service
    
    XML  - Extensible Markup Language
    
    VXML - Voice XML
    
    URL  - Uniform Resource Locator  ";

  revision 2002-05-01 {
    description
     "[Revision added by libsmi due to a LAST-UPDATED clause.]";
  }

  typedef DnisMapname {
    type string;
    description
     "An identification for a DNIS map name or a DNIS name. A
      DNIS map name correspods to a group of individual DNIS
      names. The DNIS map names are unique in the system, and
      within each map name, individual DNIS names are unique.";
    smiv2:display-hint "32a";
  }

  typedef CvE164String {
    type string;
    description
     "A UTF-8 string limited to the character set defined for
      E.164, '0123456789*#,<quote>'.
      Note that <quote> represents the double quote which
      cannot be contained in a SMI description clause.";
    smiv2:display-hint "32a";
  }


  container CISCO-VOICE-DNIS-MIB {
    config false;

    container cvDnisMappingTable {
      description
       "The table contains the map name and a url specifying
        a file name. The file contains DNIS entries that belong
        to the DNIS mapping.";
      smiv2:oid "1.3.6.1.4.1.9.9.219.1.1.1";

      list cvDnisMappingEntry {
        key "cvDnisMappingName";
        smiv2:implied "cvDnisMappingName";
        description
         "Information about a single DNIS mapping. There is a
          unique DNIS map name. New DNIS mapping can be created
          using cvDnisMappingStatus.
          
          The entry can be created with or without a file location 
          specified by cvDnisMappingUrl. The mapping file contains
          DNIS name and VXML page per line. For example, a 
          cvDnisMappingUrl could be tftp://someserver/dnismap.txt.
          This file is a text file and the content format is
            dnis <dnisname> url <urlname>.
          An example of the contents of the file itself can be
            dnis 18004251234 url http://www.b.com/p/vwelcome.vxml
            dnis 18004253421 url http://www.c.com/j/vxmlintf.vxml
          If a mapping file location is specified, then new rows
          corresponding to this map name are created and populated
          in cvDnisNodeTable from the contents of the file. The
          rows corresponding to this map name in cvDnisNodeTable
          cannot be created or modified or deleted but can be
          read. 
          
          If a mapping file location is not specified in
          cvDnisMappingUrl, then individual DNIS entries
          corresponding to this map name can be created, modified
          and deleted in cvDnisNodeTable. 
          
          Deleting an entry deletes all the related entries in
          cvDnisNodeTable. ";
        smiv2:oid "1.3.6.1.4.1.9.9.219.1.1.1.1";

        leaf cvDnisMappingName {
          type CISCO-VOICE-DNIS-MIB:DnisMapname {
            length "1..32";
          }
          description
           "The name which uniquely identifies a DNIS mapping. ";
          smiv2:max-access "not-accessible";
          smiv2:oid "1.3.6.1.4.1.9.9.219.1.1.1.1.1";
        }

        leaf cvDnisMappingUrl {
          type snmpv2-tc:DisplayString;
          description
           "The url specifies a file location. The file contains
            individual DNIS entries that belong to the DNIS map 
            name specified by cvDnisMappingName.
            
            Once a url is created and associated with a map name (the
            association is complete when the row is made active(1)),
            it cannot be modified while cvDnisMappingStatus is
            active. If a different url needs to be associated with
            the current map name, the row status should be made
            notInService(2) and this object has to be modified to
            associate a new url. When a new association is made all
            the DNIS entries corresponding to the old association
            will be deleted from the cvDnisNodeTable.
            
            The url is read when the row status is made active(1) or
            when the row status is active and the object 
             cvDnisMappingRefresh is explicitly set to refresh(2). 
             If the url is not accessible then a
            cvDnisMappingUrlInaccessible notification will be
            generted. ";
          smiv2:defval "";
          smiv2:max-access "read-write";
          smiv2:oid "1.3.6.1.4.1.9.9.219.1.1.1.1.2";
        }

        leaf cvDnisMappingRefresh {
          type enumeration {
            enum "idle" {
              value "1";
            }
            enum "refresh" {
              value "2";
            }
          }
          description
           "Whenever there is a need to re-read the contents of the
            file specified by cvDnisMappingUrl, this object can be
            set to refresh(2). This will cause the contents of the
            file to be re-read and correspondingly update the
            cvDnisNodeTable. After the completion of this operation,
            the value of this object is reset to idle(1). The only
            operation allowed on this object is setting it to
            refresh(2). This can only be done when the current value
            is idle(1) and the rowstatus is active(1).
            
            idle       - The refreshing process is idle and the user
                         can modify this object to refresh.
            refresh    - The refreshing process is currently busy and
                         the user have to wait till the object
                         becomes idle to issue new refresh.";
          smiv2:defval "idle";
          smiv2:max-access "read-write";
          smiv2:oid "1.3.6.1.4.1.9.9.219.1.1.1.1.3";
        }

        leaf cvDnisMappingUrlAccessError {
          type snmpv2-tc:DisplayString;
          description
           "ASCII text describing the error on last access of the url
            specified in cvDnisMappingUrl.
            
            If the url access does not succeed, then this object is
            populated with an error message indicating the reason for
            failure. If the url access succeeds, this object is set
            to null string.";
          smiv2:defval "";
          smiv2:max-access "read-only";
          smiv2:oid "1.3.6.1.4.1.9.9.219.1.1.1.1.4";
        }

        leaf cvDnisMappingStatus {
          type snmpv2-tc:RowStatus;
          description
           "This object is used to create a new row or modify or
            delete an existing row in this table. When making the
            status active(1), if a valid cvDnisMappingUrl is present
            the contents of the url is downloaded and during that
            time cvDnisMappingRefresh is set to refresh(2). When
            cvDnisMappingRefresh is set to refresh(2), only the
            destroy(6) operation is allowed.";
          smiv2:max-access "read-write";
          smiv2:oid "1.3.6.1.4.1.9.9.219.1.1.1.1.5";
        }
      }
    }

    container cvDnisNodeTable {
      description
       "The table contains a DNIS name and a url. The url is a
        pointer to a VXML page for the DNIS name. ";
      smiv2:oid "1.3.6.1.4.1.9.9.219.1.1.2";

      list cvDnisNodeEntry {
        key "cvDnisMappingName cvDnisNumber";
        smiv2:implied "cvDnisNumber";
        description
         "Each entry is a DNIS name and the location of the
          associated VXML page. New DNIS entries can be created or
          the existing entries can be modified or deleted only if
          the corresponding map name (defined in
          cvDnisMappingTable) does not have any file name provided
          in the cvDnisMappingUrl object. 
          
          If a file name is provided in cvDnisMappingUrl
          corresponding to this entry's map name, then this row
          will have read permission only.";
        smiv2:oid "1.3.6.1.4.1.9.9.219.1.1.2.1";

        leaf cvDnisMappingName {
          type leafref {
            path "/CISCO-VOICE-DNIS-MIB:CISCO-VOICE-DNIS-MIB/CISCO-VOICE-DNIS-MIB:cvDnisMappingTable/CISCO-VOICE-DNIS-MIB:cvDnisMappingEntry/CISCO-VOICE-DNIS-MIB:cvDnisMappingName";
          }
        }

        leaf cvDnisNumber {
          type CISCO-VOICE-DNIS-MIB:CvE164String;
          description
           "The individual DNIS name. It is unique within a DNIS
            mapping.";
          smiv2:max-access "not-accessible";
          smiv2:oid "1.3.6.1.4.1.9.9.219.1.1.2.1.1";
        }

        leaf cvDnisNodeUrl {
          type snmpv2-tc:DisplayString;
          description
           "The url specifies a VXML page. This page contains
            voice XML links to play audio data.
            
            This url which is a VXML page is not read immediately
            when the row is made active(1), but only when a call that
            requires the use of this DNIS comes through.";
          smiv2:defval "";
          smiv2:max-access "read-write";
          smiv2:oid "1.3.6.1.4.1.9.9.219.1.1.2.1.2";
        }

        leaf cvDnisNodeModifiable {
          type boolean;
          description
           "This object specifies whether the object in a particular
            row is modifiable. The object is set to true(1) if the
            corresponding map name (defined in cvDnisMappingTable)
            does not have any file name provided in the
            cvDnisMappingUrl object. Otherwise this object is set to
            false(2) and the row becomes read only.  ";
          smiv2:max-access "read-only";
          smiv2:oid "1.3.6.1.4.1.9.9.219.1.1.2.1.3";
        }

        leaf cvDnisNodeStatus {
          type snmpv2-tc:RowStatus;
          description
           "This object is used to create a new row or modify or
            delete an existing row in this table. The objects in a
            row can be modified or deleted while the row status is
            active(1) and cvDnisNodeModifiable is true(1). The row
            status cannot be set to notInService(2) or
            createAndWait(5). ";
          smiv2:max-access "read-write";
          smiv2:oid "1.3.6.1.4.1.9.9.219.1.1.2.1.4";
        }
      }
    }
  }

  notification cvDnisMappingUrlInaccessible {
    description
     "Inaccessible DNIS mapping url notification. A
      cvDnisMappingUrlInaccessible notification is sent if the
      specified url is not accessible.";
    smiv2:oid "1.3.6.1.4.1.9.9.219.2.0.1";

    container object-1 {

      leaf cvDnisMappingName {
        type leafref {
          path "/CISCO-VOICE-DNIS-MIB:CISCO-VOICE-DNIS-MIB/CISCO-VOICE-DNIS-MIB:cvDnisMappingTable/CISCO-VOICE-DNIS-MIB:cvDnisMappingEntry/CISCO-VOICE-DNIS-MIB:cvDnisMappingName";
        }
      }

      leaf cvDnisMappingUrl {
        type leafref {
          path "/CISCO-VOICE-DNIS-MIB:CISCO-VOICE-DNIS-MIB/CISCO-VOICE-DNIS-MIB:cvDnisMappingTable/CISCO-VOICE-DNIS-MIB:cvDnisMappingEntry/CISCO-VOICE-DNIS-MIB:cvDnisMappingUrl";
        }
      }
    }

    container object-2 {

      leaf cvDnisMappingName {
        type leafref {
          path "/CISCO-VOICE-DNIS-MIB:CISCO-VOICE-DNIS-MIB/CISCO-VOICE-DNIS-MIB:cvDnisMappingTable/CISCO-VOICE-DNIS-MIB:cvDnisMappingEntry/CISCO-VOICE-DNIS-MIB:cvDnisMappingName";
        }
      }

      leaf cvDnisMappingUrlAccessError {
        type leafref {
          path "/CISCO-VOICE-DNIS-MIB:CISCO-VOICE-DNIS-MIB/CISCO-VOICE-DNIS-MIB:cvDnisMappingTable/CISCO-VOICE-DNIS-MIB:cvDnisMappingEntry/CISCO-VOICE-DNIS-MIB:cvDnisMappingUrlAccessError";
        }
      }
    }
  }

  smiv2:alias "ciscoVoiceDnisMIB" {
    smiv2:oid "1.3.6.1.4.1.9.9.219";
  }

  smiv2:alias "cvDnisMIBObjects" {
    smiv2:oid "1.3.6.1.4.1.9.9.219.1";
  }

  smiv2:alias "cvDnisMap" {
    smiv2:oid "1.3.6.1.4.1.9.9.219.1.1";
  }

  smiv2:alias "cvDnisMIBNotificationPrefix" {
    smiv2:oid "1.3.6.1.4.1.9.9.219.2";
  }

  smiv2:alias "cvDnisMIBNotifications" {
    smiv2:oid "1.3.6.1.4.1.9.9.219.2.0";
  }

  smiv2:alias "cvDnisMIBConformance" {
    smiv2:oid "1.3.6.1.4.1.9.9.219.3";
  }

  smiv2:alias "cvDnisMIBCompliances" {
    smiv2:oid "1.3.6.1.4.1.9.9.219.3.1";
  }

  smiv2:alias "cvDnisMIBGroups" {
    smiv2:oid "1.3.6.1.4.1.9.9.219.3.2";
  }

}
