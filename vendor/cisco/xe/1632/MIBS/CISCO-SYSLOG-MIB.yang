/*
 * Generated by confdc --mib2yang-std
 * Source: mgmt/dmi/model/common/mib-source/CISCO-SYSLOG-MIB.mib
 */
/*
 * This YANG module has been generated by smidump 0.5.0:
 *
 *      smidump -f yang CISCO-SYSLOG-MIB
 *
 * Do not edit. Edit the source file instead!
 */

module CISCO-SYSLOG-MIB {

  namespace "urn:ietf:params:xml:ns:yang:smiv2:CISCO-SYSLOG-MIB";
  prefix CISCO-SYSLOG-MIB;

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "       Cisco Systems
    Customer Service
    
    Postal: 170 W Tasman Drive
    San Jose, CA  95134
    USA
    
    Tel: +1 800 553-NETS
    
    E-mail: cs-snmp@cisco.com";

  description
   "The MIB module to describe and store the system
    messages generated by the IOS and any other
    OS which supports syslogs.";

  revision 2005-12-03 {
    description
     "Removed UNITS clause for clogOriginIDType
      as UNITS clause is not applicable.";
  }

  revision 2005-08-11 {
    description
     "Added following objects:
      clogOriginIDType
      clogOriginID";
  }

  revision 2005-06-01 {
    description
     "Added clogServerGroup.";
  }

  revision 1995-08-07 {
    description
     "Initial version of this MIB module.";
  }

  typedef SyslogSeverity {
    type enumeration {
      enum "emergency" {
        value "1";
      }
      enum "alert" {
        value "2";
      }
      enum "critical" {
        value "3";
      }
      enum "error" {
        value "4";
      }
      enum "warning" {
        value "5";
      }
      enum "notice" {
        value "6";
      }
      enum "info" {
        value "7";
      }
      enum "debug" {
        value "8";
      }
    }
    description
     "The severity of a syslog message.  The enumeration
      values are equal to the values that syslog uses + 1.
      For example, with syslog, emergency=0.
      
       'emergency' : system is unusable
       'alert'     : action must be taken immediately
       'critical'  : critical conditions
       'error'     : error conditions
       'warning'   : warning conditions
       'notice'    : normal but significant condition
       'informational': informational messages 
       'debug'        : debug-level messages.";
    reference
     "RFC 3164, Section 4.1 - syslog Message Parts";
  }


  container CISCO-SYSLOG-MIB {
    config false;

    container clogBasic {
      smiv2:oid "1.3.6.1.4.1.9.9.41.1.1";

      leaf clogNotificationsSent {
        type yang:counter32;
        units "notifications";
        description
         "The number of clogMessageGenerated notifications that
          have been sent. This number may include notifications
          that were prevented from being transmitted due to
          reasons such as resource limitations and/or
          non-connectivity.  If one is receiving notifications,
          one can periodically poll this object to determine if
          any notifications were missed.  If so, a poll of the
          clogHistoryTable might be appropriate.";
        smiv2:max-access "read-only";
        smiv2:oid "1.3.6.1.4.1.9.9.41.1.1.1";
      }

      leaf clogNotificationsEnabled {
        type boolean;
        description
         "Indicates whether clogMessageGenerated notifications
          will or will not be sent when a syslog message is
          generated by the device.  Disabling notifications
          does not prevent syslog messages from being added
          to the clogHistoryTable.";
        smiv2:defval "false";
        smiv2:max-access "read-write";
        smiv2:oid "1.3.6.1.4.1.9.9.41.1.1.2";
      }

      leaf clogMaxSeverity {
        type CISCO-SYSLOG-MIB:SyslogSeverity;
        description
         "Indicates which syslog severity levels will be
          processed.  Any syslog message with a severity value
          greater than this value will be ignored by the agent.
          note: severity numeric values increase as their
          severity decreases, e.g. 'error' is more severe than
          'debug'.";
        smiv2:defval "warning";
        smiv2:max-access "read-write";
        smiv2:oid "1.3.6.1.4.1.9.9.41.1.1.3";
      }

      leaf clogMsgIgnores {
        type yang:counter32;
        units "messages";
        description
         "The number of syslog messages which were ignored.  A
          message will be ignored if it has a severity value
          greater than clogMaxSeverity.";
        smiv2:max-access "read-only";
        smiv2:oid "1.3.6.1.4.1.9.9.41.1.1.4";
      }

      leaf clogMsgDrops {
        type yang:counter32;
        units "messages";
        description
         "The number of syslog messages which could not be
          processed due to lack of system resources. Most
          likely this will occur at the same time that syslog
          messages are generated to indicate this lack of
          resources.  Increases in this object's value may serve
          as an indication that system resource levels should be
          examined via other mib objects.  A message that is
          dropped will not appear in the history table and
          no notification will be sent for this message.";
        smiv2:max-access "read-only";
        smiv2:oid "1.3.6.1.4.1.9.9.41.1.1.5";
      }

      leaf clogOriginIDType {
        type enumeration {
          enum "none" {
            value "1";
          }
          enum "other" {
            value "2";
          }
          enum "hostName" {
            value "3";
          }
          enum "ipv4Address" {
            value "4";
          }
          enum "contextName" {
            value "5";
          }
          enum "userDefined" {
            value "6";
          }
        }
        description
         "This object identifies the type of value that
          will be contained in clogOriginID object.
          
          The possible value(s) are:
             'none'       : do not send origin identifier in 
                            syslog messages.
             'other'      : type that is not identified by other 
                            values specified in this object.
             'hostName'   : Send hostname of the system in syslog
                            messages.
             'ipv4Address': Send IP address of the sending interface.
             'contextName': Send context name of the security device.
             'userDefined': Send user configured string in
                            syslog message.
          
             The value 'other' and 'none' can not be set but
             can only be read.";
        smiv2:defval "none";
        smiv2:max-access "read-write";
        smiv2:oid "1.3.6.1.4.1.9.9.41.1.1.6";
      }

      leaf clogOriginID {
        type snmp-framework:SnmpAdminString;
        description
         "This object is used for configuring the
          origin identifier for the syslog messages.
          
          The origin identifier is useful for identifying 
          the source of system logging messages in cases 
          syslog messages from multiple devices are sent 
          to a single syslog host.
          The origin identifier is added to the beginning of
          all system logging (syslog) messages sent to remote 
          hosts.
          
          The type of the identifier is specified
          by clogOriginIDType object.
          
          This object can be written by the SNMP manager
          only when clogOriginIDType is set to 'userDefined'.
          
          For following value(s) of clogOriginIDType,
          this object can not be set; the value of this
          object is derived by the system in these cases:
             'contextName' 
             'ipv4Address'
             'hostName'
             'other'     
             'none'     
          
          This object contains the context name
          of the device, when clogOriginIDType is 
          set to 'contextName'.
          
          This object contains IPv4 address
          (in dotted decimal notation) of the sending 
          interface when clogOriginIDType is set to
          'ipv4Address'.
          
          This object contains hostname of the system
          when clogOriginIDType is set to 'hostName'.
          
          This object will contain zero length
          octet string when clogOriginIDType is
          either 'none' or 'other'.";
        smiv2:defval "";
        smiv2:max-access "read-write";
        smiv2:oid "1.3.6.1.4.1.9.9.41.1.1.7";
      }
    }

    container clogHistory {
      smiv2:oid "1.3.6.1.4.1.9.9.41.1.2";

      leaf clogHistTableMaxLength {
        type int32 {
          range "0..500";
        }
        units "entries";
        description
         "The upper limit on the number of entries that the
          clogHistoryTable may contain.  A value of 0 will
          prevent any history from being retained. When this
          table is full, the oldest entry will be deleted and
          a new one will be created.";
        smiv2:defval "1";
        smiv2:max-access "read-write";
        smiv2:oid "1.3.6.1.4.1.9.9.41.1.2.1";
      }

      leaf clogHistMsgsFlushed {
        type yang:counter32;
        units "messages";
        description
         "The number of entries that have been removed from
          the clogHistoryTable in order to make room for new
          entries. This object can be utilized to determine
          whether your polling frequency on the history table
          is fast enough and/or the size of your history table
          is large enough such that you are not missing
          messages.";
        smiv2:max-access "read-only";
        smiv2:oid "1.3.6.1.4.1.9.9.41.1.2.2";
      }
    }

    container clogServer {
      smiv2:oid "1.3.6.1.4.1.9.9.41.1.3";

      leaf clogMaxServers {
        type uint32;
        description
         "The maximum number of syslog servers that can be
          configured for the system in clogServerConfigTable.
          
          A value of zero for this object indicates there is
          no specified limit for the system and is only dictated
          by system resources.";
        smiv2:max-access "read-only";
        smiv2:oid "1.3.6.1.4.1.9.9.41.1.3.1";
      }
    }

    container clogHistoryTable {
      description
       "A table of syslog messages generated by this device.
        All 'interesting' syslog messages (i.e. severity <=
        clogMaxSeverity) are entered into this table.";
      smiv2:oid "1.3.6.1.4.1.9.9.41.1.2.3";

      list clogHistoryEntry {
        key "clogHistIndex";
        description
         "A syslog message that was previously generated by this
          device. Each entry is indexed by a message index.";
        smiv2:oid "1.3.6.1.4.1.9.9.41.1.2.3.1";

        leaf clogHistIndex {
          type int32 {
            range "1..2147483647";
          }
          description
           "A monotonically increasing integer for the sole
            purpose of indexing messages.  When it reaches the
            maximum value the agent flushes the table and wraps
            the value back to 1.";
          smiv2:max-access "not-accessible";
          smiv2:oid "1.3.6.1.4.1.9.9.41.1.2.3.1.1";
        }

        leaf clogHistFacility {
          type snmpv2-tc:DisplayString {
            length "1..20";
          }
          description
           "Name of the facility that generated this message.
            For example: 'SYS'.";
          smiv2:max-access "read-only";
          smiv2:oid "1.3.6.1.4.1.9.9.41.1.2.3.1.2";
        }

        leaf clogHistSeverity {
          type CISCO-SYSLOG-MIB:SyslogSeverity;
          description
           "The severity of the message.";
          smiv2:max-access "read-only";
          smiv2:oid "1.3.6.1.4.1.9.9.41.1.2.3.1.3";
        }

        leaf clogHistMsgName {
          type snmpv2-tc:DisplayString {
            length "1..30";
          }
          description
           "A textual identification for the message type.
            A facility name in conjunction with a message name
            uniquely identifies a message type.";
          smiv2:max-access "read-only";
          smiv2:oid "1.3.6.1.4.1.9.9.41.1.2.3.1.4";
        }

        leaf clogHistMsgText {
          type snmpv2-tc:DisplayString {
            length "1..255";
          }
          description
           "The text of the message.  If the text of the message
            exceeds 255 bytes, the message will be truncated to
            254 bytes and a '*' character will be appended -
            indicating that the message has been truncated.";
          smiv2:max-access "read-only";
          smiv2:oid "1.3.6.1.4.1.9.9.41.1.2.3.1.5";
        }

        leaf clogHistTimestamp {
          type yang:timestamp;
          description
           "The value of sysUpTime when this message was
            generated.";
          smiv2:max-access "read-only";
          smiv2:oid "1.3.6.1.4.1.9.9.41.1.2.3.1.6";
        }
      }
    }

    container clogServerConfigTable {
      description
       "This table contains entries that allow application
        to configure syslog servers for the system.
        
        The maximum number of entries that can be created
        for this table is limited by the object
        clogMaxServers.";
      smiv2:oid "1.3.6.1.4.1.9.9.41.1.3.2";

      list clogServerConfigEntry {
        key "clogServerAddrType clogServerAddr";
        description
         "An entry containing information about syslog servers
          configured for the system.";
        smiv2:oid "1.3.6.1.4.1.9.9.41.1.3.2.1";

        leaf clogServerAddrType {
          type inet-address:InetAddressType;
          description
           "The type of Internet address of this syslog server.";
          smiv2:max-access "not-accessible";
          smiv2:oid "1.3.6.1.4.1.9.9.41.1.3.2.1.1";
        }

        leaf clogServerAddr {
          type inet-address:InetAddress {
            length "0..64";
          }
          description
           "The Internet address of this syslog server.
            The type of this address is determined by the
            value of the clogServerAddrType object.";
          smiv2:max-access "not-accessible";
          smiv2:oid "1.3.6.1.4.1.9.9.41.1.3.2.1.2";
        }

        leaf clogServerStatus {
          type snmpv2-tc:RowStatus;
          description
           "The status object used to manage rows in this table.
            
            A row may only be created by setting this object to
            'createAndGo'.
            
            A row may only be deleted by setting this object to
            'destroy'.";
          smiv2:max-access "read-write";
          smiv2:oid "1.3.6.1.4.1.9.9.41.1.3.2.1.3";
        }
      }
    }
  }

  notification clogMessageGenerated {
    description
     "When a syslog message is generated by the device a
      clogMessageGenerated notification is sent.  The
      sending of these notifications can be enabled/disabled
      via the clogNotificationsEnabled object.";
    smiv2:oid "1.3.6.1.4.1.9.9.41.2.0.1";

    container object-1 {

      leaf clogHistIndex {
        type leafref {
          path "/CISCO-SYSLOG-MIB:CISCO-SYSLOG-MIB/CISCO-SYSLOG-MIB:clogHistoryTable/CISCO-SYSLOG-MIB:clogHistoryEntry/CISCO-SYSLOG-MIB:clogHistIndex";
        }
      }

      leaf clogHistFacility {
        type leafref {
          path "/CISCO-SYSLOG-MIB:CISCO-SYSLOG-MIB/CISCO-SYSLOG-MIB:clogHistoryTable/CISCO-SYSLOG-MIB:clogHistoryEntry/CISCO-SYSLOG-MIB:clogHistFacility";
        }
      }
    }

    container object-2 {

      leaf clogHistIndex {
        type leafref {
          path "/CISCO-SYSLOG-MIB:CISCO-SYSLOG-MIB/CISCO-SYSLOG-MIB:clogHistoryTable/CISCO-SYSLOG-MIB:clogHistoryEntry/CISCO-SYSLOG-MIB:clogHistIndex";
        }
      }

      leaf clogHistSeverity {
        type leafref {
          path "/CISCO-SYSLOG-MIB:CISCO-SYSLOG-MIB/CISCO-SYSLOG-MIB:clogHistoryTable/CISCO-SYSLOG-MIB:clogHistoryEntry/CISCO-SYSLOG-MIB:clogHistSeverity";
        }
      }
    }

    container object-3 {

      leaf clogHistIndex {
        type leafref {
          path "/CISCO-SYSLOG-MIB:CISCO-SYSLOG-MIB/CISCO-SYSLOG-MIB:clogHistoryTable/CISCO-SYSLOG-MIB:clogHistoryEntry/CISCO-SYSLOG-MIB:clogHistIndex";
        }
      }

      leaf clogHistMsgName {
        type leafref {
          path "/CISCO-SYSLOG-MIB:CISCO-SYSLOG-MIB/CISCO-SYSLOG-MIB:clogHistoryTable/CISCO-SYSLOG-MIB:clogHistoryEntry/CISCO-SYSLOG-MIB:clogHistMsgName";
        }
      }
    }

    container object-4 {

      leaf clogHistIndex {
        type leafref {
          path "/CISCO-SYSLOG-MIB:CISCO-SYSLOG-MIB/CISCO-SYSLOG-MIB:clogHistoryTable/CISCO-SYSLOG-MIB:clogHistoryEntry/CISCO-SYSLOG-MIB:clogHistIndex";
        }
      }

      leaf clogHistMsgText {
        type leafref {
          path "/CISCO-SYSLOG-MIB:CISCO-SYSLOG-MIB/CISCO-SYSLOG-MIB:clogHistoryTable/CISCO-SYSLOG-MIB:clogHistoryEntry/CISCO-SYSLOG-MIB:clogHistMsgText";
        }
      }
    }

    container object-5 {

      leaf clogHistIndex {
        type leafref {
          path "/CISCO-SYSLOG-MIB:CISCO-SYSLOG-MIB/CISCO-SYSLOG-MIB:clogHistoryTable/CISCO-SYSLOG-MIB:clogHistoryEntry/CISCO-SYSLOG-MIB:clogHistIndex";
        }
      }

      leaf clogHistTimestamp {
        type leafref {
          path "/CISCO-SYSLOG-MIB:CISCO-SYSLOG-MIB/CISCO-SYSLOG-MIB:clogHistoryTable/CISCO-SYSLOG-MIB:clogHistoryEntry/CISCO-SYSLOG-MIB:clogHistTimestamp";
        }
      }
    }
  }

  smiv2:alias "ciscoSyslogMIB" {
    smiv2:oid "1.3.6.1.4.1.9.9.41";
  }

  smiv2:alias "ciscoSyslogMIBObjects" {
    smiv2:oid "1.3.6.1.4.1.9.9.41.1";
  }

  smiv2:alias "clogBasic" {
    smiv2:oid "1.3.6.1.4.1.9.9.41.1.1";
  }

  smiv2:alias "clogHistory" {
    smiv2:oid "1.3.6.1.4.1.9.9.41.1.2";
  }

  smiv2:alias "clogServer" {
    smiv2:oid "1.3.6.1.4.1.9.9.41.1.3";
  }

  smiv2:alias "ciscoSyslogMIBNotificationPrefix" {
    smiv2:oid "1.3.6.1.4.1.9.9.41.2";
  }

  smiv2:alias "ciscoSyslogMIBNotifications" {
    smiv2:oid "1.3.6.1.4.1.9.9.41.2.0";
  }

  smiv2:alias "ciscoSyslogMIBConformance" {
    smiv2:oid "1.3.6.1.4.1.9.9.41.3";
  }

  smiv2:alias "ciscoSyslogMIBCompliances" {
    smiv2:oid "1.3.6.1.4.1.9.9.41.3.1";
  }

  smiv2:alias "ciscoSyslogMIBGroups" {
    smiv2:oid "1.3.6.1.4.1.9.9.41.3.2";
  }

}
