/*
 * Generated by confdc --mib2yang-std
 * Source: mgmt/dmi/model/common/mib-source/BRIDGE-MIB.mib
 */
/*
 * This YANG module has been generated by smidump 0.5.0:
 *
 *      smidump -f yang BRIDGE-MIB
 *
 * Do not edit. Edit the source file instead!
 */

module BRIDGE-MIB {

  namespace "urn:ietf:params:xml:ns:yang:smiv2:BRIDGE-MIB";
  prefix BRIDGE-MIB;

  import IF-MIB {
    prefix "if-mib";
  }

  import ietf-yang-smiv2 {
    prefix "smiv2";
  }

  import ietf-yang-types {
    prefix "yang";
  }

  organization
   "IETF Bridge MIB Working Group";

  contact
   "Email: bridge-mib@ietf.org
    
    K.C. Norseth (Editor)
    L-3 Communications
    Tel: +1 801-594-2809
    Email: kenyon.c.norseth@L-3com.com
    Postal: 640 N. 2200 West.
    Salt Lake City, Utah 84116-0850
    
    Les Bell (Editor)
    3Com Europe Limited
    Phone: +44 1442 438025
    Email: elbell@ntlworld.com
    Postal: 3Com Centre, Boundary Way
    Hemel Hempstead
    Herts.  HP2 7YU
    UK
    
    Send comments to <bridge-mib@ietf.org>";

  description
   "The Bridge MIB module for managing devices that support
    IEEE 802.1D.
    
    Copyright (C) The Internet Society (2005).  This version of
    this MIB module is part of RFC 4188; see the RFC itself for
    full legal notices.";

  revision 2005-09-19 {
    description
     "Third revision, published as part of RFC 4188.
      
      The MIB module has been converted to SMIv2 format.
      Conformance statements have been added and some
      description and reference clauses have been updated.
      
      The object dot1dStpPortPathCost32 was added to
      support IEEE 802.1t and the permissible values of
      dot1dStpPriority and dot1dStpPortPriority have been
      clarified for bridges supporting IEEE 802.1t or
      IEEE 802.1w.
      
      The interpretation of dot1dStpTimeSinceTopologyChange
      has been clarified for bridges supporting the Rapid
      Spanning Tree Protocol (RSTP).";
  }

  revision 1993-07-31 {
    description
     "Second revision, published as part of RFC 1493.";
  }

  revision 1991-12-31 {
    description
     "Initial revision, published as part of RFC 1286.";
  }

  typedef BridgeId {
    type binary {
      length "8";
    }
    description
     "The Bridge-Identifier, as used in the Spanning Tree
      Protocol, to uniquely identify a bridge.  Its first two
      octets (in network byte order) contain a priority value,
      and its last 6 octets contain the MAC address used to
      refer to a bridge in a unique fashion (typically, the
      numerically smallest MAC address of all ports on the
      bridge).";
  }

  typedef Timeout {
    type int32;
    description
     "A Spanning Tree Protocol (STP) timer in units of 1/100
      seconds.  Several objects in this MIB module represent
      values of timers used by the Spanning Tree Protocol.
      In this MIB, these timers have values in units of
      hundredths of a second (i.e., 1/100 secs).
      
      These timers, when stored in a Spanning Tree Protocol's
      BPDU, are in units of 1/256 seconds.  Note, however, that
      802.1D-1998 specifies a settable granularity of no more
      than one second for these timers.  To avoid ambiguity,
      a conversion algorithm is defined below for converting
      between the different units, which ensures a timer's
      value is not distorted by multiple conversions.
      
      To convert a Timeout value into a value in units of
      1/256 seconds, the following algorithm should be used:
      
          b = floor( (n * 256) / 100)
      
      where:
          floor   =  quotient [ignore remainder]
          n is the value in 1/100 second units
          b is the value in 1/256 second units
      
      To convert the value from 1/256 second units back to
      1/100 seconds, the following algorithm should be used:
      
          n = ceiling( (b * 100) / 256)
      
      where:
          ceiling = quotient [if remainder is 0], or
                    quotient + 1 [if remainder is nonzero]
          n is the value in 1/100 second units
      
          b is the value in 1/256 second units
      
      Note: it is important that the arithmetic operations are
      done in the order specified (i.e., multiply first,
      divide second).";
    smiv2:display-hint "d";
  }


  container BRIDGE-MIB {
    config false;

    container dot1dBase {
      smiv2:oid "1.3.6.1.2.1.17.1";

      leaf dot1dBaseBridgeAddress {
        type yang:mac-address;
        description
         "The MAC address used by this bridge when it must be
          referred to in a unique fashion.  It is recommended
          that this be the numerically smallest MAC address of
          all ports that belong to this bridge.  However, it is only
          
          required to be unique.  When concatenated with
          dot1dStpPriority, a unique BridgeIdentifier is formed,
          which is used in the Spanning Tree Protocol.";
        reference
         "IEEE 802.1D-1998: clauses 14.4.1.1.3 and 7.12.5";
        smiv2:max-access "read-only";
        smiv2:oid "1.3.6.1.2.1.17.1.1";
      }

      leaf dot1dBaseNumPorts {
        type int32;
        units "ports";
        description
         "The number of ports controlled by this bridging
          entity.";
        reference
         "IEEE 802.1D-1998: clause 14.4.1.1.3";
        smiv2:max-access "read-only";
        smiv2:oid "1.3.6.1.2.1.17.1.2";
      }

      leaf dot1dBaseType {
        type enumeration {
          enum "unknown" {
            value "1";
          }
          enum "transparent-only" {
            value "2";
          }
          enum "sourceroute-only" {
            value "3";
          }
          enum "srt" {
            value "4";
          }
        }
        description
         "Indicates what type of bridging this bridge can
          perform.  If a bridge is actually performing a
          certain type of bridging, this will be indicated by
          entries in the port table for the given type.";
        smiv2:max-access "read-only";
        smiv2:oid "1.3.6.1.2.1.17.1.3";
      }
    }

    container dot1dStp {
      smiv2:oid "1.3.6.1.2.1.17.2";

      leaf dot1dStpProtocolSpecification {
        type enumeration {
          enum "unknown" {
            value "1";
          }
          enum "decLb100" {
            value "2";
          }
          enum "ieee8021d" {
            value "3";
          }
        }
        description
         "An indication of what version of the Spanning Tree
          Protocol is being run.  The value 'decLb100(2)'
          indicates the DEC LANbridge 100 Spanning Tree protocol.
          IEEE 802.1D implementations will return 'ieee8021d(3)'.
          If future versions of the IEEE Spanning Tree Protocol
          that are incompatible with the current version
          are released a new value will be defined.";
        smiv2:max-access "read-only";
        smiv2:oid "1.3.6.1.2.1.17.2.1";
      }

      leaf dot1dStpPriority {
        type int32 {
          range "0..65535";
        }
        description
         "The value of the write-able portion of the Bridge ID
          (i.e., the first two octets of the (8 octet long) Bridge
          ID).  The other (last) 6 octets of the Bridge ID are
          given by the value of dot1dBaseBridgeAddress.
          On bridges supporting IEEE 802.1t or IEEE 802.1w,
          permissible values are 0-61440, in steps of 4096.";
        reference
         "IEEE 802.1D-1998 clause 8.10.2, Table 8-4,
          IEEE 802.1t clause 8.10.2, Table 8-4, clause 14.3.";
        smiv2:max-access "read-write";
        smiv2:oid "1.3.6.1.2.1.17.2.2";
      }

      leaf dot1dStpTimeSinceTopologyChange {
        type yang:timeticks;
        units "centi-seconds";
        description
         "The time (in hundredths of a second) since the
          last time a topology change was detected by the
          bridge entity.
          For RSTP, this reports the time since the tcWhile
          timer for any port on this Bridge was nonzero.";
        reference
         "IEEE 802.1D-1998 clause 14.8.1.1.,
          IEEE 802.1w clause 14.8.1.1.";
        smiv2:max-access "read-only";
        smiv2:oid "1.3.6.1.2.1.17.2.3";
      }

      leaf dot1dStpTopChanges {
        type yang:counter32;
        description
         "The total number of topology changes detected by
          this bridge since the management entity was last
          reset or initialized.";
        reference
         "IEEE 802.1D-1998 clause 14.8.1.1.";
        smiv2:max-access "read-only";
        smiv2:oid "1.3.6.1.2.1.17.2.4";
      }

      leaf dot1dStpDesignatedRoot {
        type BRIDGE-MIB:BridgeId;
        description
         "The bridge identifier of the root of the spanning
          tree, as determined by the Spanning Tree Protocol,
          as executed by this node.  This value is used as
          the Root Identifier parameter in all Configuration
          Bridge PDUs originated by this node.";
        reference
         "IEEE 802.1D-1998: clause 8.5.3.1";
        smiv2:max-access "read-only";
        smiv2:oid "1.3.6.1.2.1.17.2.5";
      }

      leaf dot1dStpRootCost {
        type int32;
        description
         "The cost of the path to the root as seen from
          this bridge.";
        reference
         "IEEE 802.1D-1998: clause 8.5.3.2";
        smiv2:max-access "read-only";
        smiv2:oid "1.3.6.1.2.1.17.2.6";
      }

      leaf dot1dStpRootPort {
        type int32;
        description
         "The port number of the port that offers the lowest
          cost path from this bridge to the root bridge.";
        reference
         "IEEE 802.1D-1998: clause 8.5.3.3";
        smiv2:max-access "read-only";
        smiv2:oid "1.3.6.1.2.1.17.2.7";
      }

      leaf dot1dStpMaxAge {
        type BRIDGE-MIB:Timeout;
        units "centi-seconds";
        description
         "The maximum age of Spanning Tree Protocol information
          learned from the network on any port before it is
          discarded, in units of hundredths of a second.  This is
          the actual value that this bridge is currently using.";
        reference
         "IEEE 802.1D-1998: clause 8.5.3.4";
        smiv2:max-access "read-only";
        smiv2:oid "1.3.6.1.2.1.17.2.8";
      }

      leaf dot1dStpHelloTime {
        type BRIDGE-MIB:Timeout;
        units "centi-seconds";
        description
         "The amount of time between the transmission of
          Configuration bridge PDUs by this node on any port when
          it is the root of the spanning tree, or trying to become
          so, in units of hundredths of a second.  This is the
          actual value that this bridge is currently using.";
        reference
         "IEEE 802.1D-1998: clause 8.5.3.5";
        smiv2:max-access "read-only";
        smiv2:oid "1.3.6.1.2.1.17.2.9";
      }

      leaf dot1dStpHoldTime {
        type int32;
        units "centi-seconds";
        description
         "This time value determines the interval length
          during which no more than two Configuration bridge
          PDUs shall be transmitted by this node, in units
          of hundredths of a second.";
        reference
         "IEEE 802.1D-1998: clause 8.5.3.14";
        smiv2:max-access "read-only";
        smiv2:oid "1.3.6.1.2.1.17.2.10";
      }

      leaf dot1dStpForwardDelay {
        type BRIDGE-MIB:Timeout;
        units "centi-seconds";
        description
         "This time value, measured in units of hundredths of a
          second, controls how fast a port changes its spanning
          state when moving towards the Forwarding state.  The
          value determines how long the port stays in each of the
          Listening and Learning states, which precede the
          Forwarding state.  This value is also used when a
          topology change has been detected and is underway, to
          age all dynamic entries in the Forwarding Database.
          [Note that this value is the one that this bridge is
          currently using, in contrast to
          dot1dStpBridgeForwardDelay, which is the value that this
          bridge and all others would start using if/when this
          bridge were to become the root.]";
        reference
         "IEEE 802.1D-1998: clause 8.5.3.6";
        smiv2:max-access "read-only";
        smiv2:oid "1.3.6.1.2.1.17.2.11";
      }

      leaf dot1dStpBridgeMaxAge {
        type BRIDGE-MIB:Timeout {
          range "600..4000";
        }
        units "centi-seconds";
        description
         "The value that all bridges use for MaxAge when this
          bridge is acting as the root.  Note that 802.1D-1998
          specifies that the range for this parameter is related
          to the value of dot1dStpBridgeHelloTime.  The
          granularity of this timer is specified by 802.1D-1998 to
          be 1 second.  An agent may return a badValue error if a
          set is attempted to a value that is not a whole number
          of seconds.";
        reference
         "IEEE 802.1D-1998: clause 8.5.3.8";
        smiv2:max-access "read-write";
        smiv2:oid "1.3.6.1.2.1.17.2.12";
      }

      leaf dot1dStpBridgeHelloTime {
        type BRIDGE-MIB:Timeout {
          range "100..1000";
        }
        units "centi-seconds";
        description
         "The value that all bridges use for HelloTime when this
          bridge is acting as the root.  The granularity of this
          timer is specified by 802.1D-1998 to be 1 second.  An
          agent may return a badValue error if a set is attempted
          
          to a value that is not a whole number of seconds.";
        reference
         "IEEE 802.1D-1998: clause 8.5.3.9";
        smiv2:max-access "read-write";
        smiv2:oid "1.3.6.1.2.1.17.2.13";
      }

      leaf dot1dStpBridgeForwardDelay {
        type BRIDGE-MIB:Timeout {
          range "400..3000";
        }
        units "centi-seconds";
        description
         "The value that all bridges use for ForwardDelay when
          this bridge is acting as the root.  Note that
          802.1D-1998 specifies that the range for this parameter
          is related to the value of dot1dStpBridgeMaxAge.  The
          granularity of this timer is specified by 802.1D-1998 to
          be 1 second.  An agent may return a badValue error if a
          set is attempted to a value that is not a whole number
          of seconds.";
        reference
         "IEEE 802.1D-1998: clause 8.5.3.10";
        smiv2:max-access "read-write";
        smiv2:oid "1.3.6.1.2.1.17.2.14";
      }
    }

    container dot1dTp {
      smiv2:oid "1.3.6.1.2.1.17.4";

      leaf dot1dTpLearnedEntryDiscards {
        type yang:counter32;
        description
         "The total number of Forwarding Database entries that
          have been or would have been learned, but have been
          discarded due to a lack of storage space in the
          Forwarding Database.  If this counter is increasing, it
          indicates that the Forwarding Database is regularly
          becoming full (a condition that has unpleasant
          performance effects on the subnetwork).  If this counter
          has a significant value but is not presently increasing,
          it indicates that the problem has been occurring but is
          not persistent.";
        reference
         "IEEE 802.1D-1998: clause 14.7.1.1.3";
        smiv2:max-access "read-only";
        smiv2:oid "1.3.6.1.2.1.17.4.1";
      }

      leaf dot1dTpAgingTime {
        type int32 {
          range "10..1000000";
        }
        units "seconds";
        description
         "The timeout period in seconds for aging out
          dynamically-learned forwarding information.
          802.1D-1998 recommends a default of 300 seconds.";
        reference
         "IEEE 802.1D-1998: clause 14.7.1.1.3";
        smiv2:max-access "read-write";
        smiv2:oid "1.3.6.1.2.1.17.4.2";
      }
    }

    container dot1dBasePortTable {
      description
       "A table that contains generic information about every
        port that is associated with this bridge.  Transparent,
        source-route, and srt ports are included.";
      smiv2:oid "1.3.6.1.2.1.17.1.4";

      list dot1dBasePortEntry {
        key "dot1dBasePort";
        description
         "A list of information for each port of the bridge.";
        reference
         "IEEE 802.1D-1998: clause 14.4.2, 14.6.1";
        smiv2:oid "1.3.6.1.2.1.17.1.4.1";

        leaf dot1dBasePort {
          type int32 {
            range "1..65535";
          }
          description
           "The port number of the port for which this entry
            contains bridge management information.";
          smiv2:max-access "read-only";
          smiv2:oid "1.3.6.1.2.1.17.1.4.1.1";
        }

        leaf dot1dBasePortIfIndex {
          type if-mib:InterfaceIndex;
          description
           "The value of the instance of the ifIndex object,
            defined in IF-MIB, for the interface corresponding
            to this port.";
          smiv2:max-access "read-only";
          smiv2:oid "1.3.6.1.2.1.17.1.4.1.2";
        }

        leaf dot1dBasePortCircuit {
          type yang:object-identifier-128;
          description
           "For a port that (potentially) has the same value of
            dot1dBasePortIfIndex as another port on the same bridge.
            This object contains the name of an object instance
            unique to this port.  For example, in the case where
            multiple ports correspond one-to-one with multiple X.25
            virtual circuits, this value might identify an (e.g.,
            the first) object instance associated with the X.25
            virtual circuit corresponding to this port.
            
            For a port which has a unique value of
            dot1dBasePortIfIndex, this object can have the value
            { 0 0 }.";
          smiv2:max-access "read-only";
          smiv2:oid "1.3.6.1.2.1.17.1.4.1.3";
        }

        leaf dot1dBasePortDelayExceededDiscards {
          type yang:counter32;
          description
           "The number of frames discarded by this port due
            to excessive transit delay through the bridge.  It
            is incremented by both transparent and source
            route bridges.";
          reference
           "IEEE 802.1D-1998: clause 14.6.1.1.3";
          smiv2:max-access "read-only";
          smiv2:oid "1.3.6.1.2.1.17.1.4.1.4";
        }

        leaf dot1dBasePortMtuExceededDiscards {
          type yang:counter32;
          description
           "The number of frames discarded by this port due
            to an excessive size.  It is incremented by both
            transparent and source route bridges.";
          reference
           "IEEE 802.1D-1998: clause 14.6.1.1.3";
          smiv2:max-access "read-only";
          smiv2:oid "1.3.6.1.2.1.17.1.4.1.5";
        }
      }
    }

    container dot1dStpPortTable {
      description
       "A table that contains port-specific information
        for the Spanning Tree Protocol.";
      smiv2:oid "1.3.6.1.2.1.17.2.15";

      list dot1dStpPortEntry {
        key "dot1dStpPort";
        description
         "A list of information maintained by every port about
          the Spanning Tree Protocol state for that port.";
        smiv2:oid "1.3.6.1.2.1.17.2.15.1";

        leaf dot1dStpPort {
          type int32 {
            range "1..65535";
          }
          description
           "The port number of the port for which this entry
            contains Spanning Tree Protocol management information.";
          reference
           "IEEE 802.1D-1998: clause 14.8.2.1.2";
          smiv2:max-access "read-only";
          smiv2:oid "1.3.6.1.2.1.17.2.15.1.1";
        }

        leaf dot1dStpPortPriority {
          type int32 {
            range "0..255";
          }
          description
           "The value of the priority field that is contained in
            the first (in network byte order) octet of the (2 octet
            long) Port ID.  The other octet of the Port ID is given
            by the value of dot1dStpPort.
            On bridges supporting IEEE 802.1t or IEEE 802.1w,
            permissible values are 0-240, in steps of 16.";
          reference
           "IEEE 802.1D-1998 clause 8.10.2, Table 8-4,
            
            IEEE 802.1t clause 8.10.2, Table 8-4, clause 14.3.";
          smiv2:max-access "read-write";
          smiv2:oid "1.3.6.1.2.1.17.2.15.1.2";
        }

        leaf dot1dStpPortState {
          type enumeration {
            enum "disabled" {
              value "1";
            }
            enum "blocking" {
              value "2";
            }
            enum "listening" {
              value "3";
            }
            enum "learning" {
              value "4";
            }
            enum "forwarding" {
              value "5";
            }
            enum "broken" {
              value "6";
            }
          }
          description
           "The port's current state, as defined by application of
            the Spanning Tree Protocol.  This state controls what
            action a port takes on reception of a frame.  If the
            bridge has detected a port that is malfunctioning, it
            will place that port into the broken(6) state.  For
            ports that are disabled (see dot1dStpPortEnable), this
            object will have a value of disabled(1).";
          reference
           "IEEE 802.1D-1998: clause 8.5.5.2";
          smiv2:max-access "read-only";
          smiv2:oid "1.3.6.1.2.1.17.2.15.1.3";
        }

        leaf dot1dStpPortEnable {
          type enumeration {
            enum "enabled" {
              value "1";
            }
            enum "disabled" {
              value "2";
            }
          }
          description
           "The enabled/disabled status of the port.";
          reference
           "IEEE 802.1D-1998: clause 8.5.5.2";
          smiv2:max-access "read-write";
          smiv2:oid "1.3.6.1.2.1.17.2.15.1.4";
        }

        leaf dot1dStpPortPathCost {
          type int32 {
            range "1..65535";
          }
          description
           "The contribution of this port to the path cost of
            paths towards the spanning tree root which include
            this port.  802.1D-1998 recommends that the default
            value of this parameter be in inverse proportion to
            
            the speed of the attached LAN.
            
            New implementations should support dot1dStpPortPathCost32.
            If the port path costs exceeds the maximum value of this
            object then this object should report the maximum value,
            namely 65535.  Applications should try to read the
            dot1dStpPortPathCost32 object if this object reports
            the maximum value.";
          reference
           "IEEE 802.1D-1998: clause 8.5.5.3";
          smiv2:max-access "read-write";
          smiv2:oid "1.3.6.1.2.1.17.2.15.1.5";
        }

        leaf dot1dStpPortDesignatedRoot {
          type BRIDGE-MIB:BridgeId;
          description
           "The unique Bridge Identifier of the Bridge
            recorded as the Root in the Configuration BPDUs
            transmitted by the Designated Bridge for the
            segment to which the port is attached.";
          reference
           "IEEE 802.1D-1998: clause 8.5.5.4";
          smiv2:max-access "read-only";
          smiv2:oid "1.3.6.1.2.1.17.2.15.1.6";
        }

        leaf dot1dStpPortDesignatedCost {
          type int32;
          description
           "The path cost of the Designated Port of the segment
            connected to this port.  This value is compared to the
            Root Path Cost field in received bridge PDUs.";
          reference
           "IEEE 802.1D-1998: clause 8.5.5.5";
          smiv2:max-access "read-only";
          smiv2:oid "1.3.6.1.2.1.17.2.15.1.7";
        }

        leaf dot1dStpPortDesignatedBridge {
          type BRIDGE-MIB:BridgeId;
          description
           "The Bridge Identifier of the bridge that this
            port considers to be the Designated Bridge for
            this port's segment.";
          reference
           "IEEE 802.1D-1998: clause 8.5.5.6";
          smiv2:max-access "read-only";
          smiv2:oid "1.3.6.1.2.1.17.2.15.1.8";
        }

        leaf dot1dStpPortDesignatedPort {
          type binary {
            length "2";
          }
          description
           "The Port Identifier of the port on the Designated
            Bridge for this port's segment.";
          reference
           "IEEE 802.1D-1998: clause 8.5.5.7";
          smiv2:max-access "read-only";
          smiv2:oid "1.3.6.1.2.1.17.2.15.1.9";
        }

        leaf dot1dStpPortForwardTransitions {
          type yang:counter32;
          description
           "The number of times this port has transitioned
            from the Learning state to the Forwarding state.";
          smiv2:max-access "read-only";
          smiv2:oid "1.3.6.1.2.1.17.2.15.1.10";
        }

        leaf dot1dStpPortPathCost32 {
          type int32 {
            range "1..200000000";
          }
          description
           "The contribution of this port to the path cost of
            paths towards the spanning tree root which include
            this port.  802.1D-1998 recommends that the default
            value of this parameter be in inverse proportion to
            the speed of the attached LAN.
            
            This object replaces dot1dStpPortPathCost to support
            IEEE 802.1t.";
          reference
           "IEEE 802.1t clause 8.10.2, Table 8-5.";
          smiv2:max-access "read-write";
          smiv2:oid "1.3.6.1.2.1.17.2.15.1.11";
        }
      }
    }

    container dot1dTpFdbTable {
      description
       "A table that contains information about unicast
        entries for which the bridge has forwarding and/or
        filtering information.  This information is used
        by the transparent bridging function in
        determining how to propagate a received frame.";
      smiv2:oid "1.3.6.1.2.1.17.4.3";

      list dot1dTpFdbEntry {
        key "dot1dTpFdbAddress";
        description
         "Information about a specific unicast MAC address
          for which the bridge has some forwarding and/or
          filtering information.";
        smiv2:oid "1.3.6.1.2.1.17.4.3.1";

        leaf dot1dTpFdbAddress {
          type yang:mac-address;
          description
           "A unicast MAC address for which the bridge has
            forwarding and/or filtering information.";
          reference
           "IEEE 802.1D-1998: clause 7.9.1, 7.9.2";
          smiv2:max-access "read-only";
          smiv2:oid "1.3.6.1.2.1.17.4.3.1.1";
        }

        leaf dot1dTpFdbPort {
          type int32;
          description
           "Either the value '0', or the port number of the port on
            which a frame having a source address equal to the value
            of the corresponding instance of dot1dTpFdbAddress has
            been seen.  A value of '0' indicates that the port
            number has not been learned, but that the bridge does
            have some forwarding/filtering information about this
            address (e.g., in the dot1dStaticTable).  Implementors
            are encouraged to assign the port value to this object
            whenever it is learned, even for addresses for which the
            corresponding value of dot1dTpFdbStatus is not
            learned(3).";
          smiv2:max-access "read-only";
          smiv2:oid "1.3.6.1.2.1.17.4.3.1.2";
        }

        leaf dot1dTpFdbStatus {
          type enumeration {
            enum "other" {
              value "1";
            }
            enum "invalid" {
              value "2";
            }
            enum "learned" {
              value "3";
            }
            enum "self" {
              value "4";
            }
            enum "mgmt" {
              value "5";
            }
          }
          description
           "The status of this entry.  The meanings of the
            values are:
                other(1) - none of the following.  This would
                    include the case where some other MIB object
                    (not the corresponding instance of
                    dot1dTpFdbPort, nor an entry in the
                    dot1dStaticTable) is being used to determine if
                    and how frames addressed to the value of the
                    corresponding instance of dot1dTpFdbAddress are
                    being forwarded.
                invalid(2) - this entry is no longer valid (e.g.,
                    it was learned but has since aged out), but has
                    not yet been flushed from the table.
                learned(3) - the value of the corresponding instance
                    of dot1dTpFdbPort was learned, and is being
                    used.
                self(4) - the value of the corresponding instance of
                    dot1dTpFdbAddress represents one of the bridge's
                    addresses.  The corresponding instance of
                    dot1dTpFdbPort indicates which of the bridge's
                    ports has this address.
                mgmt(5) - the value of the corresponding instance of
                    dot1dTpFdbAddress is also the value of an
                    existing instance of dot1dStaticAddress.";
          smiv2:max-access "read-only";
          smiv2:oid "1.3.6.1.2.1.17.4.3.1.3";
        }
      }
    }

    container dot1dTpPortTable {
      description
       "A table that contains information about every port that
        is associated with this transparent bridge.";
      smiv2:oid "1.3.6.1.2.1.17.4.4";

      list dot1dTpPortEntry {
        key "dot1dTpPort";
        description
         "A list of information for each port of a transparent
          bridge.";
        smiv2:oid "1.3.6.1.2.1.17.4.4.1";

        leaf dot1dTpPort {
          type int32 {
            range "1..65535";
          }
          description
           "The port number of the port for which this entry
            contains Transparent bridging management information.";
          smiv2:max-access "read-only";
          smiv2:oid "1.3.6.1.2.1.17.4.4.1.1";
        }

        leaf dot1dTpPortMaxInfo {
          type int32;
          units "bytes";
          description
           "The maximum size of the INFO (non-MAC) field that
            
            this port will receive or transmit.";
          smiv2:max-access "read-only";
          smiv2:oid "1.3.6.1.2.1.17.4.4.1.2";
        }

        leaf dot1dTpPortInFrames {
          type yang:counter32;
          units "frames";
          description
           "The number of frames that have been received by this
            port from its segment.  Note that a frame received on the
            interface corresponding to this port is only counted by
            this object if and only if it is for a protocol being
            processed by the local bridging function, including
            bridge management frames.";
          reference
           "IEEE 802.1D-1998: clause 14.6.1.1.3";
          smiv2:max-access "read-only";
          smiv2:oid "1.3.6.1.2.1.17.4.4.1.3";
        }

        leaf dot1dTpPortOutFrames {
          type yang:counter32;
          units "frames";
          description
           "The number of frames that have been transmitted by this
            port to its segment.  Note that a frame transmitted on
            the interface corresponding to this port is only counted
            by this object if and only if it is for a protocol being
            processed by the local bridging function, including
            bridge management frames.";
          reference
           "IEEE 802.1D-1998: clause 14.6.1.1.3";
          smiv2:max-access "read-only";
          smiv2:oid "1.3.6.1.2.1.17.4.4.1.4";
        }

        leaf dot1dTpPortInDiscards {
          type yang:counter32;
          units "frames";
          description
           "Count of received valid frames that were discarded
            (i.e., filtered) by the Forwarding Process.";
          reference
           "IEEE 802.1D-1998: clause 14.6.1.1.3";
          smiv2:max-access "read-only";
          smiv2:oid "1.3.6.1.2.1.17.4.4.1.5";
        }
      }
    }

    container dot1dStaticTable {
      description
       "A table containing filtering information configured
        into the bridge by (local or network) management
        specifying the set of ports to which frames received
        from specific ports and containing specific destination
        addresses are allowed to be forwarded.  The value of
        zero in this table, as the port number from which frames
        with a specific destination address are received, is
        used to specify all ports for which there is no specific
        entry in this table for that particular destination
        address.  Entries are valid for unicast and for
        group/broadcast addresses.";
      reference
       "IEEE 802.1D-1998: clause 14.7.2";
      smiv2:oid "1.3.6.1.2.1.17.5.1";

      list dot1dStaticEntry {
        key "dot1dStaticAddress dot1dStaticReceivePort";
        description
         "Filtering information configured into the bridge by
          (local or network) management specifying the set of
          ports to which frames received from a specific port and
          containing a specific destination address are allowed to
          be forwarded.";
        reference
         "IEEE 802.1D-1998: clause 14.7.2";
        smiv2:oid "1.3.6.1.2.1.17.5.1.1";

        leaf dot1dStaticAddress {
          type yang:mac-address;
          description
           "The destination MAC address in a frame to which this
            entry's filtering information applies.  This object can
            take the value of a unicast address, a group address, or
            the broadcast address.";
          reference
           "IEEE 802.1D-1998: clause 7.9.1, 7.9.2";
          smiv2:max-access "read-write";
          smiv2:oid "1.3.6.1.2.1.17.5.1.1.1";
        }

        leaf dot1dStaticReceivePort {
          type int32 {
            range "0..65535";
          }
          description
           "Either the value '0', or the port number of the port
            from which a frame must be received in order for this
            entry's filtering information to apply.  A value of zero
            indicates that this entry applies on all ports of the
            bridge for which there is no other applicable entry.";
          smiv2:max-access "read-write";
          smiv2:oid "1.3.6.1.2.1.17.5.1.1.2";
        }

        leaf dot1dStaticAllowedToGoTo {
          type binary {
            length "0..512";
          }
          description
           "The set of ports to which frames received from a
            specific port and destined for a specific MAC address,
            are allowed to be forwarded.  Each octet within the
            value of this object specifies a set of eight ports,
            with the first octet specifying ports 1 through 8, the
            second octet specifying ports 9 through 16, etc.  Within
            each octet, the most significant bit represents the
            lowest numbered port, and the least significant bit
            represents the highest numbered port.  Thus, each port
            of the bridge is represented by a single bit within the
            value of this object.  If that bit has a value of '1',
            then that port is included in the set of ports; the port
            is not included if its bit has a value of '0'.  (Note
            that the setting of the bit corresponding to the port
            from which a frame is received is irrelevant.)  The
            default value of this object is a string of ones of
            appropriate length.
            
            The value of this object may exceed the required minimum
            maximum message size of some SNMP transport (484 bytes,
            in the case of SNMP over UDP, see RFC 3417, section 3.2).
            SNMP engines on bridges supporting a large number of
            ports must support appropriate maximum message sizes.";
          smiv2:max-access "read-write";
          smiv2:oid "1.3.6.1.2.1.17.5.1.1.3";
        }

        leaf dot1dStaticStatus {
          type enumeration {
            enum "other" {
              value "1";
            }
            enum "invalid" {
              value "2";
            }
            enum "permanent" {
              value "3";
            }
            enum "deleteOnReset" {
              value "4";
            }
            enum "deleteOnTimeout" {
              value "5";
            }
          }
          description
           "This object indicates the status of this entry.
            The default value is permanent(3).
                other(1) - this entry is currently in use but the
                    conditions under which it will remain so are
                    different from each of the following values.
                invalid(2) - writing this value to the object
                    removes the corresponding entry.
                permanent(3) - this entry is currently in use and
                    will remain so after the next reset of the
                    bridge.
                deleteOnReset(4) - this entry is currently in use
                    and will remain so until the next reset of the
                    bridge.
                deleteOnTimeout(5) - this entry is currently in use
                    and will remain so until it is aged out.";
          smiv2:max-access "read-write";
          smiv2:oid "1.3.6.1.2.1.17.5.1.1.4";
        }
      }
    }
  }

  notification newRoot {
    description
     "The newRoot trap indicates that the sending agent has
      become the new root of the Spanning Tree; the trap is
      sent by a bridge soon after its election as the new
      
      root, e.g., upon expiration of the Topology Change Timer,
      immediately subsequent to its election.  Implementation
      of this trap is optional.";
    smiv2:oid "1.3.6.1.2.1.17.0.1";
  }

  notification topologyChange {
    description
     "A topologyChange trap is sent by a bridge when any of
      its configured ports transitions from the Learning state
      to the Forwarding state, or from the Forwarding state to
      the Blocking state.  The trap is not sent if a newRoot
      trap is sent for the same transition.  Implementation of
      this trap is optional.";
    smiv2:oid "1.3.6.1.2.1.17.0.2";
  }

  smiv2:alias "dot1dBridge" {
    smiv2:oid "1.3.6.1.2.1.17";
  }

  smiv2:alias "dot1dNotifications" {
    smiv2:oid "1.3.6.1.2.1.17.0";
  }

  smiv2:alias "dot1dBase" {
    smiv2:oid "1.3.6.1.2.1.17.1";
  }

  smiv2:alias "dot1dStp" {
    smiv2:oid "1.3.6.1.2.1.17.2";
  }

  smiv2:alias "dot1dSr" {
    smiv2:oid "1.3.6.1.2.1.17.3";
  }

  smiv2:alias "dot1dTp" {
    smiv2:oid "1.3.6.1.2.1.17.4";
  }

  smiv2:alias "dot1dStatic" {
    smiv2:oid "1.3.6.1.2.1.17.5";
  }

  smiv2:alias "dot1dConformance" {
    smiv2:oid "1.3.6.1.2.1.17.8";
  }

  smiv2:alias "dot1dGroups" {
    smiv2:oid "1.3.6.1.2.1.17.8.1";
  }

  smiv2:alias "dot1dCompliances" {
    smiv2:oid "1.3.6.1.2.1.17.8.2";
  }

}
