/*
 * Generated by confdc --mib2yang-std
 * Source: mgmt/dmi/model/common/mib-source/NHRP-MIB.mib
 */
/*
 * This YANG module has been generated by smidump 0.5.0:
 *
 *      smidump -f yang NHRP-MIB
 *
 * Do not edit. Edit the source file instead!
 */

module NHRP-MIB {

  namespace "urn:ietf:params:xml:ns:yang:smiv2:NHRP-MIB";
  prefix NHRP-MIB;

  import IANA-ADDRESS-FAMILY-NUMBERS-MIB {
    prefix "iana-address";
  }

  import IF-MIB {
    prefix "if-mib";
  }

  import SNMPv2-TC {
    prefix "snmpv2-tc";
  }

  import ietf-yang-smiv2 {
    prefix "smiv2";
  }

  import ietf-yang-types {
    prefix "yang";
  }

  organization
   "Internetworking Over NBMA (ion) Working Group";

  contact
   "Maria Greene (maria@xedia.com)
    Contractor
    
    Joan Cucchiara (joan@ironbridgenetworks.com)
    IronBridge Networks
    
    James V. Luciani (luciani@baynetworks.com)
    Bay Networks";

  description
   "This MIB contains managed object definitions for the Next
    Hop Resolution Procol, NHRP, as defined in RFC 2332 [17].";

  revision 1999-08-26 {
    description
     "Initial version, published as RFC 2677.";
  }

  typedef NhrpGenAddr {
    type binary {
      length "0..64";
    }
    description
     "The value of an internetwork layer or NBMA address.";
  }


  container NHRP-MIB {
    config false;

    container nhrpGeneralObjects {
      smiv2:oid "1.3.6.1.2.1.71.1.1";

      leaf nhrpNextIndex {
        type uint32;
        description
         "This scalar is used for creating rows in the
          nhrpClientTable and the nhrpServerTable.
          The value of this variable is a currently unused value
          for nhrpClientIndex and nhrpServerIndex.
          
          
          
          
          The value returned when reading this variable must be
          unique for the NHC's and NHS's indices associated with
          this row. Subsequent attempts to read this variable
          must return different values.
          
          NOTE:  this object exists in the General Group because
          it is to be used in establishing rows in the
          nhrpClientTable and the nhrpServerTable.  In other words,
          the value retrieved from this object could become the
          value of nhrpClientIndex and nhprServerIndex.
          
          In the situation of an agent re-initialization the value
          of this object must be saved in non-volatile storage.
          
          This variable will return the special value 0 if no new
          rows can be created.";
        smiv2:max-access "read-only";
        smiv2:oid "1.3.6.1.2.1.71.1.1.1";
      }
    }

    container nhrpCacheTable {
      description
       "This table contains mappings between internetwork layer
        addresses and NBMA subnetwork layer addresses.";
      smiv2:oid "1.3.6.1.2.1.71.1.1.2";

      list nhrpCacheEntry {
        key "nhrpCacheInternetworkAddrType nhrpCacheInternetworkAddr ifIndex nhrpCacheIndex";
        description
         "A cached mapping between an internetwork layer address
          and an NBMA address. Entries can be created by the
          network administrator using the nhrpCacheRowStatus
          column, or they may be added dynamically based on
          protocol operation (including NHRP, SCSP, and others,
          such as ATMARP).
          
          When created based by NHRP protocol operations
          this entry is largely based on contents contained in
          the Client Information Entry (CIE).
          
          Zero or more Client Information Entries (CIEs) may be
          included in the NHRP Packet. For a complete description
          of the CIE, refer to Section 5.2.0.1 of
          RFC 2332 [17].";
        smiv2:oid "1.3.6.1.2.1.71.1.1.2.1";

        leaf ifIndex {
          type leafref {
            path "/if-mib:IF-MIB/if-mib:ifTable/if-mib:ifEntry/if-mib:ifIndex";
          }
        }

        leaf nhrpCacheInternetworkAddrType {
          type iana-address:AddressFamilyNumbers;
          description
           "The internetwork layer address type of this Next Hop
            Resolution Cache entry. The value of this object indicates
            how to interpret the values of nhrpCacheInternetworkAddr
            and nhrpCacheNextHopInternetworkAddr.";
          smiv2:max-access "not-accessible";
          smiv2:oid "1.3.6.1.2.1.71.1.1.2.1.1";
        }

        leaf nhrpCacheInternetworkAddr {
          type NHRP-MIB:NhrpGenAddr;
          description
           "The value of the internetwork address of the
            destination.";
          smiv2:max-access "not-accessible";
          smiv2:oid "1.3.6.1.2.1.71.1.1.2.1.2";
        }

        leaf nhrpCacheIndex {
          type uint32 {
            range "1..4294967295";
          }
          description
           "An identifier for this entry that has local
            significance within the scope of the General
            Group.  This identifier is used here to
            uniquely identify this row, and also used
            in the 'nhrpPurgeTable' for the value of
            the 'nhrpPurgeCacheIdentifier'.";
          smiv2:max-access "not-accessible";
          smiv2:oid "1.3.6.1.2.1.71.1.1.2.1.3";
        }

        leaf nhrpCachePrefixLength {
          type int32 {
            range "0..255";
          }
          description
           "The number of bits that define the internetwork layer
            prefix associated with the nhrpCacheInternetworkAddr.";
          smiv2:max-access "read-only";
          smiv2:oid "1.3.6.1.2.1.71.1.1.2.1.4";
        }

        leaf nhrpCacheNextHopInternetworkAddr {
          type NHRP-MIB:NhrpGenAddr;
          description
           "The value of the internetwork address of the next hop.";
          smiv2:max-access "read-write";
          smiv2:oid "1.3.6.1.2.1.71.1.1.2.1.5";
        }

        leaf nhrpCacheNbmaAddrType {
          type iana-address:AddressFamilyNumbers;
          description
           "The NBMA address type. The value of this
            object indicates how to interpret
            the values of nhrpCacheNbmaAddr and
            nhrpCacheNbmaSubaddr.";
          smiv2:max-access "read-write";
          smiv2:oid "1.3.6.1.2.1.71.1.1.2.1.6";
        }

        leaf nhrpCacheNbmaAddr {
          type NHRP-MIB:NhrpGenAddr;
          description
           "The value of the NBMA subnetwork address of the next
            hop.";
          smiv2:max-access "read-write";
          smiv2:oid "1.3.6.1.2.1.71.1.1.2.1.7";
        }

        leaf nhrpCacheNbmaSubaddr {
          type NHRP-MIB:NhrpGenAddr;
          description
           "The value of the NBMA subaddress of the next hop. If
            there is no subaddress concept for the NBMA address
            family, this value will be a zero-length OCTET STRING.";
          smiv2:max-access "read-write";
          smiv2:oid "1.3.6.1.2.1.71.1.1.2.1.8";
        }

        leaf nhrpCacheType {
          type enumeration {
            enum "other" {
              value "1";
            }
            enum "register" {
              value "2";
            }
            enum "resolveAuthoritative" {
              value "3";
            }
            enum "resoveNonauthoritative" {
              value "4";
            }
            enum "transit" {
              value "5";
            }
            enum "administrativelyAdded" {
              value "6";
            }
            enum "atmarp" {
              value "7";
            }
            enum "scsp" {
              value "8";
            }
          }
          description
           "An indication of how this cache entry
            was created. The values are:
            
            'other(1)'                   The entry was added by some
                                         other means.
            
            'register(2)'                In a server, added based on a
                                         client registration.
            
            'resolveAuthoritative(3)'    In a client, added based on
                                         receiving an Authoritative
                                         NHRP Resolution Reply.
            
            
            
            
            'resolveNonauthoritative(4)' In a client, added based on
                                         receiving a Nonauthoritative
                                         NHRP Resolution Reply.
            
            'transit(5)'                 In a transit server, added by
                                         examining a forwarded NHRP
                                         packet.
            
            'administrativelyAdded(6)'   In a client or server,
                                         manually added by the
                                         administrator. The
                                         StorageType of this entry is
                                         reflected in
                                         'nhrpCacheStorageType'.
            
            'atmarp(7)'                  The entry was added due to an
                                         ATMARP.
            
            'scsp(8)'                    The entry was added due to
                                         SCSP.
            
            
            When the entry is under creation using the
            nhrpCacheRowStatus column, the only value that can be
            specified by the administrator is 'administrativelyAdded'.
            Attempting to set any other value will cause an
            'inconsistentValue' error.
            
            The value cannot be modified once the entry is active.";
          smiv2:max-access "read-write";
          smiv2:oid "1.3.6.1.2.1.71.1.1.2.1.9";
        }

        leaf nhrpCacheState {
          type enumeration {
            enum "incomplete" {
              value "1";
            }
            enum "ackReply" {
              value "2";
            }
            enum "nakReply" {
              value "3";
            }
          }
          description
           "An indication of the state of this entry. The values are:
            
            'incomplete(1)' The client has sent a NHRP Resolution
                            Request but has not yet received the
                            NHRP Resolution Reply.
            
            
            'ackReply(2)'   For a client or server, this is a
                            cached valid mapping.
            
            'nakReply(3)'   For a client or server, this is a
                            cached NAK mapping.";
          smiv2:max-access "read-only";
          smiv2:oid "1.3.6.1.2.1.71.1.1.2.1.10";
        }

        leaf nhrpCacheHoldingTimeValid {
          type boolean;
          description
           "True(1) is returned if the value of
            'nhrpCacheType' is not
            'administrativelyAdded'.  Since the
            value of 'nhrpCacheType' was not
            configured by a user, the value of
            'nhrpCacheHoldingTime' is
            considered valid.  In other words, the value of
            'nhrpCacheHoldingTime' represents
            the Holding Time for the cache Entry.
            
            If 'nhrpCacheType has been configured by a
            user, (i.e. the value of 'nhrpCacheType' is
            'administrativelyAdded') then false(2) will be returned.
            This indicates that the value of
            'nhrpCacheHoldingTime' is undefined because this row
            could possibly be backed up in nonvolatile storage.";
          smiv2:max-access "read-only";
          smiv2:oid "1.3.6.1.2.1.71.1.1.2.1.11";
        }

        leaf nhrpCacheHoldingTime {
          type uint32 {
            range "0..65535";
          }
          units "seconds";
          description
           "If the value of 'nhrpCacheHoldingTimeValid is
            true(1) then this object represents the number
            of seconds that the cache entry will remain in this
            table.  When this value reaches 0 (zero) the row should
            be deleted.
            
            If the value of 'nhrpCacheHoldingTimeValid is
            false(2) then this object is undefined.";
          smiv2:max-access "read-only";
          smiv2:oid "1.3.6.1.2.1.71.1.1.2.1.12";
        }

        leaf nhrpCacheNegotiatedMtu {
          type int32 {
            range "0..65535";
          }
          description
           "The maximum transmission unit (MTU) that was negotiated
            or registered for this entity. In other words, this is the
            actual MTU being used.";
          smiv2:max-access "read-only";
          smiv2:oid "1.3.6.1.2.1.71.1.1.2.1.13";
        }

        leaf nhrpCachePreference {
          type int32 {
            range "0..255";
          }
          description
           "An object which reflects the Preference value of the
            Client Information Entry (CIE).
            
            Zero or more Client Information Entries (CIEs) may be
            included in the NHRP Packet.  One of the fields in the
            CIE is the Preference.  For a complete description of
            the CIE, refer to Section 5.2.0.1 of  RFC 2332 [17].";
          reference
           "Section 5.2.0.1 Mandatory Part Format, RFC 2332 [17].";
          smiv2:max-access "read-write";
          smiv2:oid "1.3.6.1.2.1.71.1.1.2.1.14";
        }

        leaf nhrpCacheStorageType {
          type snmpv2-tc:StorageType;
          description
           "This value only has meaning when the 'nhrpCacheType'
            has the value of 'administrativelyAdded'.
            
            When the row is created due to being
            'administrativelyAdded', this object reflects whether
            this row is kept in volatile storage
            and lost upon reboot or if this row is backed up by
            non-volatile or permanent storage.
            
            If the value of 'nhrpCacheType' has a value which
            is not 'administrativelyAdded, then the value of this
            object is 'other(1)'.";
          smiv2:defval "nonVolatile";
          smiv2:max-access "read-write";
          smiv2:oid "1.3.6.1.2.1.71.1.1.2.1.15";
        }

        leaf nhrpCacheRowStatus {
          type snmpv2-tc:RowStatus;
          description
           "An object that allows entries in this table to be
            created and deleted using the RowStatus convention.";
          smiv2:max-access "read-write";
          smiv2:oid "1.3.6.1.2.1.71.1.1.2.1.16";
        }
      }
    }

    container nhrpPurgeReqTable {
      description
       "This table will track Purge Request Information.";
      smiv2:oid "1.3.6.1.2.1.71.1.1.3";

      list nhrpPurgeReqEntry {
        key "nhrpPurgeIndex";
        description
         "Information regarding a Purge Request.";
        smiv2:oid "1.3.6.1.2.1.71.1.1.3.1";

        leaf nhrpPurgeIndex {
          type uint32 {
            range "1..4294967295";
          }
          description
           "An index for this entry that has local significance
            within the scope of this table.";
          smiv2:max-access "not-accessible";
          smiv2:oid "1.3.6.1.2.1.71.1.1.3.1.1";
        }

        leaf nhrpPurgeCacheIdentifier {
          type uint32 {
            range "1..4294967295";
          }
          description
           "This object identifies which row in
            'nhrpCacheTable' is being purged.  This object
            should have the same value as the 'nhrpCacheIndex'
            in the 'nhrpCacheTable'.";
          smiv2:max-access "read-write";
          smiv2:oid "1.3.6.1.2.1.71.1.1.3.1.2";
        }

        leaf nhrpPurgePrefixLength {
          type int32 {
            range "0..255";
          }
          description
           "In the case of NHRP Purge Requests, this specifies the
            equivalence class of addresses which match the first
            'Prefix Length' bit positions of the Client Protocol
            Address specified in the Client Information Entry (CIE).";
          smiv2:max-access "read-only";
          smiv2:oid "1.3.6.1.2.1.71.1.1.3.1.3";
        }

        leaf nhrpPurgeRequestID {
          type uint32;
          description
           "The Request ID used in the purge request.";
          smiv2:max-access "read-write";
          smiv2:oid "1.3.6.1.2.1.71.1.1.3.1.4";
        }

        leaf nhrpPurgeReplyExpected {
          type boolean;
          description
           "An indication of whether this Purge Request has the
            'N' Bit cleared (off).";
          smiv2:max-access "read-write";
          smiv2:oid "1.3.6.1.2.1.71.1.1.3.1.5";
        }

        leaf nhrpPurgeRowStatus {
          type snmpv2-tc:RowStatus;
          description
           "An object that allows entries in this table to be
            created and deleted using the RowStatus convention.";
          smiv2:max-access "read-write";
          smiv2:oid "1.3.6.1.2.1.71.1.1.3.1.6";
        }
      }
    }

    container nhrpClientTable {
      description
       "Information about NHRP clients (NHCs) managed by this
        agent.";
      smiv2:oid "1.3.6.1.2.1.71.1.2.1";

      list nhrpClientEntry {
        key "nhrpClientIndex";
        description
         "Information about a single NHC.";
        smiv2:oid "1.3.6.1.2.1.71.1.2.1.1";

        leaf nhrpClientIndex {
          type uint32 {
            range "1..4294967295";
          }
          description
           "An identifier for the NHRP client that is unique within
            the scope of this agent.  The 'nhrpNextIndex' value
            should be consulted (read), prior to creating a row in
            this table, and the value returned from reading
            'nhrpNextIndex' should be used as this object's value.";
          smiv2:max-access "not-accessible";
          smiv2:oid "1.3.6.1.2.1.71.1.2.1.1.1";
        }

        leaf nhrpClientInternetworkAddrType {
          type iana-address:AddressFamilyNumbers;
          description
           "The type of the internetwork layer address of this
            client. This object indicates how the value of
            nhrpClientInternetworkAddr is to be interpreted.";
          smiv2:max-access "read-write";
          smiv2:oid "1.3.6.1.2.1.71.1.2.1.1.2";
        }

        leaf nhrpClientInternetworkAddr {
          type NHRP-MIB:NhrpGenAddr;
          description
           "The value of the internetwork layer address of this
            client.";
          smiv2:max-access "read-write";
          smiv2:oid "1.3.6.1.2.1.71.1.2.1.1.3";
        }

        leaf nhrpClientNbmaAddrType {
          type iana-address:AddressFamilyNumbers;
          description
           "The type of the NBMA subnetwork address of this client.
            This object indicates how the values of
            nhrpClientNbmaAddr and nhrpClientNbmaSubaddr are to be
            interpreted.";
          smiv2:max-access "read-write";
          smiv2:oid "1.3.6.1.2.1.71.1.2.1.1.4";
        }

        leaf nhrpClientNbmaAddr {
          type NHRP-MIB:NhrpGenAddr;
          description
           "The NBMA subnetwork address of this client.";
          smiv2:max-access "read-write";
          smiv2:oid "1.3.6.1.2.1.71.1.2.1.1.5";
        }

        leaf nhrpClientNbmaSubaddr {
          type NHRP-MIB:NhrpGenAddr;
          description
           "The NBMA subaddress of this client. For NBMA address
            families without a subaddress concept, this will be a
            zero-length OCTET STRING.";
          smiv2:max-access "read-write";
          smiv2:oid "1.3.6.1.2.1.71.1.2.1.1.6";
        }

        leaf nhrpClientInitialRequestTimeout {
          type int32 {
            range "1..900";
          }
          units "seconds";
          description
           "The number of seconds that the client will wait before
            timing out an NHRP initial request.  This object only has
            meaning for the initial timeout period.";
          smiv2:defval "10";
          smiv2:max-access "read-write";
          smiv2:oid "1.3.6.1.2.1.71.1.2.1.1.7";
        }

        leaf nhrpClientRegistrationRequestRetries {
          type int32 {
            range "0..65535";
          }
          description
           "The number of times the client will retry the
            registration request before failure. A value of
            0 means don't retry. A value of 65535 means
            retry forever.";
          smiv2:defval "3";
          smiv2:max-access "read-write";
          smiv2:oid "1.3.6.1.2.1.71.1.2.1.1.8";
        }

        leaf nhrpClientResolutionRequestRetries {
          type int32 {
            range "0..65535";
          }
          description
           "The number of times the client will retry the resolution
            request before failure. A value of 0 means don't retry.
            A value of 65535 means retry forever.";
          smiv2:defval "3";
          smiv2:max-access "read-write";
          smiv2:oid "1.3.6.1.2.1.71.1.2.1.1.9";
        }

        leaf nhrpClientPurgeRequestRetries {
          type int32 {
            range "0..65535";
          }
          description
           "The number of times the client will retry a purge request
            before failure. A value of 0 means don't retry. A value of
            65535 means retry forever.";
          smiv2:defval "3";
          smiv2:max-access "read-write";
          smiv2:oid "1.3.6.1.2.1.71.1.2.1.1.10";
        }

        leaf nhrpClientDefaultMtu {
          type uint32 {
            range "0..65535";
          }
          description
           "The default maximum transmission unit (MTU) of the
            LIS/LAG which this client should use. This object
            will be initialized by the agent to the default MTU
            of the LIS/LAG (which is 9180) unless a different MTU
            value is specified during creation of this Client.";
          reference
           "RFC 2225 [25], Classical IP and ARP over ATM, Section 7,
            DEFAULT VALUE FOR IP MTU OVER ATM AAL5.";
          smiv2:defval "9180";
          smiv2:max-access "read-write";
          smiv2:oid "1.3.6.1.2.1.71.1.2.1.1.11";
        }

        leaf nhrpClientHoldTime {
          type uint32 {
            range "0..65535";
          }
          units "seconds";
          description
           "The hold time the client will register.";
          smiv2:defval "900";
          smiv2:max-access "read-write";
          smiv2:oid "1.3.6.1.2.1.71.1.2.1.1.12";
        }

        leaf nhrpClientRequestID {
          type uint32;
          description
           "The Request ID used to register this client with its
            server. According to Section 5.2.3 of the NHRP
            Specification, RFC 2332 [17], the Request ID must
            be kept in non-volatile storage, so that if an NHC
            crashes and  re-initializes, it will use a different
            
            Request ID during the registration process
            when reregistering with the same NHS.";
          reference
           "Section 5.2.3 NHRP Registration Request, RFC 2332 [17].";
          smiv2:max-access "read-write";
          smiv2:oid "1.3.6.1.2.1.71.1.2.1.1.13";
        }

        leaf nhrpClientStorageType {
          type snmpv2-tc:StorageType;
          description
           "This object defines whether this row is kept in
            volatile storage and lost upon a Client crash or
            reboot situation, or if this row is backed up by
            nonvolatile or permanent storage.";
          smiv2:defval "nonVolatile";
          smiv2:max-access "read-write";
          smiv2:oid "1.3.6.1.2.1.71.1.2.1.1.14";
        }

        leaf nhrpClientRowStatus {
          type snmpv2-tc:RowStatus;
          description
           "An object that allows entries in this table to be
            created and deleted using the RowStatus convention.";
          smiv2:max-access "read-write";
          smiv2:oid "1.3.6.1.2.1.71.1.2.1.1.15";
        }
      }
    }

    container nhrpClientRegistrationTable {
      description
       "A table of Registration Request Information that
        needs to be maintained by the NHCs (clients).";
      reference
       "Section 5.2.3 NHRP Registration Request, RFC 2332 [17].";
      smiv2:oid "1.3.6.1.2.1.71.1.2.2";

      list nhrpClientRegistrationEntry {
        key "nhrpClientIndex nhrpClientRegIndex";
        description
         "An NHC needs to maintain registration request information
          between the NHC and the NHS.  An entry in this table
          represents information for a single registration request.";
        smiv2:oid "1.3.6.1.2.1.71.1.2.2.1";

        leaf nhrpClientIndex {
          type leafref {
            path "/NHRP-MIB:NHRP-MIB/NHRP-MIB:nhrpClientTable/NHRP-MIB:nhrpClientEntry/NHRP-MIB:nhrpClientIndex";
          }
        }

        leaf nhrpClientRegIndex {
          type uint32 {
            range "1..4294967295";
          }
          description
           "An identifier for this entry such that it
            identifies a specific Registration Request from
            the NHC represented by the nhrpClientIndex.";
          smiv2:max-access "not-accessible";
          smiv2:oid "1.3.6.1.2.1.71.1.2.2.1.1";
        }

        leaf nhrpClientRegUniqueness {
          type enumeration {
            enum "requestUnique" {
              value "1";
            }
            enum "requestNotUnique" {
              value "2";
            }
          }
          description
           "The Uniqueness indicator for this Registration Request.
            If this object has the value of requestUnique(1), then
            the Uniqueness bit is set in the the NHRP Registration
            Request represented by this row.  The value cannot
            be changed once the row is created.";
          smiv2:max-access "read-write";
          smiv2:oid "1.3.6.1.2.1.71.1.2.2.1.2";
        }

        leaf nhrpClientRegState {
          type enumeration {
            enum "other" {
              value "1";
            }
            enum "registering" {
              value "2";
            }
            enum "ackRegisterReply" {
              value "3";
            }
            enum "nakRegisterReply" {
              value "4";
            }
          }
          description
           "The registration state of this client. The values are:
            'other(1)'             The state of the registration
                                   request is not one of
                                   'registering',
                                   'ackRegisterReply' or
                                   'nakRegisterReply'.
            
            'registering(2)'        A registration request has
                                    been issued and a registration
                                    reply is expected.
            
            'ackRegisterReply(3)'   A positive registration reply
                                    has been received.
            
            'nakRegisterReply(4)'   The client has received a
                                    negative registration
                                    reply (NAK).";
          smiv2:max-access "read-only";
          smiv2:oid "1.3.6.1.2.1.71.1.2.2.1.3";
        }

        leaf nhrpClientRegRowStatus {
          type snmpv2-tc:RowStatus;
          description
           "An object that allows entries in this table to be
            created and deleted using the RowStatus convention.";
          smiv2:max-access "read-write";
          smiv2:oid "1.3.6.1.2.1.71.1.2.2.1.4";
        }
      }
    }

    container nhrpClientNhsTable {
      description
       "A table of NHSes that are available for use by this NHC
        (client). By default, the agent will add an entry to this
        table that corresponds to the client's default router.";
      smiv2:oid "1.3.6.1.2.1.71.1.2.3";

      list nhrpClientNhsEntry {
        key "nhrpClientIndex nhrpClientNhsIndex";
        description
         "An NHS that may be used by an NHC.";
        smiv2:oid "1.3.6.1.2.1.71.1.2.3.1";

        leaf nhrpClientIndex {
          type leafref {
            path "/NHRP-MIB:NHRP-MIB/NHRP-MIB:nhrpClientTable/NHRP-MIB:nhrpClientEntry/NHRP-MIB:nhrpClientIndex";
          }
        }

        leaf nhrpClientNhsIndex {
          type uint32 {
            range "1..4294967295";
          }
          description
           "An identifier for an NHS available to an NHC.";
          smiv2:max-access "not-accessible";
          smiv2:oid "1.3.6.1.2.1.71.1.2.3.1.1";
        }

        leaf nhrpClientNhsInternetworkAddrType {
          type iana-address:AddressFamilyNumbers;
          description
           "The type of the internetwork layer address of the
            NHRP server represented in this entry. This object
            indicates how the value of
            nhrpClientNhsInternetworkAddr is to be interpreted.";
          smiv2:max-access "read-write";
          smiv2:oid "1.3.6.1.2.1.71.1.2.3.1.2";
        }

        leaf nhrpClientNhsInternetworkAddr {
          type NHRP-MIB:NhrpGenAddr;
          description
           "The value of the destination internetwork layer
            address of the NHRP server represented by this
            
            
            
            entry.  If this value is not known, this will be
            a zero-length OCTET STRING.";
          smiv2:max-access "read-write";
          smiv2:oid "1.3.6.1.2.1.71.1.2.3.1.3";
        }

        leaf nhrpClientNhsNbmaAddrType {
          type iana-address:AddressFamilyNumbers;
          description
           "The type of the NBMA subnetwork address of the NHRP
            Server represented by this entry. This object indicates
            how the values of nhrpClientNhsNbmaAddr and
            nhrpClientNhsNbmaSubaddr are to be interpreted.";
          smiv2:max-access "read-write";
          smiv2:oid "1.3.6.1.2.1.71.1.2.3.1.4";
        }

        leaf nhrpClientNhsNbmaAddr {
          type NHRP-MIB:NhrpGenAddr;
          description
           "The NBMA subnetwork address of the NHS. The type of
            the address is indicated by the corresponding value of
            nhrpClientNhsNbmaAddrType.";
          smiv2:max-access "read-write";
          smiv2:oid "1.3.6.1.2.1.71.1.2.3.1.5";
        }

        leaf nhrpClientNhsNbmaSubaddr {
          type NHRP-MIB:NhrpGenAddr;
          description
           "The NBMA subaddress of the NHS. For NMBA address
            families that do not have the concept of subaddress,
                 this will be a zero-length OCTET STRING.";
          smiv2:max-access "read-write";
          smiv2:oid "1.3.6.1.2.1.71.1.2.3.1.6";
        }

        leaf nhrpClientNhsInUse {
          type boolean;
          description
           "An indication of whether this NHS is in use by the NHC.";
          smiv2:max-access "read-only";
          smiv2:oid "1.3.6.1.2.1.71.1.2.3.1.7";
        }

        leaf nhrpClientNhsRowStatus {
          type snmpv2-tc:RowStatus;
          description
           "An object that allows entries in this table to be
            created and deleted using the RowStatus convention.";
          smiv2:max-access "read-write";
          smiv2:oid "1.3.6.1.2.1.71.1.2.3.1.8";
        }
      }
    }

    container nhrpClientStatTable {
      description
       "This table contains statistics collected by NHRP
        clients.";
      smiv2:oid "1.3.6.1.2.1.71.1.2.4";

      list nhrpClientStatEntry {
        key "nhrpClientIndex";
        description
         "Statistics collected by a NHRP client.";
        smiv2:oid "1.3.6.1.2.1.71.1.2.4.1";

        leaf nhrpClientIndex {
          type leafref {
            path "/NHRP-MIB:NHRP-MIB/NHRP-MIB:nhrpClientTable/NHRP-MIB:nhrpClientEntry/NHRP-MIB:nhrpClientIndex";
          }
        }

        leaf nhrpClientStatTxResolveReq {
          type yang:counter32;
          description
           "The number of NHRP Resolution Requests transmitted
            by this client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.1";
        }

        leaf nhrpClientStatRxResolveReplyAck {
          type yang:counter32;
          description
           "The number of positively acknowledged NHRP Resolution
            Replies received by this client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.2";
        }

        leaf nhrpClientStatRxResolveReplyNakProhibited {
          type yang:counter32;
          description
           "The number of NAKed NHRP Resolution Replies received
            by this client that contained the code indicating
            'Administratively Prohibited'.
            
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.3";
        }

        leaf nhrpClientStatRxResolveReplyNakInsufResources {
          type yang:counter32;
          description
           "The number of NAKed NHRP Resolution Replies received
            by this client that contained the code indicating
            'Insufficient Resources'.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.4";
        }

        leaf nhrpClientStatRxResolveReplyNakNoBinding {
          type yang:counter32;
          description
           "The number of NAKed NHRP Resolution Replies received
            by this client that contained the code indicating
            'No Internetworking Layer Address to NBMA Address
            Binding Exists'.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.5";
        }

        leaf nhrpClientStatRxResolveReplyNakNotUnique {
          type yang:counter32;
          description
           "The number of NAKed NHRP Resolution Replies received
            by this client that contained the code indicating
            'Binding Exists But Is Not Unique'.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.6";
        }

        leaf nhrpClientStatTxRegisterReq {
          type yang:counter32;
          description
           "The number of NHRP Registration Requests transmitted
            by this client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.7";
        }

        leaf nhrpClientStatRxRegisterAck {
          type yang:counter32;
          description
           "The number of positively acknowledged NHRP Registration
            Replies received by this client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.8";
        }

        leaf nhrpClientStatRxRegisterNakProhibited {
          type yang:counter32;
          description
           "The number of NAKed NHRP Registration Replies received
            by this client that contained the code indicating
            'Administratively Prohibited'.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.9";
        }

        leaf nhrpClientStatRxRegisterNakInsufResources {
          type yang:counter32;
          description
           "The number of NAKed NHRP Registration Replies received
            by this client that contained the code indicating
            'Insufficient Resources'.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.10";
        }

        leaf nhrpClientStatRxRegisterNakAlreadyReg {
          type yang:counter32;
          description
           "The number of NAKed NHRP Registration Replies received
            by this client that contained the code indicating 'Unique
            Internetworking Layer Address Already Registered'.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.11";
        }

        leaf nhrpClientStatRxPurgeReq {
          type yang:counter32;
          description
           "The number of NHRP Purge Requests received by this
            client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.12";
        }

        leaf nhrpClientStatTxPurgeReq {
          type yang:counter32;
          description
           "The number of NHRP Purge Requests transmitted by this
            client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.13";
        }

        leaf nhrpClientStatRxPurgeReply {
          type yang:counter32;
          description
           "The number of NHRP Purge Replies received by this
            client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.14";
        }

        leaf nhrpClientStatTxPurgeReply {
          type yang:counter32;
          description
           "The number of NHRP Purge Replies transmitted by this
            client.
            
            Discontinuities in the value of this counter can occur
            at re-initialization of the management system, at
            NHRP Client re-initialization and at
            other times as indicated by the value of
            nhrpClientStatDiscontinuityTime.";
          smiv2:max-access "read-only";
          smiv2:oid "1.3.6.1.2.1.71.1.2.4.1.15";
        }

        leaf nhrpClientStatTxErrorIndication {
          type yang:counter32;
          description
           "The number of NHRP Error Indication packets transmitted
            by this client.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.16";
        }

        leaf nhrpClientStatRxErrUnrecognizedExtension {
          type yang:counter32;
          description
           "The number of NHRP Error Indication packets received
            by this client with the error code
            'Unrecognized Extension'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.17";
        }

        leaf nhrpClientStatRxErrLoopDetected {
          type yang:counter32;
          description
           "The number of NHRP Error Indication packets received
            by this client with the error code 'NHRP Loop Detected'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.18";
        }

        leaf nhrpClientStatRxErrProtoAddrUnreachable {
          type yang:counter32;
          description
           "The number of NHRP Error Indication packets received
            by this client with the error code 'Protocol Address
            Unreachable'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.19";
        }

        leaf nhrpClientStatRxErrProtoError {
          type yang:counter32;
          description
           "The number of NHRP Error Indication packets received
            by this client with the error code 'Protocol Error'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.20";
        }

        leaf nhrpClientStatRxErrSduSizeExceeded {
          type yang:counter32;
          description
           "The number of NHRP Error Indication packets received
            by this client with the error code 'NHRP SDU Size
            
            Exceeded'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.21";
        }

        leaf nhrpClientStatRxErrInvalidExtension {
          type yang:counter32;
          description
           "The number of NHRP Error Indication packets received
            by this client with the error code 'Invalid Extension'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.22";
        }

        leaf nhrpClientStatRxErrAuthenticationFailure {
          type yang:counter32;
          description
           "The number of NHRP Error Indication packets received
            by this client with the error code 'Authentication
            Failure'.
            
            
            
            
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.23";
        }

        leaf nhrpClientStatRxErrHopCountExceeded {
          type yang:counter32;
          description
           "The number of NHRP Error Indication packets received
            by this client with the error code 'Hop Count Exceeded'.
            
            Discontinuities in the value of this counter can occur
            at re-initialization of the management system, at
            NHRP Client re-initialization and at
            other times as indicated by the value of
            nhrpClientStatDiscontinuityTime.";
          reference
           "Section 5.2.7 NHRP Error Indication, RFC 2332 [17].";
          smiv2:max-access "read-only";
          smiv2:oid "1.3.6.1.2.1.71.1.2.4.1.24";
        }

        leaf nhrpClientStatDiscontinuityTime {
          type yang:timestamp;
          description
           "The value of sysUpTime on the most recent occasion at
            which any one or more of this Client's counters
            suffered a discontinuity.  If no such discontinuities
            have occurred since the last re-initialization of the
            local management subsystem or the NHRP Client
            re-initialization associated with this entry, then
            this object contains a zero value.";
          reference
           "RFC 2233 [18].";
          smiv2:max-access "read-only";
          smiv2:oid "1.3.6.1.2.1.71.1.2.4.1.25";
        }
      }
    }

    container nhrpServerTable {
      description
       "This table contains information for a set of NHSes
        associated with this agent.";
      smiv2:oid "1.3.6.1.2.1.71.1.3.1";

      list nhrpServerEntry {
        key "nhrpServerIndex";
        description
         "Information about a single NHS.";
        smiv2:oid "1.3.6.1.2.1.71.1.3.1.1";

        leaf nhrpServerIndex {
          type uint32 {
            range "1..4294967295";
          }
          description
           "An identifier for the server that is unique within the
            scope of this agent.";
          smiv2:max-access "not-accessible";
          smiv2:oid "1.3.6.1.2.1.71.1.3.1.1.1";
        }

        leaf nhrpServerInternetworkAddrType {
          type iana-address:AddressFamilyNumbers;
          description
           "The type of the internetwork layer address of this
            server. This object is used to interpret the value of
            nhrpServerInternetworkAddr.";
          smiv2:max-access "read-write";
          smiv2:oid "1.3.6.1.2.1.71.1.3.1.1.2";
        }

        leaf nhrpServerInternetworkAddr {
          type NHRP-MIB:NhrpGenAddr;
          description
           "The value of the internetwork layer address of this
            server.";
          smiv2:max-access "read-write";
          smiv2:oid "1.3.6.1.2.1.71.1.3.1.1.3";
        }

        leaf nhrpServerNbmaAddrType {
          type iana-address:AddressFamilyNumbers;
          description
           "The type of the NBMA subnetwork address of this server.
            This object is used to interpret the value of
            nhrpServerNbmaAddr.";
          smiv2:max-access "read-write";
          smiv2:oid "1.3.6.1.2.1.71.1.3.1.1.4";
        }

        leaf nhrpServerNbmaAddr {
          type NHRP-MIB:NhrpGenAddr;
          description
           "The value of the NBMA subnetwork address of this
            server.";
          smiv2:max-access "read-write";
          smiv2:oid "1.3.6.1.2.1.71.1.3.1.1.5";
        }

        leaf nhrpServerNbmaSubaddr {
          type NHRP-MIB:NhrpGenAddr;
          description
           "The value of the NBMA subaddress of this server.
            For NBMA address families without a subaddress
            concept, this will be a zero-length OCTET STRING.";
          smiv2:max-access "read-write";
          smiv2:oid "1.3.6.1.2.1.71.1.3.1.1.6";
        }

        leaf nhrpServerStorageType {
          type snmpv2-tc:StorageType;
          description
           "This object defines whether this row is kept in
            volatile storage and lost upon a Server crash or
            reboot situation, or if this row is backed up by
            nonvolatile or permanent storage.";
          smiv2:defval "nonVolatile";
          smiv2:max-access "read-write";
          smiv2:oid "1.3.6.1.2.1.71.1.3.1.1.7";
        }

        leaf nhrpServerRowStatus {
          type snmpv2-tc:RowStatus;
          description
           "An object that allows entries in this table to be
            created and deleted using the RowStatus convention.";
          smiv2:max-access "read-write";
          smiv2:oid "1.3.6.1.2.1.71.1.3.1.1.8";
        }
      }
    }

    container nhrpServerCacheTable {
      description
       "This table extends the nhrpCacheTable for
        NHSes.  If the nhrpCacheTable has a row added due to
        an NHS or based on information regarding an NHS then
        a row is also added in this table.
        
        The rows in this table will be created when rows in
        the nhrpCacheTable are created.  However, there may
        be rows created in the nhrpCacheTable which do not
        have corresponding rows in this table.  For example,
        if the nhrpCacheTable has a row added due to a Next
        Hop Client which is co-resident on the same device
        as the NHS, a row will not be added to this table.";
      smiv2:oid "1.3.6.1.2.1.71.1.3.2";

      list nhrpServerCacheEntry {
        key "nhrpCacheInternetworkAddrType nhrpCacheInternetworkAddr ifIndex nhrpCacheIndex";
        description
         "Additional information kept by a NHS for a relevant
          Next Hop Resolution Cache entry.";
        smiv2:oid "1.3.6.1.2.1.71.1.3.2.1";

        leaf nhrpCacheInternetworkAddrType {
          type leafref {
            path "/NHRP-MIB:NHRP-MIB/NHRP-MIB:nhrpCacheTable/NHRP-MIB:nhrpCacheEntry/NHRP-MIB:nhrpCacheInternetworkAddrType";
          }
        }

        leaf nhrpCacheInternetworkAddr {
          type leafref {
            path "/NHRP-MIB:NHRP-MIB/NHRP-MIB:nhrpCacheTable/NHRP-MIB:nhrpCacheEntry/NHRP-MIB:nhrpCacheInternetworkAddr";
          }
        }

        leaf ifIndex {
          type leafref {
            path "/if-mib:IF-MIB/if-mib:ifTable/if-mib:ifEntry/if-mib:ifIndex";
          }
        }

        leaf nhrpCacheIndex {
          type leafref {
            path "/NHRP-MIB:NHRP-MIB/NHRP-MIB:nhrpCacheTable/NHRP-MIB:nhrpCacheEntry/NHRP-MIB:nhrpCacheIndex";
          }
        }

        leaf nhrpServerCacheAuthoritative {
          type boolean;
          description
           "An indication of whether this cache entry is
            authoritative, which means the entry was added because
            of a direct registration request with this server or
            by Server Cache Synchronization Protocol (SCSP) from
            an authoritative source.";
          smiv2:max-access "read-only";
          smiv2:oid "1.3.6.1.2.1.71.1.3.2.1.1";
        }

        leaf nhrpServerCacheUniqueness {
          type boolean;
          description
           "The Uniqueness indicator for this cache
            entry used in duplicate address detection. This value
            cannot be changed after the entry is active.";
          smiv2:max-access "read-write";
          smiv2:oid "1.3.6.1.2.1.71.1.3.2.1.2";
        }
      }
    }

    container nhrpServerNhcTable {
      description
       "A table of NHCs that are available for use by this NHS
        (Server).";
      reference
       "Section 4 Configuration (Next Hop Servers),
        RFC 2332 [17].";
      smiv2:oid "1.3.6.1.2.1.71.1.3.3";

      list nhrpServerNhcEntry {
        key "nhrpServerIndex nhrpServerNhcIndex";
        description
         "An NHC that may be used by an NHS.";
        smiv2:oid "1.3.6.1.2.1.71.1.3.3.1";

        leaf nhrpServerIndex {
          type leafref {
            path "/NHRP-MIB:NHRP-MIB/NHRP-MIB:nhrpServerTable/NHRP-MIB:nhrpServerEntry/NHRP-MIB:nhrpServerIndex";
          }
        }

        leaf nhrpServerNhcIndex {
          type uint32 {
            range "1..4294967295";
          }
          description
           "An identifier for an NHC available to an NHS.";
          smiv2:max-access "not-accessible";
          smiv2:oid "1.3.6.1.2.1.71.1.3.3.1.1";
        }

        leaf nhrpServerNhcPrefixLength {
          type int32 {
            range "0..255";
          }
          description
           "The number of bits that define the internetwork
            layer prefix associated with the
            nhrpServerNhcInternetworkAddr.";
          smiv2:max-access "read-write";
          smiv2:oid "1.3.6.1.2.1.71.1.3.3.1.2";
        }

        leaf nhrpServerNhcInternetworkAddrType {
          type iana-address:AddressFamilyNumbers;
          description
           "The type of the internetwork layer address of the
            NHRP Client represented in this entry. This object
            indicates how the value of nhrpServerNhcInternetworkAddr
            is to be interpreted.";
          smiv2:max-access "read-write";
          smiv2:oid "1.3.6.1.2.1.71.1.3.3.1.3";
        }

        leaf nhrpServerNhcInternetworkAddr {
          type NHRP-MIB:NhrpGenAddr;
          description
           "The value of the internetwork layer address of
            the NHRP Client represented by this entry.  If this
            value is not known, this will be a zero-length
            OCTET STRING.";
          smiv2:max-access "read-write";
          smiv2:oid "1.3.6.1.2.1.71.1.3.3.1.4";
        }

        leaf nhrpServerNhcNbmaAddrType {
          type iana-address:AddressFamilyNumbers;
          description
           "The type of the NBMA subnetwork address of the NHRP
            Client represented by this entry. This object indicates
            how the values of nhrpServerNhcNbmaAddr and
            nhrpServerNhcNbmaSubaddr are to be interpreted.";
          smiv2:max-access "read-write";
          smiv2:oid "1.3.6.1.2.1.71.1.3.3.1.5";
        }

        leaf nhrpServerNhcNbmaAddr {
          type NHRP-MIB:NhrpGenAddr;
          description
           "The NBMA subnetwork address of the NHC. The type of the
            address is indicated by the corresponding value of
            nhrpServerNbmaAddrType.";
          smiv2:max-access "read-write";
          smiv2:oid "1.3.6.1.2.1.71.1.3.3.1.6";
        }

        leaf nhrpServerNhcNbmaSubaddr {
          type NHRP-MIB:NhrpGenAddr;
          description
           "The NBMA subaddress of the NHC. For NMBA address familes
            that do not have the concept of subaddress, this will
            be a zero-length OCTET STRING.";
          smiv2:max-access "read-write";
          smiv2:oid "1.3.6.1.2.1.71.1.3.3.1.7";
        }

        leaf nhrpServerNhcInUse {
          type boolean;
          description
           "An indication of whether this NHC is in use by the NHS.";
          smiv2:max-access "read-only";
          smiv2:oid "1.3.6.1.2.1.71.1.3.3.1.8";
        }

        leaf nhrpServerNhcRowStatus {
          type snmpv2-tc:RowStatus;
          description
           "An object that allows entries in this table to be
            created and deleted using the RowStatus convention.";
          smiv2:max-access "read-write";
          smiv2:oid "1.3.6.1.2.1.71.1.3.3.1.9";
        }
      }
    }

    container nhrpServerStatTable {
      description
       "Statistics collected by Next Hop Servers.";
      smiv2:oid "1.3.6.1.2.1.71.1.3.4";

      list nhrpServerStatEntry {
        key "nhrpServerIndex";
        description
         "Statistics for a particular NHS. The statistics are
          broken into received (Rx), transmitted (Tx)
          and forwarded (Fw).  Forwarded (Fw) would be done
          by a transit NHS.";
        smiv2:oid "1.3.6.1.2.1.71.1.3.4.1";

        leaf nhrpServerIndex {
          type leafref {
            path "/NHRP-MIB:NHRP-MIB/NHRP-MIB:nhrpServerTable/NHRP-MIB:nhrpServerEntry/NHRP-MIB:nhrpServerIndex";
          }
        }

        leaf nhrpServerStatRxResolveReq {
          type yang:counter32;
          description
           "The number of NHRP Resolution Requests received by this
            server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.1";
        }

        leaf nhrpServerStatTxResolveReplyAck {
          type yang:counter32;
          description
           "The number of positively acknowledged NHRP
            Resolution Replies transmitted by this server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.2";
        }

        leaf nhrpServerStatTxResolveReplyNakProhibited {
          type yang:counter32;
          description
           "The number of NAKed NHRP Resolution Replies
            transmitted by this server with the code
            'Administratively Prohibited'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.3";
        }

        leaf nhrpServerStatTxResolveReplyNakInsufResources {
          type yang:counter32;
          description
           "The number of NAKed NHRP Resolution Replies
            transmitted by this server with the code
            'Insufficient Resources'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.4";
        }

        leaf nhrpServerStatTxResolveReplyNakNoBinding {
          type yang:counter32;
          description
           "The number of NAKed NHRP Resolution Replies
            transmitted by this server with the code
            'No Internetworking Layer Address to NBMA
            Address Binding Exists'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.5";
        }

        leaf nhrpServerStatTxResolveReplyNakNotUnique {
          type yang:counter32;
          description
           "The number of NAKed NHRP Resolution Replies
            transmitted by this server with the code
            'Binding Exists But Is Not Unique'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.6";
        }

        leaf nhrpServerStatRxRegisterReq {
          type yang:counter32;
          description
           "The number of NHRP Registration Requests received
            by this server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.7";
        }

        leaf nhrpServerStatTxRegisterAck {
          type yang:counter32;
          description
           "The number of positively acknowledged NHRP Registration
            Replies transmitted by this server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.8";
        }

        leaf nhrpServerStatTxRegisterNakProhibited {
          type yang:counter32;
          description
           "The number of NAKed NHRP Registration Replies
            transmitted by this server with the code
            'Administratively Prohibited'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.9";
        }

        leaf nhrpServerStatTxRegisterNakInsufResources {
          type yang:counter32;
          description
           "The number of NAKed NHRP Registration Replies
            transmitted by this server with the code
            'Insufficient Resources'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.10";
        }

        leaf nhrpServerStatTxRegisterNakAlreadyReg {
          type yang:counter32;
          description
           "The number of NAKed NHRP Registration Replies
            transmitted by this server with the code
            'Unique Internetworking Layer Address Already
            Registered'.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.11";
        }

        leaf nhrpServerStatRxPurgeReq {
          type yang:counter32;
          description
           "The number of NHRP Purge Requests received by
            this server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.12";
        }

        leaf nhrpServerStatTxPurgeReq {
          type yang:counter32;
          description
           "The number of NHRP Purge Requests transmitted by this
            server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.13";
        }

        leaf nhrpServerStatRxPurgeReply {
          type yang:counter32;
          description
           "The number of NHRP Purge Replies received by this
            server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.14";
        }

        leaf nhrpServerStatTxPurgeReply {
          type yang:counter32;
          description
           "The number of NHRP Purge Replies transmitted by
            this server.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.15";
        }

        leaf nhrpServerStatRxErrUnrecognizedExtension {
          type yang:counter32;
          description
           "The number of NHRP Error Indication packets received
            by this server with the error code
            
            'Unrecognized Extension'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.16";
        }

        leaf nhrpServerStatRxErrLoopDetected {
          type yang:counter32;
          description
           "The number of NHRP Error Indication packets received
            by this server with the error code 'NHRP Loop Detected'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.17";
        }

        leaf nhrpServerStatRxErrProtoAddrUnreachable {
          type yang:counter32;
          description
           "The number of NHRP Error Indication packets received
            by this server with the error code 'Protocol Address
            Unreachable'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.18";
        }

        leaf nhrpServerStatRxErrProtoError {
          type yang:counter32;
          description
           "The number of NHRP Error Indication packets received
            by this server with the error code 'Protocol Error'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.19";
        }

        leaf nhrpServerStatRxErrSduSizeExceeded {
          type yang:counter32;
          description
           "The number of NHRP Error Indication packets received
            by this server with the error code 'NHRP SDU Size
            Exceeded'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.20";
        }

        leaf nhrpServerStatRxErrInvalidExtension {
          type yang:counter32;
          description
           "The number of NHRP Error Indication packets received
            by this server with the error code 'Invalid Extension'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.21";
        }

        leaf nhrpServerStatRxErrInvalidResReplyReceived {
          type yang:counter32;
          description
           "The number of NHRP Error Indication packets received
            by this server with the error code 'Invalid Resolution
            Reply Received'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.22";
        }

        leaf nhrpServerStatRxErrAuthenticationFailure {
          type yang:counter32;
          description
           "The number of NHRP Error Indication packets
            received by this server with the error code
            'Authentication Failure'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.23";
        }

        leaf nhrpServerStatRxErrHopCountExceeded {
          type yang:counter32;
          description
           "The number of NHRP Error Indication packets
            received by this server with the error code
            'Hop Count Exceeded'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.24";
        }

        leaf nhrpServerStatTxErrUnrecognizedExtension {
          type yang:counter32;
          description
           "The number of NHRP Error Indication packets
            transmitted by this server with the error code
            'Unrecognized Extension'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.25";
        }

        leaf nhrpServerStatTxErrLoopDetected {
          type yang:counter32;
          description
           "The number of NHRP Error Indication packets
            transmitted by this server with the error code
            'NHRP Loop Detected'.
            
            
            
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.26";
        }

        leaf nhrpServerStatTxErrProtoAddrUnreachable {
          type yang:counter32;
          description
           "The number of NHRP Error Indication packets
            transmitted by this server with the error code
            'Protocol Address Unreachable'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.27";
        }

        leaf nhrpServerStatTxErrProtoError {
          type yang:counter32;
          description
           "The number of NHRP Error Indication packets
            transmitted by this server with the error
            code 'Protocol Error'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.28";
        }

        leaf nhrpServerStatTxErrSduSizeExceeded {
          type yang:counter32;
          description
           "The number of NHRP Error Indication packets
            transmitted by this server with the error code
            'NHRP SDU Size Exceeded'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.29";
        }

        leaf nhrpServerStatTxErrInvalidExtension {
          type yang:counter32;
          description
           "The number of NHRP Error Indication packets
            transmitted by this server with the error code
            
            'Invalid Extension'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.30";
        }

        leaf nhrpServerStatTxErrAuthenticationFailure {
          type yang:counter32;
          description
           "The number of NHRP Error Indication packets
            transmitted by this server with the error code
            'Authentication Failure'.
            
            
            
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.31";
        }

        leaf nhrpServerStatTxErrHopCountExceeded {
          type yang:counter32;
          description
           "The number of NHRP Error Indication packets
            transmitted by this server with the error
            code 'Hop Count Exceeded'.
            
            Discontinuities in the value of this counter can occur
            at re-initialization of the management system, at
            NHRP Server re-initialization and at
            other times as indicated by the value of
            nhrpServerStatDiscontinuityTime.";
          reference
           "Section 5.2.7 NHRP Error Indication, RFC 2332 [17].";
          smiv2:max-access "read-only";
          smiv2:oid "1.3.6.1.2.1.71.1.3.4.1.32";
        }

        leaf nhrpServerStatFwResolveReq {
          type yang:counter32;
          description
           "The number of NHRP Resolution Requests
            forwarded by this server acting as a transit NHS.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.33";
        }

        leaf nhrpServerStatFwResolveReply {
          type yang:counter32;
          description
           "The number of NHRP Resolution Replies forwarded
            by this server acting as a transit NHS.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.34";
        }

        leaf nhrpServerStatFwRegisterReq {
          type yang:counter32;
          description
           "The number of NHRP Registration Requests forwarded
            by this server acting as a transit NHS.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.35";
        }

        leaf nhrpServerStatFwRegisterReply {
          type yang:counter32;
          description
           "The number of NHRP Registration Replies forwarded
            by this server acting as a transit NHS.
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.36";
        }

        leaf nhrpServerStatFwPurgeReq {
          type yang:counter32;
          description
           "The number of NHRP Purge Requests forwarded
            by this server acting as a transit NHS.
            
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.37";
        }

        leaf nhrpServerStatFwPurgeReply {
          type yang:counter32;
          description
           "The number of NHRP Purge Replies forwarded by this
            server acting as a transit NHS.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.38";
        }

        leaf nhrpServerStatFwErrorIndication {
          type yang:counter32;
          description
           "The number of NHRP Error Indication packets forwarded
            by this server acting as a transit NHS.
            
            Discontinuities in the value of this counter can occur
            at re-initialization of the management system, at
            NHRP Server re-initialization and at
            other times as indicated by the value of
            nhrpServerStatDiscontinuityTime.";
          smiv2:max-access "read-only";
          smiv2:oid "1.3.6.1.2.1.71.1.3.4.1.39";
        }

        leaf nhrpServerStatDiscontinuityTime {
          type yang:timestamp;
          description
           "The value of sysUpTime on the most recent occasion at
            which any one or more of this Server's counters
            suffered a discontinuity.  If no such discontinuities
            have occurred since the last re-initialization of the
            
            
            
            local management subsystem or the NHRP Server
            re-initialization associated with this entry, then
            this object contains a zero value.";
          reference
           "RFC 2233 [18].";
          smiv2:max-access "read-only";
          smiv2:oid "1.3.6.1.2.1.71.1.3.4.1.40";
        }
      }
    }
  }

  smiv2:alias "nhrpMIB" {
    smiv2:oid "1.3.6.1.2.1.71";
  }

  smiv2:alias "nhrpObjects" {
    smiv2:oid "1.3.6.1.2.1.71.1";
  }

  smiv2:alias "nhrpGeneralObjects" {
    smiv2:oid "1.3.6.1.2.1.71.1.1";
  }

  smiv2:alias "nhrpClientObjects" {
    smiv2:oid "1.3.6.1.2.1.71.1.2";
  }

  smiv2:alias "nhrpServerObjects" {
    smiv2:oid "1.3.6.1.2.1.71.1.3";
  }

  smiv2:alias "nhrpConformance" {
    smiv2:oid "1.3.6.1.2.1.71.2";
  }

  smiv2:alias "nhrpCompliances" {
    smiv2:oid "1.3.6.1.2.1.71.2.1";
  }

  smiv2:alias "nhrpGroups" {
    smiv2:oid "1.3.6.1.2.1.71.2.2";
  }

}
