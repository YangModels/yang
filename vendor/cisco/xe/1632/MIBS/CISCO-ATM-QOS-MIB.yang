/*
 * Generated by confdc --mib2yang-std
 * Source: mgmt/dmi/model/common/mib-source/CISCO-ATM-QOS-MIB.mib
 */
/*
 * This YANG module has been generated by smidump 0.5.0:
 *
 *      smidump -f yang CISCO-ATM-QOS-MIB
 *
 * Do not edit. Edit the source file instead!
 */

module CISCO-ATM-QOS-MIB {

  namespace "urn:ietf:params:xml:ns:yang:smiv2:CISCO-ATM-QOS-MIB";
  prefix CISCO-ATM-QOS-MIB;

  import ATM-FORUM-TC-MIB {
    prefix "atm-forum";
  }

  import ATM-MIB {
    prefix "atm-mib";
  }

  import IF-MIB {
    prefix "if-mib";
  }

  import ietf-yang-smiv2 {
    prefix "smiv2";
  }

  organization
   "Cisco Systems, Inc.";

  contact
   "Cisco Systems
    Customer Service
    
    Postal: 170 W. Tasman Drive
          San Jose, CA  95134
          SA
    
    Tel: +1 800 553-NETS
    
    Email: cs-atm@cisco.com";

  description
   "The MIB is created to provide ATM QoS information in
    these areas:
    
    1. Traffic shaping on a per-VC basis
    2. Traffic shaping on a per-VP basis 
    3. Per-VC queuing/buffering
    
    Although the initial requirements of the MIB are
    driven to support the GSR TAZ line card,
    CISCO-ATM-QOS-MIB is designed as a generic MIB to
    support ATM interfaces across all platforms.
    
    Here are the tables defined in this MIB:
    ciscoAtmQosVccTable 
         - to provide information on traffic shaping on 
           a per-VC basis.
                          
    ciscoAtmQosVpcTable 
         - to provide information on traffic shaping on
           a per-VP basis.
        
    ciscoAtmQosVcQueuingTable
    ciscoAtmQosVcQueuingClassTable
         - to provide information on per-VC
           queuing/buffering.";

  revision 2002-06-10 {
    description
     "Initial version of this MIB module.";
  }

  typedef VcParamConfigLocation {
    type enumeration {
      enum "configDefault" {
        value "1";
      }
      enum "configVcDirect" {
        value "2";
      }
      enum "configVcClass" {
        value "3";
      }
      enum "configVcClassSubInterface" {
        value "4";
      }
      enum "configVcClassInterface" {
        value "5";
      }
    }
    description
     "The configuration source of a vc parameter:
      1 - Not configured - using default
      2 - Configured on vc directly
      3 - VC-class configured on vc
      4 - VC-class configured on sub-interface
      5 - VC-class configured on main-interface.";
  }

  typedef VpState {
    type enumeration {
      enum "vpStateInactive" {
        value "1";
      }
      enum "vpStateActive" {
        value "2";
      }
    }
    description
     "States of virtual path:
      1 - Inactive
      2 - Active";
  }


  container CISCO-ATM-QOS-MIB {
    config false;

    container caqVccParamsTable {
      description
       "This table is defined to provide QoS information for
        each active ATM VC existing on the interface.";
      smiv2:oid "1.3.6.1.4.1.9.9.279.1.1.1";

      list caqVccParamsEntry {
        key "ifIndex atmVclVpi atmVclVci";
        description
         "This list contains the ATM QoS parameters provided by
          ciscoAtmQosVccEntry.";
        smiv2:oid "1.3.6.1.4.1.9.9.279.1.1.1.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf caqVccParamsType {
          type atm-forum:AtmServiceCategory;
          description
           "The service category of this virtual circuit connection.";
          smiv2:max-access "read-write";
          smiv2:oid "1.3.6.1.4.1.9.9.279.1.1.1.1.1";
        }

        leaf caqVccParamsPcrIn0 {
          type uint32;
          description
           "Input Peak Cell Rate (PCR) in kbps with 
            Cell Loss Priority bit set to 0 (clp0).";
          smiv2:max-access "read-write";
          smiv2:oid "1.3.6.1.4.1.9.9.279.1.1.1.1.2";
        }

        leaf caqVccParamsPcrIn01 {
          type uint32;
          description
           "Number of OAM F5 end to end loopback cells sent through
            the VCC.";
          smiv2:max-access "read-write";
          smiv2:oid "1.3.6.1.4.1.9.9.279.1.1.1.1.3";
        }

        leaf caqVccParamsPcrOut0 {
          type uint32;
          description
           "Output Peak Cell Rate (PCR) in kbps with
            Cell Loss Priority bit set to 0 (clp0).";
          smiv2:max-access "read-write";
          smiv2:oid "1.3.6.1.4.1.9.9.279.1.1.1.1.4";
        }

        leaf caqVccParamsPcrOut01 {
          type uint32;
          description
           "Output Peak Cell Rate (PCR) in kbps with
            Cell Loss Priority bit set to 1 (clp01).";
          smiv2:max-access "read-write";
          smiv2:oid "1.3.6.1.4.1.9.9.279.1.1.1.1.5";
        }

        leaf caqVccParamsScrIn0 {
          type uint32;
          description
           "Input Sustained Cell Rate (SCR) in kbps
            for connection with VBR type of QoS and
            Cell Loss Priority bit set to 0 (clp0).";
          smiv2:max-access "read-write";
          smiv2:oid "1.3.6.1.4.1.9.9.279.1.1.1.1.6";
        }

        leaf caqVccParamsScrIn01 {
          type uint32;
          description
           "Input Sustained Cell Rate (SCR) in kbps
            for connection with VBR type of QoS and
            Cell Loss Priority bit set to 1 (clp01).";
          smiv2:max-access "read-write";
          smiv2:oid "1.3.6.1.4.1.9.9.279.1.1.1.1.7";
        }

        leaf caqVccParamsScrOut0 {
          type uint32;
          description
           "Output Sustained Cell Rate (SCR) in kbps
            for connection with VBR type of QoS and
            Cell Loss Priority bit set to 0 (clp0).";
          smiv2:max-access "read-write";
          smiv2:oid "1.3.6.1.4.1.9.9.279.1.1.1.1.8";
        }

        leaf caqVccParamsScrOut01 {
          type uint32;
          description
           "Output Sustained Cell Rate (SCR) in kbps
            for connection with VBR type of QoS and
            Cell Loss Priority bit set to 1 (clp01).";
          smiv2:max-access "read-write";
          smiv2:oid "1.3.6.1.4.1.9.9.279.1.1.1.1.9";
        }

        leaf caqVccParamsBcsIn0 {
          type uint32;
          description
           "Input Burst Cell Size (BCS) for connection
            with VBR type of QoS and
            Cell Loss Priority bit set to 0 (clp0).";
          smiv2:max-access "read-write";
          smiv2:oid "1.3.6.1.4.1.9.9.279.1.1.1.1.10";
        }

        leaf caqVccParamsBcsIn01 {
          type uint32;
          description
           "Input Burst Cell Size (BCS) for connection
            with VBR type of QoS and
            Cell Loss Priority bit set to 1 (clp01).";
          smiv2:max-access "read-write";
          smiv2:oid "1.3.6.1.4.1.9.9.279.1.1.1.1.11";
        }

        leaf caqVccParamsBcsOut0 {
          type uint32;
          description
           "Output Burst Cell Size (BCS) for connection
            with VBR type of QoS and 
            Cell Loss Priority bit set to 0 (clp0).";
          smiv2:max-access "read-write";
          smiv2:oid "1.3.6.1.4.1.9.9.279.1.1.1.1.12";
        }

        leaf caqVccParamsBcsOut01 {
          type uint32;
          description
           "Output Burst Cell Size (BCS) for connection
            with VBR type of QoS and
            Cell Loss Priority bit set to 1 (clp01).";
          smiv2:max-access "read-write";
          smiv2:oid "1.3.6.1.4.1.9.9.279.1.1.1.1.13";
        }

        leaf caqVccParamsInheritLevel {
          type CISCO-ATM-QOS-MIB:VcParamConfigLocation;
          description
           "The source of configuration for peak cell rate.";
          smiv2:max-access "read-only";
          smiv2:oid "1.3.6.1.4.1.9.9.279.1.1.1.1.14";
        }

        leaf caqVccParamsMcrIn {
          type uint32;
          description
           "Input Minimum Cell Rate (MCR) in kbps for
            connection with VBR-nrt or ABR type of QoS.";
          smiv2:max-access "read-write";
          smiv2:oid "1.3.6.1.4.1.9.9.279.1.1.1.1.15";
        }

        leaf caqVccParamsMcrOut {
          type uint32;
          description
           "Output Minimum Cell Rate (MCR) in kbps for
            connection with VBR-nrt or ABR type of QoS.";
          smiv2:max-access "read-write";
          smiv2:oid "1.3.6.1.4.1.9.9.279.1.1.1.1.16";
        }

        leaf caqVccParamsInvRdf {
          type uint32;
          description
           "Inverse of rate decrease factor.";
          smiv2:max-access "read-write";
          smiv2:oid "1.3.6.1.4.1.9.9.279.1.1.1.1.17";
        }

        leaf caqVccParamsInvRif {
          type uint32;
          description
           "Inverse of rate increase factor.";
          smiv2:max-access "read-write";
          smiv2:oid "1.3.6.1.4.1.9.9.279.1.1.1.1.18";
        }

        leaf caqVccParamsRfl {
          type CISCO-ATM-QOS-MIB:VcParamConfigLocation;
          description
           "The source of configuration for rate factor.";
          smiv2:max-access "read-only";
          smiv2:oid "1.3.6.1.4.1.9.9.279.1.1.1.1.19";
        }

        leaf caqVccParamsCdv {
          type uint32;
          description
           "Cell delay variation.";
          smiv2:max-access "read-only";
          smiv2:oid "1.3.6.1.4.1.9.9.279.1.1.1.1.20";
        }

        leaf caqVccParamsCdvt {
          type uint32;
          description
           "Cell delay variation tolerance.";
          smiv2:max-access "read-write";
          smiv2:oid "1.3.6.1.4.1.9.9.279.1.1.1.1.21";
        }

        leaf caqVccParamsIcr {
          type uint32;
          description
           "Initial cell rate.";
          smiv2:max-access "read-write";
          smiv2:oid "1.3.6.1.4.1.9.9.279.1.1.1.1.22";
        }

        leaf caqVccParamsTbe {
          type uint32;
          description
           "Transient buffer exposure.";
          smiv2:max-access "read-write";
          smiv2:oid "1.3.6.1.4.1.9.9.279.1.1.1.1.23";
        }

        leaf caqVccParamsFrtt {
          type uint32;
          description
           "Fixed round-trip time.";
          smiv2:max-access "read-write";
          smiv2:oid "1.3.6.1.4.1.9.9.279.1.1.1.1.24";
        }

        leaf caqVccParamsNrm {
          type uint32;
          description
           "Maximum number of tx cells for each forward rm cell.";
          smiv2:max-access "read-write";
          smiv2:oid "1.3.6.1.4.1.9.9.279.1.1.1.1.25";
        }

        leaf caqVccParamsInvTrm {
          type uint32;
          description
           "Maximum time between forward rm cells.";
          smiv2:max-access "read-write";
          smiv2:oid "1.3.6.1.4.1.9.9.279.1.1.1.1.26";
        }

        leaf caqVccParamsInvCdf {
          type uint32;
          description
           "Inverse of cutoff decrease factor.";
          smiv2:max-access "read-write";
          smiv2:oid "1.3.6.1.4.1.9.9.279.1.1.1.1.27";
        }

        leaf caqVccParamsAdtf {
          type uint32;
          description
           "Allowed cell rate decrease time factor.";
          smiv2:max-access "read-write";
          smiv2:oid "1.3.6.1.4.1.9.9.279.1.1.1.1.28";
        }
      }
    }

    container caqVpcParamsTable {
      description
       "This table is defined to provide QoS information for
        each active ATM VP existing on the interface.";
      smiv2:oid "1.3.6.1.4.1.9.9.279.1.2.1";

      list caqVpcParamsEntry {
        key "ifIndex atmVplVpi";
        description
         "This list contains the ATM QoS parameters provided by
          ciscoAtmQosVpcEntry.";
        smiv2:oid "1.3.6.1.4.1.9.9.279.1.2.1.1";

        leaf ifIndex {
          type leafref {
            path "/if-mib:IF-MIB/if-mib:ifTable/if-mib:ifEntry/if-mib:ifIndex";
          }
        }

        leaf atmVplVpi {
          type leafref {
            path "/atm-mib:ATM-MIB/atm-mib:atmVplTable/atm-mib:atmVplEntry/atm-mib:atmVplVpi";
          }
        }

        leaf caqVpcParamsVpState {
          type CISCO-ATM-QOS-MIB:VpState;
          description
           "VP state of the current permanent virtual path.";
          smiv2:max-access "read-only";
          smiv2:oid "1.3.6.1.4.1.9.9.279.1.2.1.1.1";
        }

        leaf caqVpcParamsPeakRate {
          type uint32;
          description
           "Maximum rate in kbps at which the associated
            permanent virtual path can transmit data.";
          smiv2:max-access "read-only";
          smiv2:oid "1.3.6.1.4.1.9.9.279.1.2.1.1.2";
        }

        leaf caqVpcParamsCesRate {
          type uint32;
          description
           "Maximum rate in kbps at which CES VCs can transmit
            data with the associated permanent virtual path.";
          smiv2:max-access "read-only";
          smiv2:oid "1.3.6.1.4.1.9.9.279.1.2.1.1.3";
        }

        leaf caqVpcParamsDataVcCount {
          type int32 {
            range "0..65535";
          }
          description
           "Number of data VCs currently associated with
            the permanent virtual path.";
          smiv2:max-access "read-only";
          smiv2:oid "1.3.6.1.4.1.9.9.279.1.2.1.1.4";
        }

        leaf caqVpcParamsCesVcCount {
          type int32 {
            range "0..65535";
          }
          description
           "Number of CES VCs currently associated with
            the permanent virtual path.";
          smiv2:max-access "read-only";
          smiv2:oid "1.3.6.1.4.1.9.9.279.1.2.1.1.5";
        }

        leaf caqVpcParamsVcdF4Seg {
          type int32 {
            range "0..65535";
          }
          description
           "Vcd for F4 OAM segment processing.";
          smiv2:max-access "read-only";
          smiv2:oid "1.3.6.1.4.1.9.9.279.1.2.1.1.6";
        }

        leaf caqVpcParamsVcdF4Ete {
          type int32 {
            range "0..65535";
          }
          description
           "Vcd for F4 OAM end to end processing.";
          smiv2:max-access "read-only";
          smiv2:oid "1.3.6.1.4.1.9.9.279.1.2.1.1.7";
        }

        leaf caqVpcParamsScr {
          type uint32;
          description
           "Sustained cell rate associated with the PVP.";
          smiv2:max-access "read-only";
          smiv2:oid "1.3.6.1.4.1.9.9.279.1.2.1.1.8";
        }

        leaf caqVpcParamsMbs {
          type uint32;
          description
           "Maximum burst size associated with the PVP.";
          smiv2:max-access "read-only";
          smiv2:oid "1.3.6.1.4.1.9.9.279.1.2.1.1.9";
        }

        leaf caqVpcParamsAvailBw {
          type uint32;
          description
           "Bandwidth in Kbps currently currently available
            on this PVP.";
          smiv2:max-access "read-only";
          smiv2:oid "1.3.6.1.4.1.9.9.279.1.2.1.1.10";
        }
      }
    }

    container caqQueuingParamsTable {
      description
       "This table provides queuing related information
        for a VC existing on an ATM interface.";
      smiv2:oid "1.3.6.1.4.1.9.9.279.1.3.1";

      list caqQueuingParamsEntry {
        key "ifIndex atmVclVpi atmVclVci";
        description
         "This is defined as an entry in caqQueuingParamsTable.";
        smiv2:oid "1.3.6.1.4.1.9.9.279.1.3.1.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf caqQueuingParamsMeanQDepth {
          type uint32;
          description
           "Mean Queue Depth associated with the vc.  This value
            is calculated based on the actual queue depth on the
            interface and the exponential weighting constant.";
          smiv2:max-access "read-only";
          smiv2:oid "1.3.6.1.4.1.9.9.279.1.3.1.1.1";
        }
      }
    }

    container caqQueuingParamsClassTable {
      description
       "This table provides queuing information for all 
        queuing classes associating with a VC.";
      smiv2:oid "1.3.6.1.4.1.9.9.279.1.3.2";

      list caqQueuingParamsClassEntry {
        key "ifIndex atmVclVpi atmVclVci caqQueuingParamsClassIndex";
        description
         "This is defined as an entry in ciscoAtmQosVcQueuingClassTable
          to provide queuing information of a specific class.";
        smiv2:oid "1.3.6.1.4.1.9.9.279.1.3.2.1";

        leaf ifIndex {
          type leafref {
            path "/if-mib:IF-MIB/if-mib:ifTable/if-mib:ifEntry/if-mib:ifIndex";
          }
        }

        leaf atmVclVpi {
          type leafref {
            path "/atm-mib:ATM-MIB/atm-mib:atmVclTable/atm-mib:atmVclEntry/atm-mib:atmVclVpi";
          }
        }

        leaf atmVclVci {
          type leafref {
            path "/atm-mib:ATM-MIB/atm-mib:atmVclTable/atm-mib:atmVclEntry/atm-mib:atmVclVci";
          }
        }

        leaf caqQueuingParamsClassIndex {
          type int32 {
            range "0..8";
          }
          description
           "A class index, which associates with an IP precedence
            (0 to 8), is defined to reference individual
            caqQueuingParamsClassEntry.";
          smiv2:max-access "not-accessible";
          smiv2:oid "1.3.6.1.4.1.9.9.279.1.3.2.1.1";
        }

        leaf caqQueuingParamsClassRandDrp {
          type uint32;
          description
           "Number of packets dropped when Mean Queue
            Length is between Minimum Threshold and
            Maximum Threshold range.";
          smiv2:max-access "read-only";
          smiv2:oid "1.3.6.1.4.1.9.9.279.1.3.2.1.2";
        }

        leaf caqQueuingParamsClassTailDrp {
          type uint32;
          description
           "Number of packets dropped because the Mean
            Queue Depth exceeds the Maximum Threshold value.";
          smiv2:max-access "read-only";
          smiv2:oid "1.3.6.1.4.1.9.9.279.1.3.2.1.3";
        }

        leaf caqQueuingParamsClassMinThre {
          type uint32;
          description
           "Minimum Threshold value in kbps.";
          smiv2:max-access "read-only";
          smiv2:oid "1.3.6.1.4.1.9.9.279.1.3.2.1.4";
        }

        leaf caqQueuingParamsClassMaxThre {
          type uint32;
          description
           "Maximum Threshold value in kbps.";
          smiv2:max-access "read-only";
          smiv2:oid "1.3.6.1.4.1.9.9.279.1.3.2.1.5";
        }

        leaf caqQueuingParamsClassMrkProb {
          type uint32;
          description
           "Mark probability denominator.  This is the value used
            in the calculation of a packet being dropped when
            the average queue size is between the minimum
            threshold and the maximum threshold.";
          smiv2:max-access "read-only";
          smiv2:oid "1.3.6.1.4.1.9.9.279.1.3.2.1.6";
        }
      }
    }
  }

  smiv2:alias "ciscoAtmQosMIB" {
    smiv2:oid "1.3.6.1.4.1.9.9.279";
  }

  smiv2:alias "ciscoAtmQosMIBNotifs" {
    smiv2:oid "1.3.6.1.4.1.9.9.279.0";
  }

  smiv2:alias "ciscoAtmQosMIBObjects" {
    smiv2:oid "1.3.6.1.4.1.9.9.279.1";
  }

  smiv2:alias "caqVccParams" {
    smiv2:oid "1.3.6.1.4.1.9.9.279.1.1";
  }

  smiv2:alias "caqVpcParams" {
    smiv2:oid "1.3.6.1.4.1.9.9.279.1.2";
  }

  smiv2:alias "caqQueuingParams" {
    smiv2:oid "1.3.6.1.4.1.9.9.279.1.3";
  }

  smiv2:alias "ciscoAtmQosMIBConform" {
    smiv2:oid "1.3.6.1.4.1.9.9.279.2";
  }

  smiv2:alias "ciscoAtmQosMIBCompliances" {
    smiv2:oid "1.3.6.1.4.1.9.9.279.2.1";
  }

  smiv2:alias "ciscoAtmQosMIBGroups" {
    smiv2:oid "1.3.6.1.4.1.9.9.279.2.2";
  }

}
