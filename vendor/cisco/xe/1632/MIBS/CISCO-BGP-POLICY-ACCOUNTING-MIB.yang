/*
 * Generated by confdc --mib2yang-std
 * Source: mgmt/dmi/model/common/mib-source/CISCO-BGP-POLICY-ACCOUNTING-MIB.mib
 */
/*
 * This YANG module has been generated by smidump 0.5.0:
 *
 *      smidump -f yang CISCO-BGP-POLICY-ACCOUNTING-MIB
 *
 * Do not edit. Edit the source file instead!
 */

module CISCO-BGP-POLICY-ACCOUNTING-MIB {

  namespace "urn:ietf:params:xml:ns:yang:smiv2:CISCO-BGP-POLICY-ACCOUNTING-MIB";
  prefix CISCO-BGP-POLICY-ACCOUNTING-MIB;

  import IF-MIB {
    prefix "if-mib";
  }

  import ietf-yang-smiv2 {
    prefix "smiv2";
  }

  import ietf-yang-types {
    prefix "yang";
  }

  organization
   "Cisco Systems, Inc.";

  contact
   "       Cisco Systems
    Customer Service
    
    Postal: 170 W. Tasman Drive
    San Jose, CA  95134
    USA
    
    Tel: +1 800 553-NETS
    
    E-mail: cs-snmp@cisco.com";

  description
   "BGP policy based accounting information";

  revision 2002-07-26 {
    description
     "Added egress, packet and octet, counters for the BGP
      policy accounting feature.";
  }

  revision 1999-12-17 {
    description
     "Initial version of this MIB module.";
  }


  container CISCO-BGP-POLICY-ACCOUNTING-MIB {
    config false;

    container cbpAcctTable {
      description
       "The cbpAcctTable provides statistics about ingress and egress 
        traffic on an interface. This data could be used for purposes 
        like billing.";
      smiv2:oid "1.3.6.1.4.1.9.9.148.1.1";

      list cbpAcctEntry {
        key "ifIndex cbpAcctTrafficIndex";
        description
         "Each cbpAcctEntry provides statistics for traffic of interest
          on an ingress and/or egress interfaces. The traffic of interest 
          may be used for purposes like billing, and is referred to from 
          here on in the MIB by the term 'traffic-type', which corresponds
          to cbpAcctTrafficIndex. Traffic-types are configured by the user
          on a per interface basis.
          
          The statistics include ingress packet counts, ingress octet
          counts, egress packet counts and egress octet counts. Entries 
          are created when traffic-type is configured on an interface.
          Entries are deleted automatically when the user 
          removes the corresponding traffic-type configuration from an
          interface.";
        smiv2:oid "1.3.6.1.4.1.9.9.148.1.1.1";

        leaf ifIndex {
          type leafref {
            path "/if-mib:IF-MIB/if-mib:ifTable/if-mib:ifEntry/if-mib:ifIndex";
          }
        }

        leaf cbpAcctTrafficIndex {
          type int32 {
            range "1..2147483647";
          }
          description
           "An integer value greater than 0, that uniquely identifies
            a traffic-type. The traffic-type has no intrinsic meaning.
            It just means the traffic coming into an interface can be
            differentiated into different types. It is up to the user to
            give meaning to and configure the various traffic-types on an 
            interface.";
          smiv2:max-access "read-only";
          smiv2:oid "1.3.6.1.4.1.9.9.148.1.1.1.1";
        }

        leaf cbpAcctInPacketCount {
          type yang:counter64;
          description
           "The total number of packets received for a particular
            traffic-type on an interface.";
          smiv2:max-access "read-only";
          smiv2:oid "1.3.6.1.4.1.9.9.148.1.1.1.2";
        }

        leaf cbpAcctInOctetCount {
          type yang:counter64;
          description
           "The total number of octets received for a particular
            traffic-type on an interface.";
          smiv2:max-access "read-only";
          smiv2:oid "1.3.6.1.4.1.9.9.148.1.1.1.3";
        }

        leaf cbpAcctOutPacketCount {
          type yang:counter64;
          description
           "The total number of packets transmitted for a particular
            traffic-type on an interface.";
          smiv2:max-access "read-only";
          smiv2:oid "1.3.6.1.4.1.9.9.148.1.1.1.4";
        }

        leaf cbpAcctOutOctetCount {
          type yang:counter64;
          description
           "The total number of octets transmitted for a particular
            traffic-type on an interface.";
          smiv2:max-access "read-only";
          smiv2:oid "1.3.6.1.4.1.9.9.148.1.1.1.5";
        }
      }
    }
  }

  smiv2:alias "ciscoBgpPolAcctMIB" {
    smiv2:oid "1.3.6.1.4.1.9.9.148";
  }

  smiv2:alias "ciscoBgpPolAcctMIBObjects" {
    smiv2:oid "1.3.6.1.4.1.9.9.148.1";
  }

  smiv2:alias "ciscoBgpPolAcctMIBConformance" {
    smiv2:oid "1.3.6.1.4.1.9.9.148.3";
  }

  smiv2:alias "ciscoBgpPolAcctMIBCompliances" {
    smiv2:oid "1.3.6.1.4.1.9.9.148.3.1";
  }

  smiv2:alias "ciscoBgpPolAcctMIBGroups" {
    smiv2:oid "1.3.6.1.4.1.9.9.148.3.2";
  }

}
