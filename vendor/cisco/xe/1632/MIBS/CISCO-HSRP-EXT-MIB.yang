/*
 * Generated by confdc --mib2yang-std
 * Source: mgmt/dmi/model/common/mib-source/CISCO-HSRP-EXT-MIB.mib
 */
/*
 * This YANG module has been generated by smidump 0.5.0:
 *
 *      smidump -f yang CISCO-HSRP-EXT-MIB
 *
 * Do not edit. Edit the source file instead!
 */

module CISCO-HSRP-EXT-MIB {

  namespace "urn:ietf:params:xml:ns:yang:smiv2:CISCO-HSRP-EXT-MIB";
  prefix CISCO-HSRP-EXT-MIB;

  import CISCO-HSRP-MIB {
    prefix "cisco-hsrp";
  }

  import IF-MIB {
    prefix "if-mib";
  }

  import INET-ADDRESS-MIB {
    prefix "inet-address";
  }

  import SNMPv2-TC {
    prefix "snmpv2-tc";
  }

  import ietf-inet-types {
    prefix "inet";
  }

  import ietf-yang-smiv2 {
    prefix "smiv2";
  }

  organization
   "Cisco Systems, Inc.";

  contact
   "Cisco Systems
    Customer Service
    
    Postal: 170 W Tasman Drive
    San Jose, CA  95134
    USA
    
    Tel: +1 800 553-NETS
    
    E-mail: cs-hsrp@cisco.com";

  description
   "The Extension MIB module for the CISCO-HSRP-MIB which is
    based on RFC2281.
    
    This MIB provides an extension to the CISCO-HSRP-MIB which 
    defines Cisco's proprietary Hot Standby Routing Protocol 
    (HSRP), defined in RFC2281. The extensions cover assigning 
    of secondary HSRP ip addresses, modifying an HSRP Group's 
    priority by tracking the operational status of interfaces, 
    etc. 
    
    Terminology:
    HSRP is a protocol used amoung a group of routers for the 
    purpose of selecting an active router and a standby router. 
    
    An active router is the router of choice for routing 
    packets.
    
    A standby router is a router that takes over the routing 
    duties when an active router fails, or when preset 
    conditions have been met.
    
    A HSRP group or a standby group is a set of routers 
    which communicate using HSRP. An HSRP group has a group 
    MAC address and a group IP address. These are the 
    designated addresses. The active router assumes  
    (i.e. inherits) these group addresses. An HSRP group is
    identified by a ( ifIndex, cHsrpGrpNumber ) pair.
    
    BIA stands for Burned In Address.";

  revision 2010-09-02 {
    description
     "The following changes have been made.
      
      [1] Objects cHsrpExtIfTrackedIpNone has been deprecated.
      
      [2] Deprecates object group cHsrpExtIfTrackedGroupSup1, which
          supplementary to cHsrpExtIfTrackedGroup.
      
      
      [3] Added new compliance cHsrpExtComplianceRev2, which
          deprecates cHsrpExtComplianceRev1.";
  }

  revision 2010-02-05 {
    description
     "Added cHsrpExtIfTrackedIpNone to
      cHsrpExtIfTrackedTable
      
      Added new table cHsrpExtIfStandbyTable.
      
      Added OBJECT-GROUP cHsrpExtIfStandbyGroup91.
      
      Added OBJECT-GROUP cHsrpExtIfTrackedGroupSup1, which
      supplementary to cHsrpExtIfTrackedGroup.
      
      Added MODULE-COMPLIANCE cHsrpExtComplianceRev1, which
      deprecates cHsrpExtCompliance.";
  }

  revision 2006-02-15 {
    description
     "Updated the imports such that Unsigned32 is imported from
      SNMPv2-SMI instead of CISCO-TC. Updated the module 
      description. Also updated the descriptions of 
      cHsrpExtIfTrackedEntry and cHsrpExtIfTracked. Formatted the
      complete MIB.";
  }

  revision 1998-08-03 {
    description
     "Initial version of this mib.";
  }


  container CISCO-HSRP-EXT-MIB {
    config false;

    container cHsrpExtIfTrackedTable {
      description
       "A table containing information about tracked interfaces per
        HSRP group.";
      smiv2:oid "1.3.6.1.4.1.9.9.107.1.1.1";

      list cHsrpExtIfTrackedEntry {
        key "ifIndex cHsrpGrpNumber cHsrpExtIfTracked";
        description
         "Each row of this table allows the tracking of one
          interface of the HSRP group which is identified by the
          (ifIndex, cHsrpGrpNumber) values in this table's INDEX clause.
          Weight(priority) is given to each and every interface tracked. 
          When a tracked interface is unavailable, the HSRP priority of
          the router is decreased. i.e cHsrpGrpPriority value assigned 
          to an HSRP group will reduce by the value assigned to
          cHsrpExtIfTrackedPriority. This reduces the likelihood 
          of a router with a failed key interface becoming the 
          active router.
          
          Setting cHsrpExtIfTrackedRowStatus to active starts
          the tracking of cHsrpExtIfTracked by the HSRP group. 
          The value of cHsrpExtIfTrackedRowStatus may be set 
          to destroy at any time.
          
          Entries may not be created via SNMP without explicitly setting
          cHsrpExtIfTrackedRowStatus to either 'createAndGo' 
          or 'createAndWait'.
          
          Entries can be created and modified via the management
          protocol or by the device's local management interface.
          
          If the row is not active, and a local management interface
          command modifies that row, the row may transition to active
          state.
          
          A row entry in the cHsrpExtIfTrackedTable can not be created
          unless the corresponding row in the cHsrpGrpTable has been 
          created. If that corresponding row in cHsrpGrpTable is 
          deleted, the interfaces it tracks also get deleted.
          
          A row which is not in active state will timeout after a
          configurable period (five minutes by default). This timeout
          period can be changed by setting cHsrpConfigTimeout.";
        smiv2:oid "1.3.6.1.4.1.9.9.107.1.1.1.1";

        leaf ifIndex {
          type leafref {
            path "/if-mib:IF-MIB/if-mib:ifTable/if-mib:ifEntry/if-mib:ifIndex";
          }
        }

        leaf cHsrpGrpNumber {
          type leafref {
            path "/cisco-hsrp:CISCO-HSRP-MIB/cisco-hsrp:cHsrpGrpTable/cisco-hsrp:cHsrpGrpEntry/cisco-hsrp:cHsrpGrpNumber";
          }
        }

        leaf cHsrpExtIfTracked {
          type if-mib:InterfaceIndex;
          description
           "The ifIndex value of the tracked interface.";
          smiv2:max-access "not-accessible";
          smiv2:oid "1.3.6.1.4.1.9.9.107.1.1.1.1.1";
        }

        leaf cHsrpExtIfTrackedPriority {
          type uint32 {
            range "0..255";
          }
          description
           "Priority of the tracked interface for the corresponding
            { ifIndex, cHsrpGrpNumber } pair. In the range of 0 to 255, 0
            is the lowest priority and 255 is the highest. When a tracked 
            interface is unavailable, the cHsrpGrpPriority of the router 
            is decreased by the value of this object instance (If the 
            cHsrpGrpPriority is less than the 
            cHsrpExtIfTrackedPriority, then the HSRP priority 
            becomes 0). This allows a standby router to be configured 
            with a priority such that if the currently active router's 
            priority is lowered because the tracked interface goes down, 
            the standby router can takeover.";
          smiv2:defval "0";
          smiv2:max-access "read-write";
          smiv2:oid "1.3.6.1.4.1.9.9.107.1.1.1.1.2";
        }

        leaf cHsrpExtIfTrackedRowStatus {
          type snmpv2-tc:RowStatus;
          description
           "The control that allows modification, creation, and deletion
            of entries. For detailed rules see the DESCRIPTION for
            cHsrpExtIfTrackedEntry.";
          smiv2:max-access "read-write";
          smiv2:oid "1.3.6.1.4.1.9.9.107.1.1.1.1.3";
        }

        leaf cHsrpExtIfTrackedIpNone {
          type boolean;
          status deprecated;
          description
           "This object specifies the disable HSRP IPv4 virtual
            IP address.";
          smiv2:defval "false";
          smiv2:max-access "read-write";
          smiv2:oid "1.3.6.1.4.1.9.9.107.1.1.1.1.4";
        }
      }
    }

    container cHsrpExtSecAddrTable {
      description
       "A table containing information about secondary HSRP IP
        Addresses per interface and group.";
      smiv2:oid "1.3.6.1.4.1.9.9.107.1.1.2";

      list cHsrpExtSecAddrEntry {
        key "ifIndex cHsrpGrpNumber cHsrpExtSecAddrAddress";
        description
         "The CHsrpExtSecAddrEntry allows creation of secondary
          IP Addresses for each cHsrpGrpEntry row.
          
          Secondary addresses can be added by setting 
          cHsrpExtSecAddrRowStatus to be active. The value of
          cHsrpExtSecAddrRowStatus may be set to destroy at any
          time.
          
          Entries may not be created via SNMP without explicitly setting
          cHsrpExtSecAddrRowStatus to either 'createAndGo'
          or 'createAndWait'.
          
          Entries can be created and modified via the management
          protocol or by the device's local management interface.
          
          If the row is not active, and a local management interface
          command modifies that row, the row may transition to active
          state.
          
          A row which is not in active state will timeout after a
          configurable period (five minutes by default). This timeout
          period can be changed by setting cHsrpConfigTimeout.
          
          Before creation of a cHsrpExtSecAddrEntry row,
          either cHsrpGrpConfiguredVirtualIpAddr or 
          cHsrpGrpLearnedVirtualIpAddr must have a valid IP Address.
          This is because a secondary ip address cannot be created
          unless the primary ip address has already been set.
          
          To create a new cHsrpExtSecAddrEntry row, a management 
          station should choose the ifIndex of the interface which is to 
          be added as part of an HSRP group. Also, an HSRP group number 
          and a cHsrpExtSecAddrAddress should be chosen.
          
          Deleting a {ifIndex, cHsrpGrpNumber} row in the
          cHsrpGrpTable will delete all corresponding
          rows in the cHsrpExtSecAddrTable.
          Deleting a primary address value in the cHsrpGrpEntry row
          will delete all secondary addresses for the same
          {ifIndex, cHsrpGrpNumber} pair.";
        smiv2:oid "1.3.6.1.4.1.9.9.107.1.1.2.1";

        leaf ifIndex {
          type leafref {
            path "/if-mib:IF-MIB/if-mib:ifTable/if-mib:ifEntry/if-mib:ifIndex";
          }
        }

        leaf cHsrpGrpNumber {
          type leafref {
            path "/cisco-hsrp:CISCO-HSRP-MIB/cisco-hsrp:cHsrpGrpTable/cisco-hsrp:cHsrpGrpEntry/cisco-hsrp:cHsrpGrpNumber";
          }
        }

        leaf cHsrpExtSecAddrAddress {
          type inet:ipv4-address;
          description
           "A secondary IpAddress for the {ifIndex, cHsrpGrpNumber} pair.
            As explained in the DESCRIPTION for cHsrpExtSecAddrEntry, a
            primary address must exist before a secondary address for 
            the same {ifIndex, cHsrpGrpNumber} pair can be created.";
          smiv2:max-access "not-accessible";
          smiv2:oid "1.3.6.1.4.1.9.9.107.1.1.2.1.1";
        }

        leaf cHsrpExtSecAddrRowStatus {
          type snmpv2-tc:RowStatus;
          description
           "The control that allows modification, creation, and deletion
            of entries. For detailed rules see the DESCRIPTION for
            cHsrpExtSecAddrEntry.";
          smiv2:max-access "read-write";
          smiv2:oid "1.3.6.1.4.1.9.9.107.1.1.2.1.2";
        }
      }
    }

    container cHsrpExtIfStandbyTable {
      description
       "A table containing information about standby
        interfaces per HSRP group.";
      smiv2:oid "1.3.6.1.4.1.9.9.107.1.1.3";

      list cHsrpExtIfStandbyEntry {
        key "ifIndex cHsrpGrpNumber cHsrpExtIfStandbyIndex";
        description
         "The cHsrpExtIfStandbyEntry allows an HSRP group
          interface to track one or more standby interfaces.
          
          To create a new cHsrpExtIfStandbyEntry row, a
          management station should choose the ifIndex of
          the interface which is to be added as part of an
          HSRP group. Also, an HSRP group number and a
          cHsrpExtIfStandbyIndex should be chosen.";
        smiv2:oid "1.3.6.1.4.1.9.9.107.1.1.3.1";

        leaf ifIndex {
          type leafref {
            path "/if-mib:IF-MIB/if-mib:ifTable/if-mib:ifEntry/if-mib:ifIndex";
          }
        }

        leaf cHsrpGrpNumber {
          type leafref {
            path "/cisco-hsrp:CISCO-HSRP-MIB/cisco-hsrp:cHsrpGrpTable/cisco-hsrp:cHsrpGrpEntry/cisco-hsrp:cHsrpGrpNumber";
          }
        }

        leaf cHsrpExtIfStandbyIndex {
          type uint32 {
            range "1..4";
          }
          description
           "This object defines the index of the standby table.";
          smiv2:max-access "not-accessible";
          smiv2:oid "1.3.6.1.4.1.9.9.107.1.1.3.1.1";
        }

        leaf cHsrpExtIfStandbyDestAddrType {
          type inet-address:InetAddressType;
          description
           "This object specifies the type of Internet address
            denoted by cHsrpExtIfStandbyDestAddr.";
          smiv2:max-access "read-write";
          smiv2:oid "1.3.6.1.4.1.9.9.107.1.1.3.1.2";
        }

        leaf cHsrpExtIfStandbyDestAddr {
          type inet-address:InetAddress;
          description
           "This object specifies the destination IP address of
            the standby router.";
          smiv2:max-access "read-write";
          smiv2:oid "1.3.6.1.4.1.9.9.107.1.1.3.1.3";
        }

        leaf cHsrpExtIfStandbySourceAddrType {
          type inet-address:InetAddressType;
          description
           "This object specifies the type of Internet address
            denoted by cHsrpExtIfStandbySourceAddr.";
          smiv2:max-access "read-write";
          smiv2:oid "1.3.6.1.4.1.9.9.107.1.1.3.1.4";
        }

        leaf cHsrpExtIfStandbySourceAddr {
          type inet-address:InetAddress;
          description
           "This object specifies the source IP address of
            the standby router.";
          smiv2:max-access "read-write";
          smiv2:oid "1.3.6.1.4.1.9.9.107.1.1.3.1.5";
        }

        leaf cHsrpExtIfStandbyRowStatus {
          type snmpv2-tc:RowStatus;
          description
           "The control that allows modification, creation,
            and deletion of entries. Entries may not be created
            via SNMP without explicitly setting
            cHsrpExtIfStandbyRowStatus to either
            'createAndGo' or 'createAndWait'.";
          smiv2:max-access "read-write";
          smiv2:oid "1.3.6.1.4.1.9.9.107.1.1.3.1.6";
        }
      }
    }

    container cHsrpExtIfTable {
      description
       "HSRP-specific configurations for each physical interface.";
      smiv2:oid "1.3.6.1.4.1.9.9.107.1.2.1";

      list cHsrpExtIfEntry {
        key "ifIndex";
        description
         "If HSRP entries on this interface must use the BIA (Burned
          In Address), there must be an entry for the interface in this 
          table. Entries of this table are only accessible if HSRP has 
          been enabled i.e entries can not be created if HSRP is not
          enabled. Also, the interfaces should be of IEEE 802 ones
          (Ethernet, Token Ring, FDDI,VLAN, LANE, TR-LANE).
          
          Setting cHsrpExtIfRowStatus to active initiates the
          entry with default value for cHsrpExtIfUseBIA as FALSE.
          The value of cHsrpExtIfRowStatus may be set to destroy
          at any time. If the row is not initiated, it is similar to
          having cHsrpExtIfUseBIA as FALSE.
          
          Entries may not be created via SNMP without explicitly setting
          cHsrpExtIfRowStatus to either 'createAndGo' or 'createAndWait'.
          
          Entries can be created and modified via the management
          protocol or by the device's local management interface.
          
          If the row is not active, and a local management interface
          command modifies that row, the row may transition to active
          state.
          
          A row which is not in active state will timeout after a
          configurable period (five minutes by default). This timeout
          period can be changed by setting cHsrpConfigTimeout.";
        smiv2:oid "1.3.6.1.4.1.9.9.107.1.2.1.1";

        leaf ifIndex {
          type leafref {
            path "/if-mib:IF-MIB/if-mib:ifTable/if-mib:ifEntry/if-mib:ifIndex";
          }
        }

        leaf cHsrpExtIfUseBIA {
          type boolean;
          description
           "If set to TRUE, the HSRP Group MAC Address for all groups
            on this  interface will be the burned-in-address. Otherwise,
            this will be determined by ciscoHsrpGroupNumber. In case of
            sub-interfaces, UseBIA applies to all sub-interfaces on an 
            interface and to all groups on those sub-interfaces.";
          smiv2:defval "false";
          smiv2:max-access "read-write";
          smiv2:oid "1.3.6.1.4.1.9.9.107.1.2.1.1.1";
        }

        leaf cHsrpExtIfRowStatus {
          type snmpv2-tc:RowStatus;
          description
           "The control that allows modification, creation, and deletion
            of entries. For detailed rules see the DESCRIPTION for
            cHsrpExtIfEntry.";
          smiv2:max-access "read-write";
          smiv2:oid "1.3.6.1.4.1.9.9.107.1.2.1.1.2";
        }
      }
    }
  }

  smiv2:alias "ciscoHsrpExtMIB" {
    smiv2:oid "1.3.6.1.4.1.9.9.107";
  }

  smiv2:alias "ciscoHsrpExtMIBObjects" {
    smiv2:oid "1.3.6.1.4.1.9.9.107.1";
  }

  smiv2:alias "cHsrpExtGroup" {
    smiv2:oid "1.3.6.1.4.1.9.9.107.1.1";
  }

  smiv2:alias "cHsrpExtIfBIA" {
    smiv2:oid "1.3.6.1.4.1.9.9.107.1.2";
  }

  smiv2:alias "cHsrpExtConformance" {
    smiv2:oid "1.3.6.1.4.1.9.9.107.3";
  }

  smiv2:alias "cHsrpExtCompliances" {
    smiv2:oid "1.3.6.1.4.1.9.9.107.3.1";
  }

  smiv2:alias "cHsrpExtComplianceGroups" {
    smiv2:oid "1.3.6.1.4.1.9.9.107.3.2";
  }

}
