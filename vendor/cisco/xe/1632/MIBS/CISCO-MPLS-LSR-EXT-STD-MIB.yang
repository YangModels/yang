/*
 * Generated by confdc --mib2yang-std
 * Source: mgmt/dmi/model/common/mib-source/CISCO-MPLS-LSR-EXT-STD-MIB.mib
 */
/*
 * This YANG module has been generated by smidump 0.5.0:
 *
 *      smidump -f yang CISCO-MPLS-LSR-EXT-STD-MIB
 *
 * Do not edit. Edit the source file instead!
 */

module CISCO-MPLS-LSR-EXT-STD-MIB {

  namespace "urn:ietf:params:xml:ns:yang:smiv2:CISCO-MPLS-LSR-EXT-STD-MIB";
  prefix CISCO-MPLS-LSR-EXT-STD-MIB;

  import MPLS-LSR-STD-MIB {
    prefix "mpls-lsr";
  }

  import SNMPv2-TC {
    prefix "snmpv2-tc";
  }

  import ietf-yang-smiv2 {
    prefix "smiv2";
  }

  organization
   "Multiprotocol Label Switching (MPLS) Working Group";

  contact
   "Venkatesan Mahalingam
    Dell Inc,
    350 Holger way, San Jose, CA, USA
    Email: venkat.mahalingams@gmail.com
    
    Kannan KV Sampath
    Aricent,
    India
    Email: Kannan.Sampath@aricent.com
    
    Sam Aldrin
    Huawei Technologies
    2330 Central Express Way,
    Santa Clara, CA 95051, USA
    
    Email:  aldrin.ietf@gmail.com
    
    Thomas D. Nadeau
    CA Technologies
    273 Corporate Drive, Portsmouth, NH, USA
    Email: thomas.nadeau@ca.com";

  description
   "Copyright (c) 2012 IETF Trust and the persons identified
    as the document authors.  All rights reserved.
    
    This MIB module contains generic object definitions for
    
    
    MPLS LSR in transport networks.";

  revision 2012-04-30 {
    description
     "[Revision added by libsmi due to a LAST-UPDATED clause.]";
  }

  revision 2012-02-22 {
    description
     "MPLS LSR specific mib objects extension";
  }


  container CISCO-MPLS-LSR-EXT-STD-MIB {
    config false;

    container cmplsXCExtTable {
      description
       "This table sparse augments the mplsXCTable of
        MPLS-LSR-STD-MIB [RFC3813] to provide MPLS-TP specific
        information about associated tunnel information";
      reference
       "1. Multiprotocol Label Switching (MPLS) Label Switching
        Router (LSR) Management Information Base (MIB), RFC 3813.";
      smiv2:oid "1.3.6.1.4.1.9.10.145.1.1";

      list cmplsXCExtEntry {
        key "mplsXCIndex mplsXCInSegmentIndex mplsXCOutSegmentIndex";
        description
         "An entry in this table extends the cross connect
          information represented by an entry in
          the mplsXCTable in MPLS-LSR-STD-MIB [RFC3813] through
          a sparse augmentation.  An entry can be created by
          a network administrator via SNMP SET commands, or in
          response to signaling protocol events.";
        reference
         "1. Multiprotocol Label Switching (MPLS) Label Switching
          Router (LSR) Management Information Base (MIB), RFC 3813.";
        smiv2:oid "1.3.6.1.4.1.9.10.145.1.1.1";

        leaf mplsXCIndex {
          type leafref {
            path "/mpls-lsr:MPLS-LSR-STD-MIB/mpls-lsr:mplsXCTable/mpls-lsr:mplsXCEntry/mpls-lsr:mplsXCIndex";
          }
        }

        leaf mplsXCInSegmentIndex {
          type leafref {
            path "/mpls-lsr:MPLS-LSR-STD-MIB/mpls-lsr:mplsXCTable/mpls-lsr:mplsXCEntry/mpls-lsr:mplsXCInSegmentIndex";
          }
        }

        leaf mplsXCOutSegmentIndex {
          type leafref {
            path "/mpls-lsr:MPLS-LSR-STD-MIB/mpls-lsr:mplsXCTable/mpls-lsr:mplsXCEntry/mpls-lsr:mplsXCOutSegmentIndex";
          }
        }

        leaf cmplsXCExtTunnelPointer {
          type snmpv2-tc:RowPointer;
          description
           "This object indicates the back pointer to the tunnel
            entry segment.  This object cannot be modified if
            mplsXCRowStatus for the corresponding entry in the
            mplsXCTable is active(1).";
          reference
           "1. Multiprotocol Label Switching (MPLS) Label Switching
            Router (LSR) Management Information Base (MIB), RFC 3813.";
          smiv2:max-access "read-write";
          smiv2:oid "1.3.6.1.4.1.9.10.145.1.1.1.1";
        }

        leaf cmplsXCOppositeDirXCPtr {
          type snmpv2-tc:RowPointer;
          description
           "This object indicates the pointer to the opposite
            direction XC entry.  This object cannot be modified if
            mplsXCRowStatus for the corresponding entry in the
            mplsXCTable is active(1).";
          reference
           "1. Multiprotocol Label Switching (MPLS) Label Switching
            Router (LSR) Management Information Base (MIB), RFC 3813.";
          smiv2:max-access "read-write";
          smiv2:oid "1.3.6.1.4.1.9.10.145.1.1.1.2";
        }
      }
    }
  }

  smiv2:alias "cmplsLsrExtStdMIB" {
    smiv2:oid "1.3.6.1.4.1.9.10.145";
  }

  smiv2:alias "cmplsLsrExtNotifications" {
    smiv2:oid "1.3.6.1.4.1.9.10.145.0";
  }

  smiv2:alias "cmplsLsrExtObjects" {
    smiv2:oid "1.3.6.1.4.1.9.10.145.1";
  }

  smiv2:alias "cmplsLsrExtConformance" {
    smiv2:oid "1.3.6.1.4.1.9.10.145.2";
  }

  smiv2:alias "cmplsLsrExtGroups" {
    smiv2:oid "1.3.6.1.4.1.9.10.145.2.1";
  }

  smiv2:alias "cmplsLsrExtCompliances" {
    smiv2:oid "1.3.6.1.4.1.9.10.145.2.2";
  }

}
