/*
 * Generated by confdc --mib2yang-std
 * Source: mgmt/dmi/model/common/mib-source/TOKEN-RING-RMON-MIB.mib
 */
/*
 * This YANG module has been generated by smidump 0.5.0:
 *
 *      smidump -f yang TOKEN-RING-RMON-MIB
 *
 * Do not edit. Edit the source file instead!
 */

module TOKEN-RING-RMON-MIB {

  namespace "urn:ietf:params:xml:ns:yang:smiv2:TOKEN-RING-RMON-MIB";
  prefix TOKEN-RING-RMON-MIB;

  import ietf-yang-smiv2 {
    prefix "smiv2";
  }

  import ietf-yang-types {
    prefix "yang";
  }

  typedef OwnerString {
    type string;
    description
     "This data type is used to model an administratively
      assigned name of the owner of a resource.  This
      information is taken from the NVT ASCII character set.
      It is suggested that this name contain one or more of
      the following: ASCII form of the manager station's
      transport address, management station name (e.g.,
      domain name), network management personnel's name,
      location, or phone number.  In some cases the agent
      itself will be the owner of an entry.  In these cases,
      this string shall be set to a string starting with
      'agent'.";
    smiv2:display-hint "255a";
  }

  typedef MacAddress {
    type binary {
      length "6";
    }
  }

  typedef TimeInterval {
    type int32;
  }

  typedef EntryStatus {
    type enumeration {
      enum "valid" {
        value "1";
      }
      enum "createRequest" {
        value "2";
      }
      enum "underCreation" {
        value "3";
      }
      enum "invalid" {
        value "4";
      }
    }
  }


  container TOKEN-RING-RMON-MIB {
    config false;

    container tokenRingMLStatsTable {
      description
       "A list of Mac-Layer Token Ring statistics
        
        
        
        
        
        entries.";
      smiv2:oid "1.3.6.1.2.1.16.1.2";

      list tokenRingMLStatsEntry {
        key "tokenRingMLStatsIndex";
        description
         "A collection of Mac-Layer statistics kept for a
          particular Token Ring interface.";
        smiv2:oid "1.3.6.1.2.1.16.1.2.1";

        leaf tokenRingMLStatsIndex {
          type int32 {
            range "1..65535";
          }
          description
           "The value of this object uniquely identifies this
            tokenRingMLStats entry.";
          smiv2:max-access "read-only";
          smiv2:oid "1.3.6.1.2.1.16.1.2.1.1";
        }

        leaf tokenRingMLStatsDataSource {
          type yang:object-identifier-128;
          description
           "This object identifies the source of the data
            that this tokenRingMLStats entry is configured to
            analyze.  This source can be any tokenRing
            interface on this device.  In order to identify a
            particular interface, this object shall identify
            the instance of the ifIndex object, defined in
            MIB-II [3], for the desired interface.  For
            example, if an entry were to receive data from
            interface #1, this object would be set to
            ifIndex.1.
            
            The statistics in this group reflect all error
            reports on the local network segment attached to
            the identified interface.
            
            This object may not be modified if the associated
            tokenRingMLStatsStatus object is equal to
            valid(1).";
          smiv2:max-access "read-write";
          smiv2:oid "1.3.6.1.2.1.16.1.2.1.2";
        }

        leaf tokenRingMLStatsDropEvents {
          type yang:counter32;
          description
           "The total number of events in which packets were
            dropped by the probe due to lack of resources.
            Note that this number is not necessarily the
            number of packets dropped; it is just the number
            of times this condition has been detected.  This
            value is the same as the corresponding
            tokenRingPStatsDropEvents.";
          smiv2:max-access "read-only";
          smiv2:oid "1.3.6.1.2.1.16.1.2.1.3";
        }

        leaf tokenRingMLStatsMacOctets {
          type yang:counter32;
          description
           "The total number of octets of data in MAC packets
            (excluding those that were not good frames)
            received on the network (excluding framing bits
            but including FCS octets).";
          smiv2:max-access "read-only";
          smiv2:oid "1.3.6.1.2.1.16.1.2.1.4";
        }

        leaf tokenRingMLStatsMacPkts {
          type yang:counter32;
          description
           "The total number of MAC packets (excluding
            packets that were not good frames) received.";
          smiv2:max-access "read-only";
          smiv2:oid "1.3.6.1.2.1.16.1.2.1.5";
        }

        leaf tokenRingMLStatsRingPurgeEvents {
          type yang:counter32;
          description
           "The total number of times that the ring enters
            the ring purge state from normal ring state.  The
            ring purge state that comes in response to the
            claim token or beacon state is not counted.";
          smiv2:max-access "read-only";
          smiv2:oid "1.3.6.1.2.1.16.1.2.1.6";
        }

        leaf tokenRingMLStatsRingPurgePkts {
          type yang:counter32;
          description
           "The total number of ring purge MAC packets
            detected by probe.";
          smiv2:max-access "read-only";
          smiv2:oid "1.3.6.1.2.1.16.1.2.1.7";
        }

        leaf tokenRingMLStatsBeaconEvents {
          type yang:counter32;
          description
           "The total number of times that the ring enters a
            beaconing state (beaconFrameStreamingState,
            beaconBitStreamingState,
            
            
            
            
            
            beaconSetRecoveryModeState, or
            beaconRingSignalLossState) from a non-beaconing
            state.  Note that a change of the source address
            of the beacon packet does not constitute a new
            beacon event.";
          smiv2:max-access "read-only";
          smiv2:oid "1.3.6.1.2.1.16.1.2.1.8";
        }

        leaf tokenRingMLStatsBeaconTime {
          type TOKEN-RING-RMON-MIB:TimeInterval;
          description
           "The total amount of time that the ring has been
            in the beaconing state.";
          smiv2:max-access "read-only";
          smiv2:oid "1.3.6.1.2.1.16.1.2.1.9";
        }

        leaf tokenRingMLStatsBeaconPkts {
          type yang:counter32;
          description
           "The total number of beacon MAC packets detected
            by the probe.";
          smiv2:max-access "read-only";
          smiv2:oid "1.3.6.1.2.1.16.1.2.1.10";
        }

        leaf tokenRingMLStatsClaimTokenEvents {
          type yang:counter32;
          description
           "The total number of times that the ring enters
            the claim token state from normal ring state or
            ring purge state.  The claim token state that
            comes in response to a beacon state is not
            counted.";
          smiv2:max-access "read-only";
          smiv2:oid "1.3.6.1.2.1.16.1.2.1.11";
        }

        leaf tokenRingMLStatsClaimTokenPkts {
          type yang:counter32;
          description
           "The total number of claim token MAC packets
            detected by the probe.";
          smiv2:max-access "read-only";
          smiv2:oid "1.3.6.1.2.1.16.1.2.1.12";
        }

        leaf tokenRingMLStatsNAUNChanges {
          type yang:counter32;
          description
           "The total number of NAUN changes detected by the
            probe.";
          smiv2:max-access "read-only";
          smiv2:oid "1.3.6.1.2.1.16.1.2.1.13";
        }

        leaf tokenRingMLStatsLineErrors {
          type yang:counter32;
          description
           "The total number of line errors reported in error
            reporting packets detected by the probe.";
          smiv2:max-access "read-only";
          smiv2:oid "1.3.6.1.2.1.16.1.2.1.14";
        }

        leaf tokenRingMLStatsInternalErrors {
          type yang:counter32;
          description
           "The total number of adapter internal errors
            reported in error reporting packets detected by
            the probe.";
          smiv2:max-access "read-only";
          smiv2:oid "1.3.6.1.2.1.16.1.2.1.15";
        }

        leaf tokenRingMLStatsBurstErrors {
          type yang:counter32;
          description
           "The total number of burst errors reported in
            error reporting packets detected by the probe.";
          smiv2:max-access "read-only";
          smiv2:oid "1.3.6.1.2.1.16.1.2.1.16";
        }

        leaf tokenRingMLStatsACErrors {
          type yang:counter32;
          description
           "The total number of AC (Address Copied)  errors
            reported in error reporting packets detected by
            the probe.";
          smiv2:max-access "read-only";
          smiv2:oid "1.3.6.1.2.1.16.1.2.1.17";
        }

        leaf tokenRingMLStatsAbortErrors {
          type yang:counter32;
          description
           "The total number of abort delimiters reported in
            error reporting packets detected by the probe.";
          smiv2:max-access "read-only";
          smiv2:oid "1.3.6.1.2.1.16.1.2.1.18";
        }

        leaf tokenRingMLStatsLostFrameErrors {
          type yang:counter32;
          description
           "The total number of lost frame errors reported in
            error reporting packets detected by the probe.";
          smiv2:max-access "read-only";
          smiv2:oid "1.3.6.1.2.1.16.1.2.1.19";
        }

        leaf tokenRingMLStatsCongestionErrors {
          type yang:counter32;
          description
           "The total number of receive congestion errors
            reported in error reporting packets detected by
            the probe.";
          smiv2:max-access "read-only";
          smiv2:oid "1.3.6.1.2.1.16.1.2.1.20";
        }

        leaf tokenRingMLStatsFrameCopiedErrors {
          type yang:counter32;
          description
           "The total number of frame copied errors reported
            in error reporting packets detected by the probe.";
          smiv2:max-access "read-only";
          smiv2:oid "1.3.6.1.2.1.16.1.2.1.21";
        }

        leaf tokenRingMLStatsFrequencyErrors {
          type yang:counter32;
          description
           "The total number of frequency errors reported in
            error reporting packets detected by the probe.";
          smiv2:max-access "read-only";
          smiv2:oid "1.3.6.1.2.1.16.1.2.1.22";
        }

        leaf tokenRingMLStatsTokenErrors {
          type yang:counter32;
          description
           "The total number of token errors reported in
            error reporting packets detected by the probe.";
          smiv2:max-access "read-only";
          smiv2:oid "1.3.6.1.2.1.16.1.2.1.23";
        }

        leaf tokenRingMLStatsSoftErrorReports {
          type yang:counter32;
          description
           "The total number of soft error report frames
            detected by the probe.";
          smiv2:max-access "read-only";
          smiv2:oid "1.3.6.1.2.1.16.1.2.1.24";
        }

        leaf tokenRingMLStatsRingPollEvents {
          type yang:counter32;
          description
           "The total number of ring poll events detected by
            the probe (i.e. the number of ring polls initiated
            by the active monitor that were detected).";
          smiv2:max-access "read-only";
          smiv2:oid "1.3.6.1.2.1.16.1.2.1.25";
        }

        leaf tokenRingMLStatsOwner {
          type TOKEN-RING-RMON-MIB:OwnerString;
          description
           "The entity that configured this entry and is
            therefore using the resources assigned to it.";
          smiv2:max-access "read-write";
          smiv2:oid "1.3.6.1.2.1.16.1.2.1.26";
        }

        leaf tokenRingMLStatsStatus {
          type TOKEN-RING-RMON-MIB:EntryStatus;
          description
           "The status of this tokenRingMLStats entry.";
          smiv2:max-access "read-write";
          smiv2:oid "1.3.6.1.2.1.16.1.2.1.27";
        }
      }
    }

    container tokenRingPStatsTable {
      description
       "A list of promiscuous Token Ring statistics
        entries.";
      smiv2:oid "1.3.6.1.2.1.16.1.3";

      list tokenRingPStatsEntry {
        key "tokenRingPStatsIndex";
        description
         "A collection of promiscuous statistics kept for
          non-MAC packets on a particular Token Ring
          interface.";
        smiv2:oid "1.3.6.1.2.1.16.1.3.1";

        leaf tokenRingPStatsIndex {
          type int32 {
            range "1..65535";
          }
          description
           "The value of this object uniquely identifies this
            tokenRingPStats entry.";
          smiv2:max-access "read-only";
          smiv2:oid "1.3.6.1.2.1.16.1.3.1.1";
        }

        leaf tokenRingPStatsDataSource {
          type yang:object-identifier-128;
          description
           "This object identifies the source of the data
            that this tokenRingPStats entry is configured to
            analyze.  This source can be any tokenRing
            interface on this device.  In order to identify a
            particular interface, this object shall identify
            the instance of the ifIndex object, defined in
            MIB-II [3], for the desired interface.  For
            example, if an entry were to receive data from
            interface #1, this object would be set to
            ifIndex.1.
            
            The statistics in this group reflect all non-MAC
            packets on the local network segment attached to
            the identified interface.
            
            This object may not be modified if the associated
            tokenRingPStatsStatus object is equal to
            valid(1).";
          smiv2:max-access "read-write";
          smiv2:oid "1.3.6.1.2.1.16.1.3.1.2";
        }

        leaf tokenRingPStatsDropEvents {
          type yang:counter32;
          description
           "The total number of events in which packets were
            dropped by the probe due to lack of resources.
            Note that this number is not necessarily the
            number of packets dropped; it is just the number
            of times this condition has been detected.  This
            value is the same as the corresponding
            tokenRingMLStatsDropEvents";
          smiv2:max-access "read-only";
          smiv2:oid "1.3.6.1.2.1.16.1.3.1.3";
        }

        leaf tokenRingPStatsDataOctets {
          type yang:counter32;
          description
           "The total number of octets of data in good frames
            received on the network (excluding framing bits
            but including FCS octets) in non-MAC packets.";
          smiv2:max-access "read-only";
          smiv2:oid "1.3.6.1.2.1.16.1.3.1.4";
        }

        leaf tokenRingPStatsDataPkts {
          type yang:counter32;
          description
           "The total number of non-MAC packets in good
            frames.  received.";
          smiv2:max-access "read-only";
          smiv2:oid "1.3.6.1.2.1.16.1.3.1.5";
        }

        leaf tokenRingPStatsDataBroadcastPkts {
          type yang:counter32;
          description
           "The total number of good non-MAC frames received
            that were directed to an LLC broadcast address
            (0xFFFFFFFFFFFF or 0xC000FFFFFFFF).";
          smiv2:max-access "read-only";
          smiv2:oid "1.3.6.1.2.1.16.1.3.1.6";
        }

        leaf tokenRingPStatsDataMulticastPkts {
          type yang:counter32;
          description
           "The total number of good non-MAC frames received
            that were directed to a local or global multicast
            or functional address.  Note that this number does
            not include packets directed to the broadcast
            address.";
          smiv2:max-access "read-only";
          smiv2:oid "1.3.6.1.2.1.16.1.3.1.7";
        }

        leaf tokenRingPStatsDataPkts18to63Octets {
          type yang:counter32;
          description
           "The total number of good non-MAC frames received
            that were between 18 and 63 octets in length
            inclusive, excluding framing bits but including
            FCS octets.";
          smiv2:max-access "read-only";
          smiv2:oid "1.3.6.1.2.1.16.1.3.1.8";
        }

        leaf tokenRingPStatsDataPkts64to127Octets {
          type yang:counter32;
          description
           "The total number of good non-MAC frames received
            that were between 64 and 127 octets in length
            inclusive, excluding framing bits but including
            FCS octets.";
          smiv2:max-access "read-only";
          smiv2:oid "1.3.6.1.2.1.16.1.3.1.9";
        }

        leaf tokenRingPStatsDataPkts128to255Octets {
          type yang:counter32;
          description
           "The total number of good non-MAC frames received
            that were between 128 and 255 octets in length
            inclusive, excluding framing bits but including
            FCS octets.";
          smiv2:max-access "read-only";
          smiv2:oid "1.3.6.1.2.1.16.1.3.1.10";
        }

        leaf tokenRingPStatsDataPkts256to511Octets {
          type yang:counter32;
          description
           "The total number of good non-MAC frames received
            that were between 256 and 511 octets in length
            inclusive, excluding framing bits but including
            FCS octets.";
          smiv2:max-access "read-only";
          smiv2:oid "1.3.6.1.2.1.16.1.3.1.11";
        }

        leaf tokenRingPStatsDataPkts512to1023Octets {
          type yang:counter32;
          description
           "The total number of good non-MAC frames received
            that were between 512 and 1023 octets in length
            inclusive, excluding framing bits but including
            FCS octets.";
          smiv2:max-access "read-only";
          smiv2:oid "1.3.6.1.2.1.16.1.3.1.12";
        }

        leaf tokenRingPStatsDataPkts1024to2047Octets {
          type yang:counter32;
          description
           "The total number of good non-MAC frames received
            that were between 1024 and 2047 octets in length
            inclusive, excluding framing bits but including
            FCS octets.";
          smiv2:max-access "read-only";
          smiv2:oid "1.3.6.1.2.1.16.1.3.1.13";
        }

        leaf tokenRingPStatsDataPkts2048to4095Octets {
          type yang:counter32;
          description
           "The total number of good non-MAC frames received
            that were between 2048 and 4095 octets in length
            inclusive, excluding framing bits but including
            FCS octets.";
          smiv2:max-access "read-only";
          smiv2:oid "1.3.6.1.2.1.16.1.3.1.14";
        }

        leaf tokenRingPStatsDataPkts4096to8191Octets {
          type yang:counter32;
          description
           "The total number of good non-MAC frames received
            that were between 4096 and 8191 octets in length
            inclusive, excluding framing bits but including
            FCS octets.";
          smiv2:max-access "read-only";
          smiv2:oid "1.3.6.1.2.1.16.1.3.1.15";
        }

        leaf tokenRingPStatsDataPkts8192to18000Octets {
          type yang:counter32;
          description
           "The total number of good non-MAC frames received
            that were between 8192 and 18000 octets in length
            inclusive, excluding framing bits but including
            FCS octets.";
          smiv2:max-access "read-only";
          smiv2:oid "1.3.6.1.2.1.16.1.3.1.16";
        }

        leaf tokenRingPStatsDataPktsGreaterThan18000Octets {
          type yang:counter32;
          description
           "The total number of good non-MAC frames received
            that were greater than 18000 octets in length,
            excluding framing bits but including FCS octets.";
          smiv2:max-access "read-only";
          smiv2:oid "1.3.6.1.2.1.16.1.3.1.17";
        }

        leaf tokenRingPStatsOwner {
          type TOKEN-RING-RMON-MIB:OwnerString;
          description
           "The entity that configured this entry and is
            therefore using the resources assigned to it.";
          smiv2:max-access "read-write";
          smiv2:oid "1.3.6.1.2.1.16.1.3.1.18";
        }

        leaf tokenRingPStatsStatus {
          type TOKEN-RING-RMON-MIB:EntryStatus;
          description
           "The status of this tokenRingPStats entry.";
          smiv2:max-access "read-write";
          smiv2:oid "1.3.6.1.2.1.16.1.3.1.19";
        }
      }
    }

    container tokenRingMLHistoryTable {
      description
       "A list of Mac-Layer Token Ring statistics
        
        
        
        
        
        entries.";
      smiv2:oid "1.3.6.1.2.1.16.2.3";

      list tokenRingMLHistoryEntry {
        key "tokenRingMLHistoryIndex tokenRingMLHistorySampleIndex";
        description
         "A collection of Mac-Layer statistics kept for a
          particular Token Ring interface.";
        smiv2:oid "1.3.6.1.2.1.16.2.3.1";

        leaf tokenRingMLHistoryIndex {
          type int32 {
            range "1..65535";
          }
          description
           "The history of which this entry is a part.  The
            history identified by a particular value of this
            index is the same history as identified by the
            same value of historyControlIndex.";
          smiv2:max-access "read-only";
          smiv2:oid "1.3.6.1.2.1.16.2.3.1.1";
        }

        leaf tokenRingMLHistorySampleIndex {
          type int32;
          description
           "An index that uniquely identifies the particular
            Mac-Layer sample this entry represents among all
            Mac-Layer samples associated with the same
            historyControlEntry.  This index starts at 1 and
            increases by one as each new sample is taken.";
          smiv2:max-access "read-only";
          smiv2:oid "1.3.6.1.2.1.16.2.3.1.2";
        }

        leaf tokenRingMLHistoryIntervalStart {
          type yang:timeticks;
          description
           "The value of sysUpTime at the start of the
            interval over which this sample was measured.  If
            the probe keeps track of the time of day, it
            should start the first sample of the history at a
            time such that when the next hour of the day
            begins, a sample is started at that instant.  Note
            that following this rule may require the probe to
            delay collecting the first sample of the history,
            as each sample must be of the same interval.  Also
            note that the sample which is currently being
            collected is not accessible in this table until
            the end of its interval.";
          smiv2:max-access "read-only";
          smiv2:oid "1.3.6.1.2.1.16.2.3.1.3";
        }

        leaf tokenRingMLHistoryDropEvents {
          type yang:counter32;
          description
           "The total number of events in which packets were
            
            
            
            
            
            dropped by the probe due to lack of resources
            during this sampling interval.  Note that this
            number is not necessarily the number of packets
            dropped, it is just the number of times this
            condition has been detected.";
          smiv2:max-access "read-only";
          smiv2:oid "1.3.6.1.2.1.16.2.3.1.4";
        }

        leaf tokenRingMLHistoryMacOctets {
          type yang:counter32;
          description
           "The total number of octets of data in MAC packets
            (excluding those that were not good frames)
            received on the network during this sampling
            interval (excluding framing bits but including FCS
            octets).";
          smiv2:max-access "read-only";
          smiv2:oid "1.3.6.1.2.1.16.2.3.1.5";
        }

        leaf tokenRingMLHistoryMacPkts {
          type yang:counter32;
          description
           "The total number of MAC packets (excluding those
            that were not good frames) received during this
            sampling interval.";
          smiv2:max-access "read-only";
          smiv2:oid "1.3.6.1.2.1.16.2.3.1.6";
        }

        leaf tokenRingMLHistoryRingPurgeEvents {
          type yang:counter32;
          description
           "The total number of times that the ring entered
            the ring purge state from normal ring state during
            this sampling interval.  The ring purge state that
            comes from the claim token or beacon state is not
            counted.";
          smiv2:max-access "read-only";
          smiv2:oid "1.3.6.1.2.1.16.2.3.1.7";
        }

        leaf tokenRingMLHistoryRingPurgePkts {
          type yang:counter32;
          description
           "The total number of Ring Purge MAC packets
            detected by the probe during this sampling
            
            
            
            
            
            interval.";
          smiv2:max-access "read-only";
          smiv2:oid "1.3.6.1.2.1.16.2.3.1.8";
        }

        leaf tokenRingMLHistoryBeaconEvents {
          type yang:counter32;
          description
           "The total number of times that the ring enters a
            beaconing state (beaconFrameStreamingState,
            beaconBitStreamingState,
            beaconSetRecoveryModeState, or
            beaconRingSignalLossState) during this sampling
            interval.  Note that a change of the source
            address of the beacon packet does not constitute a
            new beacon event.";
          smiv2:max-access "read-only";
          smiv2:oid "1.3.6.1.2.1.16.2.3.1.9";
        }

        leaf tokenRingMLHistoryBeaconTime {
          type TOKEN-RING-RMON-MIB:TimeInterval;
          description
           "The amount of time that the ring has been in the
            beaconing state during this sampling interval.";
          smiv2:max-access "read-only";
          smiv2:oid "1.3.6.1.2.1.16.2.3.1.10";
        }

        leaf tokenRingMLHistoryBeaconPkts {
          type yang:counter32;
          description
           "The total number of beacon MAC packets detected
            by the probe during this sampling interval.";
          smiv2:max-access "read-only";
          smiv2:oid "1.3.6.1.2.1.16.2.3.1.11";
        }

        leaf tokenRingMLHistoryClaimTokenEvents {
          type yang:counter32;
          description
           "The total number of times that the ring enters
            the claim token state from normal ring state or
            ring purge state during this sampling interval.
            The claim token state that comes from the beacon
            state is not counted.";
          smiv2:max-access "read-only";
          smiv2:oid "1.3.6.1.2.1.16.2.3.1.12";
        }

        leaf tokenRingMLHistoryClaimTokenPkts {
          type yang:counter32;
          description
           "The total number of claim token MAC packets
            detected by the probe during this sampling
            interval.";
          smiv2:max-access "read-only";
          smiv2:oid "1.3.6.1.2.1.16.2.3.1.13";
        }

        leaf tokenRingMLHistoryNAUNChanges {
          type yang:counter32;
          description
           "The total number of NAUN changes detected by the
            probe during this sampling interval.";
          smiv2:max-access "read-only";
          smiv2:oid "1.3.6.1.2.1.16.2.3.1.14";
        }

        leaf tokenRingMLHistoryLineErrors {
          type yang:counter32;
          description
           "The total number of line errors reported in error
            reporting packets detected by the probe during
            this sampling interval.";
          smiv2:max-access "read-only";
          smiv2:oid "1.3.6.1.2.1.16.2.3.1.15";
        }

        leaf tokenRingMLHistoryInternalErrors {
          type yang:counter32;
          description
           "The total number of adapter internal errors
            reported in error reporting packets detected by
            the probe during this sampling interval.";
          smiv2:max-access "read-only";
          smiv2:oid "1.3.6.1.2.1.16.2.3.1.16";
        }

        leaf tokenRingMLHistoryBurstErrors {
          type yang:counter32;
          description
           "The total number of burst errors reported in
            error reporting packets detected by the probe
            during this sampling interval.";
          smiv2:max-access "read-only";
          smiv2:oid "1.3.6.1.2.1.16.2.3.1.17";
        }

        leaf tokenRingMLHistoryACErrors {
          type yang:counter32;
          description
           "The total number of AC (Address Copied) errors
            reported in error reporting packets detected by
            the probe during this sampling interval.";
          smiv2:max-access "read-only";
          smiv2:oid "1.3.6.1.2.1.16.2.3.1.18";
        }

        leaf tokenRingMLHistoryAbortErrors {
          type yang:counter32;
          description
           "The total number of abort delimiters reported in
            error reporting packets detected by the probe
            during this sampling interval.";
          smiv2:max-access "read-only";
          smiv2:oid "1.3.6.1.2.1.16.2.3.1.19";
        }

        leaf tokenRingMLHistoryLostFrameErrors {
          type yang:counter32;
          description
           "The total number of lost frame errors reported in
            error reporting packets detected by the probe
            during this sampling interval.";
          smiv2:max-access "read-only";
          smiv2:oid "1.3.6.1.2.1.16.2.3.1.20";
        }

        leaf tokenRingMLHistoryCongestionErrors {
          type yang:counter32;
          description
           "The total number of receive congestion errors
            reported in error reporting packets detected by
            the probe during this sampling interval.";
          smiv2:max-access "read-only";
          smiv2:oid "1.3.6.1.2.1.16.2.3.1.21";
        }

        leaf tokenRingMLHistoryFrameCopiedErrors {
          type yang:counter32;
          description
           "The total number of frame copied errors reported
            in error reporting packets detected by the probe
            during this sampling interval.";
          smiv2:max-access "read-only";
          smiv2:oid "1.3.6.1.2.1.16.2.3.1.22";
        }

        leaf tokenRingMLHistoryFrequencyErrors {
          type yang:counter32;
          description
           "The total number of frequency errors reported in
            error reporting packets detected by the probe
            during this sampling interval.";
          smiv2:max-access "read-only";
          smiv2:oid "1.3.6.1.2.1.16.2.3.1.23";
        }

        leaf tokenRingMLHistoryTokenErrors {
          type yang:counter32;
          description
           "The total number of token errors reported in
            error reporting packets detected by the probe
            during this sampling interval.";
          smiv2:max-access "read-only";
          smiv2:oid "1.3.6.1.2.1.16.2.3.1.24";
        }

        leaf tokenRingMLHistorySoftErrorReports {
          type yang:counter32;
          description
           "The total number of soft error report frames
            detected by the probe during this sampling
            interval.";
          smiv2:max-access "read-only";
          smiv2:oid "1.3.6.1.2.1.16.2.3.1.25";
        }

        leaf tokenRingMLHistoryRingPollEvents {
          type yang:counter32;
          description
           "The total number of ring poll events detected by
            the probe during this sampling interval.";
          smiv2:max-access "read-only";
          smiv2:oid "1.3.6.1.2.1.16.2.3.1.26";
        }

        leaf tokenRingMLHistoryActiveStations {
          type int32;
          description
           "The maximum number of active stations on the ring
            detected by the probe during this sampling
            
            
            
            
            
            interval.";
          smiv2:max-access "read-only";
          smiv2:oid "1.3.6.1.2.1.16.2.3.1.27";
        }
      }
    }

    container tokenRingPHistoryTable {
      description
       "A list of promiscuous Token Ring statistics
        entries.";
      smiv2:oid "1.3.6.1.2.1.16.2.4";

      list tokenRingPHistoryEntry {
        key "tokenRingPHistoryIndex tokenRingPHistorySampleIndex";
        description
         "A collection of promiscuous statistics kept for a
          particular Token Ring interface.";
        smiv2:oid "1.3.6.1.2.1.16.2.4.1";

        leaf tokenRingPHistoryIndex {
          type int32 {
            range "1..65535";
          }
          description
           "The history of which this entry is a part.  The
            history identified by a particular value of this
            index is the same history as identified by the
            same value of historyControlIndex.";
          smiv2:max-access "read-only";
          smiv2:oid "1.3.6.1.2.1.16.2.4.1.1";
        }

        leaf tokenRingPHistorySampleIndex {
          type int32;
          description
           "An index that uniquely identifies the particular
            sample this entry represents among all samples
            associated with the same historyControlEntry.
            This index starts at 1 and increases by one as
            each new sample is taken.";
          smiv2:max-access "read-only";
          smiv2:oid "1.3.6.1.2.1.16.2.4.1.2";
        }

        leaf tokenRingPHistoryIntervalStart {
          type yang:timeticks;
          description
           "The value of sysUpTime at the start of the
            interval over which this sample was measured.  If
            the probe keeps track of the time of day, it
            should start the first sample of the history at a
            time such that when the next hour of the day
            begins, a sample is started at that instant.  Note
            that following this rule may require the probe to
            delay collecting the first sample of the history,
            as each sample must be of the same interval.  Also
            note that the sample which is currently being
            collected is not accessible in this table until
            the end of its interval.";
          smiv2:max-access "read-only";
          smiv2:oid "1.3.6.1.2.1.16.2.4.1.3";
        }

        leaf tokenRingPHistoryDropEvents {
          type yang:counter32;
          description
           "The total number of events in which packets were
            dropped by the probe due to lack of resources
            during this sampling interval.  Note that this
            number is not necessarily the number of packets
            dropped, it is just the number of times this
            condition has been detected.";
          smiv2:max-access "read-only";
          smiv2:oid "1.3.6.1.2.1.16.2.4.1.4";
        }

        leaf tokenRingPHistoryDataOctets {
          type yang:counter32;
          description
           "The total number of octets of data in good frames
            received on the network (excluding framing bits
            but including FCS octets) in non-MAC packets
            during this sampling interval.";
          smiv2:max-access "read-only";
          smiv2:oid "1.3.6.1.2.1.16.2.4.1.5";
        }

        leaf tokenRingPHistoryDataPkts {
          type yang:counter32;
          description
           "The total number of good non-MAC frames received
            during this sampling interval.";
          smiv2:max-access "read-only";
          smiv2:oid "1.3.6.1.2.1.16.2.4.1.6";
        }

        leaf tokenRingPHistoryDataBroadcastPkts {
          type yang:counter32;
          description
           "The total number of good non-MAC frames received
            during this sampling interval that were directed
            to an LLC broadcast address (0xFFFFFFFFFFFF or
            0xC000FFFFFFFF).";
          smiv2:max-access "read-only";
          smiv2:oid "1.3.6.1.2.1.16.2.4.1.7";
        }

        leaf tokenRingPHistoryDataMulticastPkts {
          type yang:counter32;
          description
           "The total number of good non-MAC frames received
            during this sampling interval that were directed
            to a local or global multicast or functional
            address.  Note that this number does not include
            packets directed to the broadcast address.";
          smiv2:max-access "read-only";
          smiv2:oid "1.3.6.1.2.1.16.2.4.1.8";
        }

        leaf tokenRingPHistoryDataPkts18to63Octets {
          type yang:counter32;
          description
           "The total number of good non-MAC frames received
            during this sampling interval that were between 18
            and 63 octets in length inclusive, excluding
            framing bits but including FCS octets.";
          smiv2:max-access "read-only";
          smiv2:oid "1.3.6.1.2.1.16.2.4.1.9";
        }

        leaf tokenRingPHistoryDataPkts64to127Octets {
          type yang:counter32;
          description
           "The total number of good non-MAC frames received
            during this sampling interval that were between 64
            and 127 octets in length inclusive, excluding
            framing bits but including FCS octets.";
          smiv2:max-access "read-only";
          smiv2:oid "1.3.6.1.2.1.16.2.4.1.10";
        }

        leaf tokenRingPHistoryDataPkts128to255Octets {
          type yang:counter32;
          description
           "The total number of good non-MAC frames received
            during this sampling interval that were between
            128 and 255 octets in length inclusive, excluding
            framing bits but including FCS octets.";
          smiv2:max-access "read-only";
          smiv2:oid "1.3.6.1.2.1.16.2.4.1.11";
        }

        leaf tokenRingPHistoryDataPkts256to511Octets {
          type yang:counter32;
          description
           "The total number of good non-MAC frames received
            during this sampling interval that were between
            
            
            
            
            
            256 and 511 octets in length inclusive, excluding
            framing bits but including FCS octets.";
          smiv2:max-access "read-only";
          smiv2:oid "1.3.6.1.2.1.16.2.4.1.12";
        }

        leaf tokenRingPHistoryDataPkts512to1023Octets {
          type yang:counter32;
          description
           "The total number of good non-MAC frames received
            during this sampling interval that were between
            512 and 1023 octets in length inclusive, excluding
            framing bits but including FCS octets.";
          smiv2:max-access "read-only";
          smiv2:oid "1.3.6.1.2.1.16.2.4.1.13";
        }

        leaf tokenRingPHistoryDataPkts1024to2047Octets {
          type yang:counter32;
          description
           "The total number of good non-MAC frames received
            during this sampling interval that were between
            1024 and 2047 octets in length inclusive,
            excluding framing bits but including FCS octets.";
          smiv2:max-access "read-only";
          smiv2:oid "1.3.6.1.2.1.16.2.4.1.14";
        }

        leaf tokenRingPHistoryDataPkts2048to4095Octets {
          type yang:counter32;
          description
           "The total number of good non-MAC frames received
            during this sampling interval that were between
            2048 and 4095 octets in length inclusive,
            excluding framing bits but including FCS octets.";
          smiv2:max-access "read-only";
          smiv2:oid "1.3.6.1.2.1.16.2.4.1.15";
        }

        leaf tokenRingPHistoryDataPkts4096to8191Octets {
          type yang:counter32;
          description
           "The total number of good non-MAC frames received
            during this sampling interval that were between
            4096 and 8191 octets in length inclusive,
            excluding framing bits but including FCS octets.";
          smiv2:max-access "read-only";
          smiv2:oid "1.3.6.1.2.1.16.2.4.1.16";
        }

        leaf tokenRingPHistoryDataPkts8192to18000Octets {
          type yang:counter32;
          description
           "The total number of good non-MAC frames received
            during this sampling interval that were between
            8192 and 18000 octets in length inclusive,
            excluding framing bits but including FCS octets.";
          smiv2:max-access "read-only";
          smiv2:oid "1.3.6.1.2.1.16.2.4.1.17";
        }

        leaf tokenRingPHistoryDataPktsGreaterThan18000Octets {
          type yang:counter32;
          description
           "The total number of good non-MAC frames received
            during this sampling interval that were greater
            than 18000 octets in length, excluding framing
            bits but including FCS octets.";
          smiv2:max-access "read-only";
          smiv2:oid "1.3.6.1.2.1.16.2.4.1.18";
        }
      }
    }

    container ringStationControlTable {
      description
       "A list of ringStation table control entries.";
      smiv2:oid "1.3.6.1.2.1.16.10.1";

      list ringStationControlEntry {
        key "ringStationControlIfIndex";
        description
         "A list of parameters that set up the discovery of
          stations on a particular interface and the
          collection of statistics about these stations.";
        smiv2:oid "1.3.6.1.2.1.16.10.1.1";

        leaf ringStationControlIfIndex {
          type int32 {
            range "1..65535";
          }
          description
           "The value of this object uniquely identifies the
            interface on this remote network monitoring device
            from which ringStation data is collected.  The
            interface identified by a particular value of this
            object is the same interface as identified by the
            same value of the ifIndex object, defined in MIB-
            II [3].";
          smiv2:max-access "read-only";
          smiv2:oid "1.3.6.1.2.1.16.10.1.1.1";
        }

        leaf ringStationControlTableSize {
          type int32;
          description
           "The number of ringStationEntries in the
            ringStationTable associated with this
            ringStationControlEntry.";
          smiv2:max-access "read-only";
          smiv2:oid "1.3.6.1.2.1.16.10.1.1.2";
        }

        leaf ringStationControlActiveStations {
          type int32;
          description
           "The number of active ringStationEntries in the
            ringStationTable associated with this
            ringStationControlEntry.";
          smiv2:max-access "read-only";
          smiv2:oid "1.3.6.1.2.1.16.10.1.1.3";
        }

        leaf ringStationControlRingState {
          type enumeration {
            enum "normalOperation" {
              value "1";
            }
            enum "ringPurgeState" {
              value "2";
            }
            enum "claimTokenState" {
              value "3";
            }
            enum "beaconFrameStreamingState" {
              value "4";
            }
            enum "beaconBitStreamingState" {
              value "5";
            }
            enum "beaconRingSignalLossState" {
              value "6";
            }
            enum "beaconSetRecoveryModeState" {
              value "7";
            }
          }
          description
           "The current status of this ring.";
          smiv2:max-access "read-only";
          smiv2:oid "1.3.6.1.2.1.16.10.1.1.4";
        }

        leaf ringStationControlBeaconSender {
          type TOKEN-RING-RMON-MIB:MacAddress;
          description
           "The address of the sender of the last beacon
            frame received by the probe on this ring.  If no
            beacon frames have been received, this object
            shall be equal to six octets of zero.";
          smiv2:max-access "read-only";
          smiv2:oid "1.3.6.1.2.1.16.10.1.1.5";
        }

        leaf ringStationControlBeaconNAUN {
          type TOKEN-RING-RMON-MIB:MacAddress;
          description
           "The address of the NAUN in the last beacon frame
            received by the probe on this ring.  If no beacon
            frames have been received, this object shall be
            equal to six octets of zero.";
          smiv2:max-access "read-only";
          smiv2:oid "1.3.6.1.2.1.16.10.1.1.6";
        }

        leaf ringStationControlActiveMonitor {
          type TOKEN-RING-RMON-MIB:MacAddress;
          description
           "The address of the Active Monitor on this
            segment.  If this address is unknown, this object
            shall be equal to six octets of zero.";
          smiv2:max-access "read-only";
          smiv2:oid "1.3.6.1.2.1.16.10.1.1.7";
        }

        leaf ringStationControlOrderChanges {
          type yang:counter32;
          description
           "The number of add and delete events in the
            ringStationOrderTable optionally associated with
            this ringStationControlEntry.";
          smiv2:max-access "read-only";
          smiv2:oid "1.3.6.1.2.1.16.10.1.1.8";
        }

        leaf ringStationControlOwner {
          type TOKEN-RING-RMON-MIB:OwnerString;
          description
           "The entity that configured this entry and is
            therefore using the resources assigned to it.";
          smiv2:max-access "read-write";
          smiv2:oid "1.3.6.1.2.1.16.10.1.1.9";
        }

        leaf ringStationControlStatus {
          type TOKEN-RING-RMON-MIB:EntryStatus;
          description
           "The status of this ringStationControl entry.
            
            If this object is not equal to valid(1), all
            associated entries in the ringStationTable shall
            be deleted by the agent.";
          smiv2:max-access "read-write";
          smiv2:oid "1.3.6.1.2.1.16.10.1.1.10";
        }
      }
    }

    container ringStationTable {
      description
       "A list of ring station entries.  An entry will
        exist for each station that is now or has
        
        
        
        
        
        previously been detected as physically present on
        this ring.";
      smiv2:oid "1.3.6.1.2.1.16.10.2";

      list ringStationEntry {
        key "ringStationIfIndex ringStationMacAddress";
        description
         "A collection of statistics for a particular
          station that has been discovered on a ring
          monitored by this device.";
        smiv2:oid "1.3.6.1.2.1.16.10.2.1";

        leaf ringStationIfIndex {
          type int32;
          description
           "The value of this object uniquely identifies the
            interface on this remote network monitoring device
            on which this station was detected.  The interface
            identified by a particular value of this object is
            the same interface as identified by the same value
            of the ifIndex object, defined in MIB-II [3].";
          smiv2:max-access "read-only";
          smiv2:oid "1.3.6.1.2.1.16.10.2.1.1";
        }

        leaf ringStationMacAddress {
          type TOKEN-RING-RMON-MIB:MacAddress;
          description
           "The physical address of this station.";
          smiv2:max-access "read-only";
          smiv2:oid "1.3.6.1.2.1.16.10.2.1.2";
        }

        leaf ringStationLastNAUN {
          type TOKEN-RING-RMON-MIB:MacAddress;
          description
           "The physical address of last known NAUN of this
            station.";
          smiv2:max-access "read-only";
          smiv2:oid "1.3.6.1.2.1.16.10.2.1.3";
        }

        leaf ringStationStationStatus {
          type enumeration {
            enum "active" {
              value "1";
            }
            enum "inactive" {
              value "2";
            }
            enum "forcedRemoval" {
              value "3";
            }
          }
          description
           "The status of this station on the ring.";
          smiv2:max-access "read-only";
          smiv2:oid "1.3.6.1.2.1.16.10.2.1.4";
        }

        leaf ringStationLastEnterTime {
          type yang:timeticks;
          description
           "The value of sysUpTime at the time this station
            last entered the ring.  If the time is unknown,
            this value shall be zero.";
          smiv2:max-access "read-only";
          smiv2:oid "1.3.6.1.2.1.16.10.2.1.5";
        }

        leaf ringStationLastExitTime {
          type yang:timeticks;
          description
           "The value of sysUpTime at the time the probe
            detected that this station last exited the ring.
            If the time is unknown, this value shall be zero.";
          smiv2:max-access "read-only";
          smiv2:oid "1.3.6.1.2.1.16.10.2.1.6";
        }

        leaf ringStationDuplicateAddresses {
          type yang:counter32;
          description
           "The number of times this station experienced a
            duplicate address error.";
          smiv2:max-access "read-only";
          smiv2:oid "1.3.6.1.2.1.16.10.2.1.7";
        }

        leaf ringStationInLineErrors {
          type yang:counter32;
          description
           "The total number of line errors reported by this
            station in error reporting packets detected by the
            probe.";
          smiv2:max-access "read-only";
          smiv2:oid "1.3.6.1.2.1.16.10.2.1.8";
        }

        leaf ringStationOutLineErrors {
          type yang:counter32;
          description
           "The total number of line errors reported in error
            reporting packets sent by the nearest active
            downstream neighbor of this station and detected
            by the probe.";
          smiv2:max-access "read-only";
          smiv2:oid "1.3.6.1.2.1.16.10.2.1.9";
        }

        leaf ringStationInternalErrors {
          type yang:counter32;
          description
           "The total number of adapter internal errors
            reported by this station in error reporting
            packets detected by the probe.";
          smiv2:max-access "read-only";
          smiv2:oid "1.3.6.1.2.1.16.10.2.1.10";
        }

        leaf ringStationInBurstErrors {
          type yang:counter32;
          description
           "The total number of burst errors reported by this
            station in error reporting packets detected by the
            probe.";
          smiv2:max-access "read-only";
          smiv2:oid "1.3.6.1.2.1.16.10.2.1.11";
        }

        leaf ringStationOutBurstErrors {
          type yang:counter32;
          description
           "The total number of burst errors reported in
            error reporting packets sent by the nearest active
            downstream neighbor of this station and detected
            by the probe.";
          smiv2:max-access "read-only";
          smiv2:oid "1.3.6.1.2.1.16.10.2.1.12";
        }

        leaf ringStationACErrors {
          type yang:counter32;
          description
           "The total number of AC (Address Copied) errors
            reported in error reporting packets sent by the
            nearest active downstream neighbor of this station
            and detected by the probe.";
          smiv2:max-access "read-only";
          smiv2:oid "1.3.6.1.2.1.16.10.2.1.13";
        }

        leaf ringStationAbortErrors {
          type yang:counter32;
          description
           "The total number of abort delimiters reported by
            this station in error reporting packets detected
            by the probe.";
          smiv2:max-access "read-only";
          smiv2:oid "1.3.6.1.2.1.16.10.2.1.14";
        }

        leaf ringStationLostFrameErrors {
          type yang:counter32;
          description
           "The total number of lost frame errors reported by
            this station in error reporting packets detected
            by the probe.";
          smiv2:max-access "read-only";
          smiv2:oid "1.3.6.1.2.1.16.10.2.1.15";
        }

        leaf ringStationCongestionErrors {
          type yang:counter32;
          description
           "The total number of receive congestion errors
            reported by this station in error reporting
            packets detected by the probe.";
          smiv2:max-access "read-only";
          smiv2:oid "1.3.6.1.2.1.16.10.2.1.16";
        }

        leaf ringStationFrameCopiedErrors {
          type yang:counter32;
          description
           "The total number of frame copied errors reported
            by this station in error reporting packets
            detected by the probe.";
          smiv2:max-access "read-only";
          smiv2:oid "1.3.6.1.2.1.16.10.2.1.17";
        }

        leaf ringStationFrequencyErrors {
          type yang:counter32;
          description
           "The total number of frequency errors reported by
            this station in error reporting packets detected
            by the probe.";
          smiv2:max-access "read-only";
          smiv2:oid "1.3.6.1.2.1.16.10.2.1.18";
        }

        leaf ringStationTokenErrors {
          type yang:counter32;
          description
           "The total number of token errors reported by this
            station in error reporting frames detected by the
            probe.";
          smiv2:max-access "read-only";
          smiv2:oid "1.3.6.1.2.1.16.10.2.1.19";
        }

        leaf ringStationInBeaconErrors {
          type yang:counter32;
          description
           "The total number of beacon frames sent by this
            station and detected by the probe.";
          smiv2:max-access "read-only";
          smiv2:oid "1.3.6.1.2.1.16.10.2.1.20";
        }

        leaf ringStationOutBeaconErrors {
          type yang:counter32;
          description
           "The total number of beacon frames detected by the
            probe that name this station as the NAUN.";
          smiv2:max-access "read-only";
          smiv2:oid "1.3.6.1.2.1.16.10.2.1.21";
        }

        leaf ringStationInsertions {
          type yang:counter32;
          description
           "The number of times the probe detected this
            station inserting onto the ring.";
          smiv2:max-access "read-only";
          smiv2:oid "1.3.6.1.2.1.16.10.2.1.22";
        }
      }
    }

    container ringStationOrderTable {
      description
       "A list of ring station entries for stations in
        the ring poll, ordered by their ring-order.";
      smiv2:oid "1.3.6.1.2.1.16.10.3";

      list ringStationOrderEntry {
        key "ringStationOrderIfIndex ringStationOrderOrderIndex";
        description
         "A collection of statistics for a particular
          
          
          
          
          
          station that is active on a ring monitored by this
          device.  This table will contain information for
          every interface that has a
          ringStationControlStatus equal to valid.";
        smiv2:oid "1.3.6.1.2.1.16.10.3.1";

        leaf ringStationOrderIfIndex {
          type int32;
          description
           "The value of this object uniquely identifies the
            interface on this remote network monitoring device
            on which this station was detected.  The interface
            identified by a particular value of this object is
            the same interface as identified by the same value
            of the ifIndex object, defined in MIB-II [3].";
          smiv2:max-access "read-only";
          smiv2:oid "1.3.6.1.2.1.16.10.3.1.1";
        }

        leaf ringStationOrderOrderIndex {
          type int32;
          description
           "This index denotes the location of this station
            with respect to other stations on the ring.  This
            index is one more than the number of hops
            downstream that this station is from the rmon
            probe.  The rmon probe itself gets the value one.";
          smiv2:max-access "read-only";
          smiv2:oid "1.3.6.1.2.1.16.10.3.1.2";
        }

        leaf ringStationOrderMacAddress {
          type TOKEN-RING-RMON-MIB:MacAddress;
          description
           "The physical address of this station.";
          smiv2:max-access "read-only";
          smiv2:oid "1.3.6.1.2.1.16.10.3.1.3";
        }
      }
    }

    container ringStationConfigControlTable {
      description
       "A list of ring station configuration control
        entries.";
      smiv2:oid "1.3.6.1.2.1.16.10.4";

      list ringStationConfigControlEntry {
        key "ringStationConfigControlIfIndex ringStationConfigControlMacAddress";
        description
         "This entry controls active management of stations
          by the probe.  One entry exists in this table for
          each active station in the ringStationTable.";
        smiv2:oid "1.3.6.1.2.1.16.10.4.1";

        leaf ringStationConfigControlIfIndex {
          type int32;
          description
           "The value of this object uniquely identifies the
            
            
            
            
            
            interface on this remote network monitoring device
            on which this station was detected.  The interface
            identified by a particular value of this object is
            the same interface as identified by the same value
            of the ifIndex object, defined in MIB-II [3].";
          smiv2:max-access "read-only";
          smiv2:oid "1.3.6.1.2.1.16.10.4.1.1";
        }

        leaf ringStationConfigControlMacAddress {
          type TOKEN-RING-RMON-MIB:MacAddress;
          description
           "The physical address of this station.";
          smiv2:max-access "read-only";
          smiv2:oid "1.3.6.1.2.1.16.10.4.1.2";
        }

        leaf ringStationConfigControlRemove {
          type enumeration {
            enum "stable" {
              value "1";
            }
            enum "removing" {
              value "2";
            }
          }
          description
           "Setting this object to `removing(2)' causes a
            Remove Station MAC frame to be sent.  The agent
            will set this object to `stable(1)' after
            processing the request.";
          smiv2:max-access "read-write";
          smiv2:oid "1.3.6.1.2.1.16.10.4.1.3";
        }

        leaf ringStationConfigControlUpdateStats {
          type enumeration {
            enum "stable" {
              value "1";
            }
            enum "updating" {
              value "2";
            }
          }
          description
           "Setting this object to `updating(2)' causes the
            configuration information associate with this
            entry to be updated.  The agent will set this
            object to `stable(1)' after processing the
            request.";
          smiv2:max-access "read-write";
          smiv2:oid "1.3.6.1.2.1.16.10.4.1.4";
        }
      }
    }

    container ringStationConfigTable {
      description
       "A list of configuration entries for stations on a
        ring monitored by this probe.";
      smiv2:oid "1.3.6.1.2.1.16.10.5";

      list ringStationConfigEntry {
        key "ringStationConfigIfIndex ringStationConfigMacAddress";
        description
         "A collection of statistics for a particular
          station that has been discovered on a ring
          monitored by this probe.";
        smiv2:oid "1.3.6.1.2.1.16.10.5.1";

        leaf ringStationConfigIfIndex {
          type int32;
          description
           "The value of this object uniquely identifies the
            
            
            
            
            
            interface on this remote network monitoring device
            on which this station was detected.  The interface
            identified by a particular value of this object is
            the same interface as identified by the same value
            of the ifIndex object, defined in MIB-II [3].";
          smiv2:max-access "read-only";
          smiv2:oid "1.3.6.1.2.1.16.10.5.1.1";
        }

        leaf ringStationConfigMacAddress {
          type TOKEN-RING-RMON-MIB:MacAddress;
          description
           "The physical address of this station.";
          smiv2:max-access "read-only";
          smiv2:oid "1.3.6.1.2.1.16.10.5.1.2";
        }

        leaf ringStationConfigUpdateTime {
          type yang:timeticks;
          description
           "The value of sysUpTime at the time this
            configuration information was last updated
            (completely).";
          smiv2:max-access "read-only";
          smiv2:oid "1.3.6.1.2.1.16.10.5.1.3";
        }

        leaf ringStationConfigLocation {
          type binary {
            length "4";
          }
          description
           "The assigned physical location of this station.";
          smiv2:max-access "read-only";
          smiv2:oid "1.3.6.1.2.1.16.10.5.1.4";
        }

        leaf ringStationConfigMicrocode {
          type binary {
            length "10";
          }
          description
           "The microcode EC level of this station.";
          smiv2:max-access "read-only";
          smiv2:oid "1.3.6.1.2.1.16.10.5.1.5";
        }

        leaf ringStationConfigGroupAddress {
          type binary {
            length "4";
          }
          description
           "The low-order 4 octets of the group address
            recognized by this station.";
          smiv2:max-access "read-only";
          smiv2:oid "1.3.6.1.2.1.16.10.5.1.6";
        }

        leaf ringStationConfigFunctionalAddress {
          type binary {
            length "4";
          }
          description
           "the functional addresses recognized by this
            station.";
          smiv2:max-access "read-only";
          smiv2:oid "1.3.6.1.2.1.16.10.5.1.7";
        }
      }
    }

    container sourceRoutingStatsTable {
      description
       "A list of source routing statistics entries.";
      smiv2:oid "1.3.6.1.2.1.16.10.6";

      list sourceRoutingStatsEntry {
        key "sourceRoutingStatsIfIndex";
        description
         "A collection of source routing statistics kept
          for a particular Token Ring interface.";
        smiv2:oid "1.3.6.1.2.1.16.10.6.1";

        leaf sourceRoutingStatsIfIndex {
          type int32;
          description
           "The value of this object uniquely identifies the
            interface on this remote network monitoring device
            on which source routing statistics will be
            detected.  The interface identified by a
            particular value of this object is the same
            interface as identified by the same value of the
            ifIndex object, defined in MIB-II [3].";
          smiv2:max-access "read-only";
          smiv2:oid "1.3.6.1.2.1.16.10.6.1.1";
        }

        leaf sourceRoutingStatsRingNumber {
          type int32;
          description
           "The ring number of the ring monitored by this
            entry.  When any object in this entry is created,
            the probe will attempt to discover the ring
            number.  Only after the ring number is discovered
            will this object be created.  After creating an
            object in this entry, the management station
            should poll this object to detect when it is
            created.  Only after this object is created can
            the management station set the
            sourceRoutingStatsStatus entry to valid(1).";
          smiv2:max-access "read-only";
          smiv2:oid "1.3.6.1.2.1.16.10.6.1.2";
        }

        leaf sourceRoutingStatsInFrames {
          type yang:counter32;
          description
           "The count of frames sent into this ring from
            another ring.";
          smiv2:max-access "read-only";
          smiv2:oid "1.3.6.1.2.1.16.10.6.1.3";
        }

        leaf sourceRoutingStatsOutFrames {
          type yang:counter32;
          description
           "The count of frames sent from this ring to
            another ring.";
          smiv2:max-access "read-only";
          smiv2:oid "1.3.6.1.2.1.16.10.6.1.4";
        }

        leaf sourceRoutingStatsThroughFrames {
          type yang:counter32;
          description
           "The count of frames sent from another ring,
            through this ring, to another ring.";
          smiv2:max-access "read-only";
          smiv2:oid "1.3.6.1.2.1.16.10.6.1.5";
        }

        leaf sourceRoutingStatsAllRoutesBroadcastFrames {
          type yang:counter32;
          description
           "The total number of good frames received that
            were All Routes Broadcast.";
          smiv2:max-access "read-only";
          smiv2:oid "1.3.6.1.2.1.16.10.6.1.6";
        }

        leaf sourceRoutingStatsSingleRouteBroadcastFrames {
          type yang:counter32;
          description
           "The total number of good frames received that
            were Single Route Broadcast.";
          smiv2:max-access "read-only";
          smiv2:oid "1.3.6.1.2.1.16.10.6.1.7";
        }

        leaf sourceRoutingStatsInOctets {
          type yang:counter32;
          description
           "The count of octets in good frames sent into this
            ring from another ring.";
          smiv2:max-access "read-only";
          smiv2:oid "1.3.6.1.2.1.16.10.6.1.8";
        }

        leaf sourceRoutingStatsOutOctets {
          type yang:counter32;
          description
           "The count of octets in good frames sent from this
            ring to another ring.";
          smiv2:max-access "read-only";
          smiv2:oid "1.3.6.1.2.1.16.10.6.1.9";
        }

        leaf sourceRoutingStatsThroughOctets {
          type yang:counter32;
          description
           "The count of octets in good frames sent another
            ring, through this ring, to another ring.";
          smiv2:max-access "read-only";
          smiv2:oid "1.3.6.1.2.1.16.10.6.1.10";
        }

        leaf sourceRoutingStatsAllRoutesBroadcastOctets {
          type yang:counter32;
          description
           "The total number of octets in good frames
            received that were All Routes Broadcast.";
          smiv2:max-access "read-only";
          smiv2:oid "1.3.6.1.2.1.16.10.6.1.11";
        }

        leaf sourceRoutingStatsSingleRoutesBroadcastOctets {
          type yang:counter32;
          description
           "The total number of octets in good frames
            received that were Single Route Broadcast.";
          smiv2:max-access "read-only";
          smiv2:oid "1.3.6.1.2.1.16.10.6.1.12";
        }

        leaf sourceRoutingStatsLocalLLCFrames {
          type yang:counter32;
          description
           "The total number of frames received who had no
            RIF field (or had a RIF field that only included
            the local ring's number) and were not All Route
            Broadcast Frames.";
          smiv2:max-access "read-only";
          smiv2:oid "1.3.6.1.2.1.16.10.6.1.13";
        }

        leaf sourceRoutingStats1HopFrames {
          type yang:counter32;
          description
           "The total number of frames received whose route
            had 1 hop, were not All Route Broadcast Frames,
            and whose source or destination were on this ring
            (i.e. frames that had a RIF field and had this
            ring number in the first or last entry of the RIF
            field).";
          smiv2:max-access "read-only";
          smiv2:oid "1.3.6.1.2.1.16.10.6.1.14";
        }

        leaf sourceRoutingStats2HopsFrames {
          type yang:counter32;
          description
           "The total number of frames received whose route
            had 2 hops, were not All Route Broadcast Frames,
            and whose source or destination were on this ring
            (i.e. frames that had a RIF field and had this
            ring number in the first or last entry of the RIF
            field).";
          smiv2:max-access "read-only";
          smiv2:oid "1.3.6.1.2.1.16.10.6.1.15";
        }

        leaf sourceRoutingStats3HopsFrames {
          type yang:counter32;
          description
           "The total number of frames received whose route
            had 3 hops, were not All Route Broadcast Frames,
            and whose source or destination were on this ring
            (i.e. frames that had a RIF field and had this
            ring number in the first or last entry of the RIF
            field).";
          smiv2:max-access "read-only";
          smiv2:oid "1.3.6.1.2.1.16.10.6.1.16";
        }

        leaf sourceRoutingStats4HopsFrames {
          type yang:counter32;
          description
           "The total number of frames received whose route
            had 4 hops, were not All Route Broadcast Frames,
            and whose source or destination were on this ring
            (i.e. frames that had a RIF field and had this
            ring number in the first or last entry of the RIF
            field).";
          smiv2:max-access "read-only";
          smiv2:oid "1.3.6.1.2.1.16.10.6.1.17";
        }

        leaf sourceRoutingStats5HopsFrames {
          type yang:counter32;
          description
           "The total number of frames received whose route
            had 5 hops, were not All Route Broadcast Frames,
            and whose source or destination were on this ring
            (i.e. frames that had a RIF field and had this
            ring number in the first or last entry of the RIF
            field).";
          smiv2:max-access "read-only";
          smiv2:oid "1.3.6.1.2.1.16.10.6.1.18";
        }

        leaf sourceRoutingStats6HopsFrames {
          type yang:counter32;
          description
           "The total number of frames received whose route
            had 6 hops, were not All Route Broadcast Frames,
            and whose source or destination were on this ring
            (i.e. frames that had a RIF field and had this
            ring number in the first or last entry of the RIF
            field).";
          smiv2:max-access "read-only";
          smiv2:oid "1.3.6.1.2.1.16.10.6.1.19";
        }

        leaf sourceRoutingStats7HopsFrames {
          type yang:counter32;
          description
           "The total number of frames received whose route
            had 7 hops, were not All Route Broadcast Frames,
            and whose source or destination were on this ring
            (i.e. frames that had a RIF field and had this
            ring number in the first or last entry of the RIF
            field).";
          smiv2:max-access "read-only";
          smiv2:oid "1.3.6.1.2.1.16.10.6.1.20";
        }

        leaf sourceRoutingStats8HopsFrames {
          type yang:counter32;
          description
           "The total number of frames received whose route
            had 8 hops, were not All Route Broadcast Frames,
            and whose source or destination were on this ring
            (i.e. frames that had a RIF field and had this
            ring number in the first or last entry of the RIF
            field).";
          smiv2:max-access "read-only";
          smiv2:oid "1.3.6.1.2.1.16.10.6.1.21";
        }

        leaf sourceRoutingStatsMoreThan8HopsFrames {
          type yang:counter32;
          description
           "The total number of frames received whose route
            had more than 8 hops, were not All Route Broadcast
            Frames, and whose source or destination were on
            this ring (i.e. frames that had a RIF field and
            had this ring number in the first or last entry of
            the RIF field).";
          smiv2:max-access "read-only";
          smiv2:oid "1.3.6.1.2.1.16.10.6.1.22";
        }

        leaf sourceRoutingStatsOwner {
          type TOKEN-RING-RMON-MIB:OwnerString;
          description
           "The entity that configured this entry and is
            therefore using the resources assigned to it.";
          smiv2:max-access "read-write";
          smiv2:oid "1.3.6.1.2.1.16.10.6.1.23";
        }

        leaf sourceRoutingStatsStatus {
          type TOKEN-RING-RMON-MIB:EntryStatus;
          description
           "The status of this sourceRoutingStats entry.";
          smiv2:max-access "read-write";
          smiv2:oid "1.3.6.1.2.1.16.10.6.1.24";
        }
      }
    }
  }

  smiv2:alias "tokenRing" {
    smiv2:oid "1.3.6.1.2.1.16.10";
  }

}
