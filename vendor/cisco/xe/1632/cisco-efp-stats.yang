module cisco-efp-stats {

	yang-version 1;

	namespace "urn:cisco:params:xml:ns:yang:cisco-efp-stats";
	prefix efp-stats;

	import ietf-yang-types {
		prefix yang;
	}

	organization
		"Cisco Systems, Inc.";

	contact
		" Cisco Systems, Inc.
		Customer Service

		Postal: 170 W Tasman Drive
		San Jose, CA 95134

		Tel: +1 1800 553-NETS

		E-mail: cs-yang@cisco.com";

	description
		" This module contains a collection of YANG definitions for
		service instance (efp) stats";

	reference "TODO";

	revision 2015-07-07 {
		description "Proposed";
	}

	container efp-stats {
		config false;

	description
	"Service instance stats";

	list efp {
		key "id interface";
		leaf id {
			type uint32;
		}
		leaf interface {
			type string;
		}
		leaf in-pkts {
			type yang:counter64;
		}
		leaf in-bytes {
			type yang:counter64;
		}
		leaf out-pkts {
			type yang:counter64;
		}
		leaf out-bytes {
			type yang:counter64;
		}

	}

}

}
