module cisco-mpls-fwd {

    yang-version 1;

    namespace "urn:cisco:params:xml:ns:yang:cisco-mpls-fwd";
    prefix mplsfwd;

    import ietf-inet-types {
        prefix inet;
    }
	import ietf-yang-types {
		prefix yang;
	}
    organization
        "Cisco Systems, Inc.";

    contact
        " Cisco Systems, Inc.
          Customer Service

          Postal: 170 W Tasman Drive
          San Jose, CA 95134

          Tel: +1 1800 553-NETS

          E-mail: cs-yang@cisco.com";

    description
        " This module contains a collection of YANG definitions for
          monitoring memory usage of processes in a Network Element.";

    reference "TODO";

    revision 2015-04-09 {
        description "Proposed";
    }
	
	grouping tunnel-tp-info {
		leaf global {
			type uint32;
		}
		leaf node {
			type inet:ip-address;
		}
		
	}
    container mpls-forwarding-table {
        config false;

        description
          "Data nodes for MPLS forwarding table entries.";

        list local-label-entry {
            key "local-label";

            description
                "The list of MPLS forwarding table entries.";

            leaf local-label {
                type uint32;
                description
                  "Value of local-label.";
            }

            list forwarding-info {
		key "outgoing-interface";

		leaf outgoing-interface {
		    type union {
			type enumeration {
			    enum drop;
			    enum punt;
			    enum aggregate;
			    enum exception;
				enum none;
			}
                        type string;
		    }
		    description
                        "The name of the outgoing interface.
			 Example possible values are 1.none, 2.drop, 3.<tunnel-name>,
			 4.<interface-name>, 5.aggregate/<vrf-name> etc.";
		}

                leaf outgoing-label {
		    type union {
                        type uint32;
                        type enumeration {
			    enum no-label;
                            enum pop-label;
			    enum aggregate;
			    enum explicit-null;
			    enum illegal;
			}
		    }
		    description
		        "Value of outgoing-label if exists or
			 the type of non-present label.";
		}

		container connection-info {
		    description
		        "The Prefix or tunnel-id info corresponding to this label.
			 Ex: 1) for l2ckt, a number tunnel-id value.
			     2) for ipv4, a prefix with [V] tag (113.113.113.113/32[V]).
			     3) for TE, a pefix with [T] tag (113.113.113.113/32[T])";

		    leaf type {
				type enumeration {
					enum ip;
					enum tunnel;
					enum nh-id;
					enum l2ckt;
					enum ip-vrf;
					enum none;
					enum tunnel-tp;
				}
                description
			    "The type of connection represented by this label";
            }

            leaf ip {
                type inet:ip-address;
            }

		    leaf mask {
				type uint16;
		    }

		    leaf tunnel-id {
                type uint32;
		    }
			leaf vrf-id {
                type uint32;
		    }
			leaf nh-id {
                type uint32;
		    }
			leaf l2ckt-id {
				type uint32;
            }
			container tunnel-tp {
		                leaf tunnel {
                	        	type uint32;
                		}
				container src-id {
					uses tunnel-tp-info;
				}
				container dst-id {
					uses tunnel-tp-info;
				}
				
			}
		}

		leaf label-switched-bytes {
		    type uint64;
		    description "The number of bytes switched using this label.";
		}

        leaf next-hop {
            type union {
				type enumeration {
                    enum point2point;
                }
		        type inet:ip-address;
				type yang:mac-address;
		    }

		    description
		        "Next hop information.
			 Example possible values are
			    1.point2point,
			    2.<ip-address>";
		}
            }
        }
    }

}
