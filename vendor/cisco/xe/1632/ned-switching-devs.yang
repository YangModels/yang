module ned-switching-devs {
    namespace "http://cisco.com/ns/yang/ned/ios/switching/devs";
    prefix ned-sw-d;

    import tailf-common {
       prefix tailf;
    }

    import ned {
       prefix ned;
    }

    organization "Cisco Systems";

    description
       "NED YANG module for IOS
        Copyright (c) 2016 by Cisco Systems, Inc.
        All rights reserved.";

    ////////////////////////////////////////////////////////////////////////////
    // REVISION
    ///////////////////////////////////////////////////////////////////////////
    revision 2016-04-20 {
       description "Added interface switchport deviation";
    }
    revision 2016-04-08 {
       description "Added line deviation";
    }
    revision 2016-04-07 {
       description "Added Copyright";
    }
    revision 2016-02-26 {
       description "Added some qos range deviations";
    }

    ////////////////////////////////////////////////////////////////////////////////
    // DEVIATION
    ///////////////////////////////////////////////////////////////////////////////

    deviation /ned:native/ned:class-map/ned:match/ned:access-group/ned:index {
      deviate replace {
        type uint32 {
          range "1..2799";
          tailf:info "<1-2799>;;Access list index";
        }
      }
    }
    deviation /ned:native/ned:policy-map/ned:class/ned:action-list/ned:action-param/ned:bandwidth-case/ned:bandwidth/ned:bits {
      deviate replace {
        type uint32 {
	  range "100..40000000";
	  tailf:info "<100-40000000>;;Kilo Bits per second";
        }
      }
    }
    deviation /ned:native/ned:policy-map/ned:class/ned:action-list/ned:action-param/ned:priority-case/ned:priority/ned:priority-type/ned:kilo-bits/ned:kilo-bits {
      deviate replace {
        type uint32 {
          range "8..40000000"; // switch range
          tailf:info "<8-40000000>;;Kilo Bits per second";
        }
      }
    }
    deviation /ned:native/ned:line/ned:vty/ned:first {
      deviate replace {
        type uint16 {
          range "0..97";
          tailf:info "<0-97>;;First Line number";
        }
      }
    }
    deviation /ned:native/ned:line/ned:vty/ned:last {
      deviate replace {
        type uint16 {
          range "1..97";
          tailf:info "<1-97>;;Last Line number";
        }
      }
    }
    deviation /ned:native/ned:interface/ned:FastEthernet/ned:switchport/ned:port-security/ned:maximum/ned:max-addresses {
      deviate replace {
        type uint16 {
	  tailf:info "<1-4096>;;Maximum addresses";
	  range "1..4096";
        }
      }
    }
    deviation /ned:native/ned:interface/ned:GigabitEthernet/ned:switchport/ned:port-security/ned:maximum/ned:max-addresses {
      deviate replace {
        type uint16 {
	  tailf:info "<1-4096>;;Maximum addresses";
	  range "1..4096";
        }
      }
    }
    deviation /ned:native/ned:interface/ned:TenGigabitEthernet/ned:switchport/ned:port-security/ned:maximum/ned:max-addresses {
      deviate replace {
        type uint16 {
	  tailf:info "<1-4096>;;Maximum addresses";
	  range "1..4096";
        }
      }
    }
    deviation /ned:native/ned:interface/ned:Port-channel/ned:switchport/ned:port-security/ned:maximum/ned:max-addresses {
      deviate replace {
        type uint16 {
	  tailf:info "<1-4096>;;Maximum addresses";
	  range "1..4096";
        }
      }
    }
    deviation /ned:native/ned:interface/ned:Port-channel-subinterface/ned:Port-channel/ned:switchport/ned:port-security/ned:maximum/ned:max-addresses {
      deviate replace {
        type uint16 {
	  tailf:info "<1-4096>;;Maximum addresses";
	  range "1..4096";
        }
      }
    }
}
