module Cisco-IOS-XE-ucse-rpc {
  namespace "http://cisco.com/ns/yang/Cisco-IOS-XE-ucse-rpc";
  prefix ios-xe-ucse-rpc;

  import cisco-semver {
    prefix cisco-semver;
  }
  import Cisco-IOS-XE-rpc {
    prefix ios-xe-rpc;
  }

  organization
    "Cisco Systems";
  contact
    "<mailto:cs-yang@cisco.com>";
  description
    "NED UCSE (Unified Computing System E-Series) RPC YANG module for IOS
     Copyright (c) 2019 by Cisco Systems, Inc.
     All rights reserved.";

  revision 2019-07-01 {
    description
      "Establish semantic version baseline";
    cisco-semver:module-version "1.0.0";
  }
  revision 2019-01-10 {
    description
      "Initial revision for NED UCSE (Unified Computing System E-Series) RPC YANG module for IOS";
  }

  rpc ucse {
    description
      "UCSE (Unified Computing System E-Series) commands";
    input {
      leaf subslot {
        description
          "UCSE (Unified Computing System E-Series) subslot";
        type string {
          pattern "[0-2]/[0-3]";
        }
        mandatory true;
      }
      choice command-choice {
        mandatory true;
        case imc-case {
          container imc {
            description
              "IMC (Integrated Management Controller) command";
            leaf password-reset {
              description
                "Reset the password for IMC (Integrated Management Controller)";
              type empty;
            }
          }
        }
        case server-case {
          container server {
            description
              "Server commands";
            choice server-command-choice {
              case server-cmos-password-reset {
                leaf cmos-reset {
                  description
                    "Reset the CMOS password for the server";
                  type empty;
                }
              }
              case server-password-reset {
                container password-reset {
                  description
                    "Reset the password for the server";
                  leaf BIOS {
                    description
                      "Reset the BIOS password for the server";
                    type empty;
                  }
                }
              }
              case server-reload {
                leaf reload {
                  description
                    "Reload the server";
                  type empty;
                }
              }
              case server-reset {
                leaf reset {
                  description
                    "Reset the server";
                  type empty;
                }
              }
              case server-start {
                leaf start {
                  description
                    "Start the server";
                  type empty;
                }
              }
              case server-stop {
                leaf stop {
                  description
                    "Stop the server";
                  type empty;
                }
              }
            }
          }
        }
        case shutdown-case {
          leaf shutdown {
            description
              "Shutdown the UCSE (Unified Computing System E-Series) module";
            type empty;
          }
        }
        case statistics-case {
          container statistics {
            description
              "Statistics command";
            leaf clear {
              description
                "Clear the statistics";
              type empty;
            }
          }
        }
      }
    }
    output {
      uses ios-xe-rpc:cisco-xe-rpc-output;
    }
  }
}
