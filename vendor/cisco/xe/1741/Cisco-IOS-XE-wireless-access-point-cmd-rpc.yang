module Cisco-IOS-XE-wireless-access-point-cmd-rpc {
  yang-version 1;
  namespace "http://cisco.com/ns/yang/Cisco-IOS-XE-wireless-access-point-cmd-rpc";
  prefix wireless-access-point-cmd-rpc;

  import Cisco-IOS-XE-wireless-enum-types {
    prefix wireless-enum-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Copyright (c) 2019-2020 by Cisco Systems, Inc.
     All rights reserved.";

  revision 2020-11-01 {
    description
      " - Added Open RRM Tx Power set RPC
        - Added Open RRM Channel change set RPC
        - Added RPC support for AP image predownload and abort
        - Added RPC support for clear AP CAPWAP session";
    reference "2.3.0";
    cisco-semver:module-version "2.3.0";
  }
  revision 2020-07-01 {
    description
      "- Added AP clear predownload statistics exec command";
    reference "2.2.0";
    cisco-semver:module-version "2.2.0";
  }
  revision 2020-03-01 {
    description
      "- Added AP reset and other exec command support.";
    reference "2.1.0";
    cisco-semver:module-version "2.1.0";
  }
  revision 2019-11-01 {
    description
      "- Add mandatory constraints for mandatory inputs";
    reference "2.0.0";
    cisco-semver:module-version "2.0.0";
  }
  revision 2019-03-01 {
    description
      "Initial revision";
    reference "1.0.0";
    cisco-semver:module-version "1.0.0";
  }

  typedef ap-identifier {
    type enumeration {
      enum "ap-identifier-name" {
        value 0;
        description
          "AP name";
      }
      enum "ap-identifier-mac-address" {
        value 1;
        description
          "AP MAC address";
      }
    }
    description
      "Access point identifier";
  }

  grouping set-rad-predownload-all {
    description
      "AP Image Predownload for all";
    leaf uuid {
      type string;
      mandatory true;
      description
        "UUID for AP Image Predownload";
    }
  }

  grouping ap-capwap-reset {
    description
      "AP capwap session reset";
    choice alternative-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ap-reset {
    description
      "AP reset data";
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping ap-image-predownload-abort {
    description
      "AP Image Predownload abort";
    leaf uuid {
      type string;
      mandatory true;
      description
        "UUID for AP Image Predownload abort";
    }
  }

  grouping clear-ap-personal-ssid {
    description
      "Clear personal SSID from office extend AP";
    choice alternative-choice {
      mandatory true;
      description
        "Alternative choice between AP name and MAC address";
      case ap-identifier-name {
        leaf ap-name {
          type string;
          mandatory true;
          description
            "AP name to clear personal SSID";
        }
      }
      case ap-identifier-mac-address {
        leaf mac-addr {
          type yang:mac-address;
          mandatory true;
          description
            "MAC address to clear personal SSID";
        }
      }
    }
  }

  grouping set-ap-static-ip-enable {
    description
      "Set static IP address for AP";
    leaf ip-addr {
      type inet:ip-address;
      mandatory true;
      description
        "Enter static IP address";
    }
    leaf net-mask {
      type inet:ip-address;
      description
        "Enter subnet mask (i.e 255.255.255.0)";
    }
    leaf prefix {
      type uint32;
      description
        "Enter network prefix according to subnet mask (i.e 24)";
    }
    leaf gateway {
      type inet:ip-address;
      mandatory true;
      description
        "Enter static IP Gateway";
    }
    choice alternative-choice {
      mandatory true;
      description
        "Alternative choice between AP name and MAC address";
      case ap-identifier-name {
        leaf ap-name {
          type string;
          mandatory true;
          description
            "AP name to enable static IP configuration";
        }
      }
      case ap-identifier-mac-address {
        leaf mac-addr {
          type yang:mac-address;
          mandatory true;
          description
            "MAC address of AP to enable static IP configuration";
        }
      }
    }
  }

  grouping set-ap-static-ip-disable {
    description
      "Unset Cisco AP static IP address configuration";
    choice alternative-choice {
      mandatory true;
      description
        "Choice between AP name and MAC address";
      case ap-identifier-name {
        leaf ap-name {
          type string;
          mandatory true;
          description
            "AP name to disable static IP configuration";
        }
      }
      case ap-identifier-mac-address {
        leaf mac-addr {
          type yang:mac-address;
          mandatory true;
          description
            "MAC address of AP to disable static IP configuration";
        }
      }
    }
  }

  grouping set-ap-predownload {
    description
      "Instruct the AP to start image predownload";
    choice alternative-choice {
      mandatory true;
      description
        "Choice between AP name and MAC address";
      case ap-identifier-name {
        leaf ap-name {
          type string;
          mandatory true;
          description
            "AP name to perform predownload";
        }
      }
      case ap-identifier-mac-address {
        leaf mac-addr {
          type yang:mac-address;
          mandatory true;
          description
            "MAC address of AP to perform predownload";
        }
      }
    }
  }

  grouping swap-ap-image {
    description
      "Instruct the AP to swap the image";
    leaf enable {
      type boolean;
      mandatory true;
      description
        "When enabled, it is an instruction to AP to swap the current image with the backup image";
    }
    choice alternative-choice {
      mandatory true;
      description
        "Alternative choice between AP name and MAC address";
      case ap-identifier-name {
        leaf ap-name {
          type string;
          mandatory true;
          description
            "AP name to swap the current image with the backup image";
        }
      }
      case ap-identifier-mac-address {
        leaf mac-addr {
          type yang:mac-address;
          mandatory true;
          description
            "MAC address of AP to swap the current image with the backup image";
        }
      }
    }
  }

  grouping clear-ap-config {
    description
      "Clear AP config";
    leaf operation-type {
      type wireless-types:ap-clear-config-op-type;
      mandatory true;
      description
        "Clear config operation type";
    }
    choice ap-identifier-choice {
      mandatory true;
      description
        "AP identifier";
      case ap-identifier-name {
        leaf ap-name {
          type string;
          mandatory true;
          description
            "AP name";
        }
      }
      case ap-identifier-mac-address {
        leaf mac-addr {
          type yang:mac-address;
          mandatory true;
          description
            "MAC address";
        }
      }
    }
  }

  grouping set-open-rrm-tx-power-auto {
    description
      "Configure Open RRM TX Power Parameters";
    leaf slot-id {
      type uint8;
      mandatory true;
      description
        "Slot ID for the Radio to which TX Power has to be applied";
    }
    leaf band {
      type wireless-enum-types:enm-radio-band;
      mandatory true;
      description
        "Band ID, 2.4GHz or 5 GHz of the Radio Slot, to which Tx Parameters to be changed";
    }
    leaf tx-power {
      type int8;
      units "dBm";
      description
        "Transmit Power in dBm specific to the Radio slot";
    }
    leaf power-change-reason {
      type wireless-types:tx-power-change-reason;
      mandatory true;
      description
        "Tx Power Change reason";
    }
    choice ap-identifier-choice {
      mandatory true;
      description
        "Alternative choice between AP name and Radio MAC address";
      case ap-identifier-name {
        leaf ap-name {
          type string;
          mandatory true;
          description
            "AP name that holds this radio which TX Power parameters to be changed ";
        }
      }
      case ap-identifier-mac-address {
        leaf mac-addr {
          type yang:mac-address;
          mandatory true;
          description
            "Radio MAC address of AP to which TX Power parameters to be changed";
        }
      }
    }
  }

  grouping set-open-rrm-channel-auto {
    description
      "Configure Open RRM Channel Parameters";
    leaf slot-id {
      type uint8 {
        range "0..2";
      }
      mandatory true;
      description
        "Slot ID for the Radio to which channel change has to be applied";
    }
    leaf band {
      type wireless-enum-types:enm-radio-band;
      mandatory true;
      description
        "Band ID, 2.4GHz or 5 GHz of the Radio Slot, to which channel has to be changed";
    }
    leaf primary-chan {
      type uint8 {
        range "0..196";
      }
      mandatory true;
      description
        "channel number to be applied";
    }
    leaf extension-chan {
      type uint8 {
        range "0..196";
      }
      mandatory true;
      description
        "Extension channel number when the channel width is greater than 20MHz channel";
    }
    leaf curr-cost-metric {
      type int8 {
        range "-128..127";
      }
      mandatory true;
      description
        "DCA cost metric for the current channel";
    }
    leaf new-cost-metric {
      type int8 {
        range "-128..127";
      }
      mandatory true;
      description
        "DCA cost metric for the new channel";
    }
    leaf secondary-chan-1 {
      type uint8 {
        range "0..196";
      }
      mandatory true;
      description
        "Extended 40MHz third channel when the channel width is greater than 40MHz channel";
    }
    leaf secondary-chan-2 {
      type uint8;
      mandatory true;
      description
        "Extended 40MHz fourth channel when the channel width is greater than 40MHz channel";
    }
    leaf chan-width {
      type wireless-enum-types:rrm-chan-width;
      mandatory true;
      description
        "Channel width number 20 for 20MHz, 40 for 40MHz, 80 for 80MHz, 160 for 160 MHz and 188 for 80 plus 80MHz";
    }
    leaf second-best-chan {
      type uint8 {
        range "0..196";
      }
      mandatory true;
      description
        "Second best channel number as recommended by DCA";
    }
    leaf second-best-width {
      type wireless-enum-types:rrm-chan-width;
      mandatory true;
      description
        "Second best channel width number 20 for 20MHz, 40 for 40MHz, 80 for 80MHz, 160 for 160 MHz and 188 for 80 plus 80MHz";
    }
    leaf second-best-metric {
      type int8 {
        range "-128..127";
      }
      mandatory true;
      description
        "DCA Cost metric for the second best channel";
    }
    leaf is-redundant {
      type boolean;
      mandatory true;
      description
        "is Radio redundant";
    }
    leaf rrf-metric {
      type uint8 {
        range "0..100";
      }
      mandatory true;
      description
        "Radios's coverage overlap rate(%) by FRA, 0 to 100";
    }
    leaf rrf-contributing {
      type boolean;
      mandatory true;
      description
        "Radio is contributing to redundant radio";
    }
    leaf dca-chan-width {
      type wireless-enum-types:rrm-chan-width;
      mandatory true;
      description
        "Configured RRM DCA Channel width number 20 for 20MHz, 40 for 40MHz, 80 for 80MHz, 160 for 160 MHz and 188 for 80 plus 80MHz";
    }
    leaf slave-chan {
      type uint16 {
        range "0..196";
      }
      mandatory true;
      description
        "The current channel of the slave radio";
    }
    leaf slave-metric {
      type int8 {
        range "-128..127";
      }
      mandatory true;
      description
        "DCA cost metric of the slave channel";
    }
    choice ap-identifier-choice {
      mandatory true;
      description
        "Alternative choice between AP name and Radio MAC address";
      case ap-identifier-name {
        leaf ap-name {
          type string;
          mandatory true;
          description
            "AP name that holds this radio to which channel parameters to be changed ";
        }
      }
      case ap-identifier-mac-address {
        leaf mac-addr {
          type yang:mac-address;
          mandatory true;
          description
            "Radio MAC address of AP to which channel parameters to be changed";
        }
      }
    }
  }

  rpc set-rad-predownload-all {
    description
      "AP Image Predownload for all";
    input {
      uses wireless-access-point-cmd-rpc:set-rad-predownload-all;
    }
  }
  rpc set-rad-capwap-reset {
    description
      "Instruct the AP to reset the CAPWAP session";
    input {
      uses wireless-access-point-cmd-rpc:ap-capwap-reset;
    }
  }
  rpc ap-reset {
    description
      "AP reset";
    input {
      uses wireless-access-point-cmd-rpc:ap-reset;
    }
  }
  rpc ap-image-predownload-abort {
    description
      "AP Image Predownload abort";
    input {
      uses wireless-access-point-cmd-rpc:ap-image-predownload-abort;
    }
  }
  rpc clear-ap-personal-ssid {
    description
      "Clear personal ssid from office extend AP";
    input {
      uses wireless-access-point-cmd-rpc:clear-ap-personal-ssid;
    }
  }
  rpc set-ap-static-ip-enable {
    description
      "Configure static IP address for AP";
    input {
      uses wireless-access-point-cmd-rpc:set-ap-static-ip-enable;
    }
  }
  rpc set-ap-static-ip-disable {
    description
      "Unset Cisco AP static IP address configuration";
    input {
      uses wireless-access-point-cmd-rpc:set-ap-static-ip-disable;
    }
  }
  rpc set-ap-predownload {
    description
      "Instruct the AP to start image predownload";
    input {
      uses wireless-access-point-cmd-rpc:set-ap-predownload;
    }
  }
  rpc swap-ap-image {
    description
      "Instruct the AP to swap the image";
    input {
      uses wireless-access-point-cmd-rpc:swap-ap-image;
    }
  }
  rpc clear-ap-config {
    description
      "Clear AP config";
    input {
      uses wireless-access-point-cmd-rpc:clear-ap-config;
    }
  }
  rpc clear-ap-predownload-statistics {
    description
      "Clear the AP predownload statistics";
  }
  rpc set-open-rrm-tx-power-auto {
    description
      "Configure Open RRM Tx Power Parameters for AP Radio";
    input {
      uses wireless-access-point-cmd-rpc:set-open-rrm-tx-power-auto;
    }
  }
  rpc set-open-rrm-channel-auto {
    description
      "Configure Open RRM Channel Parameters for AP Radio";
    input {
      uses wireless-access-point-cmd-rpc:set-open-rrm-channel-auto;
    }
  }
}
