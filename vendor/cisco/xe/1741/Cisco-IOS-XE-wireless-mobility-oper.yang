module Cisco-IOS-XE-wireless-mobility-oper {
  yang-version 1;
  namespace "http://cisco.com/ns/yang/Cisco-IOS-XE-wireless-mobility-oper";
  prefix wireless-mobility-oper;

  import Cisco-IOS-XE-ntp-oper {
    prefix ntp-ios-xe-oper;
  }
  import Cisco-IOS-XE-wireless-mobility-types {
    prefix wireless-mobility-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless mobility operational data.
     Copyright (c) 2016-2020 by Cisco Systems, Inc.
     All rights reserved.";

  revision 2020-11-01 {
    description
      "Added mobility peer data link encryption status";
    reference "6.1.0";
    cisco-semver:module-version "6.1.0";
  }
  revision 2019-11-01 {
    description
      "- Added a constraint for client association time in mobility client data.
       - Added mobility domain information.";
    reference "6.0.0";
    cisco-semver:module-version "6.0.0";
  }
  revision 2019-05-01 {
    description
      "Added semantic version";
    reference "5.1.0";
    cisco-semver:module-version "5.1.0";
  }
  revision 2019-02-25 {
    description
      "- Removed sclient username and password as it is sensitive data
       - Removal of unused leaves
       - Cleaned up spelling errors in descriptions
       - Removed few mobility attributes
       - Removed private fields of mobility peer
       - Removed mobility management event stats";
    reference "5.0.0";
    cisco-semver:module-version "5.0.0";
  }
  revision 2018-09-06 {
    description
      "- Added Units to leaves carrying timestamps
       - Added roam and delete handoff statistics in mobility event statistics
       - Added roam and handoff stats in mobility peer stats";
    reference "4.0.0";
    cisco-semver:module-version "4.0.0";
  }
  revision 2018-03-22 {
    description
      "Table renames";
    reference "3.0.0";
    cisco-semver:module-version "3.0.0";
  }
  revision 2018-01-24 {
    description
      "The first generally available version";
    reference "2.0.0";
    cisco-semver:module-version "2.0.0";
  }
  revision 2017-05-05 {
    description
      "Initial revision";
    reference "1.0.0";
    cisco-semver:module-version "1.0.0";
  }

  typedef mobility-ap-list-source-type {
    type enumeration {
      enum "self" {
        value 0;
        description
          "AP entry connected locally";
      }
      enum "mobility-group" {
        value 1;
        description
          "AP entry from other controllers in mobility group";
      }
    }
    description
      "AP entries connected locally or from the other
       controllers in the mobility group";
  }

  grouping mmif-global-msg-stats {
    description
      "Mobility Interface global message statistics";
    list ipc-stats {
      max-elements "255";
      description
        "Inter-process messaging statistics for mobility control CAPWAP messages";
      uses wireless-mobility-types:mm-msg-stats;
    }
  }

  grouping mmif-global-stats {
    description
      "Mobility Interface global event statistics";
    container mblty-stats {
      description
        "Mobility Interface event statistics";
      uses wireless-mobility-types:mmif-mobility-stats;
    }
    container mblty-domain-info {
      description
        "Mobility domain information for local mobility group";
      uses wireless-mobility-types:mobility-domain-info;
    }
  }

  grouping mm-dtls-stats {
    description
      "Global mobility DTLS statistics";
    list event-stats {
      max-elements "2";
      description
        "DTLS event statistics for mobility control and data tunnels";
      uses wireless-mobility-types:mm-dtls-event-stats;
    }
    list msg-stats {
      max-elements "2";
      description
        "DTLS message statistics for mobility control and data tunnels";
      uses wireless-mobility-types:mm-dtls-msg-stats;
    }
  }

  grouping mm-global-msg-stats {
    description
      "Global mobility message statistics";
    list ipc-stats {
      max-elements "255";
      description
        "Inter-process messaging statistics for mobility control CAPWAP messages";
      uses wireless-mobility-types:mm-msg-stats;
    }
    list dgram-stats {
      max-elements "255";
      description
        "Inter-controller messaging statistics for mobility control tunnel CAPWAP messages";
      uses wireless-mobility-types:mm-msg-stats;
    }
    list dgram-data-stats {
      max-elements "255";
      description
        "Inter-controller messaging statistics for mobility data tunnel CAPWAP messages";
      uses wireless-mobility-types:mm-msg-stats;
    }
  }

  grouping mm-global-stats {
    description
      "Mobility global statistics";
    container mm-mblty-stats {
      description
        "Mobility management event statistics";
      uses wireless-mobility-types:mm-mobility-stats;
    }
  }

  grouping mm-client-stats {
    description
      "Mobility and message statistics for client";
    leaf client-mac {
      type yang:mac-address;
      description
        "Ethernet MAC of client";
    }
    container mm-mblty-stats {
      description
        "Mobility statistics for client";
      uses wireless-mobility-types:mm-mobility-stats;
    }
    list ipc-stats {
      max-elements "255";
      description
        "Inter-process messaging statistics for mobility control CAPWAP messages";
      uses wireless-mobility-types:mm-msg-stats;
    }
    list dgram-stats {
      max-elements "255";
      description
        "Inter-controller messaging statistics for mobility control tunnel CAPWAP messages";
      uses wireless-mobility-types:mm-msg-stats;
    }
  }

  grouping mobility-client-params {
    description
      "Mobility client parameters";
    leaf client-mac {
      type yang:mac-address;
      description
        "Client MAC address";
    }
    leaf client-ifid {
      type uint32;
      description
        "Client IFID";
    }
    leaf owner-instance {
      type uint8;
      description
        "Owner instance for mobility client";
    }
    leaf assoc-time-stamp {
      when "(count(/ntp-ios-xe-oper:ntp-oper-data/ntp-ios-xe-oper:ntp-status-info/ntp-ios-xe-oper:ntp-associations) > 0)";
      type yang:date-and-time;
      units "seconds";
      description
        "Client association time";
    }
    leaf mobility-state {
      type wireless-mobility-types:mm-mobility-state;
      description
        "Mobility state";
    }
    leaf client-role {
      type wireless-mobility-types:mm-client-role;
      description
        "Client role";
    }
    leaf client-type {
      type wireless-mobility-types:mm-client-type;
      description
        "Client type";
    }
    leaf client-mode {
      type wireless-mobility-types:mm-client-mode;
      description
        "Mobility client mode";
    }
    leaf client-roam-type {
      type wireless-mobility-types:mm-client-roam-type;
      description
        "Mobility client roam type";
    }
    leaf peer-ip {
      type inet:ip-address;
      description
        "Mobility peer IP for an anchor or foreign client";
    }
    leaf entry-last-update-time {
      type yang:date-and-time;
      units "seconds";
      description
        "Client mobility discovery complete timestamp";
    }
    leaf client-create-time {
      type yang:date-and-time;
      units "seconds";
      description
        "Mobility client create timestamp";
    }
    leaf wlan-profile {
      type string;
      description
        "Mobility client wlan profile name";
    }
  }

  grouping keepalive-state {
    description
      "Keepalive status for peer and link";
    leaf peer-responses-in-interval {
      type uint8;
      description
        "Responses for peer (in interval)";
    }
    leaf intervals-without-response {
      type uint8;
      description
        "Keepalive intervals elapsed without receiving response from mobility peer";
    }
    leaf peer-status {
      type boolean;
      description
        "Keepalive status of peer";
    }
    leaf link-status {
      type boolean;
      description
        "Keepalive status of link";
    }
    leaf packet-failure-cnt {
      type uint32;
      description
        "Packet failure counter";
    }
    leaf flaps-cnt {
      type uint32;
      description
        "Link flap counter";
    }
    leaf last-flap-timestamp {
      type yang:date-and-time;
      units "seconds";
      description
        "Last flap timestamp";
    }
  }

  grouping mobility-dtls-info {
    description
      "Mobility DTLS information";
    leaf connection-status {
      type wireless-mobility-types:mm-dtls-status;
      description
        "Mobility DTLS status of connection";
    }
  }

  grouping policy-id {
    description
      "Policy Id for anchor management";
    leaf id {
      type uint32;
      description
        "ID for the policy of the anchor";
    }
  }

  grouping mm-node-stats {
    description
      "Mobility Node Statistics";
    leaf l2-roam-cnt {
      type uint32;
      description
        "Mobility l2 roam count";
    }
    leaf l3-roam-cnt {
      type uint32;
      description
        "Mobility l3 roam count";
    }
    leaf handoff-recvd-ok {
      type uint32;
      description
        "Successful handoffs received from peer";
    }
    leaf handoff-recvd-grp-mismatch {
      type uint32;
      description
        "Handoffs with group mismatch status received from peer";
    }
    leaf handoff-recvd-ms-unknown {
      type uint32;
      description
        "Handoffs with unknown client status received from peer";
    }
    leaf handoff-recvd-ms-blacklist {
      type uint32;
      description
        "Handoffs with blacklisted client status received from peer";
    }
    leaf handoff-recvd-ms-ssid {
      type uint32;
      description
        "Handoffs with SSID mismatch received from peer";
    }
    leaf handoff-recvd-deny {
      type uint32;
      description
        "Handoff denies received from peer";
    }
    leaf handoff-sent-ok {
      type uint32;
      description
        "Successful handoffs sent to peer";
    }
    leaf handoff-sent-grp-mismatch {
      type uint32;
      description
        "Handoffs with group mismatch status sent to peer";
    }
    leaf handoff-sent-ms-unknown {
      type uint32;
      description
        "Handoffs with unknown client status sent to peer";
    }
    leaf handoff-sent-ms-blacklist {
      type uint32;
      description
        "Handoffs with blacklist client status sent to peer";
    }
    leaf handoff-sent-ms-ssid {
      type uint32;
      description
        "Handoffs with SSID mismatch status sent to peer";
    }
    leaf handoff-sent-deny {
      type uint32;
      description
        "Handoff denies sent to peer";
    }
  }

  grouping mobility-node-list-entry {
    description
      "Entry for mobility node list";
    leaf node-ip {
      type inet:ip-address;
      description
        "Mobility node IP";
    }
    leaf nat-ip {
      type inet:ip-address;
      description
        "Mobility node NAT IP";
    }
    leaf node-mac-addr {
      type yang:mac-address;
      description
        "Mobility node MAC Address";
    }
    leaf ulink-status {
      type wireless-mobility-types:unified-link-status;
      description
        "Mobility node link status";
    }
    leaf tunnel-ifid {
      type uint32;
      description
        "Mobility node tunnel IFID";
    }
    leaf group-name {
      type string;
      description
        "Mobility node group name";
    }
    leaf num-clients {
      type uint32;
      description
        "Total number of clients at mobility node";
    }
    leaf tunnel-plumbed {
      type boolean;
      description
        "Tunnel plumbing status for mobility node";
    }
    leaf pmtu {
      type uint32;
      units "bytes";
      description
        "PMTU for mobility node";
    }
    list peer-capability {
      max-elements "2";
      description
        "Architecture, DTLS and tunnel capability of peer for mobility node";
      uses wireless-mobility-types:capability;
    }
    container ctrl-state {
      description
        "Control keepalive state for mobility node";
      uses wireless-mobility-oper:keepalive-state;
    }
    container data-state {
      description
        "Data keepalive state for mobility node";
      uses wireless-mobility-oper:keepalive-state;
    }
    leaf dtls-session-id {
      type uint64;
      description
        "Control tunnel DTLS session id";
    }
    leaf data-dtls-session-id {
      type uint64;
      description
        "Data tunnel DTLS session id";
    }
    list dtls-info {
      max-elements "2";
      description
        "DTLS information for mobility node";
      uses wireless-mobility-oper:mobility-dtls-info;
    }
    leaf is-anchor {
      type boolean;
      description
        "Indicates whether or not mobility node is anchor";
    }
    leaf is-anchor-full {
      type boolean;
      description
        "Indicates whether or not anchor mobility node is full";
    }
    leaf num-exported-clients {
      type uint32;
      description
        "Number of clients anchored to mobility node";
    }
    leaf num-imported-clients {
      type uint32;
      description
        "Number of anchored clients from mobility node";
    }
    list policy-ids {
      description
        "Policy IDs";
      uses wireless-mobility-oper:policy-id;
    }
    container node-stats {
      description
        "Statistics for mobility node";
      uses wireless-mobility-oper:mm-node-stats;
    }
    leaf dl-encrypt {
      type boolean;
      description
        "Data link encryption status for mobility node";
    }
  }

  grouping wlan-info-entry {
    description
      "Wlan info";
    leaf wlan-profile {
      type string;
      description
        "Name of the wlan profile";
    }
    leaf curr-clients-count {
      type uint32;
      description
        "Number of clients connected to the wlan";
    }
  }

  grouping mm-sclient {
    description
      "Mobility sclient";
    leaf client-mac {
      type yang:mac-address;
      description
        "Mobility sclient MAC address";
    }
    leaf vap-ssid {
      type string;
      description
        "VAP SSID for mobility sclient";
    }
    leaf sclient-timestamp {
      type yang:date-and-time;
      units "seconds";
      description
        "Mobility sclient timestamp";
    }
  }

  grouping mesh-ap-channel-list-peer {
    description
      "Represents a list of mobility members from which bridge group name and channel is learnt";
    leaf node-ip {
      type inet:ip-address;
      description
        "Represents IP Address of the mobility member from which bridge group name and channel is learnt";
    }
  }

  grouping mesh-ap-channel-list {
    description
      "Represent list of bridge group name and channel learnt from mobility members";
    leaf local-wncd-info {
      type uint32;
      description
        "Represents the information about WNCD instance from which bridge group name and channel is learnt";
    }
    list mm-ap-channel-list-peer-ip {
      key "node-ip";
      description
        "Represents Ip Address of the member controller frm which bridge group name and channel information is learnt";
      uses wireless-mobility-oper:mesh-ap-channel-list-peer;
    }
  }

  grouping mesh-ap-channel-peer-list-info {
    description
      "Represents if the Ip Address bridge group name Channel entry information";
    leaf stale {
      type uint8;
      description
        "Represents if the Ip address bridge group name channel entry is stale";
    }
  }

  grouping mobility-ap-list-entry {
    description
      "Each entry in this table provides information about AP
       that is reported by this MC or its peer MC or its MA.";
    leaf mac-addr {
      type yang:mac-address;
      description
        "Reported AP's mac address.";
    }
    leaf name {
      type string;
      description
        "Reported AP's name";
    }
    leaf controller-ip {
      type inet:ip-address;
      description
        "Reporting device's IP address";
    }
    leaf source {
      type wireless-mobility-oper:mobility-ap-list-source-type;
      description
        "Reporting device's IP address type";
    }
  }

  grouping mobility-ap-list-peer-entry {
    description
      "Each entry in this table provides information on total 
       number of APs that is reported by this MC or its peer 
       MC or its MA";
    leaf peer-ip {
      type inet:ip-address;
      description
        "Reporting device's IP address";
    }
    leaf ap-count {
      type uint32;
      description
        "Total number of APs reported by this device: this 
         MC, or its peer MC or its MA";
    }
    leaf source {
      type wireless-mobility-oper:mobility-ap-list-source-type;
      description
        "Reporting device's IP address type";
    }
  }

  container mobility-oper-data {
    config false;
    description
      "Yang model for wireless mobility oper";
    container mm-if-global-stats {
      presence "mm-if-global-stats";
      description
        "Container for global mobility interface event statistics";
      uses wireless-mobility-oper:mmif-global-stats;
    }
    container mm-if-global-msg-stats {
      presence "mm-if-global-msg-stats";
      description
        "Container for global mobility interface message statistics";
      uses wireless-mobility-oper:mmif-global-msg-stats;
    }
    container mobility-global-stats {
      presence "mobility-global-stats";
      description
        "Container for global mobility statistics";
      uses wireless-mobility-oper:mm-global-stats;
    }
    container mobility-global-msg-stats {
      presence "mobility-global-msg-stats";
      description
        "Container for global mobility message statistics";
      uses wireless-mobility-oper:mm-global-msg-stats;
    }
    list mobility-client-data {
      key "client-mac";
      description
        "Each entry in this table provides information about
         one 802.11 LWAPP Mobility Clients on this MC";
      uses wireless-mobility-oper:mobility-client-params;
    }
    list ap-cache {
      key "mac-addr";
      description
        "Each entry in this table provides information about
         AP that is reported by this MC or its peer MC or its
         MA";
      uses wireless-mobility-oper:mobility-ap-list-entry;
    }
    list ap-peer-list {
      key "peer-ip";
      description
        "Each entry in this table provides information on 
         total number of APs that is reported by this MC or 
         its peer MC or its MA";
      uses wireless-mobility-oper:mobility-ap-list-peer-entry;
    }
    list mobility-client-stats {
      key "client-mac";
      description
        "Container for client mobility event and message statistics";
      uses wireless-mobility-oper:mm-client-stats;
    }
    list mobility-node-data {
      key "node-ip";
      description
        "Container for mobility node data";
      uses wireless-mobility-oper:mobility-node-list-entry;
    }
    list wlan-client-limit {
      key "wlan-profile";
      description
        "Container for WLAN client limit data";
      uses wireless-mobility-oper:wlan-info-entry;
    }
    list sleeping-client-stats {
      key "client-mac";
      description
        "Mobility sclient";
      uses wireless-mobility-oper:mm-sclient;
    }
    list mm-ap-channel-list {
      key "bgn channel";
      description
        "Container for mobility subset channel data for mesh APs";
      uses wireless-types:bgn-channel-key;
      uses wireless-mobility-oper:mesh-ap-channel-list;
    }
    list mm-ap-channel-peer-list {
      key "node-ip bgn channel";
      description
        "Container for mobility subset channel data for mesh APs learnt from mobility peers";
      uses wireless-types:ipaddr-bgn-channel-key;
      uses wireless-mobility-oper:mesh-ap-channel-peer-list-info;
    }
    container mobility-global-dtls-stats {
      presence "mobility-global-dtls-stats";
      description
        "Container for global mobility DTLS statistics";
      uses wireless-mobility-oper:mm-dtls-stats;
    }
  }
}
