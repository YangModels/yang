module Cisco-IOS-XE-platform-events-oper {
  yang-version 1;
  namespace "http://cisco.com/ns/yang/Cisco-IOS-XE-platform-events-oper";
  prefix platform-events-ios-xe-oper;

  import Cisco-IOS-XE-platform-common-oper {
    prefix platform-common-ios-xe-oper;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring of platform components events.
     Copyright (c) 2019-2020 by Cisco Systems, Inc.
     All rights reserved.";

  revision 2020-07-01 {
    description
      "- Remove unused empty container platform-events";
    reference "2.0.0";
    cisco-semver:module-version "2.0.0";
  }
  revision 2019-11-01 {
    description
      "Initial revision";
    reference "1.0.0";
    cisco-semver:module-version "1.0.0";
  }

  typedef plat-notif-severity {
    type enumeration {
      enum "notif-sev-critical" {
        value 0;
        description
          "Notification severity - critical";
      }
      enum "notif-sev-major" {
        value 1;
        description
          "Notification severity - major";
      }
      enum "notif-sev-minor" {
        value 2;
        description
          "Notification severity - minor";
      }
    }
    description
      "Notification severity";
  }

  typedef plat-comp-state {
    type enumeration {
      enum "module-present" {
        value 0;
        description
          "Module present";
      }
      enum "module-inserted" {
        value 1;
        description
          "Module inserted";
      }
      enum "module-removed" {
        value 2;
        description
          "Module removed";
      }
    }
    description
      "Platform module state";
  }

  grouping plat-sensor-state-data {
    description
      "platform sensor state events data model";
    leaf severity {
      type platform-events-ios-xe-oper:plat-notif-severity;
      description
        "Event severity";
    }
    leaf comp-type {
      type platform-common-ios-xe-oper:plat-comp-type;
      description
        "Platform component type";
    }
    leaf sensor-type {
      type platform-common-ios-xe-oper:plat-sensor-type;
      description
        "Platform sensor type";
    }
    leaf description {
      type string;
      description
        "Platform sensor description";
    }
    leaf location {
      type string;
      description
        "Platform sensor location containing chassis, slot, bay";
    }
    leaf id {
      type string;
      description
        "Platform sensor SNMP physical index";
    }
    container sensor-val {
      description
        "Sensor readings of a component. Values include
         the instantaneous, average, max, and min statistics";
      uses platform-common-ios-xe-oper:plat-sensor-data;
    }
    container alarm-data {
      description
        "Contains sensor alarm data. It includes alarm status, 
         high threshold, low threshold and alarm severity";
      uses platform-common-ios-xe-oper:plat-sensor-alarm-data;
    }
    leaf new-state {
      type platform-common-ios-xe-oper:plat-sensor-state;
      description
        "Platform sensor temperature new state";
    }
    leaf time-stamp {
      type yang:date-and-time;
      description
        "Notification time stamp";
    }
  }

  grouping plat-comp-state-data {
    description
      "platform component state events data model";
    leaf severity {
      type platform-events-ios-xe-oper:plat-notif-severity;
      description
        "Event severity";
    }
    leaf comp-type {
      type platform-common-ios-xe-oper:plat-comp-type;
      description
        "Platform component type";
    }
    leaf description {
      type string;
      description
        "Platform component description";
    }
    leaf location {
      type string;
      description
        "Platform component location containing chassis, slot, bay";
    }
    leaf id {
      type string;
      description
        "Platform component SNMP physical index";
    }
    leaf part-no {
      type string;
      description
        "Platform component part number";
    }
    leaf comp-state {
      type platform-events-ios-xe-oper:plat-comp-state;
      description
        "Platform component state";
    }
    leaf new-status {
      type platform-common-ios-xe-oper:plat-comp-status;
      description
        "Platform component new status";
    }
    leaf status-desc {
      type platform-common-ios-xe-oper:plat-comp-status-desc;
      description
        "Platform component new status description";
    }
    leaf time-stamp {
      type yang:date-and-time;
      description
        "Notification time stamp";
    }
  }

  notification platform-sensor-state-update {
    description
      "Component sensor state change notification";
    uses platform-events-ios-xe-oper:plat-sensor-state-data;
  }
  notification platform-component-state-update {
    description
      "Platform component state change notification";
    uses platform-events-ios-xe-oper:plat-comp-state-data;
  }
}
