module Cisco-IOS-XE-wireless-me-general-cfg {
  yang-version 1;
  namespace "http://cisco.com/ns/yang/Cisco-IOS-XE-wireless-me-general-cfg";
  prefix wireless-me-general-cfg;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing Embedded Wireless Controller miscellaneous configuration.
     Copyright (c) 2019-2020 by Cisco Systems, Inc.
     All rights reserved.";

  revision 2020-11-01 {
    description
      "- Added Web-auth archive config";
    reference "1.1.0";
    cisco-semver:module-version "1.1.0";
  }
  revision 2019-11-01 {
    description
      "Initial revision";
    reference "1.0.0";
    cisco-semver:module-version "1.0.0";
  }

  grouping webauth-arch-path {
    description
      "Web-auth archive download attributes";
    leaf archive-path {
      type string {
        length "0..100" {
          error-message "Invalid string length for archive path. Valid string has to be between 0 and 100 characters";
          error-app-tag "must-violation";
        }
        pattern "(flash:|bootflash:)[-A-Za-z_.0-9/]*[-A-Za-z_0-9].tar";
      }
      description
        "Archive path on the controller";
    }
    leaf archive-description {
      type string;
      default "";
      description
        "Description of the archive";
    }
  }

  grouping st-vlan-central-nat {
    description
      "VLAN configuration for centralized NAT";
    leaf vlan-id {
      type uint16 {
        range "1 .. 4094";
      }
      description
        "VLAN ID where centralized NAT is enabled";
    }
    leaf peer-blocking {
      type boolean;
      default "false";
      description
        "Enable or disable peer to peer traffic on this centralized NAT VLAN";
    }
  }

  container me-general-cfg-data {
    description
      "Top level container for Embedded Wireless Controller miscellaneous configuration";
    container central-nats {
      description
        "Configuration for the centralized NAT enabled VLANs";
      list central-nat {
        key "vlan-id";
        description
          "Centralized NAT configuration on a given VLAN";
        uses wireless-me-general-cfg:st-vlan-central-nat;
      }
    }
    container webauth-archives {
      description
        "Web-auth archive configuration";
      list webauth-archive {
        must "(count(../webauth-archive) <= 20)" {
          error-message "Maximum number of 20 archives is already configured";
          error-app-tag "must-violation";
        }
        key "archive-path";
        description
          "Web-auth archive configuration";
        uses wireless-me-general-cfg:webauth-arch-path;
      }
    }
  }
}
