module Cisco-IOS-XE-memory-oper {
  yang-version 1;
  namespace "http://cisco.com/ns/yang/Cisco-IOS-XE-memory-oper";
  prefix memory-ios-xe-oper;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring memory in a Network Element.
     Copyright (c) 2016-2017, 2019 by Cisco Systems, Inc.
     All rights reserved.";

  revision 2019-05-01 {
    description
      "Added semantic version";
    reference "2.1.0";
    cisco-semver:module-version "2.1.0";
  }
  revision 2017-04-01 {
    description
      "Top level container name change";
    reference "2.0.0";
    cisco-semver:module-version "2.0.0";
  }
  revision 2017-02-07 {
    description
      "Initial revision";
    reference "1.0.0";
    cisco-semver:module-version "1.0.0";
  }

  grouping memory-stats {
    description
      "Memory statistics";
    leaf name {
      type string;
      description
        "The name of the memory pool";
    }
    leaf total-memory {
      type uint64;
      units "bytes";
      description
        "Total memory in the pool (bytes)";
    }
    leaf used-memory {
      type uint64;
      units "bytes";
      description
        "Total used memory in the pool (bytes)";
    }
    leaf free-memory {
      type uint64;
      units "bytes";
      description
        "Total free memory in the pool (bytes)";
    }
    leaf lowest-usage {
      type uint64;
      units "bytes";
      description
        "Historical lowest memory usage (bytes)";
    }
    leaf highest-usage {
      type uint64;
      units "bytes";
      description
        "Historical highest memory usage (bytes)";
    }
  }

  container memory-statistics {
    config false;
    description
      "Data nodes for All Memory Pool Statistics.";
    list memory-statistic {
      key "name";
      description
        "The list of software memory pools in the system.";
      uses memory-ios-xe-oper:memory-stats;
    }
  }
}
