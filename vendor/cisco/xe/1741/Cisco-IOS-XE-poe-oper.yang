module Cisco-IOS-XE-poe-oper {
  yang-version 1;
  namespace "http://cisco.com/ns/yang/Cisco-IOS-XE-poe-oper";
  prefix poe-ios-xe-oper;

  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring power over ethernet feature in a Network Element.
     Copyright (c) 2016-2020 by Cisco Systems, Inc.
     All rights reserved.";

  revision 2020-07-01 {
    description
      "Extended PoE port data with module number and chassis number";
    reference "1.4.0";
    cisco-semver:module-version "1.4.0";
  }
  revision 2019-11-01 {
    description
      "Enhanced and re-structured the PoE operational data with layer 2
       power-negotiation data and information relevant to each pair";
    reference "1.3.0";
    cisco-semver:module-version "1.3.0";
  }
  revision 2019-05-01 {
    description
      "Added semantic version";
    reference "1.2.0";
    cisco-semver:module-version "1.2.0";
  }
  revision 2018-10-11 {
    description
      "Extended PoE model by adding PoE module/port/stack information";
    reference "1.1.0";
    cisco-semver:module-version "1.1.0";
  }
  revision 2018-02-04 {
    description
      "Initial revision";
    reference "1.0.0";
    cisco-semver:module-version "1.0.0";
  }

  typedef ilpower-pd-class {
    type enumeration {
      enum "poe-null" {
        value 0;
        description
          "Power class not available";
      }
      enum "poe-unknown" {
        value 1;
        description
          "Power class unknown";
      }
      enum "poe-cisco" {
        value 2;
        description
          "Power class Cisco";
      }
      enum "poe-ieee0" {
        value 3;
        description
          "IEEE power class 0";
      }
      enum "poe-ieee1" {
        value 4;
        description
          "IEEE power class 1";
      }
      enum "poe-ieee2" {
        value 5;
        description
          "IEEE power class 2";
      }
      enum "poe-ieee3" {
        value 6;
        description
          "IEEE power class 3";
      }
      enum "poe-ieee4" {
        value 7;
        description
          "IEEE power class 4";
      }
      enum "poe-ieee5" {
        value 8;
        description
          "IEEE power class 5";
      }
      enum "poe-ieee-unknown-class" {
        value 9;
        description
          "IEEE power class unknown";
      }
    }
    description
      "Name of the power class";
  }

  typedef ilpower-device-state {
    type enumeration {
      enum "attached-ok" {
        value 0;
        description
          "Device state is attached-ok";
      }
      enum "attached-faulty" {
        value 1;
        description
          "Device state is attached-faulty";
      }
      enum "detached" {
        value 2;
        description
          "Device state is detached";
      }
    }
    description
      "State of the power device";
  }

  typedef ilpower-pd-discovery-protocol {
    type enumeration {
      enum "discovery-unknown" {
        value 0;
        description
          "Discovery protocol is unknown";
      }
      enum "discovery-invalid" {
        value 1;
        description
          "Discovery protocol is invalid";
      }
      enum "discovery-off" {
        value 2;
        description
          "Discovery protocol is off";
      }
      enum "discovery-ieee" {
        value 3;
        description
          "Discovery protocol is IEEE";
      }
      enum "discovery-cisco" {
        value 4;
        description
          "Discovery protocol is Cisco";
      }
      enum "discovery-cisco-ieee" {
        value 5;
        description
          "Discovery protocol is Cisco and IEEE";
      }
    }
    description
      "Discovery protocol of the power device";
  }

  typedef poe-lldp-power-type {
    type enumeration {
      enum "type-two-pse" {
        value 0;
        description
          "LLDP power source equipment type is two";
      }
      enum "type-two-pd" {
        value 1;
        description
          "LLDP powered device type is two";
      }
      enum "type-one-pse" {
        value 2;
        description
          "LLDP power source equipment type is one";
      }
      enum "type-one-pd" {
        value 3;
        description
          "LLDP powered device type is one";
      }
    }
    description
      "lldp power type";
  }

  typedef poe-lldp-power-source {
    type enumeration {
      enum "power-source-unknown" {
        value 0;
        description
          "Source is unknown";
      }
      enum "power-source-pse-primary" {
        value 1;
        description
          "Source is primary power source equipment";
      }
      enum "power-source-pd-pse" {
        value 2;
        description
          "Source is power device and power source equipment";
      }
      enum "power-source-pse-backup" {
        value 3;
        description
          "Source is backup power source equipment";
      }
      enum "power-source-pd-reserved" {
        value 4;
        description
          "Source is reserved power device";
      }
      enum "power-source-pse-reserved" {
        value 5;
        description
          "Source is reserved power source equipment";
      }
      enum "power-source-pd-pse-and-local" {
        value 6;
        description
          "Source is power device,power source equipment and local";
      }
    }
    description
      "LLDP power source";
  }

  typedef poe-lldp-power-priority {
    type enumeration {
      enum "power-priority-unknown" {
        value 0;
        description
          "LLDP power priority is unknown";
      }
      enum "power-priority-critical" {
        value 1;
        description
          "LLDP power priority is critical";
      }
      enum "power-priority-high" {
        value 2;
        description
          "LLDP power priority is high";
      }
      enum "power-priority-low" {
        value 3;
        description
          "LLDP power priority is low";
      }
    }
    description
      "LLDP power priority";
  }

  typedef power-state {
    type enumeration {
      enum "power-status-null" {
        value 0;
        description
          "Device power state is not available";
      }
      enum "power-status-ok" {
        value 1;
        description
          "Device power state is ok";
      }
      enum "power-status-deny" {
        value 2;
        description
          "Device power state is deny";
      }
      enum "power-status-off" {
        value 3;
        description
          "Device power state is off";
      }
    }
    description
      "Device power state";
  }

  typedef poe-upoe-cmd-mode {
    type enumeration {
      enum "upoe-mode-auto" {
        value 0;
        description
          "Cisco Universal Power Over Ethernet mode is auto";
      }
      enum "upoe-mode-forced" {
        value 1;
        description
          "Cisco Universal Power Over Ethernet mode is forced";
      }
      enum "upoe-mode-diag" {
        value 2;
        description
          "Cisco Universal Power Over Ethernet mode is diag";
      }
    }
    description
      "Upoe mode";
  }

  typedef ilpower-pd-power-state {
    type enumeration {
      enum "pd-power-off" {
        value 0;
        description
          "Inline powered device power state is off";
      }
      enum "pd-power-on" {
        value 1;
        description
          "Inline powered device power state is on";
      }
      enum "pd-power-faulty" {
        value 2;
        description
          "Inline powered device power state is faulty";
      }
      enum "pd-power-deny" {
        value 3;
        description
          "Inline powered device power state is deny";
      }
      enum "pd-power-overdrawn" {
        value 4;
        description
          "Inline powered device power state is overdrawn";
      }
    }
    description
      "Ilpower device power state";
  }

  typedef ilpower-admin-state {
    type enumeration {
      enum "admin-state-null" {
        value 0;
        description
          "Inline powered device power admin state is not available";
      }
      enum "admin-state-off" {
        value 1;
        description
          "Inline powered device power admin state is off";
      }
      enum "admin-state-auto" {
        value 2;
        description
          "Inline powered device power admin state is auto";
      }
      enum "admin-state-static" {
        value 3;
        description
          "Inline powered device power admin state is static";
      }
    }
    description
      "Ilpower device power admin state";
  }

  typedef poe-pd-class {
    type enumeration {
      enum "pd-null" {
        value 0;
        description
          "Power class not available";
      }
      enum "pd-unknown" {
        value 1;
        description
          "Power class unknown";
      }
      enum "pd-cisco" {
        value 2;
        description
          "Power class Cisco";
      }
      enum "pd-ieee0" {
        value 3;
        description
          "IEEE power class 0";
      }
      enum "pd-ieee1" {
        value 4;
        description
          "IEEE power class 1";
      }
      enum "pd-ieee2" {
        value 5;
        description
          "IEEE power class 2";
      }
      enum "pd-ieee3" {
        value 6;
        description
          "IEEE power class 3";
      }
      enum "pd-ieee4" {
        value 7;
        description
          "IEEE power class 4";
      }
      enum "pd-ieee5" {
        value 8;
        description
          "IEEE power class 5";
      }
      enum "pd-ieee-unknown-class" {
        value 9;
        description
          "IEEE power class unknown";
      }
      enum "pd-ieee6" {
        value 10;
        description
          "IEEE power class 6";
      }
      enum "pd-ieee7" {
        value 11;
        description
          "IEEE power class 7";
      }
      enum "pd-ieee8" {
        value 12;
        description
          "IEEE power class 8";
      }
      enum "pd-mismatch" {
        value 13;
        description
          "Power class not available";
      }
    }
    description
      "Name of the power class";
  }

  typedef poe-pd-power-state {
    type enumeration {
      enum "power-deny" {
        value 0;
        description
          "Powered device power state is power deny";
      }
      enum "faulty" {
        value 1;
        description
          "Powered device power state is faulty";
      }
      enum "on" {
        value 2;
        description
          "Powered device power state is on";
      }
      enum "off" {
        value 3;
        description
          "Powered device power state is off";
      }
      enum "error-disable" {
        value 4;
        description
          "Powered device power state is error disable";
      }
    }
    description
      "Poe device power state";
  }

  typedef poe-police-action {
    type enumeration {
      enum "police-action-none" {
        value 0;
        description
          "Police action not available";
      }
      enum "police-action-error-disable" {
        value 1;
        description
          "Police action is error disable";
      }
      enum "police-action-log" {
        value 2;
        description
          "Police action is log";
      }
    }
    description
      "PoE police action";
  }

  typedef poe-police-oper {
    type enumeration {
      enum "oper-police-none" {
        value 0;
        description
          "Operational police state is not available";
      }
      enum "oper-police-ok" {
        value 1;
        description
          "Operational police state is ok";
      }
      enum "oper-police-overdrawn" {
        value 2;
        description
          "Operational police state is overdrawn";
      }
    }
    description
      "PoE operational police state";
  }

  typedef poe-conn-check {
    type enumeration {
      enum "conn-chk-none" {
        value 0;
        description
          "PoE connection check is not available";
      }
      enum "conn-chk-ds" {
        value 1;
        description
          "PoE connection check is dual signature";
      }
      enum "conn-chk-ss" {
        value 2;
        description
          "PoE connection check is single signature";
      }
      enum "conn-chk-sp" {
        value 3;
        description
          "PoE connection check is signal pair";
      }
    }
    description
      "PoE connection check";
  }

  typedef ilpower-lldp-power-source {
    type enumeration {
      enum "power-source-reserved" {
        value 0;
        description
          "LLDP power source is reserved";
      }
      enum "power-source-backup" {
        value 1;
        description
          "LLDP power source is backup";
      }
      enum "power-source-primary" {
        value 2;
        description
          "LLDP power source is primary";
      }
      enum "power-source-type-unknown" {
        value 3;
        description
          "LLDP power source is unknown";
      }
      enum "power-source-pse-and-local" {
        value 4;
        description
          "LLDP power source is PSE and local";
      }
      enum "power-source-pse" {
        value 5;
        description
          "LLDP power source is PSE";
      }
    }
    description
      "LLDP power source";
  }

  typedef pse-lldp-pwr-status {
    type enumeration {
      enum "pse-power-status-ignore" {
        value 0;
        description
          "PSE LLDP power status is ignore";
      }
      enum "pse-power-status-2-pair-pd" {
        value 1;
        description
          "PSE LLDP power status is 2 pair power device";
      }
      enum "pse-power-status-4-pair-ss-pd" {
        value 2;
        description
          "PSE LLDP power status is 4 pair single signature power device";
      }
      enum "pse-power-status-4-pair-ds-pd" {
        value 3;
        description
          "PSE LLDP power status is 4 pair dual signature power device";
      }
    }
    description
      "PSE LLDP power status";
  }

  typedef pd-lldp-pwr-status {
    type enumeration {
      enum "pd-power-status-ignore" {
        value 0;
        description
          "PD LLDP power status is ignore";
      }
      enum "pd-power-status-ss-pd" {
        value 1;
        description
          "PD LLDP power status is single signature power device";
      }
      enum "pd-power-status-2-pair-ds-pd" {
        value 2;
        description
          "PD LLDP power status is 2 pair dual signature power device";
      }
      enum "pd-power-status-4-pair-ds-pd" {
        value 3;
        description
          "PD LLDP power status is 4 pair dual signature power device";
      }
    }
    description
      "PD LLDP power status";
  }

  typedef lldp-pse-pwr-ext-type {
    type enumeration {
      enum "lldp-power-type-ignore" {
        value 0;
        description
          "LLDP PSE power type is ignore";
      }
      enum "lldp-power-type-alt-a" {
        value 1;
        description
          "LLDP PSE power type is alternative A";
      }
      enum "lldp-power-type-alt-b" {
        value 2;
        description
          "LLDP PSE power type is alternative B";
      }
      enum "lldp-power-type-both-alternatives" {
        value 3;
        description
          "LLDP PSE power type is both alternative";
      }
    }
    description
      "LLDP PSE power ext type";
  }

  typedef dual-sig-pwr-class {
    type enumeration {
      enum "ds-power-class-ignore" {
        value 0;
        description
          "Dual signature power class is ignore";
      }
      enum "ds-power-class-1" {
        value 1;
        description
          "Dual signature power class is 1";
      }
      enum "ds-power-class-2" {
        value 2;
        description
          "Dual signature power class is 2";
      }
      enum "ds-power-class-3" {
        value 3;
        description
          "Dual signature power class is 3";
      }
      enum "ds-power-class-4" {
        value 4;
        description
          "Dual signature power class is 4";
      }
      enum "ds-power-class-5" {
        value 5;
        description
          "Dual signature power class is 5";
      }
      enum "ds-power-class-ss-pd" {
        value 6;
        description
          "Dual signature power class is single signature power device";
      }
    }
    description
      "Dual signature power class";
  }

  typedef ss-pwr-class {
    type enumeration {
      enum "ss-power-class-ignore" {
        value 0;
        description
          "Single signature power class is ignore";
      }
      enum "ss-power-class-1" {
        value 1;
        description
          "Single signature power class is 1";
      }
      enum "ss-power-class-2" {
        value 2;
        description
          "Single signature power class is 2";
      }
      enum "ss-power-class-3" {
        value 3;
        description
          "Single signature power class is 3";
      }
      enum "ss-power-class-4" {
        value 4;
        description
          "Single signature power class is 4";
      }
      enum "ss-power-class-5" {
        value 5;
        description
          "Single signature power class is 5";
      }
      enum "ss-power-class-6" {
        value 6;
        description
          "Single signature power class is 6";
      }
      enum "ss-power-class-7" {
        value 7;
        description
          "Single signature power class is 7";
      }
      enum "ss-power-class-8" {
        value 8;
        description
          "Single signature power class is 8";
      }
      enum "ss-power-class-ds-pd" {
        value 15;
        description
          "Single signature power class is single signature power device";
      }
    }
    description
      "Single signature power class";
  }

  typedef lldp-power-ext {
    type enumeration {
      enum "lldp-power-ext-type-3-pse" {
        value 0;
        description
          "LLDP power type is type 3 power source equipment";
      }
      enum "lldp-power-ext-type-4-pse" {
        value 1;
        description
          "LLDP power type is type 4 power source equipment";
      }
      enum "lldp-power-ext-type-3-ss-pd" {
        value 2;
        description
          "LLDP power type is type 3 single signature power device";
      }
      enum "lldp-power-ext-type-3-ds-pd" {
        value 3;
        description
          "LLDP power type is type 3 dual signature power device";
      }
      enum "lldp-power-ext-type-4-ss-pd" {
        value 5;
        description
          "LLDP power type is type 4 single signature power device";
      }
      enum "lldp-power-ext-type-4-ds-pd" {
        value 6;
        description
          "LLDP power type is type 4 dual signature power device";
      }
      enum "lldp-power-ext-type-ignore" {
        value 7;
        description
          "LLDP power type is ignore";
      }
    }
    description
      "LLDP power ext type";
  }

  typedef power-neg-used {
    type enumeration {
      enum "power-negotiation-none" {
        value 0;
        description
          "Power negotiation used is none";
      }
      enum "power-negotiation-cdp" {
        value 1;
        description
          "Power negotiation used is CDP";
      }
      enum "power-negotiation-lldp-med" {
        value 2;
        description
          "Power negotiation used is LLDP MED";
      }
      enum "power-negotiation-ieee-802-3-at" {
        value 3;
        description
          "Power negotiation used is IEEE 802.3 AT LLDP";
      }
      enum "power-negotiation-ieee-802-3-bt" {
        value 4;
        description
          "Power negotiation used is IEEE 802.3 BT LLDP";
      }
    }
    description
      "Power negotiation used";
  }

  typedef four-pair-pd-architecture {
    type enumeration {
      enum "pd-architecture-none" {
        value 0;
        description
          "Four pair pd architecture is none";
      }
      enum "pd-architecture-indendent" {
        value 1;
        description
          "Four pair pd architecture is independent";
      }
      enum "pd-architecture-shared" {
        value 2;
        description
          "Four pair pd architecture is shared";
      }
    }
    description
      "Four pair pd architecture";
  }

  typedef port-oper-priority {
    type enumeration {
      enum "port-oper-priority-0" {
        value 0;
        description
          "Port operational priority is 0";
      }
      enum "port-oper-priority-1" {
        value 1;
        description
          "Port operational priority is 1";
      }
      enum "port-oper-priority-2" {
        value 2;
        description
          "Port operational priority is 2";
      }
      enum "port-oper-priority-3" {
        value 3;
        description
          "Port operational priority is 3";
      }
      enum "port-oper-priority-4" {
        value 4;
        description
          "Port operational priority is 4";
      }
      enum "port-oper-priority-5" {
        value 5;
        description
          "Port operational priority is 5";
      }
      enum "port-oper-priority-6" {
        value 6;
        description
          "Port operational priority is 6";
      }
      enum "port-oper-priority-7" {
        value 7;
        description
          "Port operational priority is 7";
      }
      enum "port-oper-priority-low" {
        value 8;
        description
          "Port operational priority is low";
      }
      enum "port-oper-priority-high" {
        value 9;
        description
          "Port operational priority is high";
      }
    }
    description
      "port operational priority";
  }

  typedef ilpower-lldp-med-power-type {
    type enumeration {
      enum "lldp-med-power-type-pse" {
        value 0;
        description
          "Power type is Power source equipment";
      }
      enum "lldp-med-power-type-pd" {
        value 1;
        description
          "Power type is Powered device";
      }
      enum "reserved-type-two" {
        value 2;
        description
          "Power type is reserved";
      }
      enum "reserved-type-three" {
        value 3;
        description
          "Power type is reserved";
      }
    }
    description
      "ilpower LLDP MED power type";
  }

  typedef ilpower-lldp-med-power-source {
    type enumeration {
      enum "lldp-med-power-src-unknown" {
        value 0;
        description
          "Power source is unknown";
      }
      enum "lldp-med-power-src-primary" {
        value 1;
        description
          "Power source is primary";
      }
      enum "lldp-med-power-src-secondary" {
        value 2;
        description
          "Power source is secondary";
      }
      enum "lldp-med-power-src-pse-local" {
        value 3;
        description
          "Power source is PSE local";
      }
    }
    description
      "ilpower LLDP MED power source";
  }

  typedef ilpower-lldp-med-power-priority {
    type enumeration {
      enum "lldp-med-power-priority-unknown" {
        value 0;
        description
          "Power priority is unknown";
      }
      enum "lldp-med-power-priority-critical" {
        value 1;
        description
          "Power priority is critical";
      }
      enum "lldp-med-power-priority-high" {
        value 2;
        description
          "Power priority is high";
      }
      enum "lldp-med-power-priority-low" {
        value 3;
        description
          "Power priority is low";
      }
      enum "lldp-med-power-priority-invalid" {
        value 4;
        description
          "Power priority is invalid";
      }
    }
    description
      "ilpower LLDP MED power priority";
  }

  typedef power-stack-mode {
    type enumeration {
      enum "stack-mode-rps" {
        value 0;
        description
          "Stack mode is redundant power supply";
      }
      enum "stack-mode-sharing-strict" {
        value 1;
        description
          "Stack mode is sharing strict";
      }
      enum "stack-mode-sharing" {
        value 2;
        description
          "Stack mode is sharing";
      }
      enum "stack-mode-redundant-strict" {
        value 3;
        description
          "Stack mode is redundant strict";
      }
      enum "stack-mode-redundant" {
        value 4;
        description
          "Stack mode is redundant";
      }
      enum "stack-mode-null" {
        value 5;
        description
          "Stack mode is not available";
      }
    }
    description
      "Mode if power stack";
  }

  typedef poe-stack-topo {
    type enumeration {
      enum "stack-topo-none" {
        value 0;
        description
          "Stack topology is none";
      }
      enum "stack-topo-star" {
        value 1;
        description
          "Stack topology is star";
      }
      enum "stack-topo-standalone" {
        value 2;
        description
          "Stack topology is standalone";
      }
      enum "stack-topo-ring" {
        value 3;
        description
          "Stack topology is ring";
      }
    }
    description
      "Poe stack topology";
  }

  typedef poe-port-status {
    type enumeration {
      enum "stack-port-status-unknown" {
        value 0;
        description
          "Stack port status is unknown";
      }
      enum "stack-port-status-shut" {
        value 1;
        description
          "Stack port status is shutdown";
      }
      enum "stack-port-status-connected" {
        value 2;
        description
          "Stack port status is connected";
      }
      enum "stack-port-status-not-connected" {
        value 3;
        description
          "Stack port status is not connected";
      }
    }
    description
      "Stack port status";
  }

  grouping poe-module {
    description
      "POE module grouping";
    leaf module {
      type uint32;
      description
        "Module number";
    }
    leaf available-power {
      type decimal64 {
        fraction-digits 2;
      }
      description
        "Available power of module";
    }
    leaf used-power {
      type decimal64 {
        fraction-digits 2;
      }
      description
        "Used power of module";
    }
    leaf remaining-power {
      type decimal64 {
        fraction-digits 2;
      }
      description
        "Remaining power of module";
    }
    leaf chassis-num {
      type uint32;
      description
        "chassis number of switch";
    }
    leaf power-pool-idx {
      type uint32;
      description
        "The power pool index";
    }
  }

  grouping ilp-port-config-details {
    description
      "Ilp port config details";
    leaf initialization {
      type boolean;
      description
        "Status of Port initialization";
    }
    leaf ilp-supported {
      type boolean;
      description
        "Status of Inline power supported";
    }
    leaf ilp-enabled {
      type boolean;
      description
        "Status of Inline power enabled";
    }
    leaf post {
      type boolean;
      description
        "Status of PoE linecard initialization";
    }
    leaf power-on {
      type boolean;
      description
        "status of Power";
    }
    leaf power-denied {
      type boolean;
      description
        "Status of Power denied";
    }
    leaf state {
      type poe-ios-xe-oper:power-state;
      description
        "Power state";
    }
    leaf short-circuit-detected {
      type uint32;
      description
        "Short circuit detected";
    }
    leaf spare-pair-mode {
      type poe-ios-xe-oper:poe-upoe-cmd-mode;
      description
        "Spare pair mode";
    }
    leaf spare-pair-power-is-on {
      type boolean;
      description
        "Status of Spare pair power";
    }
    leaf pd-power-state {
      type poe-ios-xe-oper:ilpower-pd-power-state;
      description
        "Status of Powered device power state";
    }
  }

  grouping ilpower-detail {
    description
      "POE ethernet details";
    leaf oper-status {
      type poe-ios-xe-oper:ilpower-device-state;
      description
        "Power Device Operational status";
    }
    leaf device-detected {
      type boolean;
      description
        "PoE Device detected or not";
    }
    leaf device-name {
      type string;
      description
        "Power Device name";
    }
    leaf discovery {
      type poe-ios-xe-oper:ilpower-pd-discovery-protocol;
      description
        "Discovery mechanism used";
    }
    leaf police-state-on {
      type boolean;
      description
        "Police state on or not";
    }
    leaf power-admin-max {
      type decimal64 {
        fraction-digits 2;
      }
      units "Watts";
      description
        "Admin max power, unit is Watts";
    }
    leaf power-from-pse {
      type decimal64 {
        fraction-digits 2;
      }
      units "Watts";
      description
        "Power from pse, unit is Watts";
    }
    leaf power-to-pd {
      type decimal64 {
        fraction-digits 2;
      }
      units "Watts";
      description
        "Power to pd, unit is Watts";
    }
    leaf power-consumption {
      type decimal64 {
        fraction-digits 2;
      }
      units "Watts";
      description
        "Actual Power consumed by power device, unit is Watts";
    }
    leaf max-power-drawn {
      type decimal64 {
        fraction-digits 2;
      }
      units "Watts";
      description
        "Max power drawn by power device, unit is Watts";
    }
    leaf power-negotiation-used {
      type string;
      units "Watts";
      description
        "power negotiation used with protocol CDP/LLDP, unit is Watts";
    }
    leaf lldp-tx-power-type {
      type poe-ios-xe-oper:poe-lldp-power-type;
      description
        "LLDP power negotiation power type send to power device";
    }
    leaf lldp-tx-power-source {
      type poe-ios-xe-oper:poe-lldp-power-source;
      description
        "LLDP power negotiation power source send to power device";
    }
    leaf lldp-tx-power-priority {
      type poe-ios-xe-oper:poe-lldp-power-priority;
      description
        "LLDP power negotiation power priority send to power device";
    }
    leaf lldp-tx-power-requested {
      type decimal64 {
        fraction-digits 2;
      }
      units "Watts";
      description
        "LLDP power negotiation power request send to power device, unit is Watts";
    }
    leaf lldp-tx-power-allocated {
      type decimal64 {
        fraction-digits 2;
      }
      units "Watts";
      description
        "LLDP power negotiation power allocation send to power device, unit is Watts";
    }
    leaf lldp-rx-power-type {
      type poe-ios-xe-oper:poe-lldp-power-type;
      description
        "LLDP power negotiation power type received from power device";
    }
    leaf lldp-rx-power-source {
      type poe-ios-xe-oper:poe-lldp-power-source;
      description
        "LLDP power negotiation power source received from power device";
    }
    leaf lldp-rx-power-priority {
      type poe-ios-xe-oper:poe-lldp-power-priority;
      description
        "LLDP power negotiation power priority received from power device";
    }
    leaf lldp-rx-power-requested {
      type decimal64 {
        fraction-digits 2;
      }
      units "Watts";
      description
        "LLDP power negotiation power request received from power device, unit is Watts";
    }
    leaf lldp-rx-power-allocated {
      type decimal64 {
        fraction-digits 2;
      }
      units "Watts";
      description
        "LLDP power negotiation power allocation received from power device, unit is Watts";
    }
    leaf four-pair-poe-supported {
      type string;
      description
        "Four pair PoE supported or not";
    }
    leaf four-pair-poe-enabled {
      type string;
      description
        "Four pair PoE enabled or not";
    }
    leaf four-pair-pd-arch {
      type string;
      description
        "Type of four pair power device architecture";
    }
    leaf over-current-counter {
      type uint32;
      description
        "Power device over current counter";
    }
    leaf short-current-counter {
      type uint32;
      description
        "Power device short current counter";
    }
  }

  grouping poe-ethernet {
    description
      "POE ethernet grouping";
    leaf intf-name {
      type string;
      description
        "Name of the POE interface";
    }
    leaf poe-intf-enabled {
      type boolean;
      description
        "POE interface administration state";
    }
    leaf power-used {
      type decimal64 {
        fraction-digits 2;
      }
      description
        "Power used by power device";
    }
    leaf pd-class {
      type poe-ios-xe-oper:ilpower-pd-class;
      description
        "Class of the power device";
    }
    leaf oper-state {
      type poe-ios-xe-oper:ilpower-pd-power-state;
      description
        "Operational state of power device";
    }
    leaf admin-state {
      type poe-ios-xe-oper:ilpower-admin-state;
      description
        "Admin state of power device";
    }
    leaf oper-power {
      type decimal64 {
        fraction-digits 2;
      }
      description
        "Operational power of power device";
    }
    leaf admin-police {
      type string;
      description
        "Police administration state of power device";
    }
    leaf oper-police {
      type string;
      description
        "Police operational state of power device";
    }
    leaf cutoff-power-police {
      type decimal64 {
        fraction-digits 2;
      }
      units "Watts";
      description
        "Police cutoff power, unit is Watts";
    }
    leaf module {
      type uint32;
      description
        "Module of this power device";
    }
    container ilp-detail {
      description
        "Inline power detail of power device";
      uses poe-ios-xe-oper:ilpower-detail;
    }
    container port-poe-detail {
      description
        "PoE detail of this power device";
      uses poe-ios-xe-oper:ilp-port-config-details;
    }
  }

  grouping ilpower-pair-detail {
    description
      "PoE signal/spare details";
    leaf pd-class {
      type poe-ios-xe-oper:poe-pd-class;
      description
        "Class of the power device";
    }
    leaf assigned-pd-class {
      type poe-ios-xe-oper:poe-pd-class;
      description
        "Assigned class of the power device";
    }
    leaf oper-power {
      type decimal64 {
        fraction-digits 2;
      }
      units "Watts";
      description
        "Operational power of power device";
    }
    leaf power-from-pse {
      type decimal64 {
        fraction-digits 2;
      }
      units "Watts";
      description
        "Power from pse";
    }
    leaf power-to-pd {
      type decimal64 {
        fraction-digits 2;
      }
      units "Watts";
      description
        "Power to pd";
    }
  }

  grouping lldp-med-pwr-via-mdi-tlv {
    description
      "LLDP MED  power fields from mdi tlv";
    leaf power-type {
      type poe-ios-xe-oper:ilpower-lldp-med-power-type;
      description
        "LLDP MED power negotiation power type";
    }
    leaf power-source {
      type poe-ios-xe-oper:ilpower-lldp-med-power-source;
      description
        "LLDP MED power negotiation power source";
    }
    leaf power-priority {
      type poe-ios-xe-oper:ilpower-lldp-med-power-priority;
      description
        "LLDP MED power negotiation power priority";
    }
  }

  grouping lldp-pwr-via-mdi-tlv {
    description
      "LLDP power fields from mdi tlv";
    leaf power-type {
      type poe-ios-xe-oper:poe-lldp-power-type;
      description
        "LLDP power negotiation power type";
    }
    leaf power-source {
      type poe-ios-xe-oper:ilpower-lldp-power-source;
      description
        "LLDP power negotiation power source";
    }
    leaf power-priority {
      type poe-ios-xe-oper:poe-lldp-power-priority;
      description
        "LLDP power negotiation power priority";
    }
    leaf power-requested {
      type decimal64 {
        fraction-digits 2;
      }
      units "Watts";
      description
        "LLDP power negotiation power request";
    }
    leaf power-allocated {
      type decimal64 {
        fraction-digits 2;
      }
      units "Watts";
      description
        "LLDP power negotiation power allocation";
    }
    leaf pd-4pid {
      type uint8;
      description
        "local PD system supports powering of both pairs";
    }
    leaf length {
      type uint16;
      description
        "length of LLDP TLV";
    }
    leaf pd-req-pwr-mode-a {
      type decimal64 {
        fraction-digits 2;
      }
      units "Watts";
      description
        "PD requested power for mode A";
    }
    leaf pd-req-pwr-mode-b {
      type decimal64 {
        fraction-digits 2;
      }
      description
        "PD requested power for mode B";
    }
    leaf pse-alloc-pwr-mode-a {
      type decimal64 {
        fraction-digits 2;
      }
      description
        "PSE allocated power value for mode A";
    }
    leaf pse-alloc-pwr-mode-b {
      type decimal64 {
        fraction-digits 2;
      }
      description
        "PSE allocated power value for mode B";
    }
    leaf pse-pwring-status {
      type poe-ios-xe-oper:pse-lldp-pwr-status;
      description
        "Powering status of PSE";
    }
    leaf pd-pwred-status {
      type poe-ios-xe-oper:pd-lldp-pwr-status;
      description
        "Powering status of PD";
    }
    leaf pse-pwr-pair-ext {
      type poe-ios-xe-oper:lldp-pse-pwr-ext-type;
      description
        "supported PSE pin out Alternative";
    }
    leaf dual-sig-pwr-class-mode-a {
      type poe-ios-xe-oper:dual-sig-pwr-class;
      description
        "Power class on Dual signature PD for Alt A ";
    }
    leaf dual-sig-pwr-class-mode-b {
      type poe-ios-xe-oper:dual-sig-pwr-class;
      description
        "Power class on Dual signature PD for Alt B ";
    }
    leaf pwr-ss-class-ext {
      type poe-ios-xe-oper:ss-pwr-class;
      description
        "Power class on Single  signature PD ";
    }
    leaf pwr-type-ext {
      type poe-ios-xe-oper:lldp-power-ext;
      description
        "PSE power type";
    }
    leaf pse-max-available-power {
      type decimal64 {
        fraction-digits 2;
      }
      description
        "PSE max power available";
    }
    leaf pse-auto-class-support {
      type boolean;
      description
        "PSE auto class support";
    }
    leaf auto-class-comp {
      type boolean;
      description
        "Whether the PSE has completed Auto class measurement";
    }
    leaf auto-class-req {
      type boolean;
      description
        "Whether Power device is requesting an auto class measurement and power budget adjustment";
    }
    leaf pwr-down-req {
      type boolean;
      description
        "A SET attribute that indicates the Power device is requesting a power down ";
    }
    leaf power-down-time {
      type uint64;
      description
        "Amount of seconds the power device requests to stay powered off";
    }
  }

  grouping poe-data-ethernet {
    description
      "POE signal/spare pair detail";
    leaf intf-name {
      type string;
      description
        "Name of the POE interface";
    }
    leaf power-used {
      type decimal64 {
        fraction-digits 2;
      }
      description
        "Power used by power device";
    }
    leaf pd-class {
      type poe-ios-xe-oper:poe-pd-class;
      description
        "Class of the power device";
    }
    leaf device-detected {
      type boolean;
      description
        "PoE Device detected or not";
    }
    leaf device-name {
      type string;
      description
        "Power Device name";
    }
    leaf police {
      type boolean;
      description
        "Police state on or not";
    }
    leaf power-admin-max {
      type decimal64 {
        fraction-digits 2;
      }
      units "Watts";
      description
        "Admin max power";
    }
    leaf power-from-pse {
      type decimal64 {
        fraction-digits 2;
      }
      units "Watts";
      description
        "Power from pse";
    }
    leaf power-to-pd {
      type decimal64 {
        fraction-digits 2;
      }
      units "Watts";
      description
        "Power to pd";
    }
    leaf power-consumption {
      type decimal64 {
        fraction-digits 2;
      }
      units "Watts";
      description
        "Actual Power consumed by power device";
    }
    leaf max-power-drawn {
      type decimal64 {
        fraction-digits 2;
      }
      units "Watts";
      description
        "Max power drawn by power device";
    }
    leaf oper-state {
      type poe-ios-xe-oper:poe-pd-power-state;
      description
        "Operational state of power device";
    }
    leaf admin-state {
      type poe-ios-xe-oper:ilpower-admin-state;
      description
        "Admin state of power device";
    }
    leaf oper-power {
      type decimal64 {
        fraction-digits 2;
      }
      description
        "Operational power of power device";
    }
    leaf admin-police {
      type poe-ios-xe-oper:poe-police-action;
      description
        "Police administration state of power device";
    }
    leaf oper-police {
      type poe-ios-xe-oper:poe-police-oper;
      description
        "Police operational state of power device";
    }
    leaf cutoff-power-police {
      type decimal64 {
        fraction-digits 2;
      }
      units "Watts";
      description
        "Police cutoff power";
    }
    leaf power-negotiation-used {
      type poe-ios-xe-oper:power-neg-used;
      units "Watts";
      description
        "power negotiation used with protocol CDP/LLDP";
    }
    leaf four-pair-poe-supported {
      type boolean;
      description
        "Four pair PoE supported or not";
    }
    leaf four-pair-poe-enabled {
      type boolean;
      description
        "Four pair PoE enabled or not";
    }
    leaf four-pair-pd-arch {
      type poe-ios-xe-oper:four-pair-pd-architecture;
      description
        "Type of four pair power device architecture";
    }
    leaf over-current-counter {
      type uint32;
      description
        "Power device over current counter";
    }
    leaf short-current-counter {
      type uint32;
      description
        "Power device short current counter";
    }
    leaf power-denied-counter {
      type uint32;
      description
        "Power device power denied counter";
    }
    leaf conn-type {
      type poe-ios-xe-oper:poe-conn-check;
      description
        "Connection type of power device";
    }
    container signal-pair-data {
      description
        "Signal pair inline power detail of power device";
      uses poe-ios-xe-oper:ilpower-pair-detail;
    }
    container spare-pair-data {
      description
        "Spare pair inline power detail of power device";
      uses poe-ios-xe-oper:ilpower-pair-detail;
    }
    leaf discovery {
      type poe-ios-xe-oper:ilpower-pd-discovery-protocol;
      description
        "Discovery mechanism used";
    }
    container lldp-mdi-rx {
      description
        "PoE LLDP rx fields";
      uses poe-ios-xe-oper:lldp-pwr-via-mdi-tlv;
    }
    container lldp-mdi-tx {
      description
        "PoE LLDP tx fields";
      uses poe-ios-xe-oper:lldp-pwr-via-mdi-tlv;
    }
    container lldp-med-mdi-rx {
      description
        "PoE LLDP MED rx fields";
      uses poe-ios-xe-oper:lldp-med-pwr-via-mdi-tlv;
    }
    container lldp-med-mdi-tx {
      description
        "PoE LLDP MED tx fields";
      uses poe-ios-xe-oper:lldp-med-pwr-via-mdi-tlv;
    }
    leaf fast-poe-enabled {
      type boolean;
      description
        "fast PoE enabled";
    }
    leaf perpetual-poe-enabled {
      type boolean;
      description
        "perpetual PoE enabled";
    }
    leaf oper-priority {
      type poe-ios-xe-oper:port-oper-priority;
      description
        "Operational priority";
    }
    leaf post-done {
      type boolean;
      description
        "Status of PoE linecard initialization";
    }
    leaf upoe-plus-enabled {
      type boolean;
      description
        "UPOE PLUS enabled";
    }
    leaf poe-intf-enabled {
      type boolean;
      description
        "POE interface administrative state";
    }
    leaf module-id {
      type uint32;
      description
        "Module ID in stack";
    }
    leaf chassis-num {
      type uint32;
      description
        "Chassis Number";
    }
  }

  grouping poe-stack {
    description
      "POE stack grouping";
    leaf power-stack-name {
      type string;
      description
        "Stack number";
    }
    leaf mode {
      type poe-ios-xe-oper:power-stack-mode;
      description
        "Stack mode";
    }
    leaf topolgy {
      type poe-ios-xe-oper:poe-stack-topo;
      description
        "Stack topology";
    }
    leaf total-power {
      type int32;
      units "Watts";
      description
        "Stack total power, unit is Watts";
    }
    leaf rsvd-power {
      type int32;
      units "Watts";
      description
        "Stack reserved power, unit is Watts";
    }
    leaf alloc-power {
      type int32;
      units "Watts";
      description
        "Stack allocated power, unit is Watts";
    }
    leaf unused-power {
      type int32;
      units "Watts";
      description
        "Stack unused power, unit is Watts";
    }
    leaf num-sw {
      type uint8;
      description
        "Number of the Switch";
    }
    leaf num-ps {
      type uint8;
      description
        "Number of power supply";
    }
  }

  grouping poe-switch {
    description
      "POE switch grouping";
    leaf switch-num {
      type uint8;
      description
        "Switch number";
    }
    leaf power-budget {
      type uint16;
      units "Watts";
      description
        "Switch power budget, unit is Watts";
    }
    leaf power-allocated {
      type uint32;
      units "Watts";
      description
        "Switch allocated power, unit is Watts";
    }
    leaf low-port-priority {
      type uint8;
      description
        "Switch low port priority";
    }
    leaf high-port-priority {
      type uint8;
      description
        "Switch high port priority";
    }
    leaf switch-priority {
      type uint8;
      description
        "Switch priority";
    }
    leaf port-one-status {
      type poe-ios-xe-oper:poe-port-status;
      description
        "Port 1 status";
    }
    leaf port-two-status {
      type poe-ios-xe-oper:poe-port-status;
      description
        "Port 2 status";
    }
    leaf neighbor-on-port-one {
      type yang:mac-address;
      description
        "Neighbor in port 1";
    }
    leaf neighbor-on-port-two {
      type yang:mac-address;
      description
        "Neighbor in port 2";
    }
    leaf consumed-switch-power {
      type uint32;
      units "Watts";
      description
        "Consumed switch power, unit is Watts";
    }
    leaf consumed-high-power {
      type uint32;
      units "Watts";
      description
        "Consumed high power, unit is Watts";
    }
    leaf consumed-low-power {
      type uint32;
      units "Watts";
      description
        "Consumed low power, unit is Watts";
    }
    leaf allocated-high-power {
      type uint32;
      units "Watts";
      description
        "Allocated high power, unit is Watts";
    }
    leaf allocated-low-power {
      type uint32;
      units "Watts";
      description
        "Allocated low power, unit is Watts";
    }
    leaf ps-a {
      type uint16;
      units "Watts";
      description
        "PS-A power, unit is Watts";
    }
    leaf ps-b {
      type uint16;
      units "Watts";
      description
        "PS-B power, unit is Watts";
    }
    leaf available-power {
      type int32;
      units "Watts";
      description
        "Available power, unit is Watts";
    }
    leaf consumed-system-power {
      type int32;
      units "Watts";
      description
        "System consumed power, unit is Watts";
    }
    leaf consumed-poe-power {
      type int32;
      units "Watts";
      description
        "PoE consumed power, unit is Watts";
    }
    leaf power-stack-name {
      type string;
      description
        "The name of the power stack that this switch belongs to";
    }
  }

  container poe-oper-data {
    config false;
    description
      "Information about PoEs";
    list poe-port {
      key "intf-name";
      description
        "List of PoE interfaces, keyed by interface name";
      uses poe-ios-xe-oper:poe-ethernet;
    }
    list poe-port-detail {
      key "intf-name";
      description
        "List of PoE interfaces, keyed by interface name";
      uses poe-ios-xe-oper:poe-data-ethernet;
    }
    list poe-module {
      key "module";
      description
        "List of PoE modules, keyed by module number";
      uses poe-ios-xe-oper:poe-module;
    }
    list poe-stack {
      key "power-stack-name";
      description
        "List of PoE stacks, keyed by stack name";
      uses poe-ios-xe-oper:poe-stack;
    }
    list poe-switch {
      key "switch-num";
      description
        "List of PoE switches, keyed by switch number";
      uses poe-ios-xe-oper:poe-switch;
    }
  }
}
