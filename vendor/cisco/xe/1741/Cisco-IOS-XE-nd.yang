module Cisco-IOS-XE-nd {
  namespace "http://cisco.com/ns/yang/Cisco-IOS-XE-nd";
  prefix ios-nd;

  import cisco-semver {
    prefix cisco-semver;
  }
  import Cisco-IOS-XE-native {
    prefix ios;
  }
  import Cisco-IOS-XE-types {
    prefix ios-types;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Neighbor Discovery (ND) Yang model.
     Copyright (c) 2016-2019 by Cisco Systems, Inc.
     All rights reserved.";

  revision 2020-11-01 {
    description
      "- Initial revision for 17.4.1";
  }
  revision 2020-07-01 {
    description
      "- Added support for ND config in Dialer interface 
       - Added 'tailf:cli-delete-container-on-delete' to the leaf
         'all' in 'ipv6 nd ra suppress all'";
  }
  revision 2020-03-01 {
    description
      "- Added support for raguard config.";
  }
  revision 2019-11-01 {
    description
      "- Added leaf for packet-priority to ipv6 ND grouping for interface ND
         configuration.
       - Deprecated ipv6 nd inspection policy.";
    cisco-semver:module-version "1.1.0";
  }
  revision 2019-07-01 {
    description
      "- Establish semantic version baseline
       - Added support for 'nd ns-interval' and 'ns reachable-time' options";
    cisco-semver:module-version "1.0.0";
  }
  revision 2019-01-25 {
    description
      "Added leaf for App-hosting Gigabit Ethernet interface";
  }
  revision 2018-07-26 {
    description
      "Added support for some interface ipv4 nd options";
  }
  revision 2017-11-27 {
    description
      "Added Change 25GE name";
  }
  revision 2017-11-14 {
    description
      "Add support for 40 and 100GE interfaces";
  }
  revision 2017-10-12 {
    description
      "Add support for command 'ipv6 nd suppress policy *'";
  }
  revision 2017-09-18 {
    description
      "This revision has changes for new 2gig interface addition";
  }
  revision 2017-08-16 {
    description
      "This revision has changes for new 5gig and 25gig interfaces addition";
  }
  revision 2017-04-07 {
    description
      "Add default-route";
  }
  revision 2017-02-07 {
    description
      "Initial revision";
  }

  grouping config-ipv6-nd-grouping {
    container inspection {
      status deprecated;
      description
        "Deprecated - NDP Inspection";
      list policy {
        status deprecated;
        description
          "Deprecated - Using device-tracking";
        key "name-nd-inspection-policy";
        leaf name-nd-inspection-policy {
          status deprecated;
          type string;
        }
        container device-role {
          status deprecated;
          description
            "Deprecated - Sets the role of the device attached to the port";
          leaf host {
            status deprecated;
            description
              "Deprecated - Attached device is a host (default)";
            type empty;
          }
          leaf monitor {
            status deprecated;
            description
              "Deprecated - Attached device is a monitor/sniffer";
            type empty;
          }
          leaf router {
            status deprecated;
            description
              "Deprecated - Attached device is a route";
            type empty;
          }
          leaf switch {
            status deprecated;
            description
              "Deprecated - Attached device is a switch";
            type empty;
          }
        }
        leaf drop-unsecure {
          status deprecated;
          description
            "Deprecated - drop unsecure (3971) messages";
          type empty;
        }
        container limit {
          status deprecated;
          description
            "Deprecated - Specifies a limit";
          leaf address-count {
            status deprecated;
            description
              "Deprecated - Configure maximum address per port";
            type uint16 {
              range "1..10000";
            }
          }
        }
        container sec-level {
          status deprecated;
          description
            "Deprecated - Specifies a minimum sec-level";
          leaf minimum {
            status deprecated;
            description
              "Deprecated - Configure minimum sec-level";
            type uint8 {
              range "1..7";
            }
          }
        }
        container tracking {
          status deprecated;
          description
            "Deprecated - Override default tracking behavior";
          container disable {
            status deprecated;
            description
              "Deprecated - Tracking off";
            presence "true";
            container stale-lifetime {
              status deprecated;
              description
                "Deprecated - Time entry is kept inactive before delete";
              leaf seconds {
                status deprecated;
                description
                  "Deprecated - Seconds";
                type uint32 {
                  range "1..86400";
                }
              }
              leaf infinite {
                status deprecated;
                description
                  "Deprecated - Keep in STALE forever";
                type empty;
              }
            }
          }
          container enable {
            status deprecated;
            description
              "Deprecated - Tracking on";
            presence "true";
            container reachable-lifetime {
              status deprecated;
              description
                "Deprecated - Time entry is kept REACHABLE";
              leaf seconds {
                status deprecated;
                description
                  "Deprecated - Seconds";
                type uint32 {
                  range "1..86400";
                }
              }
              leaf infinite {
                status deprecated;
                description
                  "Deprecated - Keep in REACHABLE forever";
                type empty;
              }
            }
          }
        }
        leaf trusted-port {
          status deprecated;
          description
            "Deprecated - setup trusted port";
          type empty;
        }
        container validate {
          status deprecated;
          description
            "Deprecated - specific validation";
          leaf source-mac {
            status deprecated;
            description
              "Deprecated - check source mac against link-layer-address";
            type empty;
          }
        }
      }
    }
    container cache {
      description
        "Cache entry";
      container expire {
        description
          "Expiry time for ND entries";
        leaf time {
          type uint16;
        }
        leaf refresh {
          description
            "Automatically refresh entry";
          type empty;
        }
      }
    }
    container raguard {
      description
        "Configure RA guard";
      list policy {
        description
          "Configure a policy for feature RA guard";
        key "raguard-policy-name";
        leaf raguard-policy-name {
          type string;
        }
        container device-role {
          description
            "Sets the role of the device attached to the port";
          leaf host {
            description
              "Attached device is a host (default)";
            type empty;
          }
          leaf monitor {
            description
              "Attached device is a monitor/sniffer";
            type empty;
          }
          leaf router {
            description
              "Attached device is a router";
            type empty;
          }
          leaf switch {
            description
              "Attached device is a switch";
            type empty;
          }
        }
        container hop-limit {
          description
            "Enable verification of the advertised Hop count limit";
          leaf maximum {
            description
              "Maximum hop count value allowed";
            type uint8 {
              range "1..255";
            }
          }
          leaf minimum {
            description
              "Minimum hop count value allowed";
            type uint8 {
              range "1..255";
            }
          }
        }
        leaf trusted-port {
          description
            "setup trusted port";
          type empty;
        }
      }
      leaf attach-policy {
        description
          "Configure a policy for feature RA guard";
        type string;
      }
    }
    container default-route {
      list vrf {
        ordered-by user;
        key "word";
        leaf word {
          type string;
        }
        leaf limit {
          type uint8 {
            range "0..5";
          }
        }
      }
      leaf limit {
        type uint8 {
          range "0..5";
        }
      }
    }
    container suppress {
      description
        "Configure ND multicast suppress";
      list policy {
        description
          "Configure a policy for feature nd suppress";
        key "nd-suppress-policy-name";
        leaf nd-suppress-policy-name {
          type string;
        }
      }
    }
  }

  grouping config-interface-ipv6-nd-grouping {
    container raguard {
      description
        "Configure RA guard on the interface";
      leaf attach-policy {
        description
          "Apply a policy for feature RA guard";
        type string;
        must "(/ios:native/ios:ipv6/ios:nd/ios-nd:raguard/ios-nd:policy[ios-nd:raguard-policy-name=current()])" {
          error-message "Create raguard policy first, then attach policy; Detach policy from interface before removing the policy";
        }
      }
    }
    container autoconfig {
      description
        "Obtain address using autoconfiguration";
      leaf default-route {
        description
          "Insert default route";
        type empty;
      }
      leaf prefix {
        description
          "Insert auto-configured prefix";
        type empty;
      }
    }
    leaf managed-config-flag {
      description
        "Use DHCP for IPv6 address configuration";
      type empty;
    }
    leaf other-config-flag {
      description
        "Hosts should use DHCP for non-address config";
      type empty;
    }
    leaf router-preference {
      description
        "Set default router preference value";
      type enumeration {
        enum "High";
        enum "Medium";
        enum "Low";
      }
      default "Medium";
    }
    container prefix {
      description
        "Configure IPv6 Routing Prefix Advertisement";
      list ipv6-prefix-list {
        description
          "IPv6 prefix x:x::y/<z>";
        key "ipv6-prefix";
        leaf ipv6-prefix {
          type ios-types:ipv6-prefix;
        }
        leaf no-advertise {
          description
            "Do not advertise prefix";
          type empty;
        }
      }
    }
    container ra {
      description
        "IPv6 nd router alert configuration";
      container suppress {
        description
          "Suppress IPv6 router-alert configuration";
        presence "true";
        leaf all {
          description
            "Suppress all IPv6 RA";
          type empty;
        }
      }
    }
    leaf ns-interval {
      description
        "Set advertised NS retransmission interval";
      type uint32 {
        range "1000..172800000";
      }
    }
    leaf reachable-time {
      description
        "Set advertised reachability time";
      type uint32 {
        range "0..3600000";
      }
    }
    leaf packet-priority {
      description
        "Use high priority for IPv6 ND packets";
      type empty;
    }
  }

  augment "/ios:native/ios:ipv6/ios:nd" {
    uses config-ipv6-nd-grouping;
  }
  augment "/ios:native/ios:interface/ios:FastEthernet/ios:ipv6/ios:nd" {
    uses config-interface-ipv6-nd-grouping;
  }
  augment "/ios:native/ios:interface/ios:GigabitEthernet/ios:ipv6/ios:nd" {
    uses config-interface-ipv6-nd-grouping;
  }
  augment "/ios:native/ios:interface/ios:TenGigabitEthernet/ios:ipv6/ios:nd" {
    uses config-interface-ipv6-nd-grouping;
  }
  augment "/ios:native/ios:interface/ios:FiveGigabitEthernet/ios:ipv6/ios:nd" {
    uses config-interface-ipv6-nd-grouping;
  }
  augment "/ios:native/ios:interface/ios:AppGigabitEthernet/ios:ipv6/ios:nd" {
    uses config-interface-ipv6-nd-grouping;
  }
  augment "/ios:native/ios:interface/ios:TwentyFiveGigE/ios:ipv6/ios:nd" {
    uses config-interface-ipv6-nd-grouping;
  }
  augment "/ios:native/ios:interface/ios:TwoGigabitEthernet/ios:ipv6/ios:nd" {
    uses config-interface-ipv6-nd-grouping;
  }
  augment "/ios:native/ios:interface/ios:FortyGigabitEthernet/ios:ipv6/ios:nd" {
    uses config-interface-ipv6-nd-grouping;
  }
  augment "/ios:native/ios:interface/ios:HundredGigE/ios:ipv6/ios:nd" {
    uses config-interface-ipv6-nd-grouping;
  }
  augment "/ios:native/ios:interface/ios:Port-channel/ios:ipv6/ios:nd" {
    uses config-interface-ipv6-nd-grouping;
  }
  augment "/ios:native/ios:interface/ios:Virtual-Template/ios:ipv6/ios:nd" {
    uses config-interface-ipv6-nd-grouping;
  }
  augment "/ios:native/ios:interface/ios:Loopback/ios:ipv6/ios:nd" {
    uses config-interface-ipv6-nd-grouping;
  }
  augment "/ios:native/ios:interface/ios:Tunnel/ios:ipv6/ios:nd" {
    uses config-interface-ipv6-nd-grouping;
  }
  augment "/ios:native/ios:interface/ios:vasileft/ios:ipv6/ios:nd" {
    uses config-interface-ipv6-nd-grouping;
  }
  augment "/ios:native/ios:interface/ios:vasiright/ios:ipv6/ios:nd" {
    uses config-interface-ipv6-nd-grouping;
  }
  augment "/ios:native/ios:interface/ios:Vlan/ios:ipv6/ios:nd" {
    uses config-interface-ipv6-nd-grouping;
  }
  augment "/ios:native/ios:interface/ios:Dialer/ios:ipv6/ios:nd" {
    uses config-interface-ipv6-nd-grouping;
  }
  augment "/ios:native/ios:interface/ios:AppNav-Compress/ios:ipv6/ios:nd" {
    uses config-interface-ipv6-nd-grouping;
  }
  augment "/ios:native/ios:interface/ios:AppNav-UnCompress/ios:ipv6/ios:nd" {
    uses config-interface-ipv6-nd-grouping;
  }
  augment "/ios:native/ios:interface/ios:ATM/ios:ipv6/ios:nd" {
    uses config-interface-ipv6-nd-grouping;
  }
  augment "/ios:native/ios:interface/ios:ATM-subinterface/ios:ATM/ios:ipv6/ios:nd" {
    uses config-interface-ipv6-nd-grouping;
  }
  augment "/ios:native/ios:interface/ios:BDI/ios:ipv6/ios:nd" {
    uses config-interface-ipv6-nd-grouping;
  }
  augment "/ios:native/ios:interface/ios:Embedded-Service-Engine/ios:ipv6/ios:nd" {
    uses config-interface-ipv6-nd-grouping;
  }
  augment "/ios:native/ios:interface/ios:Ethernet/ios:ipv6/ios:nd" {
    uses config-interface-ipv6-nd-grouping;
  }
  augment "/ios:native/ios:interface/ios:ucse/ios:ipv6/ios:nd" {
    uses config-interface-ipv6-nd-grouping;
  }
  augment "/ios:native/ios:interface/ios:Ethernet-Internal/ios:ipv6/ios:nd" {
    uses config-interface-ipv6-nd-grouping;
  }
  augment "/ios:native/ios:interface/ios:Service-Engine/ios:ipv6/ios:nd" {
    uses config-interface-ipv6-nd-grouping;
  }
  augment "/ios:native/ios:interface/ios:TwentyFiveGigabitEthernet/ios:ipv6/ios:nd" {
    uses config-interface-ipv6-nd-grouping;
  }
  augment "/ios:native/ios:interface/ios:LISP/ios:ipv6/ios:nd" {
    uses config-interface-ipv6-nd-grouping;
  }
  augment "/ios:native/ios:interface/ios:LISP-subinterface/ios:LISP/ios:ipv6/ios:nd" {
    uses config-interface-ipv6-nd-grouping;
  }
  augment "/ios:native/ios:interface/ios:nve/ios:ipv6/ios:nd" {
    uses config-interface-ipv6-nd-grouping;
  }
  augment "/ios:native/ios:interface/ios:Port-channel-subinterface/ios:Port-channel/ios:ipv6/ios:nd" {
    uses config-interface-ipv6-nd-grouping;
  }
  augment "/ios:native/ios:interface/ios:SM/ios:ipv6/ios:nd" {
    uses config-interface-ipv6-nd-grouping;
  }
  augment "/ios:native/ios:interface/ios:Cellular/ios:ipv6/ios:nd" {
    uses config-interface-ipv6-nd-grouping;
  }
  augment "/ios:native/ios:interface/ios:GMPLS/ios:ipv6/ios:nd" {
    uses config-interface-ipv6-nd-grouping;
  }
  augment "/ios:native/ios:interface/ios:Group-Async/ios:ipv6/ios:nd" {
    uses config-interface-ipv6-nd-grouping;
  }
  augment "/ios:native/ios:interface/ios:Multilink/ios:ipv6/ios:nd" {
    uses config-interface-ipv6-nd-grouping;
  }
  augment "/ios:native/ios:interface/ios:Serial/ios:ipv6/ios:nd" {
    uses config-interface-ipv6-nd-grouping;
  }
  augment "/ios:native/ios:interface/ios:Async/ios:ipv6/ios:nd" {
    uses config-interface-ipv6-nd-grouping;
  }
  augment "/ios:native/ios:interface/ios:Virtual-PPP/ios:ipv6/ios:nd" {
    uses config-interface-ipv6-nd-grouping;
  }
  augment "/ios:native/ios:interface/ios:VirtualPortGroup/ios:ipv6/ios:nd" {
    uses config-interface-ipv6-nd-grouping;
  }
  augment "/ios:native/ios:interface/ios:Vif/ios:ipv6/ios:nd" {
    uses config-interface-ipv6-nd-grouping;
  }
  augment "/ios:native/ios:interface/ios:Wlan-GigabitEthernet/ios:ipv6/ios:nd" {
    uses config-interface-ipv6-nd-grouping;
  }
  augment "/ios:native/ios:interface/ios:BD-VIF/ios:ipv6/ios:nd" {
    uses config-interface-ipv6-nd-grouping;
  }
  augment "/ios:native/ios:interface/ios:MFR/ios:ipv6/ios:nd" {
    uses config-interface-ipv6-nd-grouping;
  }
  augment "/ios:native/ios:interface/ios:Serial-subinterface/ios:Serial/ios:ipv6/ios:nd" {
    uses config-interface-ipv6-nd-grouping;
  }
  augment "/ios:native/ios:interface/ios:MFR-subinterface/ios:MFR/ios:ipv6/ios:nd" {
    uses config-interface-ipv6-nd-grouping;
  }
}
