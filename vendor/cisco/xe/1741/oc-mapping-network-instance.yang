module oc-mapping-network-instance {

  yang-version "1";

  // namespace
  namespace "http://openconfig.net/yang/oc-mapping-network-instance";

  prefix "oc-map-netinst";

  import ietf-inet-types { prefix inet; }
  import openconfig-policy-types { prefix oc-pt; }
  import openconfig-extensions { prefix "oc-ext"; }

  // meta
  organization "OpenConfig working group";

  contact
    "OpenConfig working group
    www.openconfig.net";

  description
    "This module defines mapping state data
    that must be saved to implement the openconfig-network-instance
    model because the capabilities are not implemented
    on XE devices";

  oc-ext:openconfig-version "0.2.0";

  revision "2017-01-17" {
    description
      "Initial revision";
    reference "TBD";
  }

  grouping mapping-static-route {
    description
      "Top-level grouping for the list of static route definitions";

    container static-routes {
      description
        "Enclosing container for the list of static routes";

      list static {
        key prefix;
        description
          "List of locally configured static routes";

        leaf prefix {
	  type inet:ip-prefix;
          description
            "Reference to the destination prefix list key.";
        }

	container config {
           leaf set-tag {
              type oc-pt:tag-type;
              description
              "Set a generic tag value on the route. This tag can be
               used for filtering routes that are distributed to other
               routing protocols.";
	   }
        }
      }
    }
  }

  grouping network-instance-top {
    description
      "Top-level grouping containing a list of network instances.";

    container netinst-mapping {
      description
        "The L2, L3, or L2+L3 forwarding instances that are
        configured on the local system";

      list network-instance {
        key "name";

        description
          "Network instances configured on the local system";

        leaf name {
	  type string;
          description
            "A unique name identifying the network instance";
        }

        container config {
          description
            "Configuration parameters relating to a network
            instance";
          leaf name {
             type string;
             description
             "An operator-assigned unique name for the forwarding
              instance";
          }
        }

	uses mapping-static-route;
      }
    }
  }

  uses network-instance-top;
}
