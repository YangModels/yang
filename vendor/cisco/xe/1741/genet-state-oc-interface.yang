/**
 * Genet internal state tables
 */
module genet-state-oc-interface {
  namespace "http://cisco.com/ns/genet/genet-state-oc-interface";
  prefix oc-interface-state;

  import openconfig-inet-types { prefix oc-inet; }

  organization
    "Cisco Systems, Inc.";

  contact
    "Cisco Systems, Inc.
     Customer Service

     Postal: 170 W Tasman Drive
     San Jose, CA 95134

     Tel: +1 1800 553-NETS

     E-mail: cs-yang@cisco.com";

  description
    "Temporary mapping state table used for model mapping in XE/Polaris.
     Copyright (c) 2018 by Cisco Systems, Inc.
     All rights reserved.";

  // =========================================================================
  // REVISION
  // =========================================================================

  revision 2018-04-11 {
    description
      "Add track-interface leaf-list for ipv4-decrement and ipv6-decrement container.";
  }
  revision 2018-02-10 {
    description
      "Seperate module for oc-interface mapping state";
  }

  //
  // Top level container for temporary storage of state data used to support mapping
  // State information in these containers are not persisted across dmi restart or device reload
  //
  container internal-genet-oc-interface {
    list ipv4-decrement {
      key "name index ip virtual-router-id";
      description
	"List of decrement-priority for vrrp ipv4 tracking interface";
      leaf name {
	type string;
	description
	  "The name of the interface.";
      }
      leaf index {
	type uint32;
	//default 0;
	description
	  "The index of the subinterface, or logical interface number.
        On systems with no support for subinterfaces, or not using
        subinterfaces, this value should default to 0, i.e., the
        default subinterface.";
      }

      leaf ip {
	type oc-inet:ipv4-address;
	description
	  "The IPv4 address on the interface.";
      }

      leaf virtual-router-id {
	type uint8 {
	  range 1..255;
	}
	description
	  "Set the virtual router id for use by the VRRP group.  This
        usually also determines the virtual MAC address that is
        generated for the VRRP group";
      }

      leaf priority-decrement {
	type uint8 {
	  range 0..254;
	}
	default 0;
	description 
	  "Set the value to subtract from priority when
           the tracked interface goes down.";
      }

      leaf-list track-interface {
        type string;
        description
          "Sets a list of one or more interfaces that should
           be tracked for up/down events.";
      }

    }

    list ipv6-decrement {
      key "name index ip virtual-router-id";
      description
	"List of decrement-priority for vrrp ipv6 tracking interface";
      leaf name {
	type string;
	description
	  "The name of the interface.";
      }
      leaf index {
	type uint32;
	//default 0;
	description
	  "The index of the subinterface, or logical interface number.
        On systems with no support for subinterfaces, or not using
        subinterfaces, this value should default to 0, i.e., the
        default subinterface.";
      }

      leaf ip {
	type oc-inet:ipv6-address;
	description
	  "The IPv6 address on the interface.";
      }

      leaf virtual-router-id {
	type uint8 {
	  range 1..255;
	}
	description
	  "Set the virtual router id for use by the VRRP group.  This
        usually also determines the virtual MAC address that is
        generated for the VRRP group";
      }

      leaf priority-decrement {
	type uint8 {
	  range 0..254;
	}
	default 0;
	description 
	  "Set the value to subtract from priority when
           the tracked interface goes down.";
      }

      leaf-list track-interface {
        type string;
        description
          "Sets a list of one or more interfaces that should
           be tracked for up/down events.";
      }

    }
  }
}
