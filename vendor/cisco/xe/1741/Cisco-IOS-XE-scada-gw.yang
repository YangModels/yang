module Cisco-IOS-XE-scada-gw {
  namespace "http://cisco.com/ns/yang/Cisco-IOS-XE-scada-gw";
  prefix ios-scada-gw;

  import cisco-semver {
    prefix cisco-semver;
  }
  import Cisco-IOS-XE-native {
    prefix ios;
  }
  import Cisco-IOS-XE-features {
    prefix ios-features;
  }
  import ietf-inet-types {
    prefix inet;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native SCADA Gateway Yang model.
     Copyright (c) 2018-2020 by Cisco Systems, Inc.
     All rights reserved.";

  revision 2020-11-01 {
    description
      "- Added support for ignore direction";
    cisco-semver:module-version "2.1.0";
  }
  revision 2020-03-01 {
    description
      "- Moved scada encapsulation to common interface";
    cisco-semver:module-version "2.0.0";
  }
  revision 2019-11-01 {
    description
      "- Added additional constraints for scada-gw enable
       - Added request config";
    cisco-semver:module-version "1.0.0";
  }
  revision 2019-03-19 {
    description
      "Initial revision";
  }

  grouping config-t101-sector-grouping {
    leaf attach-to-session {
      description
        "Name of the Session to attach";
      must "count( /ios:native/ios:scada-gw/ios-scada-gw:protocol/ios-scada-gw:t101/ios-scada-gw:config-t101/ios-scada-gw:sector[ ios-scada-gw:config-t101-sector/ios-scada-gw:attach-to-session = current() ] ) < 2" {
        error-message "Maximum number of sectors attached to this session";
      }
      type leafref {
        path "/ios:native/ios:scada-gw/ios-scada-gw:protocol/ios-scada-gw:t101/ios-scada-gw:config-t101/ios-scada-gw:session/ios-scada-gw:name";
      }
    }
    leaf asdu-addr {
      description
        "Asdu Address";
      must "boolean(../attach-to-session) and (((not(boolean(deref(../attach-to-session)/../config-t101-session/common-addr-size)) or deref(../attach-to-session)/../config-t101-session/common-addr-size = 'two')) or(deref(../attach-to-session)/../config-t101-session/common-addr-size = 'one' and current() < 256)) " {
        error-message "Sector not attached-to-session or asdu-addr out of range. Acceptable ranges based on common-addr-size : {'one': addr<256, 'two': addr<65536}";
      }
      type uint16 {
        range "0..65535";
      }
    }
    list request {
      description
        "customized request (expert mode)";
      key "id";
      leaf id {
        description
          "request id";
        type uint8 {
          range "1..16";
        }
      }
      leaf function {
        description
          "request function";
        type enumeration {
          enum "clock" {
            description
              "set clock to rtu";
          }
          enum "poll" {
            description
              "poll rtu";
          }
        }
      }
      leaf period {
        description
          "request period in seconds";
        type uint16 {
          range "0..3600";
        }
      }
      leaf timeout {
        description
          "request timeout in seconds";
        type uint8 {
          range "1..60";
        }
      }
      leaf retry {
        description
          "failure retry count";
        type uint8 {
          range "0..100";
        }
      }
    }
  }

  grouping config-t101-session-grouping {
    leaf attach-to-channel {
      description
        "Name of the Channel to attach";
      must "boolean(current())" {
        error-message "Must specify a channel";
      }
      must "count( /ios:native/ios:scada-gw/ios-scada-gw:protocol/ios-scada-gw:t101/ios-scada-gw:config-t101/ios-scada-gw:session[ ios-scada-gw:config-t101-session/ios-scada-gw:attach-to-channel = current() ] ) < 2" {
        error-message "Maximum number of sessions attached to this channel";
      }
      type leafref {
        path "/ios:native/ios:scada-gw/ios-scada-gw:protocol/ios-scada-gw:t101/ios-scada-gw:config-t101/ios-scada-gw:channel/ios-scada-gw:name";
      }
    }
    leaf common-addr-size {
      description
        "Configure scada-gw t101 session common-addr-size";
      type enumeration {
        enum "one" {
          description
            "One octet";
        }
        enum "two" {
          description
            "Two octets";
        }
      }
    }
    leaf cot-size {
      description
        "Configure scada-gw t101 session cot-size";
      type enumeration {
        enum "one" {
          description
            "One octet";
        }
        enum "two" {
          description
            "Two octets";
        }
      }
    }
    leaf info-obj-addr-size {
      description
        "Configure scada-gw t101 session information object address size";
      type enumeration {
        enum "one" {
          description
            "One octet";
        }
        enum "two" {
          description
            "Two octets";
        }
        enum "three" {
          description
            "Three octets";
        }
      }
    }
    leaf link-addr {
      description
        "Link Address";
      must "not(boolean(../attach-to-channel)) or ((( (not(boolean(deref(../attach-to-channel)/../config-t101-channel/link-addr-size)) or deref(../attach-to-channel)/../config-t101-channel/link-addr-size = 'one') and current() < 256) or (deref(../attach-to-channel)/../config-t101-channel/link-addr-size = 'none' and current() = 0) or (deref(../attach-to-channel)/../config-t101-channel/link-addr-size = 'two')))" {
        error-message "Link-addr out of range. Acceptable ranges based on link-addr-size : {'none': addr=0, 'one': addr<256, 'two': addr<65536}";
      }
      type uint16 {
        range "0..65535";
      }
    }
    list request {
      description
        "customized request (expert mode)";
      key "id";
      leaf id {
        description
          "request id";
        type uint8 {
          range "1..8";
        }
      }
      leaf function {
        description
          "request function";
        type enumeration {
          enum "test" {
            description
              "test request";
          }
          enum "event" {
            description
              "event poll from rtu";
          }
        }
      }
      leaf period {
        description
          "request period in seconds";
        type uint16 {
          range "0..3600";
        }
      }
      leaf timeout {
        description
          "request timeout in seconds";
        type uint8 {
          range "1..60";
        }
      }
      leaf retry {
        description
          "failure retry count";
        type uint8 {
          range "0..100";
        }
      }
    }
  }

  grouping config-t104-session-grouping {
    leaf attach-to-channel {
      description
        "Name of the Channel to attach";
      must "count( /ios:native/ios:scada-gw/ios-scada-gw:protocol/ios-scada-gw:t104/ios-scada-gw:config-t104/ios-scada-gw:session[ ios-scada-gw:config-t104-session/ios-scada-gw:attach-to-channel = current() ] ) < 2" {
        error-message "Maximum number of sessions attached to this channel";
      }
      type leafref {
        path "/ios:native/ios:scada-gw/ios-scada-gw:protocol/ios-scada-gw:t104/ios-scada-gw:config-t104/ios-scada-gw:channel/ios-scada-gw:name";
      }
    }
  }

  grouping config-t101-channel-grouping {
    leaf bind-to-interface {
      description
        "Interface name T101 binds to";
      type string;
    }
    container day-of-week {
      description
        "Include Day of week information in timestamp";
      leaf enable {
        description
          "Enable";
        type empty;
      }
    }
    leaf link-addr-size {
      description
        "Link Address Size";
      type enumeration {
        enum "none" {
          description
            "none";
        }
        enum "one" {
          description
            "One octet";
        }
        enum "two" {
          description
            "Two octets";
        }
      }
    }
    leaf link-mode {
      description
        "Link Mode";
      must "not(boolean(../link-addr-size)) or (../link-addr-size != 'none' or current() != 'Unbalanced')" {
        error-message "link-addr-size can't be NONE for UNBALANCED link-mode!";
      }
      type enumeration {
        enum "Balanced" {
          description
            "Balanced Mode";
        }
        enum "Unbalanced" {
          description
            "Unbalanced Mode";
        }
      }
    }
  }

  grouping config-dnp3n-session-grouping {
    leaf attach-to-channel {
      description
        "Name of the Channel to attach";
      must "count( \t/ios:native/ios:scada-gw/ios-scada-gw:protocol/ios-scada-gw:dnp3-ip/ios-scada-gw:config-dnp3n/ios-scada-gw:session[ ios-scada-gw:config-dnp3n-session/ios-scada-gw:attach-to-channel = current() ] ) < 2" {
        error-message "Maximum number of sessions are attached to this channel";
      }
      type leafref {
        path "/ios:native/ios:scada-gw/ios-scada-gw:protocol/ios-scada-gw:dnp3-ip/ios-scada-gw:config-dnp3n/ios-scada-gw:channel/ios-scada-gw:name";
      }
    }
    container link-addr {
      description
        "Configure scada-gw dnp3 network session link-addr";
      leaf source {
        description
          "Source address(Slave)";
        type uint16 {
          range "0..65535";
        }
      }
    }
    leaf map-to-session {
      description
        "Configure lower session mapping to";
      type leafref {
        path "/ios:native/ios:scada-gw/ios-scada-gw:protocol/ios-scada-gw:dnp3-serial/ios-scada-gw:config-dnp3s/ios-scada-gw:session/ios-scada-gw:name";
      }
    }
  }

  grouping config-dnp3s-session-grouping {
    leaf attach-to-channel {
      description
        "Name of the Channel to attach";
      must "count( /ios:native/ios:scada-gw/ios-scada-gw:protocol/ios-scada-gw:dnp3-serial/ios-scada-gw:config-dnp3s/ios-scada-gw:session[ ios-scada-gw:config-dnp3s-session/ios-scada-gw:attach-to-channel = current() ] ) < 2" {
        error-message "Maximum number of sessions are attached to this channel";
      }
      type leafref {
        path "/ios:native/ios:scada-gw/ios-scada-gw:protocol/ios-scada-gw:dnp3-serial/ios-scada-gw:config-dnp3s/ios-scada-gw:channel/ios-scada-gw:name";
      }
    }
    container link-addr {
      description
        "Configure scada-gw dnp3 serial session link-addr";
      leaf dest {
        description
          "Destination address(Slave)";
        type uint16 {
          range "0..65535";
        }
      }
    }
    list request {
      description
        "customized request (expert mode)";
      key "id";
      leaf id {
        description
          "request id";
        type uint8 {
          range "1..16";
        }
      }
      leaf function {
        description
          "request function";
        type enumeration {
          enum "clock" {
            description
              "set clock to rtu";
          }
          enum "poll" {
            description
              "class poll to rtu";
          }
          enum "event" {
            description
              "poll event from rtu";
          }
          enum "initialize" {
            description
              "initialize rtu";
          }
          enum "test" {
            description
              "test rtu";
          }
          enum "read" {
            description
              "read variable";
          }
        }
      }
      leaf object {
        description
          "object ID";
        when "../function = 'read'";
        type enumeration {
          enum "analog-input" {
            description
              "analog input, id 30";
          }
          enum "binary-input" {
            description
              "binary input, id 1";
          }
          enum "counter-input" {
            description
              "counter input, id 20";
          }
          enum "double-input" {
            description
              "double input, id 3";
          }
        }
      }
      leaf period {
        description
          "request period in seconds";
        type uint16 {
          range "0..3600";
        }
      }
      leaf timeout {
        description
          "request timeout in seconds";
        type uint8 {
          range "1..60";
        }
      }
      leaf retry {
        description
          "failure retry count";
        type uint8 {
          range "0..100";
        }
      }
    }
  }

  grouping config-dnp3n-channel-grouping {
    container link-addr {
      description
        "Configure scada-gw dnp3 network channel link-addr";
      leaf dest {
        description
          "Destination address(Master)";
        type uint16 {
          range "0..65535";
        }
      }
    }
    container send-unsolicited-msg {
      description
        "Send Unsolicited Message";
      leaf enable {
        description
          "Enable";
        type empty;
      }
    }
    container tcp-connection {
      description
        "TCP connection";
      container local-port {
        description
          "2000-65535, default 20000";
        choice local-port-choice {
          leaf port {
            type inet:port-number {
              range "2000..max";
            }
          }
          leaf default {
            description
              "Default port 20000";
            type empty;
          }
        }
      }
      leaf remote-ip {
        description
          "Single host, subnet or any";
        type union {
          type inet:ipv4-address;
          type inet:ipv4-prefix;
          type enumeration {
            enum "any" {
              description
                "Any remote hosts 0.0.0.0/0";
            }
          }
        }
      }
    }
  }

  grouping config-dnp3s-channel-grouping {
    leaf bind-to-interface {
      description
        "Interface name DNP3-serial binds to";
      type string;
    }
    container link-addr {
      description
        "Configure scada-gw dnp3 serial channel link-addr";
      leaf source {
        description
          "Source address(Master)";
        type uint16 {
          range "0..65535";
        }
      }
    }
    leaf link-timeout {
      description
        "Timeout in second";
      type uint8 {
        range "1..60";
      }
    }
    container protocol {
      description
        "configure protocol choice, expert mode";
      leaf test-link {
        description
          "test link request";
        type empty;
      }
    }
    leaf request-timeout {
      description
        "Timeout in second";
      type uint8 {
        range "1..60";
      }
    }
    container unsolicited-response {
      description
        "Unsolicited Response";
      leaf enable {
        description
          "Enable";
        type empty;
      }
    }
  }

  grouping config-scada-gw-grouping {
    container protocol {
      description
        "Protocols selection";
      container clock {
        description
          "Scada Clock";
        leaf passthru {
          description
            "Enable scada clock pass from master to rtu";
          type empty;
        }
      }
      container dnp3-serial {
        description
          "DNP3-SERIAL protocol";
        container config-dnp3s {
          list channel {
            description
              "Channel Name";
            max-elements "2";
            key "name";
            leaf name {
              description
                "Name of the Channel";
              type string {
                length "1..32";
              }
            }
            container config-dnp3s-channel {
              uses config-dnp3s-channel-grouping;
              container default {
                description
                  "Set a command to its defaults";
                uses config-dnp3s-channel-grouping;
              }
            }
          }
          list session {
            description
              "Session Name";
            max-elements "2";
            key "name";
            leaf name {
              description
                "Name of the Session";
              type string {
                length "1..32";
              }
            }
            container config-dnp3s-session {
              uses config-dnp3s-session-grouping;
              container default {
                description
                  "Set a command to its defaults";
                uses config-dnp3s-session-grouping;
              }
            }
          }
        }
      }
      container dnp3-ip {
        description
          "DNP3-IP protocol";
        container config-dnp3n {
          list channel {
            description
              "Channel Name";
            max-elements "2";
            key "name";
            leaf name {
              description
                "Name of the Channel";
              type string {
                length "1..32";
              }
            }
            container config-dnp3n-channel {
              uses config-dnp3n-channel-grouping;
              container default {
                description
                  "Set a command to its defaults";
                uses config-dnp3n-channel-grouping;
              }
            }
          }
          list session {
            description
              "Session Name";
            max-elements "2";
            key "name";
            leaf name {
              description
                "Name of the Session";
              type string {
                length "1..32";
              }
            }
            container config-dnp3n-session {
              uses config-dnp3n-session-grouping;
              container default {
                description
                  "Set a command to its defaults";
                uses config-dnp3n-session-grouping;
              }
            }
          }
        }
      }
      container event {
        description
          "Scada Event";
        leaf persist {
          description
            "Enable scada non-volatile storage";
          type empty;
        }
      }
      container ignore {
        description
          "scada loosing connection on non-conforming device";
        container error {
          description
            "Scada error detection";
          leaf address {
            description
              "Scada address";
            type empty;
          }
        }
        leaf direction {
          description
            "Scada ignore direction bit in header";
          type empty;
        }
      }
      leaf interlock {
        description
          "Enable interlock up/down stream";
        type empty;
      }
      container t101 {
        description
          "T101 protocol";
        container config-t101 {
          list channel {
            description
              "Channel Name";
            max-elements "2";
            key "name";
            leaf name {
              description
                "Name of the Channel";
              type string {
                length "1..32";
              }
            }
            container config-t101-channel {
              uses config-t101-channel-grouping;
            }
          }
          list session {
            description
              "Session Name";
            max-elements "2";
            key "name";
            leaf name {
              description
                "Name of the Session";
              type string {
                length "1..32";
              }
            }
            container config-t101-session {
              uses config-t101-session-grouping;
            }
          }
          list sector {
            description
              "Sector Name";
            max-elements "2";
            key "name";
            leaf name {
              description
                "Name of the Sector";
              type string {
                length "1..32";
              }
            }
            container config-t101-sector {
              uses config-t101-sector-grouping;
            }
          }
        }
      }
      container t104 {
        description
          "T104 protocol";
        container config-t104 {
          list channel {
            description
              "Channel Name";
            max-elements "2";
            key "name";
            leaf name {
              description
                "Name of the Channel";
              type string {
                length "1..32";
              }
            }
            container config-t104-channel {
              container day-of-week {
                description
                  "Include Day of week information in timestamp";
                leaf enable {
                  description
                    "Enable";
                  type empty;
                }
              }
              leaf k-value {
                description
                  "K-value";
                type uint16 {
                  range "1..32767";
                }
              }
              container send-ei {
                description
                  "Send End of Initialization when T104 session re-established";
                leaf enable {
                  description
                    "Enable";
                  type empty;
                }
              }
              leaf t0-timeout {
                description
                  "T0-timeout";
                type uint8 {
                  range "1..255";
                }
              }
              leaf t1-timeout {
                description
                  "T1-timeout";
                must "(not(boolean(../t2-timeout)) or (../t2-timeout < current() )) and (not(boolean(../t3-timeout)) or (../t3-timeout > current() ))" {
                  error-message "Please ensure (t2 < t1) and (t3 > t1)";
                }
                type uint8 {
                  range "1..255";
                }
              }
              leaf t2-timeout {
                description
                  "T2-timeout";
                type uint8 {
                  range "1..255";
                }
              }
              leaf t3-timeout {
                description
                  "T3-timeout";
                type uint8 {
                  range "1..255";
                }
              }
              list tcp-connection {
                description
                  "TCP connection";
                max-elements "2";
                key "num-connection";
                leaf num-connection {
                  description
                    "No. of connection";
                  type uint8 {
                    range "0..1";
                  }
                }
                container local-port {
                  description
                    "2000-65535, default 2404";
                  choice local-port-choice {
                    leaf port {
                      type inet:port-number {
                        range "2000..max";
                      }
                    }
                    leaf default {
                      description
                        "Default port 2404";
                      type empty;
                    }
                  }
                }
                leaf remote-ip {
                  description
                    "Single host, subnet or any";
                  type union {
                    type inet:ipv4-address;
                    type inet:ipv4-prefix;
                    type enumeration {
                      enum "any" {
                        description
                          "Any remote hosts 0.0.0.0/0";
                      }
                    }
                  }
                }
              }
              leaf w-value {
                description
                  "W-value";
                type uint16 {
                  range "1..32767";
                }
              }
            }
          }
          list session {
            description
              "Session Name";
            max-elements "2";
            key "name";
            leaf name {
              description
                "Name of the Session";
              type string {
                length "1..32";
              }
            }
            container config-t104-session {
              uses config-t104-session-grouping;
            }
          }
          list sector {
            description
              "Sector Name";
            max-elements "4";
            key "name";
            leaf name {
              description
                "Name of the Sector";
              type string {
                length "1..32";
              }
            }
            container config-t104-sector {
              leaf attach-to-session {
                description
                  "Name of the Session to attach";
                must "count( /ios:native/ios:scada-gw/ios-scada-gw:protocol/ios-scada-gw:t104/ios-scada-gw:config-t104/ios-scada-gw:sector[ ios-scada-gw:config-t104-sector/ios-scada-gw:attach-to-session = current() ] ) <= 2" {
                  error-message "Maximum number of sectors attached to this session";
                }
                type leafref {
                  path "/ios:native/ios:scada-gw/ios-scada-gw:protocol/ios-scada-gw:t104/ios-scada-gw:config-t104/ios-scada-gw:session/ios-scada-gw:name";
                }
              }
              leaf map-to-sector {
                description
                  "Sector name";
                type leafref {
                  path "/ios:native/ios:scada-gw/ios-scada-gw:protocol/ios-scada-gw:t101/ios-scada-gw:config-t101/ios-scada-gw:sector/ios-scada-gw:name";
                }
              }
              leaf asdu-addr {
                description
                  "Asdu Address";
                type uint16 {
                  range "0..65535";
                }
              }
            }
          }
        }
      }
    }
    leaf enable {
      must "count(/ios:native/ios:scada-gw/ios-scada-gw:protocol/ios-scada-gw:t104/ios-scada-gw:config-t104/ios-scada-gw:channel[ not( contains( /ios:native/ios:scada-gw/ios-scada-gw:protocol/ios-scada-gw:t104/ios-scada-gw:config-t104/ios-scada-gw:session/ios-scada-gw:config-t104-session/ios-scada-gw:attach-to-channel,ios-scada-gw:name ) ) ] ) = 0" {
        error-message "Unused T104 channel(s) found";
      }
      must "count(/ios:native/ios:scada-gw/ios-scada-gw:protocol/ios-scada-gw:t104/ios-scada-gw:config-t104/ios-scada-gw:session[ not( contains( /ios:native/ios:scada-gw/ios-scada-gw:protocol/ios-scada-gw:t104/ios-scada-gw:config-t104/ios-scada-gw:sector/ios-scada-gw:config-t104-sector/ios-scada-gw:attach-to-session, ios-scada-gw:name ) ) ] ) = 0" {
        error-message "Unused T104 session(s) found";
      }
      must "count(/ios:native/ios:scada-gw/ios-scada-gw:protocol/ios-scada-gw:t104/ios-scada-gw:config-t104/ios-scada-gw:sector[ not(ios-scada-gw:config-t104-sector/ios-scada-gw:attach-to-session) ]) = 0" {
        error-message "Unattached T104 Sectors found. Attach the sector to a session and try again";
      }
      must "count(/ios:native/ios:scada-gw/ios-scada-gw:protocol/ios-scada-gw:t104/ios-scada-gw:config-t104/ios-scada-gw:session[ not(ios-scada-gw:config-t104-session/ios-scada-gw:attach-to-channel) ]) = 0" {
        error-message "Unattached T104 Sessions found. Attach the session to a channel and try again";
      }
      must "count(/ios:native/ios:scada-gw/ios-scada-gw:protocol/ios-scada-gw:t104/ios-scada-gw:config-t104/ios-scada-gw:session/ios-scada-gw:name) = 0 or count(/ios:native/ios:scada-gw/ios-scada-gw:protocol/ios-scada-gw:t104/ios-scada-gw:config-t104/ios-scada-gw:sector/ios-scada-gw:name) > 0" {
        error-message "No T104 Sectors were found";
      }
      must "count(/ios:native/ios:scada-gw/ios-scada-gw:protocol/ios-scada-gw:t104/ios-scada-gw:config-t104/ios-scada-gw:channel/ios-scada-gw:name) = 0 or count(/ios:native/ios:scada-gw/ios-scada-gw:protocol/ios-scada-gw:t104/ios-scada-gw:config-t104/ios-scada-gw:session/ios-scada-gw:name) > 0" {
        error-message "No T104 Sessions were found";
      }
      must "count(/ios:native/ios:scada-gw/ios-scada-gw:protocol/ios-scada-gw:t101/ios-scada-gw:config-t101/ios-scada-gw:channel/ios-scada-gw:name) = 0 or count(/ios:native/ios:scada-gw/ios-scada-gw:protocol/ios-scada-gw:t104/ios-scada-gw:config-t104/ios-scada-gw:channel/ios-scada-gw:name) > 0" {
        error-message "No T104 Channels were found";
      }
      must "count(/ios:native/ios:scada-gw/ios-scada-gw:protocol/ios-scada-gw:t101/ios-scada-gw:config-t101/ios-scada-gw:channel[ not( contains( /ios:native/ios:scada-gw/ios-scada-gw:protocol/ios-scada-gw:t101/ios-scada-gw:config-t101/ios-scada-gw:session/ios-scada-gw:config-t101-session/ios-scada-gw:attach-to-channel,ios-scada-gw:name ) ) ] ) = 0" {
        error-message "Unused T101 channel(s) found";
      }
      must "count(/ios:native/ios:scada-gw/ios-scada-gw:protocol/ios-scada-gw:t101/ios-scada-gw:config-t101/ios-scada-gw:session[ not( contains( /ios:native/ios:scada-gw/ios-scada-gw:protocol/ios-scada-gw:t101/ios-scada-gw:config-t101/ios-scada-gw:sector/ios-scada-gw:config-t101-sector/ios-scada-gw:attach-to-session, ios-scada-gw:name ) ) ] ) = 0" {
        error-message "Unused T101 session(s) found";
      }
      must "count(/ios:native/ios:scada-gw/ios-scada-gw:protocol/ios-scada-gw:t101/ios-scada-gw:config-t101/ios-scada-gw:sector[ not( contains( /ios:native/ios:scada-gw/ios-scada-gw:protocol/ios-scada-gw:t104/ios-scada-gw:config-t104/ios-scada-gw:sector/ios-scada-gw:config-t104-sector/ios-scada-gw:map-to-sector, ios-scada-gw:name ) ) ] ) = 0" {
        error-message "Unmapped T101 sector(s) found";
      }
      must "count(/ios:native/ios:scada-gw/ios-scada-gw:protocol/ios-scada-gw:t101/ios-scada-gw:config-t101/ios-scada-gw:sector[ not(ios-scada-gw:config-t101-sector/ios-scada-gw:attach-to-session) ]) = 0" {
        error-message "Unattached T101 Sectors found. Attach the sector to a session and try again";
      }
      must "count(/ios:native/ios:scada-gw/ios-scada-gw:protocol/ios-scada-gw:t101/ios-scada-gw:config-t101/ios-scada-gw:session[ not(ios-scada-gw:config-t101-session/ios-scada-gw:attach-to-channel) ]) = 0" {
        error-message "Unattached T101 Sessions found. Attach the session to a channel and try again";
      }
      must "count(/ios:native/ios:scada-gw/ios-scada-gw:protocol/ios-scada-gw:t101/ios-scada-gw:config-t101/ios-scada-gw:channel[ not(ios-scada-gw:config-t101-channel/ios-scada-gw:bind-to-interface) ]) = 0" {
        error-message "Unbound T101 Channels were found. Bind the channel to an interface and try again";
      }
      must "count(/ios:native/ios:scada-gw/ios-scada-gw:protocol/ios-scada-gw:t101/ios-scada-gw:config-t101/ios-scada-gw:session/ios-scada-gw:name) = 0 or count(/ios:native/ios:scada-gw/ios-scada-gw:protocol/ios-scada-gw:t101/ios-scada-gw:config-t101/ios-scada-gw:sector/ios-scada-gw:name) > 0" {
        error-message "No T101 Sectors were found";
      }
      must "count(/ios:native/ios:scada-gw/ios-scada-gw:protocol/ios-scada-gw:t101/ios-scada-gw:config-t101/ios-scada-gw:channel/ios-scada-gw:name) = 0 or count(/ios:native/ios:scada-gw/ios-scada-gw:protocol/ios-scada-gw:t101/ios-scada-gw:config-t101/ios-scada-gw:session/ios-scada-gw:name) > 0" {
        error-message "No T101 Sessions were found";
      }
      must "count(/ios:native/ios:scada-gw/ios-scada-gw:protocol/ios-scada-gw:dnp3-ip/ios-scada-gw:config-dnp3n/ios-scada-gw:channel[ not( contains( /ios:native/ios:scada-gw/ios-scada-gw:protocol/ios-scada-gw:dnp3-ip/ios-scada-gw:config-dnp3n/ios-scada-gw:session/ios-scada-gw:config-dnp3n-session/ios-scada-gw:attach-to-channel,ios-scada-gw:name ) ) ] ) = 0" {
        error-message "Unused DNP3 IP channel(s) found";
      }
      must "count(/ios:native/ios:scada-gw/ios-scada-gw:protocol/ios-scada-gw:dnp3-ip/ios-scada-gw:config-dnp3n/ios-scada-gw:session[ not(ios-scada-gw:config-dnp3n-session/ios-scada-gw:attach-to-channel) ]) = 0" {
        error-message "Unattached DNP3 IP Sessions found. Attach the session to a channel and try again";
      }
      must "count(/ios:native/ios:scada-gw/ios-scada-gw:protocol/ios-scada-gw:dnp3-ip/ios-scada-gw:config-dnp3n/ios-scada-gw:channel/ios-scada-gw:name) = 0 or count(/ios:native/ios:scada-gw/ios-scada-gw:protocol/ios-scada-gw:dnp3-ip/ios-scada-gw:config-dnp3n/ios-scada-gw:session/ios-scada-gw:name) > 0" {
        error-message "No DNP3 IP Sessions were found";
      }
      must "count(/ios:native/ios:scada-gw/ios-scada-gw:protocol/ios-scada-gw:dnp3-serial/ios-scada-gw:config-dnp3s/ios-scada-gw:channel/ios-scada-gw:name) = 0 or count(/ios:native/ios:scada-gw/ios-scada-gw:protocol/ios-scada-gw:dnp3-ip/ios-scada-gw:config-dnp3n/ios-scada-gw:channel/ios-scada-gw:name) > 0" {
        error-message "No DNP3 IP Channels were found";
      }
      must "count(/ios:native/ios:scada-gw/ios-scada-gw:protocol/ios-scada-gw:dnp3-serial/ios-scada-gw:config-dnp3s/ios-scada-gw:channel[ not( contains( /ios:native/ios:scada-gw/ios-scada-gw:protocol/ios-scada-gw:dnp3-serial/ios-scada-gw:config-dnp3s/ios-scada-gw:session/ios-scada-gw:config-dnp3s-session/ios-scada-gw:attach-to-channel,ios-scada-gw:name ) ) ] ) = 0" {
        error-message "Unused DNP3 Serial channel(s) found";
      }
      must "count(/ios:native/ios:scada-gw/ios-scada-gw:protocol/ios-scada-gw:dnp3-serial/ios-scada-gw:config-dnp3s/ios-scada-gw:session[ not( contains( /ios:native/ios:scada-gw/ios-scada-gw:protocol/ios-scada-gw:dnp3-ip/ios-scada-gw:config-dnp3n/ios-scada-gw:session/ios-scada-gw:config-dnp3n-session/ios-scada-gw:map-to-session, ios-scada-gw:name ) ) ] ) = 0" {
        error-message "Unmapped DNP3 Serial session(s) found";
      }
      must "count(/ios:native/ios:scada-gw/ios-scada-gw:protocol/ios-scada-gw:dnp3-serial/ios-scada-gw:config-dnp3s/ios-scada-gw:session[ not(ios-scada-gw:config-dnp3s-session/ios-scada-gw:attach-to-channel) ]) = 0" {
        error-message "Unattached DNP3 Serial Sessions found. Attach the session to a channel and try again";
      }
      must "count(/ios:native/ios:scada-gw/ios-scada-gw:protocol/ios-scada-gw:dnp3-serial/ios-scada-gw:config-dnp3s/ios-scada-gw:channel[ not(ios-scada-gw:config-dnp3s-channel/ios-scada-gw:bind-to-interface) ]) = 0" {
        error-message "Unbound DNP3 Serial Channels were found. Bind the channel to an interface and try again";
      }
      must "count(/ios:native/ios:scada-gw/ios-scada-gw:protocol/ios-scada-gw:dnp3-serial/ios-scada-gw:config-dnp3s/ios-scada-gw:channel/ios-scada-gw:name) = 0 or count(/ios:native/ios:scada-gw/ios-scada-gw:protocol/ios-scada-gw:dnp3-serial/ios-scada-gw:config-dnp3s/ios-scada-gw:session/ios-scada-gw:name) > 0" {
        error-message "No DNP3 Serial Sessions were found";
      }
      must "count(/ios:native/ios:scada-gw/ios-scada-gw:protocol/ios-scada-gw:dnp3-serial/ios-scada-gw:config-dnp3s/ios-scada-gw:channel/ios-scada-gw:name) > 0 or count(/ios:native/ios:scada-gw/ios-scada-gw:protocol/ios-scada-gw:t101/ios-scada-gw:config-t101/ios-scada-gw:channel/ios-scada-gw:name) > 0" {
        error-message "No DNP3 or T101/T104 configuration was found";
      }
      description
        "Enable protocol translation";
      type empty;
    }
  }

  augment "/ios:native/ios:interface/ios:Async/ios:encapsulation" {
    leaf scada {
      status obsolete;
      if-feature "ios-features:scada-gw";
      description
        "SCADA Encapsulation";
      type empty;
    }
  }
  augment "/ios:native/ios:scada-gw" {
    uses config-scada-gw-grouping;
  }
}
