module Cisco-IOS-XE-aaa {
  namespace "http://cisco.com/ns/yang/Cisco-IOS-XE-aaa";
  prefix ios-aaa;

  import cisco-semver {
    prefix cisco-semver;
  }
  import ietf-inet-types {
    prefix inet;
  }
  import Cisco-IOS-XE-types {
    prefix ios-types;
  }
  import Cisco-IOS-XE-native {
    prefix ios;
  }
  import Cisco-IOS-XE-interface-common {
    prefix ios-ifc;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Authentication, Authorization and Accounting (AAA) Yang Model.
     Copyright (c) 2016-2020 by Cisco Systems, Inc.
     All rights reserved.";

  revision 2020-11-01 {
    description
      "- aaa group server tacacs+ TACACS+CG
            key type 6 introduced.
       - Multi group support and added missing leafs for below clis
             aaa accounting exec default start-stop group tacacs+ 
             aaa authorization commands 15 default group tacacs+ none
             aaa accounting commands 1 default start-stop group tacacs+
             aaa authorization exec default group TACACS+CG if-authenticated
             aaa accounting network default start-stop group <TACACS Group Name>
             aaa accounting system default start-stop group <TACACS Group Name>
       -  added type 6 support for 
             tacacs-server key 6
             radius-server key 6
       - tls port support for dynamic-author";
  }
  revision 2020-07-01 {
    description
      "-Added key 7 option for Encrypted key in radius-server
       - Added support for tacacs-server attribute allow unknown
       - Added support aaa authentication username-prompt and password-prompt
       - Fixed support for multiple groups for aaa authentication dot1x";
  }
  revision 2019-11-01 {
    description
      "-Added key 7 option for Encrypted key in radius-server";
    cisco-semver:module-version "1.1.0";
  }
  revision 2019-07-01 {
    description
      "-Added handling of special char in key for radius server
       -Added key 6 encryption option for radius-server
       -Establish semantic version baseline";
    cisco-semver:module-version "1.0.0";
  }
  revision 2018-12-06 {
    description
      "Added delete after ordering dependency on native line vty for aaa  
       authentication and authorization";
  }
  revision 2018-12-03 {
    description
      "Added dependency for aaa authentication/accounting/group/server/session=id
       sub cli for aaa new-model";
  }
  revision 2018-11-29 {
    description
      "Added dependency for aaa authentication dot1x default local";
  }
  revision 2018-11-28 {
    description
      "Added handling of special char in pac key for radius server";
  }
  revision 2018-11-28 {
    description
      "added fix for accounting update";
  }
  revision 2018-11-22 {
    description
      "Added wireless attribute for radius-server";
  }
  revision 2018-11-21 {
    description
      "Cleanup spelling errors in description statements";
  }
  revision 2018-11-13 {
    description
      "Change to use + in multi-line descriptions to avoid NSO compile error";
  }
  revision 2018-11-07 {
    description
      "Added dependency for tacacs server configuration";
  }
  revision 2018-10-29 {
    description
      "Added all options for aaa group server tacacs+ <group name>";
  }
  revision 2018-10-16 {
    description
      "Added cli-full-command to handle authorization commands create delete";
  }
  revision 2018-10-09 {
    description
      "Added 'cli-preformatted' for handling special char in aaa server-key";
  }
  revision 2018-10-02 {
    description
      "Added new AAA attributes and radius-server load-balance support";
  }
  revision 2018-08-28 {
    description
      "Added automate-tester support for radius server";
  }
  revision 2018-08-24 {
    description
      "Added options under aaa accounting update *";
  }
  revision 2018-08-03 {
    description
      "Added IPv6 support for radius";
  }
  revision 2018-08-02 {
    description
      "Added IPv6 support for tacacs";
  }
  revision 2018-05-29 {
    description
      "Add default for aaa session common";
  }
  revision 2018-01-15 {
    description
      "Add Support for suppress node under aaa accounting";
  }
  revision 2018-01-11 {
    description
      "Changed aaa group radius ip source-interface to implement correct native interface model";
  }
  revision 2017-12-15 {
    description
      "Added aaa server group acct-port leaf";
  }
  revision 2017-12-04 {
    description
      "Added support back for aaa accounting dot1x required for DNA-C removed in revision below on 06-01";
  }
  revision 2017-11-17 {
    description
      "Added support for named tacacs and radius servers in both aaa groups for radius and tacacs";
  }
  revision 2017-11-16 {
    description
      "Support server-private <ip> key under aaa group server radius";
  }
  revision 2017-10-10 {
    description
      "Support new aaa local authorization auth-proxy";
  }
  revision 2017-10-06 {
    description
      "Add server-private list to radius server group";
  }
  revision 2017-10-05 {
    description
      "Add support for 'subscriber *' and 'mac-delimiter *' commands under aaa group server";
  }
  revision 2017-09-28 {
    description
      "Support wireless aaa misc commands";
  }
  revision 2017-09-05 {
    description
      "Support new aaa login commands and aaa server commands";
  }
  revision 2017-06-05 {
    description
      "Update domain delimeter description to conform to YANG 1.1";
    reference "RFC 7950: The YANG 1.1 Data Modeling Language";
  }
  revision 2017-06-01 {
    description
      "Changed aaa accounting dot1x to aaa accounting identity";
  }
  revision 2017-03-24 {
    description
      "Remove banner and fail-message";
  }
  revision 2017-03-08 {
    description
      "Add radius retransmit/automate-tester";
  }
  revision 2017-03-03 {
    description
      "add aaa login support and deadtimer for radius";
  }
  revision 2017-02-28 {
    description
      "Add attribute 31 to radius-server";
  }
  revision 2017-02-07 {
    description
      "Initial revision";
  }

  typedef ipv4-mask-slash-prefix-len-type {
    type string {
      pattern "/(([0-9])|([1-2][0-9])|(3[0-2]))";
    }
  }

  typedef short-lower-upper {
    type enumeration {
      enum "lower";
      enum "upper";
    }
  }

  typedef delimiter-option {
    type enumeration {
      enum "colon";
      enum "hyphen";
      enum "none";
      enum "single-hyphen";
    }
  }

  grouping aaa-accounting-identity {
    container start-stop {
      description
        "Record start and stop without waiting";
      leaf broadcast {
        description
          "Use Broadcast for Accounting";
        type empty;
      }
      leaf group {
        description
          "Use Server-group";
        type union {
          type enumeration {
            enum "radius";
            enum "tacacs+";
          }
          type string;
        }
      }
    }
  }

  grouping aaa-group-server-tacas-grouping {
    container server {
      description
        "Specify a TACACS server";
      list name {
        description
          "Name of tacacs server";
        ordered-by user;
        key "name";
        leaf name {
          type string;
        }
      }
      list server-ip {
        key "name";
        leaf name {
          type inet:host;
        }
      }
    }
    list server-private {
      description
        "Define a private TACACS server (per group)";
      key "name";
      leaf name {
        description
          "Hostname or IPv4 or IPV6 address of TACACS server";
        type ios-types:host-type;
      }
      leaf port {
        description
          "TCP port for TACACS+ server (default is 49)";
        type uint16 {
          range "1..65535";
        }
      }
      leaf timeout {
        description
          "Time to wait for this TACACS server to reply (overrides default)";
        type uint16 {
          range "1..1000";
        }
      }
      container key {
        description
          "per-server encryption key (overrides default)";
        leaf encryption {
          description
            "0 - Specifies an UNENCRYPTED key will follow
             6 - Specifies an ENCRYPTED key will follow
             7 - Specifies HIDDEN key will follow";
          type enumeration {
            enum "0";
            enum "6";
            enum "7";
          }
        }
        leaf key {
          description
            "The UNENCRYPTED (cleartext) server key";
          type string;
        }
      }
    }
    container ip {
      description
        "Internet Protocol config commands";
      container tacacs {
        description
          "TACACS configuration commands";
        uses config-ip-tacacs-main-grouping;
      }
      container vrf {
        description
          "Set VPN Routing Forwarding to use with the servers";
        leaf forwarding {
          description
            "Configure forwarding table";
          type string;
        }
      }
    }
    container accounting {
      description
        "Accounting specific command";
      container acknowledge {
        description
          "Send accounting response";
        leaf broadcast {
          description
            "Acknowledge broadcast accounting";
          type empty;
        }
      }
    }
    container cache {
      description
        "cached DB profile configuration";
      container authentication {
        description
          "Authentication Cache profile configuration";
        leaf profile {
          description
            "Match profile to use for caching authentication responses";
          type string;
        }
      }
      container authorization {
        description
          "Authorization Cache profile configuration";
        leaf profile {
          description
            "Match profile to use for caching authentication responses";
          type string;
        }
      }
      leaf expiry {
        description
          "Time for cached DB profile entry to expire";
        type uint32 {
          range "0..2147483647";
        }
      }
    }
    leaf dns-alias-lookup {
      description
        "Enable IP Domain Name System Alias lookup for TACACS";
      type empty;
    }
    container host {
      description
        "Specify a TACACS server";
      leaf ip-address {
        description
          "Hostname or A.B.C.D  IP address of TACACS server";
        type union {
          type inet:ipv4-address;
          type string;
        }
      }
    }
    container ipv6 {
      description
        "IPv6 config commands";
      container tacacs {
        description
          "TACACS configuration commands";
        uses config-ip-tacacs-main-grouping;
      }
      container vrf {
        description
          "Set VPN Routing Forwarding to use with the servers";
        leaf forwarding {
          description
            "Configure forwarding table";
          type string;
        }
      }
    }
    leaf pick-method {
      description
        "Method by which the next host will be picked";
      type enumeration {
        enum "load-balanced";
        enum "next";
        enum "round-robin";
      }
    }
    leaf timeout {
      description
        "Time to wait for a TACACS server to reply";
      type uint32 {
        range "1..1000";
      }
    }
  }

  grouping aaa-accounting-dot1x {
    container start-stop {
      description
        "Record start and stop without waiting";
      leaf broadcast {
        description
          "Use Broadcast for Accounting";
        type empty;
      }
      leaf group {
        description
          "Use Server-group";
        type union {
          type string;
          type enumeration {
            enum "radius";
            enum "tacacs+";
          }
        }
      }
    }
  }

  grouping aaa-authorization-cred-download {
    leaf local {
      description
        "Use local database";
      type empty;
    }
    leaf cache {
      description
        "Use Cached-group";
      type union {
        type string;
        type enumeration {
          enum "ldap";
          enum "radius";
          enum "tacacs+";
        }
      }
    }
    leaf group {
      description
        "Use server-group";
      type union {
        type string;
        type enumeration {
          enum "ldap";
          enum "radius";
          enum "tacacs+";
        }
      }
    }
    leaf if-authenticated {
      description
        "Succeed if user has authenticated";
      type empty;
    }
    leaf none {
      description
        "No authorization (always succeeds)";
      type empty;
    }
  }

  grouping aaa-server-radius-key-grouping {
    container key {
      description
        "Specify a RADIUS client";
      uses aaa-server-radius-key;
    }
  }

  grouping aaa-server-proxy-common {
    container accounting {
      description
        "Specify accounting details";
      uses aaa-server-method;
      uses aaa-server-radius-port;
    }
    container authentication {
      description
        "Specify authentication details";
      uses aaa-server-method;
      uses aaa-server-radius-port;
    }
    container calling-station-id {
      description
        "Specify format of Calling-Station-Id, attribute
         31.Default format is to expect mac-address in
         calling-station-id";
      container format {
        description
          "Specify the format as MAC or MSISDN";
        choice type {
          container mac-address {
            description
              "Expect MAC address to be present in CLID";
            choice mac-format {
              container default {
                description
                  "format ex: 0000.4096.3e4a";
                presence "true";
                uses aaa-case-grouping;
              }
              container ietf {
                description
                  "format ex: 00-00-40-96-3E-4A";
                presence "true";
                uses aaa-case-grouping;
              }
              leaf none {
                description
                  "format unspecified";
                type empty;
              }
              container one-byte {
                description
                  "format ex: 00.00.40.96.3e.4a";
                uses aaa-server-delimiter-groupingg;
              }
              container three-byte {
                description
                  "format ex: 000040.963e4a";
                uses aaa-server-delimiter-groupingg;
              }
              container two-byte {
                description
                  "format ex: 0000.4096.3e4a";
                uses aaa-server-delimiter-groupingg;
              }
              container unformatted {
                description
                  "format ex: 000040963e4a";
                presence "true";
                uses aaa-case-grouping;
              }
            }
          }
          leaf msisdn {
            description
              "Expect MSISDN value to be present in CLID";
            type empty;
          }
        }
      }
    }
    container eap-user {
      description
        "EAP users";
      leaf ignore-open-session {
        description
          "for EAP authenticated users, open-session is not supported";
        type empty;
      }
    }
    container filter {
      description
        "Configure filter";
      container access {
        description
          "For access requests";
        uses aaa-server-filter;
      }
      container accounting {
        description
          "For accounting requests";
        uses aaa-server-filter;
      }
      container attribute {
        description
          "Filter attributes in packets sent to clients";
        choice attr-type {
          leaf allow {
            description
              "Allow only the attributes specified in the list";
            type string;
          }
          leaf block {
            description
              "Block the attributes specified in the list";
            type string;
          }
        }
      }
    }
    uses aaa-server-radius-key-grouping;
    container message-authenticator {
      description
        "Message Authenticator attribute from Clients";
      container ignore {
        description
          "Ignore checking of Message Authenticator attribute from Clients";
        presence "true";
        leaf accounting {
          description
            "Ignore checking of Message Authenticator attribute from accounting packets";
          type empty;
        }
      }
    }
    container mode {
      description
        "Radius Proxy Pass thru mode";
      leaf pass-through {
        description
          "Enable the pass-through mode for Radius Proxy";
        type empty;
      }
    }
    container pwlan-session {
      description
        "PWLAN Reconnect feature";
      leaf reconnect {
        description
          "Enable the reconnect feature for PWLAN RP sessions";
        type empty;
      }
    }
    container re-authentication {
      description
        "Specify re-authentication details";
      leaf do-not-apply {
        description
          "Do not apply new data during re-authentication";
        type empty;
      }
    }
    container session-identifier {
      description
        "This attribute will be used to correlate Radius requests of a session and to identify sessions within radius-proxy";
      leaf attribute {
        description
          "Specify an IETF Radius attribute";
        type uint8 {
          range "1..255";
        }
      }
      container vsa {
        description
          "Specify Vendor-Specific Attribute";
        leaf vendor {
          description
            "Specify the vendor type";
          type uint16 {
            range "1..65535";
          }
        }
        leaf type {
          description
            "Give attribute type for vsa";
          type uint8 {
            range "1..255";
          }
        }
      }
    }
    container timer {
      description
        "Configure RADIUS proxy timer values";
      container disconnect {
        description
          "Specify disconnect timer";
        leaf acct-stop {
          description
            "Specify disconnect delay timer for accounting stop";
          type uint16 {
            range "0..43200";
          }
        }
        leaf reauth-fail {
          description
            "Specify disconnect delay timer for reauthentication failure";
          type uint16 {
            range "0..43200";
          }
        }
      }
      leaf ip-address {
        description
          "Specify value of wait for IP timer";
        type uint16 {
          range "0..43200";
        }
      }
      leaf reconnect {
        description
          "Specify value of wait for reconnect timer";
        type uint16 {
          range "0..43200";
        }
      }
      leaf request {
        description
          "Specify value of wait for Access-Request timer";
        type uint16 {
          range "0..43200";
        }
      }
      leaf roaming {
        description
          "Specify value of wait for roaming timer";
        type uint16 {
          range "0..43200";
        }
      }
    }
  }

  grouping aaa-server-options {
    leaf word1 {
      description
        "Name of the filter to be applied (max 31 chars. longer will be ignored)";
      type string;
    }
    leaf word2 {
      description
        "Name of the filter to be applied (max 31 chars. longer will be ignored)";
      type string;
    }
    leaf word3 {
      description
        "Name of the filter to be applied (max 31 chars. longer will be ignored)";
      type string;
    }
    leaf word4 {
      description
        "Name of the filter to be applied (max 31 chars. longer will be ignored)";
      type string;
    }
  }

  grouping aaa-server-filter {
    choice filter-type {
      container ack {
        description
          "Acknowledge the packet";
        uses aaa-server-options;
      }
      container drop {
        description
          "Drop the packet";
        uses aaa-server-options;
      }
      container ignore {
        description
          "Ignore the packet for applying ISG features";
        uses aaa-server-options;
      }
    }
  }

  grouping aaa-server-radius-port {
    leaf port {
      description
        "Radius server port";
      type uint16;
    }
  }

  grouping aaa-server-radius-key {
    leaf key {
      type enumeration {
        enum "0";
        enum "6";
        enum "7";
      }
    }
    leaf string {
      type string {
        pattern ".*";
      }
    }
  }

  grouping aaa-load-balance-grouping {
    container load-balance {
      when "/ios:native/ios:aaa/ios-aaa:new-model";
      description
        "Radius / Server group load-balancing options.";
      container method {
        description
          "Method by which the next host will be picked.";
        container least-outstanding {
          description
            "Pick the server with the least transactions outstanding.";
          presence "true";
          leaf batch-size {
            description
              "Size of the transaction batch that should be load-balanced.";
            type uint32 {
              range "1..2147483647";
            }
          }
          leaf ignore-preferred-server {
            description
              "Should the preferred-server be ignored.";
            type empty;
          }
        }
      }
    }
  }

  grouping aaa-server-method {
    container method-list {
      description
        "Authentication method list details";
      choice method {
        leaf method-name {
          description
            "Method list name";
          type string;
        }
        leaf default {
          description
            "The default authentication list";
          type empty;
        }
      }
    }
  }

  grouping aaa-case-grouping {
    leaf type {
      type enumeration {
        enum "lower-case";
        enum "upper-case";
      }
    }
  }

  grouping aaa-server-delimiter-groupingg {
    container delimiter {
      choice delimeter-type {
        container colon {
          presence "true";
          uses aaa-case-grouping;
        }
        container dot {
          presence "true";
          uses aaa-case-grouping;
        }
        container hyphen {
          presence "true";
          uses aaa-case-grouping;
        }
      }
    }
  }

  grouping aaa-authentication-dot1x-grouping-container {
    leaf group {
      status deprecated;
      description
        "Use Server-group";
      type union {
        type string;
        type enumeration {
          enum "radius";
          enum "ldap";
        }
      }
    }
    leaf local {
      status deprecated;
      description
        "Use local username authentication";
      type empty;
    }
    leaf cache {
      status deprecated;
      description
        "Use Cached-group";
      type union {
        type string;
        type enumeration {
          enum "radius";
          enum "ldap";
        }
      }
    }
    leaf radius {
      status deprecated;
      description
        "Use list of all Radius hosts";
      type empty;
    }
  }

  grouping aaa-authentication-dot1x-grouping {
    container a1-config {
      choice dot1x-auth {
        leaf group {
          description
            "Use Server-group";
          type union {
            type string;
            type enumeration {
              enum "radius";
              enum "ldap";
            }
          }
        }
        leaf local {
          description
            "Use local username authentication";
          type empty;
        }
        leaf cache {
          description
            "Use Cached-group";
          type union {
            type string;
            type enumeration {
              enum "radius";
              enum "ldap";
            }
          }
        }
        leaf radius {
          description
            "Use list of all Radius hosts";
          type empty;
        }
      }
    }
    container a1 {
      status deprecated;
      uses aaa-authentication-dot1x-grouping-container;
    }
    container a2-config {
      choice dot1x-auth {
        leaf group {
          description
            "Use Server-group";
          type union {
            type string;
            type enumeration {
              enum "radius";
              enum "ldap";
            }
          }
        }
        leaf local {
          when "not(../../a1-config/local)";
          description
            "Use local username authentication";
          type empty;
        }
        leaf cache {
          description
            "Use Cached-group";
          type union {
            type string;
            type enumeration {
              enum "radius";
              enum "ldap";
            }
          }
        }
        leaf radius {
          when "not(../../a1-config/radius)";
          description
            "Use list of all Radius hosts";
          type empty;
        }
      }
    }
    container a2 {
      status deprecated;
      uses aaa-authentication-dot1x-grouping-container {
        refine "local" {
          must "not(../../a1/local)" {
            description
              "Use local username authentication";
          }
        }
        refine "radius" {
          must "not(../../a1/radius)" {
            description
              "Use list of all Radius hosts";
          }
        }
      }
    }
    container a3-config {
      choice dot1x-auth {
        leaf group {
          description
            "Use Server-group";
          type union {
            type string;
            type enumeration {
              enum "radius";
              enum "ldap";
            }
          }
        }
        leaf local {
          when "not(../../a1-config/local) and not(../../a2-config/local)";
          description
            "Use local username authentication";
          type empty;
        }
        leaf cache {
          description
            "Use Cached-group";
          type union {
            type string;
            type enumeration {
              enum "radius";
              enum "ldap";
            }
          }
        }
        leaf radius {
          when "not(../../a2-config/radius) and not(../../a1-config/radius)";
          description
            "Use list of all Radius hosts";
          type empty;
        }
      }
    }
    container a3 {
      status deprecated;
      uses aaa-authentication-dot1x-grouping-container {
        refine "local" {
          must "not(../../a1/local) and not(../../a2/local)" {
            description
              "Use local username authentication";
          }
        }
        refine "radius" {
          must "not(../../a1/radius) and not(../../a2/radius)" {
            description
              "Use list of all Radius hosts";
          }
        }
      }
    }
    container a4-config {
      choice dot1x-auth {
        leaf group {
          description
            "Use Server-group";
          type union {
            type string;
            type enumeration {
              enum "radius";
              enum "ldap";
            }
          }
        }
        leaf local {
          when "not(../../a1-config/local) and not(../../a2-config/local) and not(../../a3-config/local)";
          description
            "Use local username authentication";
          type empty;
        }
        leaf cache {
          description
            "Use Cached-group";
          type union {
            type string;
            type enumeration {
              enum "radius";
              enum "ldap";
            }
          }
        }
        leaf radius {
          when "not(../../a2-config/radius) and not(../../a1-config/radius) and not(../../a3-config/radius)";
          description
            "Use list of all Radius hosts";
          type empty;
        }
      }
    }
    container a4 {
      status deprecated;
      uses aaa-authentication-dot1x-grouping-container {
        refine "local" {
          must "not(../../a1/local) and not(../../a2/local) and not (../../a3/local)" {
            description
              "Use local username authentication";
          }
        }
        refine "radius" {
          must "not(../../a1/radius) and not(../../a2/radius) and not (../../a3/radius)" {
            description
              "Use list of all Radius hosts";
          }
        }
      }
    }
    leaf group {
      status deprecated;
      description
        "Use Server-group (DEPRECATED, use group within container)";
      type union {
        type string;
        type enumeration {
          enum "radius";
          enum "ldap";
        }
      }
    }
    leaf local {
      status deprecated;
      description
        "Use local username authentication (DEPRECATED, use local within container)";
      type empty;
    }
    leaf cache {
      status deprecated;
      description
        "Use Cached-group (DEPRECATED, use cache within container)";
      type union {
        type string;
        type enumeration {
          enum "radius";
          enum "ldap";
        }
      }
    }
  }

  grouping aaa-server-group-grouping {
    leaf group {
      description
        "Use Server-group";
      type union {
        type string;
        type enumeration {
          enum "radius";
          enum "tacacs+";
        }
      }
    }
  }

  grouping aaa-accounting-sub-grouping {
    leaf broadcast {
      description
        "Use Broadcast for Accounting";
      type empty;
    }
    leaf logger {
      description
        "Use system logger for Accounting";
      type empty;
    }
    container group1 {
      description
        "server group name";
      uses aaa-server-group-grouping;
    }
    container group2 {
      description
        "server group name";
      uses aaa-server-group-grouping;
    }
    container group3 {
      description
        "server group name";
      uses aaa-server-group-grouping;
    }
    container group4 {
      description
        "server group name";
      uses aaa-server-group-grouping;
    }
  }

  grouping aaa-accounting-grouping {
    choice accounting-choice {
      leaf none {
        description
          "No accounting.";
        type empty;
      }
      container start-stop {
        description
          "Record start and stop without waiting";
        uses aaa-accounting-sub-grouping;
      }
      container stop-only {
        description
          "Record stop when service terminates.";
        uses aaa-accounting-sub-grouping;
      }
      container wait-start {
        description
          "Same as start-stop but wait for start-record commit.";
        uses aaa-accounting-sub-grouping;
      }
    }
  }

  grouping config-aaa-grouping {
    leaf new-model {
      description
        "Enable NEW access control commands and functions.(Disables OLD commands.)";
      type empty;
    }
    container session-mib {
      description
        "AAA session MIB options";
      when "/ios:native/ios:aaa/ios-aaa:new-model";
      leaf disconnect {
        description
          "AAA session MIB disconnect enable";
        type empty;
      }
      container populate {
        description
          "Populate session options";
        leaf setup {
          description
            "Populate during setup";
          type empty;
        }
        leaf start {
          description
            "Populate during accounting start";
          type empty;
        }
      }
    }
    container cache {
      description
        "AAA cache definitions";
      when "/ios:native/ios:aaa/ios-aaa:new-model";
      list cache-profile {
        description
          "AAA cache profile definitions";
        key "name";
        leaf name {
          description
            "Cache profile name";
          type string;
        }
      }
    }
    container group {
      description
        "AAA group definitions";
      when "/ios:native/ios:aaa/ios-aaa:new-model";
      container server {
        description
          "AAA Server group definitions";
        list tacacsplus {
          description
            "Tacacs+ server-group definition";
          key "name";
          leaf name {
            description
              "Server-group name with max string length 32";
            type string;
          }
          uses aaa-group-server-tacas-grouping;
        }
        list tacacs {
          description
            "Tacacs+ server-group definition";
          key "name";
          leaf name {
            description
              "Server-group name with max string length 32";
            type string;
          }
        }
        list radius {
          description
            "Radius server-group definition";
          key "name";
          leaf name {
            description
              "Radius Server-group name with max string length 32";
            type string {
              pattern "[0-9a-zA-Z!->@^_]*";
            }
          }
          container server {
            description
              "Specify a RADIUS server";
            list name {
              description
                "Name of radius server";
              ordered-by user;
              key "name";
              leaf name {
                description
                  "Radius server name";
                type string;
              }
            }
            list direct {
              key "name";
              leaf name {
                type inet:host;
              }
              leaf auth-port {
                description
                  "UDP port for RADIUS authentication server (default is 1645)";
                type uint16 {
                  range "0..65535";
                }
              }
              leaf acct-port {
                description
                  "UDP port for RADIUS accounting server (default is 1646)";
                type uint16 {
                  range "0..65535";
                }
              }
            }
          }
          container subscriber {
            description
              "Configures MAC Filtering RADIUS Compatibility mode";
            container mac-filtering {
              description
                "MAC Filtering";
              leaf security-mode {
                description
                  "Security Mode";
                type enumeration {
                  enum "mac";
                  enum "none";
                  enum "shared-secret";
                }
              }
            }
          }
          leaf mac-delimiter {
            description
              "MAC Delimiter for Radius Compatibility Mode";
            type enumeration {
              enum "colon";
              enum "hyphen";
              enum "none";
              enum "single-hyphen";
            }
          }
          list server-private {
            description
              "Define a private RADIUS server (per group)";
            ordered-by user;
            key "name";
            leaf name {
              description
                "Hostname or IP 4 or IP 6 address of RADIUS server";
              type ios-types:host-type;
            }
            leaf auth-port {
              description
                "UDP port for RADIUS authentication server (default is 1812)";
              default "1812";
              type uint16 {
                range "0..65534";
              }
            }
            leaf acct-port {
              description
                "UDP port for RADIUS accounting server (default is 1813)";
              default "1813";
              type uint16 {
                range "0..65534";
              }
            }
            leaf timeout {
              description
                "Time to wait for this RADIUS server to reply (overrides default)";
              type uint16 {
                range "1..1000";
              }
            }
            leaf retransmit {
              description
                "Number of retries to active server (overrides default)";
              type uint8 {
                range "0..100";
              }
            }
            leaf pac {
              description
                "Protected Access Credential key";
              type empty;
            }
            container key {
              description
                "per-server encryption key (overrides default)";
              leaf encryption {
                description
                  "0 - Specifies an UNENCRYPTED key will follow
                   6 - Specifies an ENCRYPTED key will follow
                   7 - Specifies HIDDEN key will follow";
                type enumeration {
                  enum "0";
                  enum "6";
                  enum "7";
                }
              }
              leaf key {
                description
                  "The UNENCRYPTED (cleartext) server key";
                type string;
              }
            }
          }
          leaf deadtime {
            description
              "Specify time in minutes to ignore an unresponsive server";
            type uint16 {
              range "0..1440";
            }
          }
          container ip {
            description
              "Internet Protocol config commands";
            container radius {
              description
                "RADIUS configuration commands";
              container source-interface {
                description
                  "Specify interface for source address in RADIUS packets";
                uses ios-ifc:interface-grouping;
              }
            }
            container vrf {
              description
                "Set VPN Routing Forwarding to use with the servers";
              leaf forwarding {
                description
                  "Configure forwarding table";
                type string;
              }
            }
          }
          container ipv6 {
            description
              "IPv6 config commands";
            container radius {
              description
                "RADIUS configuration commands";
              container source-interface {
                description
                  "Specify interface for source address in RADIUS packets";
                uses ios-ifc:interface-grouping;
              }
            }
            container vrf {
              description
                "Set VPN Routing Forwarding to use with the servers";
              leaf forwarding {
                description
                  "Configure forwarding table";
                type string;
              }
            }
          }
          container accounting {
            description
              "Specify a RADIUS attribute filter for accounting";
            container request {
              description
                "Attribute filtering for Access-Request";
              leaf reject {
                description
                  "Reject the attributes specified in this list";
                type string;
              }
            }
          }
          container cache {
            description
              "cached DB profile configuration";
            container authentication {
              description
                "Authentication Cache profile configuration";
              leaf profile {
                description
                  "Match profile to use for caching authentication responses";
                type string;
              }
            }
            container authorization {
              description
                "Authorization Cache profile configuration";
              leaf profile {
                description
                  "Match profile to use for caching authentication responses";
                type string;
              }
            }
            leaf expiry {
              description
                "Expiry time in hours (default 24 hours) - 0 is never";
              type uint32 {
                range "0..2147483647";
              }
            }
          }
          uses aaa-load-balance-grouping;
        }
        list ldap {
          description
            "Ldap server-group definition";
          key "name";
          leaf name {
            type string;
          }
          container server {
            description
              "Specify a LDAP server";
            list name {
              description
                "Name of ldap server";
              ordered-by user;
              key "name";
              leaf name {
                type string;
              }
            }
          }
        }
      }
    }
    container attribute {
      description
        "AAA attribute definitions";
      list list {
        description
          "AAA attribute list definition";
        key "name";
        leaf name {
          type string;
        }
        container attribute {
          description
            "Specify an AAA attribute";
          list type {
            key "attr-name attr-value";
            description
              "Specify an AAA attribute type";
            leaf attr-name {
              type union {
                type enumeration {
                  enum "password";
                  enum "timeout";
                  enum "tunnel-medium-type";
                  enum "tunnel-type";
                  enum "tunnel-private-group-id";
                  enum "tunnel-id";
                  enum "bsn-acl-name";
                  enum "sub-qos-policy-in";
                  enum "sub-qos-policy-out";
                  enum "bw-area-code";
                  enum "bw-city-name";
                  enum "bw-class";
                  enum "bw-e164-country-code";
                  enum "bw-iso-country-code";
                  enum "bw-operator-name";
                  enum "bw-state-name";
                  enum "bw-user-group";
                  enum "bw-venue-description";
                  enum "bw-venue-id";
                  enum "bw-venue-nam";
                  enum "bw-venue-tz";
                  enum "aggregation-aaa";
                  enum "svr-device-model-number";
                  enum "svr-device-type";
                  enum "svr-lat-long";
                  enum "svr-network-type";
                  enum "svr-venue-category";
                  enum "svr-zip-code";
                }
                type string;
              }
            }
            leaf attr-value {
              type union {
                type uint32;
                type string;
              }
            }
            leaf mandatory {
              description
                "Specify an AAA attribute as mandatory";
              type empty;
            }
            leaf tag {
              description
                "Specify an AAA attribute tag";
              type uint8 {
                range "1..31";
              }
            }
          }
        }
      }
    }
    container authentication {
      description
        "Authentication configurations parameters.";
      when "/ios:native/ios:aaa/ios-aaa:new-model";
      container attempts {
        description
          "Set the maximum number of authentication attempts";
        leaf login {
          description
            "Set the max. number of attempts for login service";
          type uint8 {
            range "1..25";
          }
        }
      }
      container suppress {
        description
          "Do not send access request for a specific type of user.";
        leaf null-username {
          description
            "Do not send access-request for users with null username.";
          type empty;
        }
      }
      container dot1x {
        description
          "Set authentication lists for IEEE 802.1x.";
        list dot1x-list {
          key "name";
          leaf name {
            type string;
          }
          uses aaa-authentication-dot1x-grouping;
        }
        container default {
          description
            "The default authentication list.";
          uses aaa-authentication-dot1x-grouping;
        }
      }
      container enable {
        description
          "Set authentication list for enable.";
        container default {
          description
            "The default authentication list.";
          leaf group {
            description
              "Use Server-group";
            type union {
              type string;
              type enumeration {
                enum "radius";
                enum "tacacs+";
              }
            }
          }
          leaf enable {
            description
              "Use enable password for authentication.";
            type empty;
          }
          leaf line {
            description
              "Use line password for authentication.";
            type empty;
          }
          leaf none {
            description
              "No authentication.";
            type empty;
          }
        }
      }
      container eou {
        description
          "Set authentication lists for EAPoUDP";
        container default {
          description
            "The default authentication list";
          container group {
            description
              "Use Server-group";
            leaf radius {
              description
                "Use list of all Radius hosts.";
              type empty;
            }
          }
        }
      }
      list login {
        description
          "Set authentication lists for logins.";
        key "name";
        leaf name {
          type union {
            type enumeration {
              enum "default";
            }
            type string {
              length "1..31";
            }
          }
        }
        container a1 {
          choice auth-login-choice {
            leaf none {
              description
                "NO authentication.";
              type empty;
            }
            leaf krb5 {
              description
                "Use Kerberos 5 authentication.";
              type empty;
            }
            leaf krb5-telnet {
              description
                "Allow logins only if already authenticated via Kerbero";
              type empty;
            }
            leaf line {
              description
                "Use line password for authentication.";
              type empty;
            }
            leaf enable {
              description
                "Use enable password for authentication.";
              type empty;
            }
            leaf local {
              description
                "Use local username authentication.";
              type empty;
            }
            leaf local-case {
              description
                "Use case-sensitive local username authentication.";
              type empty;
            }
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
          }
        }
        container a2 {
          when "not(../a1/none)";
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet)";
              type empty;
            }
            leaf krb5-telnet {
              when "not(../../a1/krb5) and not(../../a1/krb5-telnet)";
              type empty;
            }
            leaf line {
              description
                "Use line password for authentication.";
              type empty;
            }
            leaf enable {
              description
                "Use enable password for authentication.";
              type empty;
            }
            leaf local {
              when "not(../../a1/local) and not(../../a1/local-case)";
              type empty;
            }
            leaf local-case {
              when "not(../../a1/local) and not(../../a1/local-case)";
              type empty;
            }
          }
        }
        container a3 {
          when "not(../a2/none) and not (../a1/none)";
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet) and not(../../a2/krb5) and not(../../a2/krb5-telnet)";
              type empty;
            }
            leaf krb5-telnet {
              when "not(../../a1/krb5) and not(../../a1/krb5-telnet) and not(../../a2/krb5) and not(../../a2/krb5-telnet)";
              type empty;
            }
            leaf line {
              description
                "Use line password for authentication.";
              type empty;
            }
            leaf enable {
              description
                "Use enable password for authentication.";
              type empty;
            }
            leaf local {
              when "not(../../a1/local) and not(../../a1/local-case) and not(../../a2/local) and not(../../a2/local-case)";
              type empty;
            }
            leaf local-case {
              when "not(../../a1/local) and not(../../a1/local-case) and not(../../a2/local) and not(../../a2/local-case)";
              type empty;
            }
          }
        }
        container a4 {
          when "not(../a2/none) and not(../a1/none) and not(../a3/none)";
          choice auth-login-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "NO authentication.";
              type empty;
            }
            leaf krb5 {
              when "not(../../a1/krb5) and not(../../a1/krb5-telnet) and not(../../a2/krb5) and not(../../a2/krb5-telnet) and not(../../a3/krb5) and not(../../a3/krb5-telnet)";
              type empty;
            }
            leaf krb5-telnet {
              when "not(../../a1/krb5) and not(../../a1/krb5-telnet) and not(../../a2/krb5) and not(../../a2/krb5-telnet) and not(../../a3/krb5) and not(../../a3/krb5-telnet)";
              type empty;
            }
            leaf line {
              description
                "Use line password for authentication.";
              type empty;
            }
            leaf enable {
              description
                "Use enable password for authentication.";
              type empty;
            }
            leaf local {
              when "not(../../a1/local) and not(../../a1/local-case) and not(../../a2/local) and not(../../a2/local-case) and not(../../a3/local) and not(../../a3/local-case)";
              type empty;
            }
            leaf local-case {
              when "not(../../a1/local) and not(../../a1/local-case) and not(../../a2/local) and not(../../a2/local-case) and not(../../a3/local) and not(../../a3/local-case)";
              type empty;
            }
          }
        }
      }
      container onep {
        description
          "Set authentication lists for ONEP";
        container default {
          description
            "The default authentication list.";
          container local {
            description
              "Use local username authentication.";
            presence "true";
          }
        }
      }
      list ppp {
        description
          "Set authentication lists for ppp.";
        key "id";
        leaf id {
          type string {
            length "1..31";
          }
        }
        container a1 {
          choice auth-choice {
            leaf if-needed {
              description
                "Only authenticate if needed.";
              type empty;
            }
            leaf none {
              description
                "NO authentication.";
              type empty;
            }
            leaf krb5 {
              description
                "Use Kerberos 5 authentication.";
              type empty;
            }
            leaf local {
              description
                "Use local username authentication.";
              type empty;
            }
            leaf local-case {
              description
                "Use case-sensitive local username authentication.";
              type empty;
            }
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
          }
        }
        container a2 {
          when "not(../a1/none)";
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5)";
              type empty;
            }
            leaf local {
              when "not(../../a1/local) and not(../../a1/local-case)";
              type empty;
            }
            leaf local-case {
              when "not(../../a1/local) and not(../../a1/local-case)";
              type empty;
            }
          }
        }
        container a3 {
          when "not(../a2/none) and not (../a1/none)";
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5) and not(../../a2/krb5)";
              type empty;
            }
            leaf local {
              when "not(../../a1/local) and not(../../a1/local-case) and not(../../a2/local) and not(../../a2/local-case)";
              type empty;
            }
            leaf local-case {
              when "not(../../a1/local) and not(../../a1/local-case) and not(../../a2/local) and not(../../a2/local-case)";
              type empty;
            }
          }
        }
        container a4 {
          when "not(../a2/none) and not(../a1/none) and not(../a3/none)";
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf krb5 {
              when "not(../../a1/krb5) and not(../../a2/krb5) and not(../../a3/krb5)";
              type empty;
            }
            leaf local {
              when "not(../../a1/local) and not(../../a1/local-case) and not(../../a2/local) and not(../../a2/local-case) and not(../../a3/local) and not(../../a3/local-case)";
              type empty;
            }
            leaf local-case {
              when "not(../../a1/local) and not(../../a1/local-case) and not(../../a2/local) and not(../../a2/local-case) and not(../../a3/local) and not(../../a3/local-case)";
              type empty;
            }
          }
        }
      }
      leaf password-prompt {
        description
          "Text to use when prompting for a password";
        type string {
          length "1..219";
        }
      }
      leaf username-prompt {
        description
          "Text to use when prompting for a username";
        type string {
          length "1..219";
        }
      }
    }
    container local {
      description
        "AAA Local method options";
      container authentication {
        description
          "Local authentication options";
        container authorization {
          leaf authen-type {
            type union {
              type enumeration {
                enum "default";
              }
              type string;
            }
          }
          leaf authorization {
            type union {
              type enumeration {
                enum "default";
              }
              type string;
            }
          }
        }
        container attempts {
          description
            "Local authentication attempts";
          leaf max-fail {
            description
              "Max failed attempts to lock the user";
            type uint16 {
              range "1..65535";
            }
          }
        }
      }
    }
    container authorization {
      description
        "Authorization configurations parameters.";
      when "/ios:native/ios:aaa/ios-aaa:new-model";
      container auth-type {
        description
          "For Authentication Proxy Services";
        container default {
          description
            "The default authorization list.";
          leaf group {
            description
              "Use server-group.";
            type enumeration {
              enum "radius";
            }
          }
        }
      }
      list commands {
        description
          "For exec (shell) commands.";
        key "level list-name";
        leaf level {
          description
            "Enable level";
          type uint8 {
            range "0..15";
          }
        }
        leaf list-name {
          type union {
            type enumeration {
              enum "default";
            }
            type string;
          }
        }
        container a1 {
          choice auth-exec-choice {
            leaf group {
              description
                "Use Server-group";
              must "(/ios:native/ios:aaa/ios-aaa:group/ios-aaa:server/ios-aaa:tacacsplus[ios-aaa:name=current()] or .='tacacs+')" {
                error-message "The server-group is not a tacacs+ server group. Please define service-group name as a tacacs+ server group";
              }
              type union {
                type string;
                type enumeration {
                  enum "tacacs+";
                  enum "ldap";
                }
              }
            }
            leaf local {
              description
                "Use local database";
              type empty;
            }
            leaf if-authenticated {
              description
                "Succeed if user has authenticated.";
              type empty;
            }
            leaf none {
              description
                "No authorization (always succeeds)";
              type empty;
            }
            leaf radius {
              description
                "Use RADIUS data for authorization";
              type empty;
            }
            leaf tacacs {
              description
                "Use TACACS+";
              type empty;
            }
          }
        }
        container a2 {
          when "not(../a1/none) and not(../a1/if-authenticated)";
          choice auth-exec-choice {
            leaf group {
              description
                "Use Server-group";
              must "(/ios:native/ios:aaa/ios-aaa:group/ios-aaa:server/ios-aaa:tacacsplus[ios-aaa:name=current()] or .='tacacs+')" {
                error-message "The server-group is not a tacacs+ server group. Please define service-group name as a tacacs+ server group";
              }
              type union {
                type string;
                type enumeration {
                  enum "tacacs+";
                  enum "ldap";
                }
              }
            }
            leaf local {
              when "not(../../a1/local)";
              type empty;
            }
            leaf if-authenticated {
              description
                "Succeed if user has authenticated.";
              type empty;
            }
            leaf none {
              description
                "No authorization (always succeeds)";
              type empty;
            }
            leaf radius {
              description
                "Use RADIUS";
              when "not(../../a1/radius)";
              type empty;
            }
            leaf tacacs {
              description
                "Use TACACS+";
              when "not(../../a1/tacacs)";
              type empty;
            }
          }
        }
        container a3 {
          when "not(../a2/none) and not (../a1/none) and not(../a2/if-authenticated) and not(../a1/if-authenticated)";
          choice auth-exec-choice {
            leaf group {
              description
                "Use Server-group";
              must "(/ios:native/ios:aaa/ios-aaa:group/ios-aaa:server/ios-aaa:tacacsplus[ios-aaa:name=current()] or .='tacacs+')" {
                error-message "The server-group is not a tacacs+ server group. Please define service-group name as a tacacs+ server group";
              }
              type union {
                type string;
                type enumeration {
                  enum "tacacs+";
                  enum "ldap";
                }
              }
            }
            leaf local {
              when "not(../../a1/local) and not(../../a2/local)";
              type empty;
            }
            leaf if-authenticated {
              description
                "Succeed if user has authenticated.";
              type empty;
            }
            leaf none {
              description
                "No authorization (always succeeds)";
              type empty;
            }
            leaf radius {
              description
                "Use RADIUS data for authorization";
              when "not(../../a1/radius)and not(../../a2/radius)";
              type empty;
            }
            leaf tacacs {
              description
                "Use TACACS+";
              when "not(../../a1/tacacs) and not(../../a2/tacacs)";
              type empty;
            }
          }
        }
        container a4 {
          when "not(../a2/none) and not(../a1/none) and not(../a3/none) and not(../a2/if-authenticated) and not(../a1/if-authenticated) and not(../a3/if-authenticated)";
          choice auth-exec-choice {
            leaf group {
              description
                "Use Server-group";
              must "(/ios:native/ios:aaa/ios-aaa:group/ios-aaa:server/ios-aaa:tacacsplus[ios-aaa:name=current()] or .='tacacs+')" {
                error-message "The server-group is not a tacacs+ server group. Please define service-group name as a tacacs+ server group";
              }
              type union {
                type string;
                type enumeration {
                  enum "tacacs+";
                  enum "ldap";
                }
              }
            }
            leaf local {
              when "not(../../a1/local) and not(../../a2/local) and not(../../a3/local)";
              type empty;
            }
            leaf if-authenticated {
              description
                "Succeed if user has authenticated.";
              type empty;
            }
            leaf none {
              description
                "No authorization (always succeeds)";
              type empty;
            }
            leaf radius {
              description
                "Use RADIUS data for authorization";
              when "not(../../a1/radius)and not(../../a2/radius) and not(../../a3/radius)";
              type empty;
            }
            leaf tacacs {
              description
                "Use TACACS+";
              when "not(../../a1/tacacs) and not(../../a2/tacacs) and not(../../a3/tacacs)";
              type empty;
            }
          }
        }
        leaf local {
          status deprecated;
          description
            "Use local database.";
          type empty;
        }
        leaf group {
          status deprecated;
          description
            "Use server-group.";
          type union {
            type enumeration {
              enum "tacacs+";
            }
            type string;
          }
        }
        leaf if-authenticated {
          status deprecated;
          description
            "Succeed if user has authenticated.";
          type empty;
        }
        leaf none {
          status deprecated;
          description
            "No authorization (always succeeds).";
          type empty;
        }
      }
      leaf config-commands {
        description
          "For configuration mode commands.";
        type empty;
      }
      container configuration {
        description
          "For downloading configurations from AAA server";
        container default {
          description
            "The default authorization list.";
          container group {
            description
              "Use server-group.";
            list group-name {
              key "group-name";
              leaf group-name {
                description
                  "Server-group name";
                type string;
              }
            }
          }
        }
      }
      leaf console {
        description
          "For enabling console authorization";
        type empty;
      }
      container credential-download {
        description
          "For downloading EAP credential from Local/RADIUS/LDAP";
        container default {
          description
            "The default authorization list";
          uses aaa-authorization-cred-download;
        }
        list authorization-list {
          description
            "Named authorization list (max 31 characters, longer will be rejected)";
          key "name";
          leaf name {
            type string;
          }
          uses aaa-authorization-cred-download;
        }
      }
      list exec {
        description
          "For starting an exec (shell).";
        key "name";
        leaf name {
          type string;
        }
        container a1 {
          choice auth-exec-choice {
            leaf if-authenticated {
              description
                "Succeed if user has authenticated.";
              type empty;
            }
            leaf none {
              description
                "No authorization (always succeeds)";
              type empty;
            }
            leaf krb5-instance {
              description
                "Use Kerberos instance privilege maps";
              type empty;
            }
            leaf local {
              description
                "Use local database";
              type empty;
            }
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf radius {
              description
                "Use radius";
              type empty;
            }
            leaf tacacs {
              description
                "Use TACACS+";
              type empty;
            }
          }
        }
        container a2 {
          when "not(../a1/none) and not(../a1/if-authenticated)";
          choice auth-exec-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf if-authenticated {
              description
                "Succeed if user has authenticated.";
              type empty;
            }
            leaf none {
              description
                "No authorization (always succeeds).";
              type empty;
            }
            leaf krb5-instance {
              when "not (../../a1/krb5-instance)";
              type empty;
            }
            leaf local {
              when "not(../../a1/local)";
              type empty;
            }
            leaf radius {
              description
                "Use Radius";
              when "not(../../a1/radius)";
              type empty;
            }
            leaf tacacs {
              description
                "Use TACACS+";
              when "not(../../a1/tacacs)";
              type empty;
            }
          }
        }
        container a3 {
          when "not(../a2/none) and not (../a1/none) and not(../a2/if-authenticated) and not(../a1/if-authenticated)";
          choice auth-exec-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "No authorization (always succeeds).";
              type empty;
            }
            leaf if-authenticated {
              description
                "Succeed if user has authenticated.";
              type empty;
            }
            leaf krb5-instance {
              when "not (../../a1/krb5-instance) and not (../../a2/krb5-instance)";
              type empty;
            }
            leaf local {
              when "not(../../a1/local) and not(../../a2/local)";
              type empty;
            }
            leaf radius {
              description
                "Use Radius";
              when "not(../../a1/radius)and not(../../a2/radius)";
              type empty;
            }
            leaf tacacs {
              description
                "Use TACACS+";
              when "not(../../a1/tacacs) and not(../../a2/tacacs)";
              type empty;
            }
          }
        }
        container a4 {
          when "not(../a2/none) and not(../a1/none) and not(../a3/none) and not(../a2/if-authenticated) and not(../a1/if-authenticated) and not(../a3/if-authenticated)";
          choice auth-exec-choice {
            leaf group {
              description
                "Use Server-group";
              type union {
                type string;
                type enumeration {
                  enum "ldap";
                  enum "radius";
                  enum "tacacs+";
                }
              }
            }
            leaf cache {
              description
                "Use Cached-group";
              type union {
                type string;
                type enumeration {
                  enum "ldap";
                  enum "radius";
                  enum "tacacs+";
                }
              }
            }
            leaf none {
              description
                "No authorization (always succeeds).";
              type empty;
            }
            leaf if-authenticated {
              description
                "Succeed if user has authenticated.";
              type empty;
            }
            leaf krb5-instance {
              when "not (../../a1/krb5-instance) and not (../../a2/krb5-instance) and not (../../a3/krb5-instance)";
              type empty;
            }
            leaf local {
              when "not(../../a1/local) and not(../../a2/local) and not(../../a3/local)";
              type empty;
            }
            leaf radius {
              description
                "Use radius";
              when "not(../../a1/radius)and not(../../a2/radius) and not(../../a3/radius)";
              type empty;
            }
            leaf tacacs {
              description
                "Use TACACS+";
              when "not(../../a1/tacacs) and not(../../a2/tacacs) and not(../../a3/tacacs)";
              type empty;
            }
          }
        }
      }
      list eventmanager {
        description
          "For starting an exec (shell).";
        key "name";
        leaf name {
          type string;
        }
        leaf group {
          description
            "Use server-group.";
          type union {
            type string;
            type enumeration {
              enum "ldap";
              enum "radius";
              enum "tacacs";
            }
          }
        }
        leaf local {
          description
            "Use local database.";
          type empty;
        }
        leaf none {
          description
            "No authorization (always succeeds).";
          type empty;
        }
      }
      list network {
        description
          "For network services. (PPP, SLIP, ARAP)";
        key "id";
        leaf id {
          type union {
            type enumeration {
              enum "default";
            }
            type string {
              length "1..31";
            }
          }
        }
        container a1 {
          choice auth-choice {
            leaf if-authenticated {
              description
                "Succeed if user has authenticated.";
              type empty;
            }
            leaf none {
              description
                "NO authentication.";
              type empty;
            }
            leaf local {
              description
                "Use local username authentication.";
              type empty;
            }
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
          }
        }
        container a2 {
          when "not(../a1/none) and not(../a1/if-authenticated)";
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf if-authenticated {
              description
                "Succeed if user has authenticated.";
              type empty;
            }
            leaf none {
              description
                "NO authentication.";
              type empty;
            }
            leaf local {
              when "not(../../a1/local)";
              type empty;
            }
          }
        }
        container a3 {
          when "not(../a2/none) and not (../a1/none) and not(../a2/if-authenticated) and not(../a1/if-authenticated)";
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf if-authenticated {
              description
                "Succeed if user has authenticated.";
              type empty;
            }
            leaf local {
              when "not(../../a1/local) and not(../../a2/local)";
              type empty;
            }
          }
        }
        container a4 {
          when "not(../a2/none) and not(../a1/none) and not(../a3/none) and not(../a2/if-authenticated) and not(../a1/if-authenticated) and not(../a3/if-authenticated)";
          choice auth-choice {
            leaf group {
              description
                "Use Server-group";
              type union {
                type string;
                type enumeration {
                  enum "radius";
                  enum "tacacs+";
                }
              }
            }
            leaf cache {
              description
                "Use Cached-group";
              type union {
                type string;
                type enumeration {
                  enum "radius";
                  enum "tacacs+";
                }
              }
            }
            leaf none {
              description
                "NO authentication.";
              type empty;
            }
            leaf if-authenticated {
              description
                "Succeed if user has authenticated.";
              type empty;
            }
            leaf local {
              when "not(../../a1/local) and not(../../a2/local) and not(../../a3/local)";
              type empty;
            }
          }
        }
      }
      container auth-proxy {
        description
          "For Authentication Proxy Services";
        container default {
          description
            "The default authorization list.";
          leaf local {
            description
              "Local authorization.";
            type empty;
          }
          leaf group {
            description
              "Use Server-group";
            type union {
              type string;
              type enumeration {
                enum "radius";
              }
            }
          }
        }
      }
      container onep {
        description
          "Set authorization lists for ONEP";
        container default {
          description
            "The default authorization list.";
          container group {
            description
              "Use Server-group";
            list group-word {
              key "group-word";
              leaf group-word {
                description
                  "Server-group name";
                type string;
              }
            }
          }
        }
      }
    }
    container accounting {
      description
        "Accounting configurations parameters.";
      when "/ios:native/ios:aaa/ios-aaa:new-model";
      list commands {
        description
          "For exec (shell) commands.";
        key "level list-name";
        leaf level {
          description
            "Enable level";
          type uint8 {
            range "0..15";
          }
        }
        leaf list-name {
          type union {
            type enumeration {
              enum "default";
            }
            type string {
              length "1..31";
            }
          }
        }
        leaf action-type {
          type enumeration {
            enum "none";
            enum "start-stop";
            enum "stop-only";
          }
        }
        leaf broadcast {
          description
            "Use Broadcast for Accounting";
          type empty;
        }
        container group-config {
          description
            "server group name";
          uses aaa-accounting-sub-grouping;
        }
        leaf group {
          status deprecated;
          description
            "Use Server-group";
          type union {
            type string;
            type enumeration {
              enum "tacacs+";
            }
          }
        }
      }
      list connection {
        description
          "For outbound connections. (telnet, rlogin)";
        key "name";
        leaf default {
          type empty;
        }
        leaf name {
          type string;
        }
        uses aaa-accounting-grouping;
      }
      container delay-start {
        description
          "Delay PPP Network start record until peer IP address is known.";
        leaf extended-delay {
          description
            "";
          type uint8 {
            range "1..2";
          }
        }
        leaf all {
          description
            "Delay start records for all vrf and non-vrf users.";
          type empty;
        }
        leaf delay-start {
          description
            "<cr>";
          type empty;
        }
      }
      container dot1x {
        description
          "For dot1x sessions.";
        container default {
          description
            "The default authorization list";
          uses aaa-accounting-dot1x;
        }
        list accounting-list {
          description
            "Named Accounting list (max 31 characters, longer will be rejected).";
          key "name";
          leaf name {
            type string;
          }
          uses aaa-accounting-dot1x;
        }
      }
      container identity {
        description
          "For identity sessions.";
        container default {
          description
            "The default authorization list";
          uses aaa-accounting-identity;
        }
        list accounting-list {
          description
            "Named Accounting list (max 31 characters, longer will be rejected).";
          key "name";
          leaf name {
            type string;
          }
          uses aaa-accounting-identity;
        }
      }
      container onep {
        description
          "For ONEP events.";
        container default {
          description
            "The default accounting list.";
          uses aaa-accounting-grouping;
        }
      }
      list exec {
        description
          "For starting an exec (shell).";
        key "name";
        leaf name {
          type string;
        }
        uses aaa-accounting-grouping;
      }
      container exec-submode {
        list exec {
          description
            "For starting an exec (shell).";
          key "name";
          leaf name {
            type string;
          }
          container action-type {
            description
              "Type of action to be performed on accounting records";
            uses aaa-accounting-grouping;
          }
        }
      }
      list network {
        description
          "For network services. (PPP, SLIP, ARAP)";
        key "id";
        leaf id {
          type union {
            type enumeration {
              enum "default";
            }
            type string {
              length "1..31";
            }
          }
        }
        container start-stop {
          description
            "Record start and stop without waiting";
          container group-config {
            description
              "server group name";
            uses aaa-accounting-sub-grouping;
          }
          leaf group {
            status deprecated;
            description
              "Use Server-group";
            type union {
              type string;
              type enumeration {
                enum "radius";
              }
            }
          }
        }
        choice network-choice {
          case a {
            leaf none {
              description
                "No accounting.";
              type empty;
            }
          }
          case b {
            leaf mode {
              type enumeration {
                enum "start-stop";
                enum "stop-only";
              }
            }
            leaf broadcast {
              description
                "Use Broadcast for Accounting";
              type empty;
            }
            container a1 {
              leaf group {
                description
                  "Use server-group.";
                type union {
                  type string;
                  type enumeration {
                    enum "ldap";
                    enum "radius";
                    enum "tacacs";
                  }
                }
              }
            }
            container a2 {
              leaf group {
                description
                  "Use server-group.";
                type union {
                  type string;
                  type enumeration {
                    enum "ldap";
                    enum "radius";
                    enum "tacacs";
                  }
                }
              }
            }
            container a3 {
              leaf group {
                description
                  "Use server-group.";
                type union {
                  type string;
                  type enumeration {
                    enum "ldap";
                    enum "radius";
                    enum "tacacs";
                  }
                }
              }
            }
            container a4 {
              leaf group {
                description
                  "Use server-group.";
                type union {
                  type string;
                  type enumeration {
                    enum "ldap";
                    enum "radius";
                    enum "tacacs";
                  }
                }
              }
            }
          }
        }
      }
      container send {
        description
          "Send records to accounting server";
        container counters {
          description
            "Enable specific counters in the Stop record";
          leaf ipv6 {
            description
              "Send IPv6 counters in the Stop Record";
            type empty;
          }
        }
        container stop-record {
          description
            "Generate STOP records for a specified event";
          leaf always {
            description
              "Generate STOP records always, even if the START record is not sent";
            type empty;
          }
          container authentication {
            description
              "Generate STOP records for authentication failures";
            container failure {
              description
                "Generate STOP records for authentication failures";
              presence "true";
              leaf vrf {
                description
                  "VPN Routing/Forwarding parameters";
                type string;
              }
            }
            container success {
              description
                "Generate STOP records for authenticated users";
              container remote-server {
                description
                  "Successfully authenticated, through access-accept, by a remote AAA server";
                presence "true";
                leaf vrf {
                  description
                    "VPN Routing/Forwarding parameters";
                  type string;
                }
              }
            }
          }
        }
      }
      container suppress {
        description
          "Do not generate accounting records for a specific type of user";
        leaf null-username {
          description
            "Do not generate accounting records for users with a null-username";
          type empty;
        }
      }
      container system {
        description
          "For system events.";
        choice default-guarantee-first {
          case default-case {
            container default {
              description
                "The default accounting list.";
              presence "true";
              leaf none {
                description
                  "No accounting.";
                type empty;
              }
              container start-stop {
                description
                  "Record start and stop without waiting";
                leaf broadcast {
                  description
                    "Use Broadcast for Accounting";
                  type empty;
                }
                container group-config {
                  description
                    "server group name";
                  uses aaa-accounting-sub-grouping;
                }
                leaf group {
                  status deprecated;
                  description
                    "Use Server-group";
                  type union {
                    type string;
                    type enumeration {
                      enum "radius";
                      enum "tacacs+";
                    }
                  }
                }
              }
              leaf vrf {
                description
                  "VPN Routing/Forwarding parameters";
                type string;
              }
            }
          }
          case guarantee-first-case {
            leaf guarantee-first {
              description
                "Guarantee system accounting as first record.";
              type boolean;
            }
          }
        }
      }
      container update {
        description
          "Enable accounting update records";
        choice update-choice {
          leaf periodic {
            description
              "Periodic intervals to send accounting update records(in minutes)";
            type uint32 {
              range "1..71582";
            }
          }
          container newinfo {
            description
              "Only send accounting update records when we have new acct info.";
            presence "true";
            leaf periodic {
              description
                "Periodic intervals to send accounting update records(in minutes)";
              type uint32 {
                range "1..71582";
              }
            }
          }
        }
      }
      container auth-proxy {
        description
          "For Authentication Proxy Services";
        container default {
          description
            "The default authorization list.";
          container start-stop {
            description
              "Record start and stop without waiting";
            leaf group {
              description
                "Use server-group.";
              type string;
            }
          }
        }
      }
    }
    container server {
      description
        "Local AAA server";
      when "/ios:native/ios:aaa/ios-aaa:new-model";
      container radius {
        description
          "Profile for local radius server";
        container dynamic-author {
          description
            "Local server profile for RFC 3576 support";
          presence "true";
          uses aaa-server-radius-port;
          list client {
            description
              "Specify a RADIUS client";
            key "ip";
            leaf ip {
              type union {
                type inet:ipv4-address;
                type inet:ipv6-address;
                type string;
              }
            }
            leaf dtls {
              description
                "Enable DTLS for the client";
              type empty;
            }
            list vrf {
              description
                " Virtual Routing/Forwarding parameters";
              key "name";
              leaf name {
                type string;
              }
              leaf dtls {
                description
                  "Enable DTLS for the client";
                type empty;
              }
              container server-key {
                description
                  "Specify a RADIUS client server-key";
                uses aaa-server-radius-key;
              }
            }
            container server-key {
              description
                "Specify a RADIUS client server-key";
              uses aaa-server-radius-key;
            }
          }
          container tls {
            description
              "TLS Source Parameters";
            presence "true";
            leaf port {
              description
                "Radius tls server port (default is 2083)";
              type uint16 {
                range "0..65535";
              }
              default "2083";
            }
          }
          container server-key {
            description
              "Specify a RADIUS client server-key";
            uses aaa-server-radius-key;
          }
          container domain {
            description
              "Username domain options";
            leaf delimiter {
              description
                "Domain delimiter, Choose from {@, /, $, %, \\, #, -}";
              type string;
            }
            container stripping {
              description
                "Match incoming username left oriented of the @ domain delimiter";
              presence "true";
              leaf right-to-left {
                description
                  "Terminate the string at the first delimiter going from right to left";
                type empty;
              }
            }
          }
          leaf auth-type {
            description
              "Specify the server authorization type";
            type enumeration {
              enum "all";
              enum "any";
              enum "session-key";
            }
          }
          container ignore {
            description
              "Override behaviour to ignore certain parameters";
            leaf retransmission {
              description
                "Drop packets using same radius id";
              type empty;
            }
            leaf server-key {
              description
                "Ignore shared secret";
              type empty;
            }
            leaf session-key {
              description
                "Ignore attr 151";
              type empty;
            }
          }
        }
        container policy-device {
          description
            "Local server profile for RADIUS External Policy Delegation client";
          presence "true";
          container accounting {
            description
              "Specify accounting details";
            uses aaa-server-radius-port;
          }
          container authentication {
            description
              "Specify authentication details";
            uses aaa-server-radius-port;
          }
          list client {
            description
              "Specify a RADIUS client";
            key "ip";
            leaf ip {
              type union {
                type inet:ipv4-address;
                type inet:ipv6-address;
                type string;
              }
            }
            leaf port {
              description
                "Port on which radius client listens for CoA messages (default is 3799)";
              type uint16 {
                range "0..65534";
              }
            }
            list vrf {
              description
                " Virtual Routing/Forwarding parameters";
              key "name";
              leaf name {
                type string;
              }
              leaf port {
                description
                  "Port on which radius client listens for CoA messages (default is 3799)";
                type uint16 {
                  range "0..65534";
                }
              }
              uses aaa-server-radius-key-grouping;
            }
            uses aaa-server-radius-key-grouping;
          }
          uses aaa-server-radius-key-grouping;
          container message-authenticator {
            description
              "Message Authenticator attribute from Clients";
            leaf ignore {
              description
                "Ignore checking of Message Authenticator attribute from Clients";
              type empty;
            }
          }
        }
        container proxy {
          description
            "Local server profile for RADIUS proxy clients";
          presence "true";
          uses aaa-server-proxy-common;
          container client-ip {
            list client {
              description
                "Specify a RADIUS client";
              key "ip";
              leaf ip {
                type union {
                  type inet:ipv4-address;
                  type inet:ipv6-address;
                  type string;
                }
              }
              uses aaa-server-proxy-common;
            }
          }
          container client-ip-mask {
            list client {
              description
                "Specify a RADIUS client";
              key "ip mask";
              leaf ip {
                type union {
                  type inet:ipv4-address;
                  type inet:ipv6-address;
                  type string;
                }
              }
              leaf mask {
                description
                  "Network mask or prefix length";
                type union {
                  type ipv4-mask-slash-prefix-len-type;
                  type inet:ipv4-address;
                }
              }
              uses aaa-server-proxy-common;
            }
          }
          container client-ip-vrf {
            list client {
              description
                "Specify a RADIUS client";
              key "ip vrf";
              leaf ip {
                type union {
                  type inet:ipv4-address;
                  type inet:ipv6-address;
                  type string;
                }
              }
              leaf vrf {
                description
                  "Virtual Routing/Forwarding parameters";
                type string;
              }
              uses aaa-server-proxy-common;
            }
          }
          container client-ip-mask-vrf {
            list client {
              description
                "Specify a RADIUS client";
              key "ip mask vrf";
              leaf ip {
                type union {
                  type inet:ipv4-address;
                  type inet:ipv6-address;
                  type string;
                }
              }
              leaf mask {
                description
                  "Network mask or prefix length";
                type union {
                  type ipv4-mask-slash-prefix-len-type;
                  type inet:ipv4-address;
                }
              }
              leaf vrf {
                description
                  "Virtual Routing/Forwarding parameters";
                type string;
              }
              uses aaa-server-proxy-common;
            }
          }
          container send {
            description
              "Send attributes in Radius requests";
            container vsa {
              description
                "Vendor specific attribute configuration";
              container rpclient-source-address {
                description
                  "AP Source Address";
                presence "true";
                leaf accounting {
                  description
                    "send in accounting requests";
                  type empty;
                }
                leaf authentication {
                  description
                    "send in access requests";
                  type empty;
                }
              }
            }
          }
        }
        container sesm {
          description
            "Local server profile for a SESM client";
          presence "true";
          list client {
            description
              "Specify a RADIUS client";
            key "ip";
            leaf ip {
              type union {
                type inet:ipv4-address;
                type inet:ipv6-address;
                type string;
              }
            }
            list vrf {
              description
                " Virtual Routing/Forwarding parameters";
              key "name";
              leaf name {
                type string;
              }
              uses aaa-server-radius-key-grouping;
            }
            uses aaa-server-radius-key-grouping;
          }
          uses aaa-server-radius-key-grouping;
          container message-authenticator {
            description
              "Message Authenticator attribute from Clients";
            leaf ignore {
              description
                "Ignore checking of Message Authenticator attribute from Clients";
              type empty;
            }
          }
          uses aaa-server-radius-port;
        }
      }
    }
    leaf session-id {
      description
        "AAA Session ID";
      when "/ios:native/ios:aaa/ios-aaa:new-model";
      type enumeration {
        enum "common";
        enum "unique";
      }
      default "common";
    }
    container login {
      description
        "AAA login enable display";
      leaf display {
        description
          "Display options for login info";
        type enumeration {
          enum "last-failure";
          enum "last-success";
          enum "number-failures";
        }
      }
      leaf success-track-conf-time {
        description
          "Track Successful login attempts occurring during configured
           time-period";
        type uint8 {
          range "1..24";
        }
      }
    }
    leaf max-sessions {
      description
        "Adjust initial hash size for estimated max sessions";
      type uint16 {
        range "1024..64000";
      }
    }
    container memory {
      description
        "AAA memory parameters";
      container threshold {
        description
          "set appropriate thresholds for the AAA process";
        container accounting {
          description
            "AAA accounting low-memory threshold";
          leaf disable {
            description
              "accounting may be disabled, if available memory falls below this percentage";
            type uint8 {
              range "1..15";
            }
          }
        }
        container authentication {
          description
            "AAA authentication low-memory threshold";
          leaf reject {
            description
              "requests will be rejected, if available memory falls below this percentage";
            type uint8 {
              range "2..15";
            }
          }
        }
      }
    }
    leaf password {
      description
        "Configure password/secret related settings";
      type enumeration {
        enum "restriction";
      }
    }
    container policy {
      description
        "AAA policy parameters";
      leaf interface-config {
        description
          "LCP interface config policy parameters";
        type enumeration {
          enum "allow-subinterface";
        }
      }
    }
    container route {
      description
        "Static route downloading";
      container download {
        description
          "Download from AAA server";
        leaf update-period {
          description
            "Route update period in minutes";
          type uint16 {
            range "1..1440";
          }
        }
        leaf authorization {
          description
            "Method list to use for authorization";
          type string;
        }
      }
    }
    leaf traceback {
      description
        "Traceback recording";
      type enumeration {
        enum "recording";
      }
    }
    container remote {
      description
        "Remote user configuration";
      leaf username {
        description
          "remote user username - Max length of 255 char";
        type string;
      }
    }
  }

  grouping config-radius-grouping {
    list filter {
      description
        "Packet filter configuration";
      when "/ios:native/ios:aaa/ios-aaa:new-model";
      key "id";
      leaf id {
        type string;
      }
      leaf match {
        type enumeration {
          enum "match-all";
          enum "match-any";
        }
      }
    }
    list server {
      description
        "Server configuration";
      when "/ios:native/ios:aaa/ios-aaa:new-model";
      key "id";
      leaf id {
        description
          "Name for the radius server configuration";
        type string;
      }
      container address {
        description
          "Specify the radius server address";
        choice radius-host-address {
          leaf ipv4 {
            description
              "IPv4 address or Hostname for radius server";
            type union {
              type inet:ipv4-address;
              type string;
            }
          }
          leaf ipv6 {
            description
              "IPv6 address or Hostname for radius server";
            type union {
              type inet:ipv6-address;
              type string;
            }
          }
          leaf fqdn {
            description
              "FQDN for server";
            type string;
          }
        }
        leaf auth-port {
          description
            "UDP port for RADIUS authentication server (default is 1645)";
          default "1645";
          type uint16 {
            range "0..65535";
          }
        }
        leaf acct-port {
          description
            "UDP port for RADIUS accounting server (default is 1646)";
          default "1646";
          type uint16 {
            range "0..65535";
          }
        }
      }
      leaf timeout {
        description
          "Time to wait for a RADIUS server to reply (overrides default)";
        type uint16 {
          range "1..1000";
        }
      }
      container automate-tester {
        description
          "Configure server automated testing.";
        leaf username {
          type string;
        }
        leaf ignore-auth-port {
          description
            "Do not test authentication port of the servers.";
          type empty;
        }
        leaf ignore-acct-port {
          description
            "Do not test accounting ports of the servers.";
          type empty;
        }
        choice type-of-testing {
          leaf probe-on-config {
            description
              "Send a packet to verify the server status";
            type empty;
          }
          leaf idle-time-config {
            description
              "Minutes of idle-time after which server state should be verified.";
            type uint16 {
              range "1..35791";
            }
          }
        }
        leaf probe-on {
          status deprecated;
          description
            "Send a packet to verify the server status";
          type empty;
        }
        leaf idle-time {
          status deprecated;
          description
            "Minutes of idle-time after which server state should be verified.";
          type uint16 {
            range "1..35791";
          }
        }
        leaf vrf {
          description
            "Set VPN Routing Forwarding to use with the servers";
          type string;
        }
      }
      container backoff {
        description
          "Retry backoff pattern(Default is retransmits with constant delay)";
        container exponential {
          description
            "Exponential retransmit backoff";
          presence "true";
          leaf max-delay {
            description
              "Max delay between retransmits(default is 3 min)";
            type uint8 {
              range "1..120";
            }
          }
          leaf backoff-retry {
            description
              "Exponential backoff retry number(default is 8)";
            type uint8 {
              range "1..50";
            }
          }
        }
      }
      container key {
        description
          "Per-server encryption key";
        leaf encryption {
          type enumeration {
            enum "0";
            enum "5";
            enum "6";
            enum "7";
          }
        }
        leaf key {
          type string {
            pattern ".*";
          }
        }
      }
      container pac {
        description
          "Protected Access Credential key";
        container key {
          description
            "Per-server encryption key";
          leaf encryption {
            description
              "0 - Specifies an UNENCRYPTED key will follow
               6 - Specifies an ENCRYPTED key will follow
               7 - Specifies HIDDEN key will follow";
            type enumeration {
              enum "0";
              enum "6";
              enum "7";
            }
          }
          leaf key {
            description
              "The UNENCRYPTED (cleartext) server key";
            type string {
              pattern ".*";
            }
          }
        }
      }
      leaf retransmit {
        description
          "Number of retries to active server (overrides default)";
        type uint8 {
          range "0..100";
        }
      }
    }
  }

  grouping config-ldap-grouping {
    list server {
      description
        "Ldap Server configuration";
      when "/ios:native/ios:aaa/ios-aaa:new-model";
      key "id";
      leaf id {
        type string;
      }
      choice ldap-host-address {
        leaf ipv4 {
          description
            "IPv4 address or Hostname for LDAP server";
          type union {
            type inet:ipv4-address;
            type string;
          }
        }
        leaf ipv6 {
          description
            "IPv6 address or Hostname for LDAP server";
          type union {
            type inet:ipv6-address;
            type string;
          }
        }
        leaf fqdn {
          description
            "FQDN for server";
          type string;
        }
      }
      container authentication {
        description
          "Authentication Process";
        container bind-first {
          description
            "User-Bind first, then Search. Default: Search then User Bind";
          presence "true";
          leaf no-authorization {
            description
              "No authorization required for authentication requests";
            type empty;
          }
        }
        leaf compare {
          description
            "Use Compare instead of Bind for authentication";
          type empty;
        }
      }
      container automate-tester {
        description
          "Configure server automated testing";
        leaf username {
          type string;
        }
        leaf probe-on {
          description
            "Send a packet to verify the server status";
          type empty;
        }
      }
      leaf base-dn {
        description
          "Base DN";
        type string;
      }
      leaf deadtime {
        description
          "Time to stop using a server that does not respond (Default: 0 min)";
        type uint32 {
          range "1..1440";
        }
      }
      container timeout {
        description
          "Timeout configurations";
        leaf retransmit {
          description
            "Retransmission timeout (Default: 30 secs)";
          type uint16 {
            range "1..65535";
          }
        }
      }
      container bind {
        description
          "Bind information";
        leaf authenticate {
          description
            "Bind authentication parameters";
          type empty;
        }
        leaf root-dn {
          description
            "Bind root-dn";
          type empty;
        }
        leaf username {
          description
            "Username string";
          type string;
        }
        leaf password {
          description
            "Bind password";
          type empty;
        }
        leaf pass-type {
          type enumeration {
            enum "0";
            enum "6";
            enum "7";
          }
        }
        leaf pass-str {
          type string;
        }
      }
      container mode {
        description
          "Server mode";
        container secure {
          description
            "Secure mode. Default: non-secure";
          presence "true";
          leaf no-negotiation {
            type empty;
          }
        }
      }
      container search-type {
        description
          "ldap search type";
        leaf nested {
          description
            "Nested Search to get hierarchical nested user groups";
          type empty;
        }
      }
      container search-filter {
        description
          "Search Filter";
        list user-object-type {
          description
            "Add User Object to filter";
          key "name";
          leaf name {
            description
              "Object Class attribute name";
            type string;
          }
        }
      }
      container secure {
        description
          "Secure options";
        container cipher {
          description
            "To enable only specific ciphers. Default is all";
          leaf _3des-ede-cbc-sha {
            type empty;
          }
          leaf des-cbc-sha {
            type empty;
          }
          leaf null-md5 {
            type empty;
          }
          leaf rc4-128-md5 {
            type empty;
          }
          leaf rc4-128-sha {
            type empty;
          }
        }
        leaf trustpoint {
          description
            "Secure trustpoint for certificate";
          type string;
        }
      }
      container transport {
        description
          "Transport configurations";
        leaf port {
          description
            " Server listening port (Default: 389)";
          type uint16 {
            range "1..65535";
          }
        }
      }
    }
  }

  grouping lower-upper-case-grouping {
    leaf lu-case {
      type enumeration {
        enum "lower-case";
        enum "upper-case";
      }
    }
  }

  grouping config-radius-server-grouping {
    list attribute {
      description
        "Customize selected radius attributes";
      when "/ios:native/ios:aaa/ios-aaa:new-model";
      key "number";
      leaf number {
        type union {
          type uint32;
          type enumeration {
            enum "wireless";
          }
        }
      }
      leaf-list send-attribute {
        when "not(../number='wireless')";
        type enumeration {
          enum "on-for-login-auth";
          enum "include-in-access-req";
          enum "support-multiple";
        }
      }
      container access-request {
        description
          "Access-Request packet";
        when "../number = '25'";
        leaf include {
          description
            "Include attribute";
          type empty;
        }
      }
      container attri31 {
        description
          "Calling Station ID";
        when "../number = '31'";
        list attri31-list {
          key "calling-station-id";
          leaf calling-station-id {
            type enumeration {
              enum "mac";
              enum "send";
            }
          }
          container id-mac {
            description
              "Customize MAC address based Calling Station ID";
            when "../calling-station-id = 'mac'";
            leaf format {
              description
                "Specify format (default format ex: 0000.4096.3e4a)
                 ietf - format ex: 00-00-40-96-3E-4A";
              type enumeration {
                enum "ietf";
              }
            }
            uses lower-upper-case-grouping;
          }
          container id-send {
            when "../calling-station-id = 'send'";
            leaf nas-port-detail {
              type empty;
            }
            leaf mac-only {
              type empty;
            }
          }
        }
      }
      container wireless {
        description
          "Radius wireless attributes";
        when "../number='wireless'";
        container accounting {
          description
            "Radius accounting attributes";
          container nas-port-id {
            description
              "Radius Attribute 87";
            leaf exclude {
              description
                "don't send the nas port id in wireless accounting request";
              type empty;
            }
          }
          leaf username-case {
            description
              "Radius accounting username-case type";
            type short-lower-upper;
          }
          leaf username-delimiter {
            description
              "Radius accounting username delimiter type";
            type delimiter-option;
          }
          uses wireless-attribute-option-grouping;
        }
        container authentication {
          description
            "Radius authentication attributes";
          uses wireless-attribute-option-grouping;
        }
        container attr44 {
          description
            "Radius attribute 44(session id)";
          leaf attr44val {
            description
              "Radius attribute 44(session id) value";
            type enumeration {
              enum "44";
            }
          }
          leaf include-in-access-req {
            description
              "Send attribute 44 in access-req packet";
            type empty;
          }
        }
      }
    }
    container dead-criteria {
      description
        "Set the criteria used to decide when a radius server is marked dead";
      when "/ios:native/ios:aaa/ios-aaa:new-model";
      leaf time {
        description
          "The time during which no properly formed response must be received from the RADIUS server";
        type uint8 {
          range "1..120";
        }
        default "10";
      }
      leaf tries {
        description
          "The number of times the router must fail to receive a response from the radius server to mark it as dead";
        type uint8 {
          range "1..100";
        }
        default "10";
      }
    }
    leaf deadtime {
      description
        "Time to stop using a server that does not respond";
      when "/ios:native/ios:aaa/ios-aaa:new-model";
      type uint32 {
        range "1..1440";
      }
    }
    list host {
      description
        "Specify a RADIUS server";
      when "/ios:native/ios:aaa/ios-aaa:new-model";
      key "id";
      leaf id {
        type union {
          type string;
          type inet:ipv4-address;
        }
      }
      leaf auth-port {
        description
          "UDP port for RADIUS authentication server (default is 1645)";
        type uint16 {
          range "0..65535";
        }
      }
      leaf acct-port {
        description
          "UDP port for RADIUS accounting server (default is 1646)";
        type uint16 {
          range "0..65535";
        }
      }
      leaf retransmit {
        description
          "Specify the number of retries to active server";
        type uint8 {
          range "1..100";
        }
      }
      container test {
        description
          "Configure server automated testing";
        list username {
          description
            "A name (from local database) that should be used to send requests.";
          key "name";
          leaf name {
            type string;
          }
          container key {
            description
              "per-server encryption key (overrides default)";
            leaf encryption {
              description
                "0 - Specifies an UNENCRYPTED key will follow
                 7 - Specifies HIDDEN key will follow";
              type enumeration {
                enum "0";
                enum "7";
              }
            }
            leaf clear-key {
              type string;
            }
          }
        }
      }
      leaf timeout {
        description
          "Time to wait for a RADIUS server to reply (overrides default)";
        type uint16 {
          range "1..1000";
        }
      }
      leaf key {
        description
          "per-server encryption key (overrides default)";
        type union {
          type enumeration {
            enum "0";
            enum "7";
          }
          type string;
        }
      }
      leaf clear-key {
        when "../key = '0' or ../key = '7'";
        type string;
      }
    }
    container key {
      description
        "encryption key shared with the radius servers";
      when "/ios:native/ios:aaa/ios-aaa:new-model";
      leaf encryption {
        description
          "0 - Specifies an UNENCRYPTED key will follow
           6 - Specifies an ENCRYPTED key will follow
           7 - Specifies HIDDEN key will follow";
        type enumeration {
          enum "0";
          enum "6";
          enum "7";
        }
      }
      leaf clear-key {
        description
          "The UNENCRYPTED (cleartext) server key";
        type string;
      }
    }
    uses aaa-load-balance-grouping;
    leaf retransmit {
      description
        "Specify the number of retries to active server";
      when "/ios:native/ios:aaa/ios-aaa:new-model";
      type uint8 {
        range "1..100";
      }
    }
    container source-ports {
      description
        "source ports used for sending out RADIUS requests";
      when "/ios:native/ios:aaa/ios-aaa:new-model";
      leaf extended {
        description
          "Use 200 source-ports between 21645-21844";
        type empty;
      }
    }
    leaf timeout {
      description
        "Time to wait for a RADIUS server to reply";
      when "/ios:native/ios:aaa/ios-aaa:new-model";
      type uint16 {
        range "1..1000";
      }
    }
    container vsa {
      description
        "Vendor specific attribute configuration";
      when "/ios:native/ios:aaa/ios-aaa:new-model";
      container disallow {
        description
          "Forbid certain VSA behaviour";
        leaf unknown {
          description
            "Forbid unknown VSAs";
          type empty;
        }
      }
      container send {
        description
          "Send vendor-specific attributes in requests";
        presence "true";
        leaf accounting-only {
          description
            "Send in accounting requests";
          type boolean;
          default "true";
        }
        container accounting-settings {
          leaf threegpp2 {
            description
              "Send 3GPP2 VSAs in accounting requests";
            type empty;
          }
        }
        leaf authentication-only {
          description
            "Send in access requests";
          type boolean;
          default "true";
        }
        container authentication-settings {
          leaf threegpp2 {
            description
              "Send 3GPP2 VSAs in authentication requests";
            type empty;
          }
        }
        container cisco-nas-port {
          description
            "Send cisco-nas-port VSA(2)";
          presence "true";
          leaf threegpp2 {
            description
              "Send 3GPP2 VSAs in accounting requests";
            type empty;
          }
        }
        container accounting {
          status deprecated;
          description
            "Send in accounting requests";
          presence "true";
          leaf threegpp2 {
            status deprecated;
            description
              "Send 3GPP2 VSAs in accounting requests";
            type empty;
          }
        }
        container authentication {
          status deprecated;
          description
            "Send in access requests";
          presence "true";
          leaf threegpp2 {
            status deprecated;
            description
              "Send 3GPP2 VSAs in accounting requests";
            type empty;
          }
        }
      }
    }
  }

  grouping wireless-attribute-option-grouping {
    leaf call-station-id {
      type enumeration {
        enum "ap-ethmac-only";
        enum "ap-ethmac-ssid";
        enum "ap-group-name";
        enum "ap-label-address";
        enum "ap-label-address-ssid";
        enum "ap-location";
        enum "ap-macaddress";
        enum "ap-macaddress-ssid";
        enum "ap-name";
        enum "ap-name-ssid";
        enum "ipaddress";
        enum "macaddress";
        enum "site-tag-name";
        enum "vlan-id";
        enum "flex-profile-name";
        enum "policy-tag-name";
        enum "ap-macaddress-ssid-flexprofilename";
        enum "ap-macaddress-ssid-sitetagname";
        enum "ap-macaddress-ssid-policytagname";
        enum "ap-ethmac-ssid-flexprofilename";
        enum "ap-ethmac-ssid-sitetagname";
        enum "ap-ethmac-ssid-policytagname";
      }
    }
    leaf callStationIdCase {
      type short-lower-upper;
    }
    leaf mac-delimiter {
      type delimiter-option;
    }
  }

  grouping config-ip-radius-grouping {
    container radius {
      description
        "RADIUS configuration commands";
      container source-interface {
        description
          "Specify interface for source address in RADIUS packets";
        uses ios-ifc:interface-grouping;
        leaf vrf {
          description
            "VPN Routing/Forwarding parameters";
          type string;
        }
      }
    }
  }

  grouping config-tacacs-grouping {
    list server {
      description
        "Server configuration";
      when "/ios:native/ios:aaa/ios-aaa:new-model";
      key "name";
      leaf name {
        description
          "Name for the tacacs server configuration";
        type string;
      }
      container address {
        description
          "Specify ip address for tacacs server";
        choice tacacs-host-address {
          leaf ipv4 {
            description
              "IPv4 address or Hostname for tacacs server";
            type union {
              type inet:ipv4-address;
              type string;
            }
          }
          leaf ipv6 {
            description
              "IPv6 address or Hostname for tacacs server";
            type union {
              type inet:ipv6-address;
              type string;
            }
          }
          leaf fqdn {
            description
              "FQDN for server";
            type string;
          }
        }
      }
      leaf port {
        description
          "TCP port for TACACS+ server (default is 49)";
        default "49";
        type uint16 {
          range "1..65535";
        }
      }
      leaf timeout {
        description
          "Time to wait for this TACACS server to reply (overrides default)";
        type uint16 {
          range "1..1000";
        }
      }
      container key {
        description
          "per-server encryption key (overrides default)";
        leaf encryption {
          description
            "0 - Specifies an UNENCRYPTED key will follow
             7 - Specifies HIDDEN key will follow";
          type enumeration {
            enum "0";
            enum "7";
          }
        }
        leaf key {
          description
            "The UNENCRYPTED (cleartext) server key";
          type string {
            pattern ".*";
          }
        }
      }
    }
  }

  grouping config-tacacs-server-grouping {
    list host {
      status deprecated;
      description
        "Specify a TACACS server";
      key "name";
      leaf name {
        status deprecated;
        type ios-types:host-type;
      }
      leaf port {
        status deprecated;
        description
          "TCP port for TACACS+ server (default is 49)";
        type uint16 {
          range "1..65535";
        }
      }
      leaf key {
        status deprecated;
        description
          "Set TACACS+ encryption key.";
        type union {
          type enumeration {
            enum "0";
            enum "7";
          }
          type string;
        }
      }
      leaf encryption-key {
        status deprecated;
        when "../key = '0' or ../key = '7'";
        type string;
      }
      leaf timeout {
        status deprecated;
        description
          "Time to wait for this TACACS server to reply (overrides default)";
        type uint16 {
          range "1..1000";
        }
      }
    }
    leaf timeout {
      description
        "Time to wait for a TACACS server to reply";
      type uint16 {
        range "1..1000";
      }
    }
    container directed-request {
      description
        "Allow user to specify tacacs server to use with `@server'";
      presence "true";
      leaf restricted {
        description
          "restrict queries to directed request servers only";
        type empty;
      }
      leaf no-truncate {
        description
          "Do not truncate the @hostname from username.";
        type empty;
      }
    }
    container key {
      description
        "Set TACACS+ encryption key.";
      leaf encryption {
        description
          "0 - Specifies an UNENCRYPTED key will follow
           6 - Specifies an ENCRYPTED key will follow
           7 - Specifies HIDDEN key will follow";
        type enumeration {
          enum "0";
          enum "6";
          enum "7";
        }
      }
      leaf key {
        type string;
      }
    }
    container attribute {
      description
        "Customize selected tacacs attributes";
      container allow {
        description
          "Allow certain tacacs attribute behavior";
        leaf unknown {
          description
            "Unknown Tacacs+ attributes";
          type empty;
        }
      }
    }
  }

  grouping config-ip-tacacs-main-grouping {
    container source-interface {
      description
        "Specify interface for source address in TACACS packets";
      uses ios-ifc:interface-grouping;
    }
  }

  grouping config-ip-tacacs-grouping {
    container tacacs {
      description
        "TACACS configuration commands";
      container source-interface {
        description
          "Specify interface for source address in TACACS packets";
        uses ios-ifc:interface-grouping;
        leaf vrf {
          description
            "VPN Routing/Forwarding parameters";
          type string;
        }
      }
    }
  }

  augment "/ios:native/ios:aaa" {
    uses config-aaa-grouping;
  }
  augment "/ios:native/ios:radius" {
    uses config-radius-grouping;
  }
  augment "/ios:native/ios:ldap" {
    uses config-ldap-grouping;
  }
  augment "/ios:native/ios:radius-server" {
    uses config-radius-server-grouping;
  }
  augment "/ios:native/ios:ip" {
    uses config-ip-radius-grouping;
  }
  augment "/ios:native/ios:tacacs" {
    uses config-tacacs-grouping;
  }
  augment "/ios:native/ios:tacacs-server" {
    uses config-tacacs-server-grouping;
  }
  augment "/ios:native/ios:ip" {
    uses config-ip-tacacs-grouping;
  }
  augment "/ios:native/ios:username" {
    container aaa {
      description
        "AAA directive";
      container attribute {
        description
          "AAA attribute directive";
        leaf list {
          description
            "AAA attribute list";
          type leafref {
            path "/ios:native/ios:aaa/ios-aaa:attribute/ios-aaa:list/ios-aaa:name";
          }
        }
      }
    }
  }
}
