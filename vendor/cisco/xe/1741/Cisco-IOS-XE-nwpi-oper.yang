module Cisco-IOS-XE-nwpi-oper {
  yang-version 1;
  namespace "http://cisco.com/ns/yang/Cisco-IOS-XE-nwpi-oper";
  prefix Cisco-IOS-XE-nwpi-oper;

  import Cisco-IOS-XE-common-types {
    prefix common-types-ios-xe;
  }
  import Cisco-IOS-XE-nwpi-types {
    prefix Cisco-IOS-XE-nwpi-types;
  }
  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Network Wide Path Insight operational data.
     Copyright (c) 2020 by Cisco Systems, Inc.
     All rights reserved.";

  revision 2020-11-01 {
    description
      "Initial revision";
    reference "1.0.0";
    cisco-semver:module-version "1.0.0";
  }

  typedef nwpi-feature-type {
    type enumeration {
      enum "feature-without-policy" {
        value 0;
        description
          "Feature without policy configured";
      }
      enum "feature-with-policy" {
        value 1;
        description
          "Feature with policy configured";
      }
    }
    description
      "Feature type";
  }

  typedef nwpi-flow-dir {
    type enumeration {
      enum "flow-upstream" {
        value 0;
        description
          "Flow forwarding from first hop to last hop";
      }
      enum "flow-downstream" {
        value 1;
        description
          "Flow forwarding from last hop to first hop";
      }
    }
    description
      "Flow direction";
  }

  typedef nwpi-feature-dir {
    type enumeration {
      enum "feature-input" {
        value 0;
        description
          "Feature running on input side";
      }
      enum "feature-output" {
        value 1;
        description
          "Feature running on output side";
      }
    }
    description
      "Feature direction";
  }

  typedef nwpi-ms-category {
    type enumeration {
      enum "endpoint-default" {
        value 0;
        description
          "Default category";
      }
      enum "endpoint-allow" {
        value 1;
        description
          "Allow category";
      }
      enum "endpoint-optimize" {
        value 2;
        description
          "Optimize category";
      }
    }
    description
      "Microsoft Office 365 endpoint category";
  }

  typedef nwpi-flow-type {
    type enumeration {
      enum "flow-unicast" {
        value 0;
        description
          "Unicast flow";
      }
      enum "flow-multicast" {
        value 1;
        description
          "Multicast flow";
      }
    }
    description
      "Flow type";
  }

  typedef nwpi-nexthop-type {
    type enumeration {
      enum "nexthop-invalid" {
        value 0;
        description
          "Invalid nexthop";
      }
      enum "nexthop-local-consumed" {
        value 1;
        description
          "Local consumed";
      }
      enum "nexthop-sdwan-session" {
        value 2;
        description
          "SD-WAN session";
      }
      enum "nexthop-sdwan-session-tloc-extension" {
        value 3;
        description
          "SD-WAN session with TLOC extension";
      }
      enum "nexthop-service-lan" {
        value 4;
        description
          "Service LAN";
      }
      enum "nexthop-nat-dia" {
        value 5;
        description
          "NAT local breakout";
      }
      enum "nexthop-cxp" {
        value 6;
        description
          "SD-WAN cloud express";
      }
      enum "nexthop-sig-tunnel" {
        value 7;
        description
          "SD-WAN secure internet gateway";
      }
    }
    description
      "Nexthop type";
  }

  typedef nwpi-color-type {
    type enumeration {
      enum "color-invalid" {
        value 0;
        description
          "Invalid color";
      }
      enum "color-default" {
        value 1;
        description
          "Default color";
      }
      enum "color-mpls" {
        value 2;
        description
          "MPLS color";
      }
      enum "color-metro-ethernet" {
        value 3;
        description
          "Metro ethernet color";
      }
      enum "color-biz-internet" {
        value 4;
        description
          "Business internet color";
      }
      enum "color-public-internet" {
        value 5;
        description
          "Public internet color";
      }
      enum "color-lte" {
        value 6;
        description
          "LTE color";
      }
      enum "color-3g" {
        value 7;
        description
          "Third generation color";
      }
      enum "color-red" {
        value 8;
        description
          "Red color";
      }
      enum "color-green" {
        value 9;
        description
          "Green color";
      }
      enum "color-blue" {
        value 10;
        description
          "Blue color";
      }
      enum "color-gold" {
        value 11;
        description
          "Gold color";
      }
      enum "color-silver" {
        value 12;
        description
          "Silver color";
      }
      enum "color-bronze" {
        value 13;
        description
          "Bronze color";
      }
      enum "color-custom1" {
        value 14;
        description
          "Custom 1 color";
      }
      enum "color-custom2" {
        value 15;
        description
          "Custom 2 color";
      }
      enum "color-custom3" {
        value 16;
        description
          "Custom 3 color";
      }
      enum "color-private1" {
        value 17;
        description
          "Private 1 color";
      }
      enum "color-private2" {
        value 18;
        description
          "Private 2 color";
      }
      enum "color-private3" {
        value 19;
        description
          "Private 3 color";
      }
      enum "color-private4" {
        value 20;
        description
          "Private 4 color";
      }
      enum "color-private5" {
        value 21;
        description
          "Private 5 color";
      }
      enum "color-private6" {
        value 22;
        description
          "Private 6 color";
      }
    }
    description
      "SD-WAN color type";
  }

  typedef nwpi-encap-type {
    type enumeration {
      enum "nwpi-encap-none" {
        value 0;
        description
          "No encap";
      }
      enum "nwpi-encap-gre" {
        value 1;
        description
          "Generic routing encapsulation";
      }
      enum "nwpi-encap-ipsec" {
        value 2;
        description
          "IPSec";
      }
      enum "nwpi-encap-control" {
        value 3;
        description
          "Control";
      }
    }
    description
      "SD-WAN tunnel encap type";
  }

  typedef nwpi-stats-type {
    type enumeration {
      enum "stats-base" {
        value 0;
        description
          "Base statistics";
      }
      enum "stats-advanced" {
        value 1;
        description
          "Advanced statistics";
      }
    }
    description
      "Statistics type";
  }

  grouping nwpi-trace {
    description
      "Trace identifier, action and filters";
    leaf trace-id {
      type uint16 {
        range "1..65535";
      }
      description
        "Global unique trace identifier";
    }
    leaf action {
      type Cisco-IOS-XE-nwpi-types:nwpi-action-type;
      description
        "Trace start/stop/clean actions";
    }
    leaf target {
      when "(../action[.='action-start-trace' or .='action-stop-trace'])";
      type Cisco-IOS-XE-nwpi-types:nwpi-target-type;
      description
        "Target types";
    }
    leaf vpn-id {
      when "(../action[.='action-start-trace' or .= 'action-stop-trace']) and (../target = 'target-vpn-id')";
      type uint32 {
        range "0..65530";
      }
      description
        "SD-WAN VPN identifier";
    }
    leaf vrf-name {
      when "(../action[.='action-start-trace' or .= 'action-stop-trace']) and (../target = 'target-vrf-name')";
      type string;
      description
        "VRF name";
    }
    leaf src-ip {
      type inet:ip-address;
      description
        "Source IP to filter";
    }
    leaf dst-ip {
      type inet:ip-address;
      description
        "Destination IP to filter";
    }
    leaf app {
      type string;
      description
        "Application to filter";
    }
    leaf src-if {
      type string;
      description
        "Source interface to filter";
    }
    leaf protocol {
      type uint8;
      description
        "IP protocol field in IP header to filter";
    }
    leaf src-port {
      type uint16;
      description
        "Source port to filter";
    }
    leaf dst-port {
      type uint16;
      description
        "Destination port to filter";
    }
    leaf dscp-is-valid {
      type boolean;
      description
        "Indicate DSCP filter was configured";
    }
    leaf dscp {
      when "(../dscp-is-valid = 'true')";
      type uint8;
      description
        "DSCP value to filter";
    }
    leaf duration {
      type uint16;
      units "minutes";
      description
        "Trace remaining duration in minutes";
    }
  }

  grouping nwpi-feature-trace {
    description
      "Feature trace";
    leaf name {
      type string;
      description
        "Feature name";
    }
    leaf feature-type {
      type Cisco-IOS-XE-nwpi-oper:nwpi-feature-type;
      description
        "Feature type";
    }
    leaf dir {
      type Cisco-IOS-XE-nwpi-oper:nwpi-feature-dir;
      description
        "Feature direction";
    }
    leaf policy {
      type string;
      description
        "Policy name";
    }
  }

  grouping packet-key {
    description
      "Key to index packet record";
    leaf trace-id {
      type uint16;
      description
        "Trace identifier";
    }
    leaf packet-id {
      type uint32;
      description
        "Packet identifier";
    }
  }

  grouping nwpi-packet {
    description
      "Packet record";
    leaf hostname {
      type string;
      description
        "Hostname";
    }
    leaf system-ip {
      type inet:ip-address;
      description
        "SD-WAN system ip";
    }
    leaf flow-id {
      type uint16;
      description
        "Flow identifier";
    }
    leaf dir {
      type Cisco-IOS-XE-nwpi-oper:nwpi-flow-dir;
      description
        "Flow direction this packet belongs to";
    }
    leaf hop-idx {
      type uint8;
      description
        "Hop index of flow";
    }
    leaf app-recognized {
      type boolean;
      description
        "Application recognized or not";
    }
    list trace {
      description
        "List of feature traces";
      uses Cisco-IOS-XE-nwpi-oper:nwpi-feature-trace;
    }
  }

  grouping flow-key {
    description
      "Key to index flow record";
    leaf trace-id {
      type uint16;
      description
        "Trace identifier";
    }
    leaf flow-id {
      type uint16;
      description
        "Flow identifier";
    }
  }

  grouping nwpi-nexthop {
    description
      "Nexthop detail info";
    leaf nexthop-type {
      type Cisco-IOS-XE-nwpi-oper:nwpi-nexthop-type;
      description
        "Nexthop type";
    }
    leaf if-name {
      when "(../nexthop-type[.!='nexthop-local-consumed' and .!='nexthop-invalid'])";
      type string;
      description
        "Input or output interface name";
    }
    leaf local-color {
      when "(../nexthop-type[.='nexthop-sdwan-session' or .='nexthop-sdwan-session-tloc-extension' or .='nexthop-nat-dia'])";
      type Cisco-IOS-XE-nwpi-oper:nwpi-color-type;
      description
        "SD-WAN local color";
    }
    leaf remote-color {
      when "(../nexthop-type[.='nexthop-sdwan-session' or .='nexthop-sdwan-session-tloc-extension'])";
      type Cisco-IOS-XE-nwpi-oper:nwpi-color-type;
      description
        "SD-WAN remote color";
    }
    leaf encap {
      when "(../nexthop-type[.='nexthop-sdwan-session' or .='nexthop-sdwan-session-tloc-extension'])";
      type Cisco-IOS-XE-nwpi-oper:nwpi-encap-type;
      description
        "SD-WAN tunnel encap";
    }
    leaf remote-system-ip {
      when "(../nexthop-type[.='nexthop-sdwan-session' or .='nexthop-sdwan-session-tloc-extension'])";
      type inet:ip-address;
      description
        "SD-WAN remote peer system ip";
    }
  }

  grouping unicast-path {
    description
      "Network path info for unicast flows";
    leaf up-hop-idx {
      type uint8;
      description
        "Upstream hop index";
    }
    container up-ingress {
      description
        "Upstream ingress info";
      uses Cisco-IOS-XE-nwpi-oper:nwpi-nexthop;
    }
    container up-egress {
      description
        "Upstream egress info";
      uses Cisco-IOS-XE-nwpi-oper:nwpi-nexthop;
    }
    leaf down-hop-idx {
      type uint8;
      description
        "Downstream hop index";
    }
    container down-ingress {
      description
        "Downstream ingress info";
      uses Cisco-IOS-XE-nwpi-oper:nwpi-nexthop;
    }
    container down-egress {
      description
        "Downstream egress info";
      uses Cisco-IOS-XE-nwpi-oper:nwpi-nexthop;
    }
  }

  grouping nwpi-flow-metrics {
    description
      "Network metrics of a flow";
    leaf jitter-mean {
      type uint32;
      units "microseconds";
      description
        "Jitter mean value";
    }
    leaf delay-mean {
      type uint32;
      units "microseconds";
      description
        "Delay mean value";
    }
  }

  grouping nwpi-flow-base-stats {
    description
      "Basic statistics used in all cases";
    leaf total-pkts {
      type uint64;
      description
        "Total packets count";
    }
    leaf total-octets {
      type uint64;
      description
        "Total octets count";
    }
    leaf drop-pkts {
      type uint64;
      description
        "Drop packets count";
    }
    leaf drop-octets {
      type uint64;
      description
        "Drop octets count";
    }
  }

  grouping nwpi-flow-adv-stats {
    description
      "Advanced statistics only used in specific cases";
    leaf frag-pkts {
      type uint64;
      description
        "Fragment packets count";
    }
    leaf frag-octets {
      type uint64;
      description
        "Fragment octets count";
    }
    leaf punt-pkts {
      type uint64;
      description
        "Punt packets count";
    }
    leaf punt-octets {
      type uint64;
      description
        "Punt octets count";
    }
    leaf recycle-pkts {
      type uint64;
      description
        "Recycle packets count";
    }
    leaf recycle-octets {
      type uint64;
      description
        "Recycle octets count";
    }
    leaf repl-pkts {
      type uint64;
      description
        "Replicate packets count";
    }
    leaf repl-octets {
      type uint64;
      description
        "Replicate octets count";
    }
  }

  grouping nwpi-flow {
    description
      "Flow record";
    leaf hostname {
      type string;
      description
        "Hostname";
    }
    leaf system-ip {
      type inet:ip-address;
      description
        "SD-WAN system ip";
    }
    leaf src-ip {
      type inet:ip-address;
      description
        "Source IP";
    }
    leaf dst-ip {
      type inet:ip-address;
      description
        "Destination IP";
    }
    leaf src-port {
      type uint16;
      description
        "Source port";
    }
    leaf dst-port {
      type uint16;
      description
        "Destination port";
    }
    leaf protocol {
      type uint8;
      description
        "IP Protocol field in IP header";
    }
    leaf up-dscp {
      type uint8;
      description
        "Upstream DSCP";
    }
    leaf down-dscp {
      type uint8;
      description
        "Downstream DSCP";
    }
    leaf app-name {
      type string;
      description
        "Application name";
    }
    leaf app-group {
      type string;
      description
        "Application group";
    }
    leaf category {
      type Cisco-IOS-XE-nwpi-oper:nwpi-ms-category;
      description
        "Office 365 endpoint category";
    }
    leaf is-fin {
      type boolean;
      description
        "Is the flow in final state after aged out or trace stopped";
    }
    leaf flow-type {
      type Cisco-IOS-XE-nwpi-oper:nwpi-flow-type;
      description
        "Flow type";
    }
    list uni-path {
      when "(../flow-type = 'flow-unicast')";
      description
        "Unicast flow network path info";
      uses Cisco-IOS-XE-nwpi-oper:unicast-path;
    }
    leaf mcast-hop-idx {
      when "(../flow-type = 'flow-multicast')";
      type uint8;
      description
        "Multicast hop index";
    }
    container mcast-ingress {
      when "(../flow-type = 'flow-multicast')";
      description
        "Multicast ingress info";
      uses Cisco-IOS-XE-nwpi-oper:nwpi-nexthop;
    }
    list mcast-egress-nexthop {
      when "(../flow-type = 'flow-multicast')";
      description
        "Multicast egress info";
      uses Cisco-IOS-XE-nwpi-oper:nwpi-nexthop;
    }
    leaf asymmetry-detected {
      type boolean;
      description
        "Asymmetry routing detected or not";
    }
    leaf loop-detected {
      type boolean;
      description
        "Routing loop detected or not";
    }
    leaf-list up-pkt {
      type uint32;
      ordered-by user;
      description
        "Upstream packets belong to this flow";
    }
    leaf-list down-pkt {
      when "(../flow-type = 'flow-unicast')";
      type uint32;
      ordered-by user;
      description
        "Downstream packets belong to this flow";
    }
    leaf-list repl-pkt {
      when "(../flow-type = 'flow-multicast')";
      type uint32;
      ordered-by user;
      description
        "Multicast replicated packets belong to this flow";
    }
    container up-ingress-metrics {
      description
        "Upstream ingress metrics";
      uses Cisco-IOS-XE-nwpi-oper:nwpi-flow-metrics;
    }
    container down-ingress-metrics {
      when "(../flow-type = 'flow-unicast')";
      description
        "Downstream ingress metrics";
      uses Cisco-IOS-XE-nwpi-oper:nwpi-flow-metrics;
    }
    container up-local-metrics {
      description
        "Upstream local metrics";
      uses Cisco-IOS-XE-nwpi-oper:nwpi-flow-metrics;
    }
    container down-local-metrics {
      when "(../flow-type = 'flow-unicast')";
      description
        "Downstream local metrics";
      uses Cisco-IOS-XE-nwpi-oper:nwpi-flow-metrics;
    }
    container up-base-stats {
      description
        "Upstream base statistics";
      uses Cisco-IOS-XE-nwpi-oper:nwpi-flow-base-stats;
    }
    container down-base-stats {
      when "(../flow-type = 'flow-unicast')";
      description
        "Downstream base statistics";
      uses Cisco-IOS-XE-nwpi-oper:nwpi-flow-base-stats;
    }
    leaf stats-type {
      type Cisco-IOS-XE-nwpi-oper:nwpi-stats-type;
      description
        "Statistics type";
    }
    container up-adv-stats {
      when "(../stats-type = 'stats-advanced')";
      description
        "Upstream advanced statistics";
      uses Cisco-IOS-XE-nwpi-oper:nwpi-flow-adv-stats;
    }
    container down-adv-stats {
      when "(../flow-type = 'flow-unicast') and (../stats-type = 'stats-advanced')";
      description
        "Downstream advanced statistics";
      uses Cisco-IOS-XE-nwpi-oper:nwpi-flow-adv-stats;
    }
  }

  container nwpi-oper-data {
    config false;
    description
      "Network Wide Path Insight operational data";
    list location {
      key "fru slot bay chassis node";
      description
        "A list of data provider locations";
      uses common-types-ios-xe:extended-location;
      list nwpi-packet {
        key "trace-id packet-id";
        description
          "Network Wide Path Insight Packets";
        uses Cisco-IOS-XE-nwpi-oper:nwpi-packet;
        uses Cisco-IOS-XE-nwpi-oper:packet-key;
      }
      list nwpi-flow {
        key "trace-id flow-id";
        description
          "Network Wide Path Insight Flows";
        uses Cisco-IOS-XE-nwpi-oper:nwpi-flow;
        uses Cisco-IOS-XE-nwpi-oper:flow-key;
      }
      list nwpi-trace {
        key "trace-id";
        description
          "Network Wide Path Insight Traces";
        uses Cisco-IOS-XE-nwpi-oper:nwpi-trace;
      }
    }
  }
}
