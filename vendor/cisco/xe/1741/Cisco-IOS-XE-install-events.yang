module Cisco-IOS-XE-install-events {
  yang-version 1;
  namespace "http://cisco.com/ns/yang/Cisco-IOS-XE-install-events";
  prefix install-ios-xe-events;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for install status notification for image install events.
     Copyright (c) 2019-2020 by Cisco Systems, Inc.
     All rights reserved.";

  revision 2020-11-01 {
    description
      "Added AP image predownload sub-states notification";
    reference "2.1.0";
    cisco-semver:module-version "2.1.0";
  }
  revision 2020-07-01 {
    description
      "- Added enum values for installation sub-states
       - Remove unused empty container install-events";
    reference "2.0.0";
    cisco-semver:module-version "2.0.0";
  }
  revision 2020-03-01 {
    description
      "Initial revision";
    reference "1.0.0";
    cisco-semver:module-version "1.0.0";
  }

  typedef installation-status {
    type enumeration {
      enum "download-start" {
        value 0;
        description
          "Download Start";
      }
      enum "download-complete" {
        value 1;
        description
          "Download Complete";
      }
      enum "verification-complete" {
        value 2;
        description
          "Verification Complete";
      }
      enum "upgrade-apply-complete" {
        value 3;
        description
          "Upgrade Apply Complete";
      }
      enum "sync-partition-start" {
        value 4;
        description
          "Sync Partition Start";
      }
      enum "sync-partition-complete" {
        value 5;
        description
          "Sync Partition Start";
      }
      enum "install-complete" {
        value 6;
        description
          "Install Complete";
      }
      enum "install-fail" {
        value 7;
        description
          "Install Fail";
      }
      enum "reboot" {
        value 8;
        description
          "Reboot";
      }
      enum "install-start" {
        value 9;
        description
          "Install Start";
      }
      enum "uninstall-complete" {
        value 10;
        description
          "Uninstall Complete";
      }
      enum "uninstall-fail" {
        value 11;
        description
          "Uninstall Fail";
      }
      enum "reset-complete" {
        value 12;
        description
          "Reset Complete";
      }
      enum "reset-fail" {
        value 13;
        description
          "Reset Fail";
      }
      enum "config-commit-confirm-complete" {
        value 14;
        description
          "Confirmation for configuration commit complete";
      }
      enum "config-commit-confirm-fail" {
        value 15;
        description
          "Confirmation for configuration commit fail";
      }
      enum "rollback-complete" {
        value 16;
        description
          "Rollback Complete";
      }
      enum "rollback-fail" {
        value 17;
        description
          "Rollback Fail";
      }
      enum "download-fail" {
        value 18;
        description
          "Download Fail";
      }
      enum "download-success" {
        value 19;
        description
          "Download Success";
      }
    }
    description
      "Installation Status";
  }

  typedef install-sub-state {
    type enumeration {
      enum "none" {
        value 0;
        description
          "None or not applicable";
      }
      enum "install-adding-pkg" {
        value 1;
        description
          "Install add package in progress";
      }
      enum "install-expanding-pkg" {
        value 2;
        description
          "Install expand package in progress";
      }
      enum "install-expand-pkg-done" {
        value 3;
        description
          "Install completes successful expand package";
      }
      enum "install-activating-pkg" {
        value 4;
        description
          "Activating package in progress";
      }
      enum "install-activate-dev-boot" {
        value 5;
        description
          "Activate or deactivate complete and starting device boot";
      }
      enum "install-error-msg" {
        value 6;
        description
          "Action failed error";
      }
      enum "install-oper-invoked" {
        value 7;
        description
          "Operation is invoked in install infra for the action";
      }
      enum "install-inprogress" {
        value 8;
        description
          "Operation is in progress";
      }
      enum "install-ewc-predwnld-none" {
        value 9;
        description
          "Predownload for Embedded Wireless Controller not started";
      }
      enum "install-ewc-ctrl-img-dwnld-initiated" {
        value 10;
        description
          "Embedded Wireless Controller - Controller image download initiated";
      }
      enum "install-ewc-ctrl-img-dwnld-in-progress" {
        value 11;
        description
          "Embedded Wireless Controller - Controller image download in progress";
      }
      enum "install-ewc-ctrl-img-dwnld-completed" {
        value 12;
        description
          "Embedded Wireless Controller - Controller image download completed";
      }
      enum "install-ewc-ctrl-img-dwnld-failed" {
        value 13;
        description
          "Embedded Wireless Controller - Controller image download failed";
      }
      enum "install-ewc-ap-img-predwnld-initiated" {
        value 14;
        description
          "Embedded Wireless Controller - AP image predownload initiated";
      }
      enum "install-ewc-ap-img-predwnld-in-progress" {
        value 15;
        description
          "Embedded Wireless Controller - AP image predownload in progress";
      }
      enum "install-ewc-ap-img-predwnld-completed" {
        value 16;
        description
          "Embedded Wireless Controller - AP image predownload completed";
      }
      enum "install-ewc-ap-img-predwnld-not-supported" {
        value 17;
        description
          "Embedded Wireless Controller - AP image predownload not supported";
      }
      enum "install-ewc-ap-img-predwnld-failed" {
        value 18;
        description
          "Embedded Wireless Controller - AP image predownload failed";
      }
      enum "install-ewc-ctrl-img-predwnld-in-progress" {
        value 19;
        description
          "Embedded Wireless Controller - Controller image predownload in progress";
      }
      enum "install-ewc-ctrl-img-predwnld-completed" {
        value 20;
        description
          "Embedded Wireless Controller - Controller image predownload completed";
      }
      enum "install-ewc-ctrl-img-predwnld-failed" {
        value 21;
        description
          "Embedded Wireless Controller - Controller image predownload failed";
      }
      enum "install-ewc-activated" {
        value 22;
        description
          "Embedded Wireless Controller - install activate successful";
      }
      enum "install-ewc-activate-failed" {
        value 23;
        description
          "Embedded Wireless Controller - install activate failed";
      }
      enum "install-status-bundle-boot-error" {
        value 24;
        description
          "Install is not allowed in bundle boot use one shot install";
      }
      enum "install-status-invalid-image-file" {
        value 25;
        description
          "RPC action failed because either image file specified is not present or invalid";
      }
      enum "install-earlier-added-image-present" {
        value 26;
        description
          "Install action detected image already installed on device with same version waiting for
           activation. Either remove this earlier installed image to install new image or use
           activate RPC action to proceed image activation";
      }
      enum "install-activate-trigg-without-add" {
        value 27;
        description
          "Activate image is triggered before image is installed on device.
           Use install RPC to install image and trigger activate on device";
      }
      enum "install-status-no-trans-to-commit" {
        value 28;
        description
          "Commit action could not find any activate transaction to commit. Either activate
           installed image first or remove installed image to start fresh Workflow";
      }
      enum "install-status-activate-pend-commit" {
        value 29;
        description
          "Rollback to base is not allowed while image is pending commit. Either use abort action to abort
           activated image transaction or use install rollback action to commit to go back to previous image";
      }
      enum "install-status-nothing-to-rollback" {
        value 30;
        description
          "No Rollback points present from the current image to rollback";
      }
      enum "install-status-already-at-base" {
        value 31;
        description
          "Rollback to base is not required as device is already at the base image";
      }
      enum "install-remove-rejected-by-platform" {
        value 32;
        description
          "Remove of the file is not allowed currently. The file is likely in use at this moment. Retry again";
      }
      enum "install-status-no-trans-to-abort" {
        value 33;
        description
          "There is no activate or deactivate operation detected on device that needs to be aborted.";
      }
      enum "install-status-no-platform-response" {
        value 34;
        description
          "Action failed due to no response from other platform or access device.
           Please check device operation status";
      }
      enum "install-rem-of-activated-img-reject" {
        value 35;
        description
          "Install remove can not remove activated image. Please use install commit
           to commit activated image.";
      }
      enum "install-ap-img-predwnld-initiated" {
        value 36;
        description
          "AP Image Predownload Initiated";
      }
      enum "install-ap-img-predwnld-inprogress" {
        value 37;
        description
          "AP Image Predownload is In progress";
      }
      enum "install-ap-img-predwnld-complete" {
        value 38;
        description
          "AP Image Predownload Completed";
      }
      enum "install-ap-img-predwnld-failed" {
        value 39;
        description
          "AP Image Predownload Failed";
      }
      enum "install-ap-img-predwnld-abort" {
        value 40;
        description
          "AP Image Predownload Aborted";
      }
    }
    description
      "Install sub state provides the intermediate sub state status during
       install and activate operations. This helps to see the progress during 
       long waiting install action operation.";
  }

  typedef install-action {
    type enumeration {
      enum "install" {
        value 0;
        description
          "Install action type";
      }
      enum "activate" {
        value 1;
        description
          "Activate action type";
      }
      enum "install-commit" {
        value 2;
        description
          "Commit action type";
      }
      enum "rollback" {
        value 3;
        description
          "Rollback action type";
      }
      enum "deactivate" {
        value 4;
        description
          "Deactivate action type";
      }
      enum "remove" {
        value 5;
        description
          "Remove action type";
      }
      enum "auto-abort-timer" {
        value 6;
        description
          "Auto abort timer action type";
      }
      enum "abort" {
        value 7;
        description
          "Abort action type";
      }
    }
    description
      "Install action type";
  }

  grouping common-notification-header {
    description
      "Install notification header";
    leaf host-name {
      type string;
      description
        "Host name";
    }
  }

  grouping install-notification-fields {
    description
      "Install operation state";
    leaf status {
      type install-ios-xe-events:installation-status;
      description
        "Installation status";
    }
    leaf action-type {
      type install-ios-xe-events:install-action;
      description
        "Action type";
    }
    leaf sub-state {
      type install-ios-xe-events:install-sub-state;
      description
        "Intermediate sub state of install status";
    }
    leaf uuid {
      type string;
      description
        "Universally unique identifier 128-bit number UUID is received from action rpc";
    }
    leaf percentage-completed {
      type int8;
      units "percent";
      description
        "Percent of completion for in-progress installations.
         If the value is -1, the field is not applicable";
    }
  }

  notification install-status {
    description
      "install status notification";
    uses install-ios-xe-events:common-notification-header;
    uses install-ios-xe-events:install-notification-fields;
  }
}
