module Cisco-IOS-XE-digital-io-oper {
  yang-version 1;
  namespace "http://cisco.com/ns/yang/Cisco-IOS-XE-digital-io-oper";
  prefix digital-io-ios-xe-oper;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Digital Input and Output port operational data.
     Copyright (c) 2020 by Cisco Systems, Inc.
     All rights reserved.";

  revision 2020-07-01 {
    description
      "Initial revision";
    reference "1.0.0";
    cisco-semver:module-version "1.0.0";
  }

  typedef dio-port-severity {
    type enumeration {
      enum "port-severity-none" {
        value 0;
        description
          "Port Severity None";
      }
      enum "port-severity-critical" {
        value 1;
        description
          "Port Severity Critical";
      }
      enum "port-severity-major" {
        value 2;
        description
          "Port Severity Major";
      }
      enum "port-severity-minor" {
        value 3;
        description
          "Port Severity Minor";
      }
      enum "port-severity-info" {
        value 4;
        description
          "Port Severity Informational";
      }
    }
    description
      "Port Severity";
  }

  typedef dio-port-state {
    type enumeration {
      enum "port-state-closed" {
        value 0;
        description
          "Port State Closed";
      }
      enum "port-state-open" {
        value 1;
        description
          "Port State Open";
      }
    }
    description
      "Port State";
  }

  typedef dio-port-status {
    type enumeration {
      enum "port-status-not-triggered" {
        value 0;
        description
          "Port Status Not Triggered";
      }
      enum "port-status-triggered" {
        value 1;
        description
          "Port Status Triggered";
      }
    }
    description
      "Port Status";
  }

  typedef dio-port-mode {
    type enumeration {
      enum "port-mode-input" {
        value 0;
        description
          "Port Mode Input";
      }
      enum "port-mode-output" {
        value 1;
        description
          "Port Mode Output";
      }
      enum "port-mode-output-relay-temp" {
        value 2;
        description
          "Port Mode Output Relay Temperature";
      }
      enum "port-mode-output-relay-input" {
        value 3;
        description
          "Port Mode Output Relay Input";
      }
    }
    description
      "Port Mode";
  }

  typedef dio-port-application {
    type enumeration {
      enum "port-app-dry" {
        value 0;
        description
          "Port Application Dry";
      }
      enum "port-app-wet" {
        value 1;
        description
          "Port Application Wet";
      }
    }
    description
      "Port Application";
  }

  typedef dio-port-output-source {
    type enumeration {
      enum "port-out-src-input0" {
        value 0;
        description
          "Port Output Source Input 0";
      }
      enum "port-out-src-input1" {
        value 1;
        description
          "Port Output Source Input 1";
      }
      enum "port-out-src-input2" {
        value 2;
        description
          "Port Output Source Input 2";
      }
      enum "port-out-src-input3" {
        value 3;
        description
          "Port Output Source Input 3";
      }
      enum "port-out-src-input4" {
        value 4;
        description
          "Port Output Source Input 4";
      }
      enum "port-out-src-temp-minor" {
        value 5;
        description
          "Port Output Source Temperature Minor";
      }
      enum "port-out-src-temp-major" {
        value 6;
        description
          "Port Output Source Temperature Major";
      }
      enum "port-out-src-temp-critical" {
        value 7;
        description
          "Port Output Source Temperature Critical";
      }
    }
    description
      "Port Output Source";
  }

  grouping digital-io-port {
    description
      "Digital IO port";
    leaf port-num {
      type uint16;
      description
        "Port number";
    }
    leaf attached-to-iox {
      type boolean;
      description
        "Attached to IOX";
    }
    leaf enabled {
      type boolean;
      description
        "Enabled";
    }
    leaf desc {
      type string;
      description
        "Description";
    }
    leaf severity {
      type digital-io-ios-xe-oper:dio-port-severity;
      description
        "Severity";
    }
    leaf port-value {
      type uint16;
      description
        "Port value";
    }
    leaf trigger {
      type digital-io-ios-xe-oper:dio-port-state;
      description
        "Trigger";
    }
    leaf status {
      type digital-io-ios-xe-oper:dio-port-status;
      description
        "Port status";
    }
    leaf mode {
      type digital-io-ios-xe-oper:dio-port-mode;
      description
        "Port mode";
    }
    leaf app {
      type digital-io-ios-xe-oper:dio-port-application;
      description
        "Application";
    }
    leaf source {
      type digital-io-ios-xe-oper:dio-port-output-source;
      description
        "Output source";
    }
    leaf voltage {
      type uint16;
      units "millivolts";
      description
        "Voltage";
    }
    leaf threshold {
      type uint16;
      units "millivolts";
      description
        "Threshold";
    }
  }

  container digital-io-oper-data {
    config false;
    description
      "Operational state of Digital IO";
    list digital-io-port {
      key "port-num";
      description
        "Digital IO port";
      uses digital-io-ios-xe-oper:digital-io-port;
    }
  }
}
