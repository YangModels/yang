submodule Cisco-IOS-XE-platform-rpc {
  belongs-to Cisco-IOS-XE-rpc {
    prefix ios-xe-rpc;
  }

  import ietf-inet-types {
    prefix inet;
  }
  import Cisco-IOS-XE-types {
    prefix ios-types;
  }
  import cisco-semver {
    prefix cisco-semver;
  }
  include Cisco-IOS-XE-crypto-rpc;
  include Cisco-IOS-XE-multicast-rpc;

  organization
    "Cisco Systems";
  contact
    "<mailto:cs-yang@cisco.com>";
  description
    "NED Platform RPC YANG module for IOS
     Copyright (c) 2016-2020 by Cisco Systems, Inc.
     All rights reserved.";

  revision 2020-07-01 {
    description
      "Added multicast feature RPC";
    cisco-semver:module-version "3.0.0";
  }
  revision 2019-11-01 {
    description
      "Added new packet tracing RPC";
    cisco-semver:module-version "2.0.0";
  }
  revision 2019-07-01 {
    description
      "Establish semantic version baseline";
    cisco-semver:module-version "1.0.0";
  }
  revision 2018-12-06 {
    description
      "created for NED RPC modularisation";
  }

  grouping clear-choice-platform-case-grouping {
    container platform {
      description
        "Clear platform information";
      choice platform-choice {
        case condition-case {
          description
            "Clear conditional debug and packet-trace configuration and data";
          container condition {
            leaf all {
              description
                "Clear all config and data";
              type empty;
            }
          }
        }
        case packet-trace-case {
          description
            "Clear packet-trace configuration and data";
          container packet-trace {
            choice packet-trace-choice {
              case configuration-case {
                leaf configuration {
                  description
                    "Clear packet-trace configuration";
                  type empty;
                }
              }
              case statistics-case {
                leaf statistics {
                  description
                    "Clear packet-trace statistics";
                  type empty;
                }
              }
            }
          }
        }
        case hardware-case {
          container hardware {
            description
              "Clear platform hardware information";
            container qfp {
              description
                "Quantum Flow Processor";
              container active {
                description
                  "Active instance";
                container feature {
                  description
                    "Clear features";
                  choice feature-choice;
                }
              }
            }
          }
        }
      }
    }
  }

  grouping direction-grouping {
    choice direction-choice {
      case both-case {
        leaf both {
          description
            "Simultaneous ingress and egress debug";
          type empty;
        }
      }
      case ingress-case {
        leaf ingress {
          description
            "Ingress only debug";
          type empty;
        }
      }
      case engress-case {
        leaf egress {
          description
            "Egress only debug";
          type empty;
        }
      }
    }
  }

  grouping ipv4-src-dst-addr-grouping {
    choice source-choice {
      case ipv4-prefix-case {
        leaf src-ipv4-address-drop-node-name {
          type string;
        }
      }
      case any-case {
        leaf any {
          description
            "Any source host";
          type empty;
        }
      }
      case host-case {
        leaf host {
          description
            "A single source host";
          type ios-types:ipv4-host;
        }
      }
    }
    container dst-addr-drop-node-name {
      choice destination-choice {
        case ipv4-prefix-case {
          leaf dest-ipv4-address-drop-node-name {
            type string;
          }
        }
        case any-case {
          leaf any {
            description
              "Any destination host";
            type empty;
          }
        }
        case host-case {
          leaf host {
            description
              "A single destination host";
            type ios-types:ipv4-host;
          }
        }
      }
    }
  }

  grouping ipv4-src-dst-addr-port-grouping {
    choice source-choice {
      case ipv4-prefix-case {
        leaf src-ipv4-address-drop-node-name {
          type string;
        }
      }
      case any-case {
        leaf any {
          description
            "Any source host";
          type empty;
        }
      }
      case host-case {
        leaf host {
          description
            "A single source host";
          type ios-types:ipv4-host;
        }
      }
    }
    choice src-port-choice {
      case src-eq-case {
        leaf eq {
          description
            "Match only packets on a given port number up to 10 ports";
          type inet:port-number;
        }
      }
      case src-gt-case {
        leaf gt {
          description
            "Match only packets with a greater port number";
          type inet:port-number;
        }
      }
      case src-lt-case {
        leaf lt {
          description
            "Match only packets with a lower port number";
          type inet:port-number;
        }
      }
      case src-neq-case {
        leaf neq {
          description
            "Match only packets not on a given port number up to 10 ports";
          type inet:port-number;
        }
      }
      case src-range-case {
        leaf range {
          description
            "Match only packets in the range of port numbers";
          type inet:port-number;
        }
        leaf src-range2-drop-node-name {
          description
            "Match only packets in the range of port numbers";
          type inet:port-number;
        }
      }
    }
    container dst-addr-port-drop-node-name {
      choice destination-choice {
        case ipv4-prefix-case {
          leaf dest-ipv4-address-drop-node-name {
            type string;
          }
        }
        case any-case {
          leaf any {
            description
              "Any destination host";
            type empty;
          }
        }
        case host-case {
          leaf host {
            description
              "A single destination host";
            type ios-types:ipv4-host;
          }
        }
      }
      choice dst-port-choice {
        case dst-eq-case {
          leaf eq {
            description
              "Match only packets on a given port number up to 10 ports";
            type inet:port-number;
          }
        }
        case dst-gt-case {
          leaf gt {
            description
              "Match only packets with a greater port number";
            type inet:port-number;
          }
        }
        case dst-lt-case {
          leaf lt {
            description
              "Match only packets with a lower port number";
            type inet:port-number;
          }
        }
        case dst-neq-case {
          leaf neq {
            description
              "Match only packets not on a given port number up to 10 ports";
            type inet:port-number;
          }
        }
        case dst-range-case {
          leaf range {
            description
              "Match only packets in the range of port numbers";
            type inet:port-number;
          }
          leaf dst-range2-drop-node-name {
            description
              "Match only packets in the range of port numbers";
            type inet:port-number;
          }
        }
      }
    }
  }

  grouping ipv6-src-dst-addr-grouping {
    choice source-choice {
      case prefix-case {
        leaf source-prefix-drop-node-name {
          type ios-types:ipv6-prefix;
        }
      }
      case any-case {
        leaf any {
          type empty;
        }
      }
      case host-case {
        leaf host {
          type ios-types:ip-host;
        }
      }
    }
    container dst-addr-drop-node-name {
      choice destination-choice {
        case prefix-case {
          leaf destination-prefix-drop-node-name {
            type ios-types:ipv6-prefix;
          }
        }
        case any-case {
          leaf any {
            type empty;
          }
        }
        case host-case {
          leaf host {
            type ios-types:ip-host;
          }
        }
      }
    }
  }

  grouping ipv6-src-dst-addr-port-grouping {
    choice source-choice {
      case prefix-case {
        leaf source-prefix-drop-node-name {
          type ios-types:ipv6-prefix;
        }
      }
      case any-case {
        leaf any {
          type empty;
        }
      }
      case host-case {
        leaf host {
          type ios-types:ip-host;
        }
      }
    }
    choice src-port-choice {
      case src-eq-case {
        leaf eq {
          description
            "Match only packets on a given port number";
          type inet:port-number;
        }
      }
      case src-gt-case {
        leaf gt {
          description
            "Match only packets with a greater port number";
          type inet:port-number;
        }
      }
      case src-lt-case {
        leaf lt {
          description
            "Match only packets with a lower port number";
          type inet:port-number;
        }
      }
      case src-neq-case {
        leaf neq {
          description
            "Match only packets not on a given port number";
          type inet:port-number;
        }
      }
      case src-range-case {
        leaf range {
          description
            "Match only packets in the range of port numbers";
          type inet:port-number;
        }
        leaf src-range2-drop-node-name {
          description
            "Match only packets in the range of port numbers";
          type inet:port-number;
        }
      }
    }
    container dst-addr-port-drop-node-name {
      choice destination-choice {
        case prefix-case {
          leaf destination-prefix-drop-node-name {
            type ios-types:ipv6-prefix;
          }
        }
        case any-case {
          leaf any {
            type empty;
          }
        }
        case host-case {
          leaf host {
            type ios-types:ip-host;
          }
        }
      }
      choice dst-port-choice {
        case dst-eq-case {
          leaf eq {
            description
              "Match only packets on a given port number";
            type inet:port-number;
          }
        }
        case dst-gt-case {
          leaf gt {
            description
              "Match only packets with a greater port number";
            type inet:port-number;
          }
        }
        case dst-lt-case {
          leaf lt {
            description
              "Match only packets with a lower port number";
            type inet:port-number;
          }
        }
        case dst-neq-case {
          leaf neq {
            description
              "Match only packets not on a given port number";
            type inet:port-number;
          }
        }
        case dst-range-case {
          leaf range {
            description
              "Match only packets in the range of port numbers";
            type inet:port-number;
          }
          leaf dst-range2-drop-node-name {
            description
              "Match only packets in the range of port numbers";
            type inet:port-number;
          }
        }
      }
    }
  }

  grouping condition-application-grouping {
    description
      "Debug Application conditions";
    leaf app-name-drop-node-name {
      description
        "Application name";
      mandatory true;
      type string;
    }
    uses direction-grouping;
  }

  grouping condition-mpls-grouping {
    description
      "Debug MPLS conditions";
    choice mpls-choice {
      case label-case {
        container label-drop-node-name {
          leaf label-id-drop-node-name {
            description
              "MPLS label id";
            mandatory true;
            type uint32 {
              range "0..1048575";
            }
          }
          leaf depth-drop-node-name {
            description
              "Depth of specified MPLS label, 1 for top label";
            type uint8 {
              range "0..127";
            }
          }
          leaf application {
            description
              "Debug Application conditions";
            type string;
          }
          uses direction-grouping;
        }
      }
      case application-case {
        container application {
          uses condition-application-grouping;
        }
      }
      case direction-case {
        uses direction-grouping;
      }
    }
  }

  grouping condition-ipv4-grouping {
    description
      "Debug IPV4 conditions";
    choice ipv4-choice {
      case direction-case {
        uses direction-grouping;
      }
      case ipv4addr-case {
        container ipv4addr-drop-node-name {
          leaf ip-addr-drop-node-name {
            description
              "IPv4 address A.B.C.D/nn";
            type string;
            mandatory true;
          }
          choice ipv4addr-choice {
            case application-case {
              container application {
                uses condition-application-grouping;
              }
            }
            case direction-case {
              uses direction-grouping;
            }
          }
        }
      }
      case access-list-case {
        description
          "Set acl for conditional debug";
        container access-list {
          leaf acl-name-drop-node-name {
            description
              "ACL name";
            type string;
            mandatory true;
          }
          uses direction-grouping;
        }
      }
    }
  }

  grouping condition-ipv6-grouping {
    description
      "Debug IPV6 conditions";
    choice ipv6-choice {
      case direction-case {
        uses direction-grouping;
      }
      case ipv6addr-case {
        container ipv6addr-drop-node-name {
          leaf ip-addr-drop-node-name {
            description
              "IPv6 address X:X:X:X::X/<0-128>";
            type string;
            mandatory true;
          }
          choice ipv6addr-choice {
            case application-case {
              container application {
                uses condition-application-grouping;
              }
            }
            case direction-case {
              uses direction-grouping;
            }
          }
        }
      }
      case access-list-case {
        description
          "Set acl for conditional debug";
        container access-list {
          leaf acl-name-drop-node-name {
            description
              "ACL name";
            type string;
            mandatory true;
          }
          uses direction-grouping;
        }
      }
    }
  }

  grouping condition-match-grouping {
    description
      "Describe inline acl filters";
    choice match-choice {
      case ipv4-case {
        description
          "Debug IPv4 conditions";
        container ipv4 {
          choice ipv4-choice {
            case protocol-case {
              container protocol {
                description
                  "Protocols";
                choice protocol-choice {
                  case icmp-case {
                    description
                      "Filter by ICMP protocol";
                    container icmp {
                      uses ipv4-src-dst-addr-grouping;
                      uses direction-grouping;
                    }
                  }
                  case tcp-case {
                    description
                      "Filter by TCP protocol";
                    container tcp {
                      uses ipv4-src-dst-addr-port-grouping;
                      uses direction-grouping;
                    }
                  }
                  case udp-case {
                    description
                      "Filter by UDP protocol";
                    container udp {
                      uses ipv4-src-dst-addr-port-grouping;
                      uses direction-grouping;
                    }
                  }
                  case proto-num-case {
                    description
                      "Filter by protocol number";
                    container proto-num-drop-node-name {
                      leaf protonum-drop-node-name {
                        description
                          "An IP protocol number<0-255>";
                        type uint8 {
                          range "0..255";
                        }
                        mandatory true;
                      }
                      uses ipv4-src-dst-addr-grouping;
                      uses direction-grouping;
                    }
                  }
                }
              }
            }
            case ipv4addr-case {
              container ipv4-addr-drop-node-name {
                uses ipv4-src-dst-addr-grouping;
                uses direction-grouping;
              }
            }
          }
        }
      }
      case ipv6-case {
        description
          "Debug IPv6 conditions";
        container ipv6 {
          choice ipv6-choice {
            case protocol-case {
              container protocol {
                description
                  "Protocols";
                choice protocol-choice {
                  case icmp-case {
                    description
                      "Filter by ICMP protocol";
                    container icmp {
                      uses ipv6-src-dst-addr-grouping;
                      uses direction-grouping;
                    }
                  }
                  case tcp-case {
                    description
                      "Filter by TCP protocol";
                    container tcp {
                      uses ipv6-src-dst-addr-port-grouping;
                      uses direction-grouping;
                    }
                  }
                  case udp-case {
                    description
                      "Filter by UDP protocol";
                    container udp {
                      uses ipv6-src-dst-addr-port-grouping;
                      uses direction-grouping;
                    }
                  }
                  case proto-num-case {
                    description
                      "Filter by protocol number";
                    container proto-num-drop-node-name {
                      leaf protonum-drop-node-name {
                        description
                          "An IP protocol number<0-255>";
                        type uint8 {
                          range "0..255";
                        }
                        mandatory true;
                      }
                      uses ipv6-src-dst-addr-grouping;
                      uses direction-grouping;
                    }
                  }
                }
              }
            }
            case ipv6addr-case {
              container ipv6-addr-drop-node-name {
                uses ipv6-src-dst-addr-grouping;
                uses direction-grouping;
              }
            }
          }
        }
      }
    }
  }

  grouping condition-interface-grouping {
    description
      "Set interface for conditional debug";
    leaf interface-name-drop-node-name {
      description
        "interface name";
      type string;
      mandatory true;
    }
    choice interface-choice {
      case direction-case {
        uses direction-grouping;
      }
      case application-case {
        container application {
          uses condition-application-grouping;
        }
      }
      case ipv4-case {
        container ipv4 {
          uses condition-ipv4-grouping;
        }
      }
      case ipv6-case {
        container ipv6 {
          uses condition-ipv6-grouping;
        }
      }
      case match-case {
        container match {
          uses condition-match-grouping;
        }
      }
      case mpls-case {
        container mpls {
          uses condition-mpls-grouping;
        }
      }
    }
  }

  grouping packet-trace-grouping {
    description
      "Debug packet trace";
    choice packet-trace-choice {
      case statistics-case {
        leaf statistics {
          description
            "Enable packet trace statistics";
          type empty;
        }
      }
      case drop-case {
        container drop {
          description
            "Trace drops only";
          presence "true";
          leaf code {
            description
              "Trace specific drop code value <0-65534>";
            type uint16 {
              range "0..65534";
            }
          }
        }
      }
      case inject-case {
        container inject {
          description
            "Trace injects only";
          presence "true";
          leaf code {
            description
              "Trace specific inject code value <0-65534>";
            type uint16 {
              range "0..65534";
            }
          }
        }
      }
      case punt-case {
        container punt {
          description
            "Trace punt only";
          presence "true";
          leaf code {
            description
              "Trace specific punt code value <0-65534>";
            type uint16 {
              range "0..65534";
            }
          }
        }
      }
      case packet-case {
        container packet {
          description
            "Packet count";
          leaf packet-num-drop-node-name {
            description
              "Packet count, value must be a power of two <16-8192>";
            type uint16 {
              range "16..8192";
            }
            mandatory true;
          }
          container option-grp1-drop-node-name {
            leaf data-size {
              description
                "Size of trace data in bytes, value must be a power of two <2048-16384>";
              type uint16 {
                range "2048..16384";
              }
            }
            leaf fia-trace {
              description
                "Trace of visited feature entries";
              type empty;
            }
            leaf circular {
              description
                "Capture last set of packets";
              type empty;
            }
          }
          container option-grp2-drop-node-name {
            leaf circular {
              description
                "Capture last set of packets";
              type empty;
            }
            leaf summary-only {
              description
                "Summary of the trace";
              type empty;
            }
          }
        }
      }
      case copy-case {
        container copy {
          description
            "Copy packet data";
          container packet {
            description
              "Copy parts of packets received or sent";
            choice direction-choice {
              mandatory true;
              case both-case {
                leaf both {
                  description
                    "Copy incoming and outgoing packets";
                  type empty;
                }
              }
              case input-case {
                leaf input {
                  description
                    "Copy incoming packets";
                  type empty;
                }
              }
              case output-case {
                leaf output {
                  description
                    "Copy outgoing packets";
                  type empty;
                }
              }
            }
            choice layer-choice {
              case l2-case {
                leaf l2 {
                  description
                    "Copy starting from layer 2";
                  type empty;
                }
              }
              case l3-case {
                leaf l3 {
                  description
                    "Copy starting from layer 3";
                  type empty;
                }
              }
              case l4-case {
                leaf l4 {
                  description
                    "Copy starting from layer 4";
                  type empty;
                }
              }
            }
            leaf size {
              description
                "Packet size in bytes, value must be a power of two";
              type uint16 {
                range "16..2048";
              }
            }
          }
        }
      }
    }
  }

  grouping debug-choice-platform-case-grouping {
    container platform {
      description
        "Debug platform information";
      choice platform-choice {
        case condtion-case {
          container condition {
            choice condition-choice {
              case start-case {
                leaf start {
                  description
                    "Start conditional debug";
                  type empty;
                }
              }
              case stop-case {
                leaf stop {
                  description
                    "Stop conditional debug";
                  type empty;
                }
              }
              case direction-case {
                container direction-drop-node-name {
                  uses direction-grouping;
                  leaf no {
                    description
                      "for no debug platform ...";
                    type empty;
                  }
                }
              }
              case application-case {
                container application {
                  uses condition-application-grouping;
                  leaf no {
                    description
                      "for no debug platform ...";
                    type empty;
                  }
                }
              }
              case mpls-case {
                container mpls {
                  uses condition-mpls-grouping;
                  leaf no {
                    description
                      "for no debug platform ...";
                    type empty;
                  }
                }
              }
              case ipv4-case {
                container ipv4 {
                  uses condition-ipv4-grouping;
                  leaf no {
                    description
                      "for no debug platform ...";
                    type empty;
                  }
                }
              }
              case ipv6-case {
                container ipv6 {
                  uses condition-ipv6-grouping;
                  leaf no {
                    description
                      "for no debug platform ...";
                    type empty;
                  }
                }
              }
              case match-case {
                container match {
                  uses condition-match-grouping;
                  leaf no {
                    description
                      "for no debug platform ...";
                    type empty;
                  }
                }
              }
              case interface-case {
                container interface {
                  uses condition-interface-grouping;
                  leaf no {
                    description
                      "for no debug platform ...";
                    type empty;
                  }
                }
              }
              case feature-case {
                container feature {
                  description
                    "For a specific feature";
                  choice feature-choice {
                    case ipsec-case {
                      uses debug-platform-condition-feature-ipsec-grouping;
                    }
                    case multicast-case {
                      uses debug-platform-condition-feature-multicast-grouping;
                    }
                  }
                }
              }
            }
          }
        }
        case packet-trace-case {
          container packet-trace {
            uses packet-trace-grouping;
            leaf no {
              description
                "for no debug platform ...";
              type empty;
            }
          }
        }
      }
    }
  }
}
