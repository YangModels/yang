module Cisco-IOS-XE-wireless-rrm-oper {
  yang-version 1;
  namespace "http://cisco.com/ns/yang/Cisco-IOS-XE-wireless-rrm-oper";
  prefix wireless-rrm-oper;

  import Cisco-IOS-XE-wireless-enum-types {
    prefix wireless-enum-types;
  }
  import Cisco-IOS-XE-wireless-rrm-types {
    prefix wireless-rrm-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless rrm operational data.
     Copyright (c) 2016-2020 by Cisco Systems, Inc.
     All rights reserved.";

  revision 2020-11-01 {
    description
      "- Added yang support for rrm-group-remote-member";
    reference "5.3.0";
    cisco-semver:module-version "5.3.0";
  }
  revision 2019-11-01 {
    description
      "- Added yang support for persistent device avoidance operational data.
       - Added when constraint to utilization and power in spectrum device data";
    reference "5.2.0";
    cisco-semver:module-version "5.2.0";
  }
  revision 2019-04-16 {
    description
      "- Added leaf nodes from rrm-load-attr.
       - Added semantic version";
    reference "5.1.0";
    cisco-semver:module-version "5.1.0";
  }
  revision 2019-02-19 {
    description
      "- Added leaf node neighbor-radio-mac to st-rad-neighbor-attr.
       - Added leaf node neighbor-radio-slot-id to st-rad-neighbor-attr.
       - Renamed the leaf node ap-name to neighbor-ap-name
       - Renamed the leaf node ip to group-leader-ip
       - Renamed the node neighbor-attr to neighbor-radio-info 
       - Renamed the node mon-neighbor-attr to mon-neighbor-radio-info 
       - Modified description for leaf nodes of neighbor-attr-info
       - Changed the type of chan-width to rf-dca-chan-width
       - Removal of less important leaf nodes from RRM operational data
       - Changed the type of chan-width to radio-neighbor-chan-width";
    reference "5.0.0";
    cisco-semver:module-version "5.0.0";
  }
  revision 2019-01-02 {
    description
      "- Removing the leaf node from init-neighbor-msg-flag
       - Changing enum type for phy-type in st-rrm-mgr-main
       - Cleaned up spelling errors in descriptions
       - Removing unused enum values from RRM group state and Antenna pattern enums
       - Add leaf node ap-name to st-rad-neighbor-attr.
       - Removed Radio Role Flexibility (RRF) related leaf nodes 
       - Removed the leaf node init-neighbor-msg-flag.";
    reference "4.0.0";
    cisco-semver:module-version "4.0.0";
  }
  revision 2018-05-01 {
    description
      "- Add sensor-covered to st-rad-neighbor-attr
       - Add st-rrm-load-attr
       - Add st-rrm-measurement-data
       - Add leafs rrf-is-contributing, rrf-sensor-metric, sensor-coverage-factor to st-rrm-radio-data
       - Add leaf member-secondary-ip to st-rrm-mgr-grp-member
       - Add leaf member-secondary-ip to st-mapping-rrm-grp-member
       - Add leafs my-group-secondary-ip, cntrlr-secondary-ip-addr, fra-sensor-coverage to st-rrm-group-ctrl
       - Add leaf mgmt-secondary-ip to st-rrm-mgr-main
       - Add list radio-measurement to rrm-oper-data";
    reference "3.1.0";
    cisco-semver:module-version "3.1.0";
  }
  revision 2018-03-22 {
    description
      "List key changes";
    reference "3.0.0";
    cisco-semver:module-version "3.0.0";
  }
  revision 2018-01-24 {
    description
      "The first generally available version";
    reference "2.0.0";
    cisco-semver:module-version "2.0.0";
  }
  revision 2017-05-05 {
    description
      "Initial revision";
    reference "1.0.0";
    cisco-semver:module-version "1.0.0";
  }

  typedef enm-cleanair-oper-state {
    type enumeration {
      enum "rrm-spectrum-down" {
        value 0;
        description
          "Clean air is not operational";
      }
      enum "rrm-spectrum-up" {
        value 1;
        description
          "Clean air is operational";
      }
    }
    description
      "Clean-air(Spectrum) operational state";
  }

  typedef enm-is-static-member {
    type enumeration {
      enum "rrm-auto-member-config" {
        value 0;
        description
          "RF group member is selected through auto selection mechanism";
      }
      enum "rrm-static-member-config" {
        value 1;
        description
          "RF group member is selected through Static configuration";
      }
    }
    description
      "RF group member type - auto or static";
  }

  typedef enm-rrm-grouping-role-db {
    type enumeration {
      enum "rrm-group-off" {
        value 0;
        description
          "RF Grouping is Disabled";
      }
      enum "rrm-group-static-leader" {
        value 1;
        description
          "Leader of static RF Group";
      }
      enum "rrm-group-static-member" {
        value 2;
        description
          "Member in static RF Group.";
      }
      enum "rrm-group-auto-leader" {
        value 3;
        description
          "Leader of automatic RF Group";
      }
      enum "rrm-group-auto-member" {
        value 4;
        description
          "Member in automatic RF Group";
      }
      enum "rrm-group-remote-member" {
        value 5;
        description
          "Member in Open RRM group";
      }
    }
    description
      "RF grouping role. The controller can be either group
       member or group leader while being in automatic or
       static grouping for a particular band.
       If grouping is off , the value of the group role
       would be 'none'.";
  }

  typedef enm-rrm-group-state {
    type enumeration {
      enum "rrm-undefined" {
        value 0;
        description
          "RRM manager is in undefined state";
      }
      enum "rrm-reset" {
        value 1;
        description
          "RRM manager is in Reset state";
      }
      enum "rrm-ha-standby" {
        value 2;
        description
          "RRM manager is in High Availability standby state";
      }
      enum "rrm-leader-idle" {
        value 3;
        description
          "RRM manager is in Idle state";
      }
      enum "rrm-leader-prep" {
        value 4;
        description
          "RRM manager is in preparation state";
      }
      enum "rrm-leader-comp" {
        value 5;
        description
          "RRM manager is in computation state";
      }
      enum "rrm-join-wait" {
        value 6;
        description
          "RRM manager is waiting for the leader to join the group";
      }
      enum "rrm-groupie" {
        value 7;
        description
          "RRM manager is in group member state";
      }
      enum "rrm-leader-assign" {
        value 8;
        description
          "RRM manager is in Leader selection state";
      }
      enum "rrm-remote-member" {
        value 9;
        description
          "RRM manager is in Remote Member state";
      }
    }
    description
      "RF grouping state";
  }

  grouping st-rad-neighbor-attr {
    description
      "RRM neighbor radio attributes";
    leaf neighbor-radio-mac {
      type yang:mac-address;
      description
        "Neighbor radio MAC address";
    }
    leaf neighbor-radio-slot-id {
      type uint8;
      description
        "Neighbor AP radio slot identifier";
    }
    leaf rssi {
      type int8;
      units "dBm";
      description
        "Received Signal Strength of Neighbor radio";
    }
    leaf snr {
      type int8;
      units "dB";
      description
        "Signal to Noise Ratio of Neighbor radio";
    }
    leaf channel {
      type uint8;
      description
        "Operating channel of Neighbor radio";
    }
    leaf power {
      type uint8;
      units "dBm";
      description
        "Tx-power of Neighbor radio";
    }
    leaf group-leader-ip {
      type inet:ip-address;
      description
        "IP Address of the Radio Resource Management (RRM) group leader";
    }
    leaf chan-width {
      type wireless-enum-types:radio-neighbor-chan-width;
      description
        "Channel width of neighbor radio";
    }
    leaf sensor-covered {
      type boolean;
      description
        "Neighbor covered by sensor";
    }
  }

  grouping st-rad-neighbor-list-data {
    description
      "Information about the list of radio neighbors";
    container neighbor-radio-info {
      description
        "Neighbor radio information";
      uses wireless-rrm-oper:st-rad-neighbor-attr;
    }
  }

  grouping st-rad-neighbor-list {
    description
      "List of neighbor radios and their properties";
    list neighbor-radio-list {
      description
        "Information about the list of neighbor radios";
      uses wireless-rrm-oper:st-rad-neighbor-list-data;
    }
  }

  grouping st-rad-neighbor-data {
    description
      "Neighbor radio information for both Monitor and Client Serving radio information";
    container neighbor-radio-info {
      description
        "List of Client Serving neighbor radio";
      uses wireless-rrm-oper:st-rad-neighbor-list;
    }
  }

  grouping st-rrm-radio-radar-info {
    description
      "Radar information for a given radio and channel";
    leaf channel-number {
      type uint32;
      description
        "Channel number on which radar was detected";
    }
    leaf radar-detected-timestamp {
      type yang:date-and-time;
      description
        "Time when radar was last detected on this radio channel";
    }
  }

  grouping st-rrm-radio-radar-info-list {
    description
      "Information related to Radar";
    list radar-info {
      max-elements "64";
      description
        "Radar information for a given radio";
      uses wireless-rrm-oper:st-rrm-radio-radar-info;
    }
  }

  grouping st-rrm-radio-radar-attr {
    description
      "Radar information for a given radio channel";
    container radar-info {
      description
        "Radar information";
      uses wireless-rrm-oper:st-rrm-radio-radar-info-list;
    }
    leaf last-radar-on-radio {
      type yang:date-and-time;
      description
        "Timestamp of last radar detected on radio (DFS hit)";
    }
  }

  grouping st-rrm-load-attr {
    description
      "Load information related to a radio";
    leaf rx-util-percentage {
      type uint16;
      units "percentage";
      description
        "Percentage RX utilization";
    }
    leaf tx-util-percentage {
      type uint16;
      units "percentage";
      description
        "Percentage TX utilization";
    }
    leaf cca-util-percentage {
      type uint16;
      units "percentage";
      description
        "Percentage value of Clear Channel Assessment";
    }
    leaf rx-noise-channel-utilization {
      type uint16;
      units "percentage";
      description
        "Received channel-utilization percentage due to Noise";
    }
  }

  grouping st-rrm-measurement-data {
    description
      "RRM Measurement information for the radio";
    container load {
      description
        "Load information related to a radio";
      uses wireless-rrm-oper:st-rrm-load-attr;
    }
  }

  grouping st-rrm-radio-data {
    description
      "Radio parameters which would be modified when RRM is active";
    leaf load-prof-passed {
      type boolean;
      description
        "Boolean value to represent if load profile passed";
    }
    leaf coverage-profile-passed {
      type boolean;
      description
        "Boolean value to represent if coverage profile passed";
    }
    leaf interference-profile-passed {
      type boolean;
      description
        "Boolean value to represent if interference profile passed";
    }
    leaf noise-profile-passed {
      type boolean;
      description
        "Boolean value to represent if noise profile passed";
    }
  }

  grouping st-rrm-rad-slot-data {
    description
      "Radio slot data";
    container radio-data {
      description
        "Radio performance profile check information";
      uses wireless-rrm-oper:st-rrm-radio-data;
    }
  }

  grouping st-spectrum-config {
    description
      "Clean air configuration for AP radio";
    leaf spectrum-intelligence-enable {
      type boolean;
      description
        "True if cleanair is enabled";
    }
    leaf spectrum-wtp-ca-si-capable {
      type wireless-rrm-types:enm-ca-si-capable;
      description
        "True if the Access point is CA/SI capable";
    }
    leaf spectrum-operation-state {
      type wireless-rrm-oper:enm-cleanair-oper-state;
      description
        "Cleanair operation state";
    }
    leaf spectrum-admin-state {
      type boolean;
      description
        "Cleanair admin state";
    }
    leaf spectrum-capable {
      type boolean;
      description
        "True if the Access point is cleanair capable";
    }
    leaf sensord-operational-status {
      type int32;
      description
        "State of the cleanair sensors on the access point";
    }
  }

  grouping st-rrm-spectrum {
    description
      "RRM spectrum information";
    container config {
      description
        "Spectrum configuration";
      uses wireless-rrm-oper:st-spectrum-config;
    }
  }

  grouping st-per-radio-spectrum-idr-data {
    description
      "Persistent device avoidance information";
    leaf detecting-ap-mac {
      type yang:mac-address;
      description
        "MAC address of the AP which has detected the persistent device";
    }
    leaf affected-channel-list {
      type string;
      description
        "Channels in which persistent device operate";
    }
    leaf util {
      when "(../is-persistent = 'true')";
      type uint16;
      units "percentage";
      description
        "Interference duty cycle of device, represented in percentage";
    }
    leaf power {
      when "(../is-persistent = 'true')";
      type int8;
      units "dBm";
      description
        "RSSI of the persistent device";
    }
    leaf is-persistent {
      type boolean;
      description
        "True if interferer is persistent device.";
    }
    leaf class-type-enum {
      type wireless-rrm-types:enm-cleanair-class-type;
      description
        "Class type of the persistent device";
    }
  }

  grouping st-spectrum-device-record {
    description
      "Persistent device avoidance device information";
    leaf device-id {
      type yang:mac-address;
      description
        "Pseudo MAC address of the persistent device";
    }
    leaf last-updated-time {
      type yang:date-and-time;
      description
        "Timestamp when the interferer device was last active";
    }
    container idr-data {
      description
        "Interference device record per device";
      uses wireless-rrm-oper:st-per-radio-spectrum-idr-data;
    }
  }

  grouping st-rrm-mgr-grp-member {
    description
      "RF group member information";
    leaf member-ip {
      type inet:ip-address;
      description
        "RF group member IP address";
    }
    leaf member-secondary-ip {
      type inet:ip-address;
      description
        "RF-Group member secondary IP address";
    }
    leaf max-radio-cnt {
      type uint16;
      description
        "Maximum number of radios a member can handle";
    }
    leaf curr-radio-cnt {
      type uint16;
      description
        "Number of radios currently associated to the member";
    }
    leaf name {
      type string;
      description
        "RF-Group member name";
    }
  }

  grouping st-rrm-group-ctrl {
    description
      "Various values related to the RF grouping algorithm";
    leaf current-state {
      type wireless-rrm-oper:enm-rrm-group-state;
      description
        "RF grouping state";
    }
    leaf current-grouping-mode {
      type wireless-rrm-types:enm-rrm-ctrl-mode;
      description
        "RF grouping mode";
    }
    leaf current-grouping-role {
      type wireless-rrm-oper:enm-rrm-grouping-role-db;
      description
        "RF grouping role";
    }
    leaf cntrlr-name {
      type string;
      description
        "RF group leader name";
    }
    leaf cntrlr-ip-addr {
      type inet:ipv4-address;
      description
        "RF group leader IP address";
    }
    leaf is-static-member {
      type wireless-rrm-oper:enm-is-static-member;
      description
        "RF group member type. 0 for auto and 1 for static";
    }
    leaf fra-sensor-coverage {
      type uint8;
      description
        "FRA global sensor coverage";
    }
  }

  grouping st-rrm-static-grp-member {
    description
      "Statically configured RF group members";
    leaf cntrlr-name {
      type string;
      description
        "RF group member name";
    }
    leaf cntrlr-ip-addr {
      type inet:ip-address;
      description
        "RF group member ip address";
    }
    leaf has-joined {
      type boolean;
      description
        "True if the member has joined this RF Group.
         This field is significant only if the current group is a static RF Group.
         In all other cases a value of 'true' would be shown";
    }
    leaf nack-reason {
      type wireless-types:enm-rrm-grp-member-nack-reason;
      description
        "Reason why a RF group member could not join the Group.
         This is relevant only if the corresponding instance for 'has_joined' is 'false'";
    }
    leaf max-radio-num {
      type uint16;
      description
        "Maximum number of radios supported for a given RF group";
    }
    leaf last-join-cmd-ts {
      type yang:date-and-time;
      description
        "Date and Time when the static member joined the controller";
    }
  }

  grouping st-rrm-mgr-oper-data {
    description
      "RRM manager operational data";
    container default-dca-channels {
      description
        "Default DCA Channels";
      uses wireless-rrm-types:st-rrm-channels-list;
    }
    container default-non-dca-channels {
      description
        "Default non DCA Channels";
      uses wireless-rrm-types:st-rrm-channels-list;
    }
  }

  grouping st-rrm-mgr-main {
    description
      "RRM manager operational information";
    leaf phy-type {
      type wireless-types:enm-ewlc-dot11-radio-band;
      description
        "Radio band type (802.11bg/802.11a)";
    }
    container grp {
      description
        "RF grouping configuration and operational data";
      uses wireless-rrm-oper:st-rrm-group-ctrl;
    }
    container oper-data {
      description
        "RRM manager operational data";
      uses wireless-rrm-oper:st-rrm-mgr-oper-data;
    }
    list rrm-mgr-static-grp-member {
      key "cntrlr-ip-addr";
      description
        "List of statically configured RF group members";
      uses wireless-rrm-oper:st-rrm-static-grp-member;
    }
    list rrm-mgr-grp-member {
      key "member-ip";
      description
        "List of auto RF group members";
      uses wireless-rrm-oper:st-rrm-mgr-grp-member;
    }
  }

  container rrm-oper-data {
    config false;
    description
      "Radio Resource Management Operational Data";
    list ap-auto-rf-dot11-data {
      key "wtp-mac radio-slot-id";
      description
        "Information related to radio RF parameters";
      uses wireless-types:radio-slot-key;
      uses wireless-rrm-oper:st-rad-neighbor-data;
    }
    list ap-dot11-radar-data {
      key "wtp-mac radio-slot-id";
      description
        "Information related to radio radar channels and events";
      uses wireless-types:radio-slot-key;
      uses wireless-rrm-oper:st-rrm-radio-radar-attr;
    }
    list ap-dot11-spectrum-data {
      key "wtp-mac radio-slot-id";
      description
        "Information related to radio spectrum parameters";
      uses wireless-types:radio-slot-key;
      uses wireless-rrm-oper:st-rrm-spectrum;
    }
    list rrm-measurement {
      key "wtp-mac radio-slot-id";
      description
        "Information related to radio measurements";
      uses wireless-types:radio-slot-key;
      uses wireless-rrm-oper:st-rrm-measurement-data;
    }
    list radio-slot {
      key "wtp-mac radio-slot-id";
      description
        "Radio slot information";
      uses wireless-types:radio-slot-key;
      uses wireless-rrm-oper:st-rrm-rad-slot-data;
    }
    list main-data {
      key "phy-type";
      description
        "Information related to RRM Manager";
      uses wireless-rrm-oper:st-rrm-mgr-main;
    }
    list spectrum-device-table {
      key "device-id";
      description
        "Information related to persistent device";
      uses wireless-rrm-oper:st-spectrum-device-record;
    }
  }
}
