module cisco-xe-ietf-ip-deviation {
  namespace "http://cisco.com/ns/cisco-xe-ietf-ip-deviation";
  prefix ip-devs;

  import ietf-interfaces {
    prefix if;
  }
  import ietf-ip {
    prefix ip;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module defines deviation statements for ietf-ip module.";

  revision 2016-08-10 {
    description
      "Updated deviation statements for 16.3.2 release.";
  }
  revision 2015-09-11 {
    description
      "Initial Revision";
    reference
      "RFC 6020: YANG - A Data Modeling Language for the
       Network Configuration Protocol (NETCONF)";
  }

  deviation "/if:interfaces/if:interface/ip:ipv4/ip:enabled" {
    deviate not-supported;
    description
      "Not supported in IOS-XE 3.17 release.";
  }
  deviation "/if:interfaces/if:interface/ip:ipv4/ip:forwarding" {
    deviate not-supported;
    description
      "Not supported in IOS-XE 3.17 release.";
  }
  deviation "/if:interfaces/if:interface/ip:ipv4/ip:mtu" {
    deviate not-supported;
    description
      "Not supported in IOS-XE 3.17 release.";
  }
  deviation "/if:interfaces/if:interface/ip:ipv4/ip:neighbor" {
    deviate not-supported;
    description
      "Not supported in IOS-XE 3.17 release.";
  }
  deviation "/if:interfaces/if:interface/ip:ipv6/ip:enabled" {
    deviate not-supported;
    description
      "Not supported in IOS-XE 3.17 release.";
  }
  deviation "/if:interfaces/if:interface/ip:ipv6/ip:forwarding" {
    deviate not-supported;
    description
      "Not supported in IOS-XE 3.17 release.";
  }
  deviation "/if:interfaces/if:interface/ip:ipv6/ip:mtu" {
    deviate not-supported;
    description
      "Not supported in IOS-XE 3.17 release.";
  }
  deviation "/if:interfaces/if:interface/ip:ipv6/ip:dup-addr-detect-transmits" {
    deviate not-supported;
    description
      "Not supported in IOS-XE 3.17 release.";
  }
  deviation "/if:interfaces/if:interface/ip:ipv6/ip:autoconf" {
    deviate not-supported;
    description
      "Not supported in IOS-XE 3.17 release.";
  }
  deviation "/if:interfaces/if:interface/ip:ipv6/ip:neighbor" {
    deviate not-supported;
    description
      "Not supported in IOS-XE 3.17 release.";
  }
  deviation "/if:interfaces-state/if:interface/ip:ipv4" {
    deviate not-supported;
    description
      "Not supported in IOS-XE 16.3.2 release";
  }
  deviation "/if:interfaces-state/if:interface/ip:ipv6" {
    deviate not-supported;
    description
      "Not supported in IOS-XE 16.3.2 release";
  }
}
