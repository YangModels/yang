module Cisco-IOS-XE-wireless-mobility-express-rpc {
  yang-version 1;
  namespace "http://cisco.com/ns/yang/Cisco-IOS-XE-wireless-mobility-express-rpc";
  prefix wireless-mobility-express-rpc;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Copyright (c) 2019 by Cisco Systems, Inc.
     All rights reserved.";

  revision 2019-03-01 {
    description
      "Initial revision";
    reference "1.0.0";
    cisco-semver:module-version "1.0.0";
  }

  rpc mobility-express-factory-reset {
    description
      "Embedded Wireless Controller factory reset";
  }
}
