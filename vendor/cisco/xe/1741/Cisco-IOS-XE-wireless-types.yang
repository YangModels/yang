module Cisco-IOS-XE-wireless-types {
  yang-version 1;
  namespace "http://cisco.com/ns/yang/Cisco-IOS-XE-wireless-types";
  prefix wireless-types;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for wireless common data types.
     Copyright (c) 2016-2020 by Cisco Systems, Inc.
     All rights reserved.";

  revision 2020-11-01 {
    description
      "- AP disconnect reason enumeration added
       - Added new sensitivity levels for Flexible Radio Assignment";
    reference "5.5.0";
    cisco-semver:module-version "5.5.0";
  }
  revision 2020-07-01 {
    description
      "- Added new AP reboot reason enumerations
       - Updated description for sensor mode
       - Added new elliptical curve cipher suite enumeration
       - Updated descriptions for DTLS version and cipher-suite configurations
       - Added EWC predownload status enumerations";
    reference "5.4.0";
    cisco-semver:module-version "5.4.0";
  }
  revision 2020-03-01 {
    description
      "- Added flags indicating 802.11k Radio Measurement Enabled Capabilities of a client
       - Added a new composite key for RADIUS counters data.
       - Added support for AP proxy";
    reference "5.3.0";
    cisco-semver:module-version "5.3.0";
  }
  revision 2019-11-01 {
    description
      "- Updated enum for dot11 radio subtype";
    reference "5.2.0";
    cisco-semver:module-version "5.2.0";
  }
  revision 2019-09-05 {
    description
      "- Added a new enum for radio frequency and few key definitions.
       - Added semantic version.
       - Added a new enum for clear AP config operation type.
       - Added new enum radio-slot-antenna-type";
    reference "5.1.0";
    cisco-semver:module-version "5.1.0";
  }
  revision 2019-03-18 {
    description
      "- Added new enum for mesh link test config status.
       - Removed enum mesh-adj-state-max.
       - Removed enum mesh-node-pkt-queue-invalid.
       - Removed enum enm_mesh_ap_neigh_type.
       - Adding new enum for dot11 radio band type.
       - Cleaned up spelling errors in descriptions.
       - Adding new enum for dot11 radio subtype.
       - Updated enum type for band.
       - Adding new enum for dot11 radio band type.
       - Adding new enum for Radio Role Flexibility (RRF) Redundancy, Metric and Silent
       - Add enm-band-switch-reason
       - Add ap-staggered-upgrade-one-shot to enum-ewlc-ap-upgrade-config.
       - Added enumeration to describe max channel width cap when channel width is set to best
       - Cleaned enum initialization
       - Added new enum for AP misconfigured tag
       - Removed FQDN URL action max enum and added none
       - Removed hard coded values for enum-ewlc-ap-upgrade-config
       - Removed enum pre-download-max-states
       - Updated enm-fra-sensor-coverage-profile enum";
    reference "5.0.0";
    cisco-semver:module-version "5.0.0";
  }
  revision 2018-05-01 {
    description
      "Enumeration enum-ewlc-lsc-key-size value changes to support 2048-4096 RSA key range";
    reference "4.0.0";
    cisco-semver:module-version "4.0.0";
  }
  revision 2018-03-22 {
    description
      "Enumeration value changes";
    reference "3.0.0";
    cisco-semver:module-version "3.0.0";
  }
  revision 2018-01-24 {
    description
      "The first generally available version";
    reference "2.0.0";
    cisco-semver:module-version "2.0.0";
  }
  revision 2017-05-05 {
    description
      "Initial revision";
    reference "1.0.0";
    cisco-semver:module-version "1.0.0";
  }

  typedef w-config-type {
    type enumeration {
      enum "config-auto" {
        value 1;
        description
          "Configuration type is Auto";
      }
      enum "customized" {
        value 2;
        description
          "Configuration type is Static";
      }
    }
    description
      "Possible values for configuration type";
  }

  typedef ewlc-url-crud {
    type enumeration {
      enum "fqdn-url-none" {
        value 0;
        description
          "No URL filter list";
      }
      enum "fqdn-url-add" {
        value 1;
        description
          "Add new URL to the url filter list";
      }
      enum "fqdn-url-no-change" {
        value 2;
        description
          "There is no change for this given URL in the urlfilter list";
      }
      enum "fqdn-url-delete" {
        value 3;
        description
          "Delete the given URL in the urlfilter list ";
      }
    }
    description
      "This action type helps to identify if any particular URL in the URL list has to be created, deleted or has not changed in this update action";
  }

  typedef ewlc-url-rule-type {
    type enumeration {
      enum "urllist-bl" {
        value 1;
        description
          "url filter list type blacklist";
      }
      enum "urllist-wl" {
        value 2;
        description
          "url filter list type whitelist";
      }
    }
    description
      "This is the filter type for the given url-filter list which dictates if it has to be used as have blacklist or whitelist";
  }

  typedef ewlc-url-filter-type {
    type enumeration {
      enum "pre-auth-url-type" {
        value 1;
        description
          "pre authentication url filter type";
      }
      enum "post-auth-url-type" {
        value 2;
        description
          "post authentication url filter type";
      }
    }
    description
      "This is the filter type for the given url-filter list which dictates if it has to be used as have post auth or pre auth filter";
  }

  typedef enm-dtls-version {
    type enumeration {
      enum "dtls-10" {
        value 0;
        description
          "DTLS-1.0";
      }
      enum "dtls-12" {
        value 1;
        description
          "DTLS-1.2";
      }
      enum "dtls-all" {
        value 2;
        description
          "Configure default DTLS version settings";
      }
    }
    description
      "enumeration for DTLS versions";
  }

  typedef enm-ciphersuite {
    type enumeration {
      enum "tls-null-with-null-null" {
        value 0;
        description
          "Configure default cipher-suite(s)";
      }
      enum "tls-rsa-aes128-cbc-sha" {
        value 1;
        description
          "TLS_RSA_AES128_CBC_SHA cipher suite";
      }
      enum "tls-dhe-rsa-aes128-cbc-sha" {
        value 2;
        description
          "TLS_DHE_RSA_AES128_CBC_SHA cipher suite";
      }
      enum "tls-dhe-rsa-aes256-cbc-sha" {
        value 3;
        description
          "TLS_DHE_RSA_AES256_CBC_SHA cipher suite";
      }
      enum "tls-dhe-rsa-aes256-cbc-sha256" {
        value 4;
        description
          "TLS_DHE_RSA_AES256_CBC_SHA256 cipher suite";
      }
      enum "tls-ecdhe-ecdsa-aes128-gcm-sha256" {
        value 5;
        description
          "TLS_ECDHE_ECDSA_AES128_GCM_SHA256 cipher suite";
      }
      enum "tls-ecdhe-ecdsa-aes256-gcm-sha384" {
        value 6;
        description
          "TLS_ECDHE_ECDSA_AES256_GCM_SHA384 cipher suite";
      }
      enum "tls-ecdhe-rsa-aes128-gcm-sha256" {
        value 7;
        description
          "TLS_ECDHE_RSA_AES128_GCM_SHA256 cipher suite";
      }
    }
    description
      "enumeration for DTLS versions";
  }

  typedef enum-xor-radio-mode {
    type enumeration {
      enum "xor-radio-mode-local" {
        value 1;
        description
          "Xor radio mode manual client serving";
      }
      enum "xor-radio-mode-monitor" {
        value 2;
        description
          "Xor radio mode manual monitor";
      }
      enum "xor-radio-mode-sensor" {
        value 3;
        description
          "Xor radio mode manual sensor";
      }
    }
    description
      "Enumeration for XOR Radio mode";
  }

  typedef enm-ewlc-spam-ap-modes {
    type enumeration {
      enum "local-mode" {
        value 0;
        description
          "Local";
      }
      enum "mode-monitor" {
        value 1;
        description
          "Monitor";
      }
      enum "mode-flex-connect" {
        value 2;
        description
          "FlexConnect";
      }
      enum "mode-rogue-detector" {
        value 3;
        description
          "Rogue Detector";
      }
      enum "mode-sniffer" {
        value 4;
        description
          "Sniffer";
      }
      enum "mode-bridge" {
        value 5;
        description
          "Bridge";
      }
      enum "mode-se-connect" {
        value 6;
        description
          "SE-Connect";
      }
      enum "mode-remote-bridge" {
        value 7;
        description
          "Remote Bridge";
      }
      enum "mode-hybrid-flexconnect" {
        value 8;
        description
          "FlexConnect";
      }
      enum "mode-sensor" {
        value 9;
        description
          "Sensor mode is not supported";
      }
    }
    description
      "Enumeration for spam AP mode";
  }

  typedef enm-ewlc-ap-radio-modes {
    type enumeration {
      enum "radio-mode-invalid" {
        value 0;
        description
          "Radio mode Invalid";
      }
      enum "radio-mode-local" {
        value 1;
        description
          "Radio mode Local";
      }
      enum "radio-mode-monitor" {
        value 2;
        description
          "Radio mode Monitor";
      }
      enum "radio-mode-flex-connect" {
        value 3;
        description
          "Radio mode FlexConnect";
      }
      enum "radio-mode-rogue-detector" {
        value 4;
        description
          "Radio mode Rogue Detector";
      }
      enum "radio-mode-sniffer" {
        value 5;
        description
          "Radio mode Sniffer";
      }
      enum "radio-mode-bridge" {
        value 6;
        description
          "Radio mode Bridge";
      }
      enum "radio-mode-se-connect" {
        value 7;
        description
          "Radio mode SE-Connect";
      }
      enum "radio-mode-remote-bridge" {
        value 8;
        description
          "Radio mode Remote Bridge";
      }
      enum "radio-mode-hybrid-flexconnect" {
        value 9;
        description
          "Radio mode FlexConnect";
      }
      enum "radio-mode-sensor" {
        value 10;
        description
          "Radio mode Sensor";
      }
    }
    description
      "Enumeration for AP radio mode";
  }

  typedef ap-radio-subtype {
    type enumeration {
      enum "ap-radio-subtype-main" {
        value 0;
        description
          "Dot11 radio subtype main";
      }
      enum "ap-radio-subtype-rx-only" {
        value 1;
        description
          "Dot11 radio subtype Rx only";
      }
      enum "ap-radio-subtype-slave-ac" {
        value 2;
        description
          "Dot11 radio subtype slave AC";
      }
      enum "ap-radio-subtype-rem-lan" {
        value 3;
        description
          "Dot11 radio subtype remote lan";
      }
      enum "ap-radio-subtype-tx-rx" {
        value 4;
        description
          "Dot11 radio subtype Tx Rx";
      }
      enum "ap-radio-subtype-slave" {
        value 5;
        description
          "Dot11 radio subtype Slave";
      }
    }
    description
      "Enum for dot11 radio subtype";
  }

  typedef enm-ip-address-type {
    type enumeration {
      enum "unknown" {
        value 0;
        description
          "IP address type unknown";
      }
      enum "ipv4" {
        value 1;
        description
          "IP address type version 4";
      }
      enum "ipv6" {
        value 2;
        description
          "IP address type version 6";
      }
      enum "ipv4z" {
        value 3;
        description
          "IP address type version 4z";
      }
      enum "ipv6z" {
        value 4;
        description
          "IP address type version 6z";
      }
    }
    description
      "Enumeration for IP address type";
  }

  typedef enum-ap-ipv6-addr-method {
    type enumeration {
      enum "unknown-method" {
        value 0;
        description
          "Method used by AP to join over IPv6 is unknown";
      }
      enum "static" {
        value 1;
        description
          "Method used by AP to join over IPv6 is Static";
      }
      enum "dhcpv6" {
        value 2;
        description
          "Method used by AP to join over IPv6 is DHCPv6";
      }
      enum "slaac" {
        value 3;
        description
          "Method used by AP to join over IPv6 is SLAAC";
      }
    }
    description
      "Enum for IPv6 address assignment method";
  }

  typedef enm-hyperlocation-reason {
    type enumeration {
      enum "hyperlocation-reason-none" {
        value 0;
        description
          "No reason";
      }
      enum "hyperlocation-reason-unknown" {
        value 1;
        description
          "Unknown reason";
      }
      enum "hyperlocation-reason-disabled" {
        value 2;
        description
          "Hyperlocation administratively disabled";
      }
      enum "hyperlocation-reason-ntp" {
        value 3;
        description
          "No NTP server";
      }
      enum "hyperlocation-reason-nmsp" {
        value 4;
        description
          "No active NMSP connection";
      }
      enum "hyperlocation-reason-no-nexthop" {
        value 5;
        description
          "No nexthop";
      }
    }
    description
      "Enumeration of all down reasons for operational status on an AP profile";
  }

  typedef ap-misconfig-tags {
    type enumeration {
      enum "ap-tag-configured" {
        value 0;
        description
          "Ap tags configured successfully";
      }
      enum "ap-policy-tag-misconfigured" {
        value 1;
        description
          "Ap Policy-tag is misconfigured";
      }
      enum "ap-site-tag-misconfigured" {
        value 2;
        description
          "Ap Site-tag is misconfigured";
      }
      enum "ap-rf-tag-misconfigured" {
        value 3;
        description
          "Ap Rf-tag is misconfigured";
      }
      enum "ap-profile-tag-misconfigured" {
        value 4;
        description
          "Ap Profile-tag is misconfigured";
      }
      enum "ap-flex-profile-misconfigured" {
        value 5;
        description
          "Ap Flex-profile is misconfigured";
      }
      enum "ap-rf-profile-24ghz-misconfigured" {
        value 6;
        description
          "Ap Rf-profile-24ghz is misconfigured";
      }
      enum "ap-rf-profile-5ghz-misconfigured" {
        value 7;
        description
          "Ap Rf-profile-5ghz is misconfigured";
      }
    }
    description
      "Enum for AP misconfigure tag";
  }

  typedef enm-hyperlocation-method {
    type enumeration {
      enum "hyperlocation-method-unknown" {
        value 0;
        description
          "Unknown hyperlocation method";
      }
      enum "hyperlocation-method-wsm" {
        value 1;
        description
          "Hyperlocation method - WSM";
      }
      enum "hyperlocation-method-halo" {
        value 2;
        description
          "HYPERLOCATION METHOD WSM2";
      }
      enum "hyperlocation-method-halo-antenna" {
        value 3;
        description
          "HYPERLOCATION METHOD WSM2+Ant";
      }
      enum "hyperlocation-method-local" {
        value 4;
        description
          "HYPERLOCATION METHOD Local";
      }
      enum "hyperlocation-method-none" {
        value 5;
        description
          "HYPERLOCATION METHOD None";
      }
    }
    description
      "Enumeration for hyperlocation methods";
  }

  typedef enm-hyperlocation-ap-tlv-received {
    type enumeration {
      enum "hyperlocation-ap-tlv-invalid" {
        value 0;
        description
          "Invalid hyperlocation AP TLV state";
      }
      enum "hyperlocation-ap-tlv-received" {
        value 1;
        description
          "Hyperlocation AP TLV received from AP";
      }
      enum "hyperlocation-ap-tlv-not-received" {
        value 2;
        description
          "Hyperlocation AP TLV not received from AP";
      }
    }
    description
      "Enumeration for hyperlocation AP TLV received state";
  }

  typedef download-protocol {
    type enumeration {
      enum "protocol-none" {
        value 0;
        description
          "unknown protocol";
      }
      enum "protocol-ftp" {
        value 1;
        description
          "protocol is ftp";
      }
      enum "protocol-sftp" {
        value 2;
        description
          "protocol is sftp";
      }
      enum "protocol-tftp" {
        value 3;
        description
          "protocol is tftp";
      }
      enum "protocol-http" {
        value 4;
        description
          "protocol is http";
      }
      enum "protocol-scp" {
        value 5;
        description
          "protocol is scp";
      }
    }
    description
      "enumeration for download protocol";
  }

  typedef enm-shut-down-reason {
    type enumeration {
      enum "reason-shutdown-global-shut" {
        value 0;
        description
          "radio shut down reason - globally shut";
      }
      enum "reason-shutdown-profile-shut" {
        value 1;
        description
          "radio shut down reason - RF profile shut";
      }
      enum "reason-shutdown-global-and-profile-shut" {
        value 2;
        description
          "radio shut down reason - profile is shut, so is radio at a global level";
      }
      enum "reason-shutdown-up" {
        value 3;
        description
          "radio shut down reason - AP is shut down";
      }
    }
    description
      "ap shutdown reason";
  }

  typedef syslog-trap-level {
    type enumeration {
      enum "syslog-level-emergency" {
        value 0;
        description
          "emergency";
      }
      enum "syslog-level-alert" {
        value 1;
        description
          "alert";
      }
      enum "syslog-level-critical" {
        value 2;
        description
          "critical";
      }
      enum "syslog-level-errors" {
        value 3;
        description
          "errors";
      }
      enum "syslog-level-warning" {
        value 4;
        description
          "warning";
      }
      enum "syslog-level-notification" {
        value 5;
        description
          "notification";
      }
      enum "syslog-level-information" {
        value 6;
        description
          "information";
      }
      enum "syslog-level-debug" {
        value 7;
        description
          "debug";
      }
    }
    description
      "syslog level for the syslog messages sent from AP to syslog server";
  }

  typedef enm-predownload-status {
    type enumeration {
      enum "pre-dwnld-none" {
        value 0;
        description
          "pre download status is None";
      }
      enum "pre-dwnld-initiated" {
        value 1;
        description
          "Initiated";
      }
      enum "pre-dwnld-in-progress" {
        value 2;
        description
          "Pre-downloading";
      }
      enum "pre-dwnld-complete" {
        value 3;
        description
          "Complete";
      }
      enum "pre-dwnld-unsupported" {
        value 4;
        description
          "Not supported";
      }
      enum "pre-dwnld-failed" {
        value 5;
        description
          "Failed";
      }
    }
    description
      "enumeration for AP pre-download command status";
  }

  typedef enm-predwnld-status-ewc {
    type enumeration {
      enum "ewc-predwnld-none" {
        value 0;
        description
          "EWC predownload none";
      }
      enum "ewc-ctrl-dwnld-init" {
        value 1;
        description
          "EWC controller download initiated";
      }
      enum "ewc-ctrl-dwnld-inprog" {
        value 2;
        description
          "EWC controller download in progress";
      }
      enum "ewc-ctrl-dwnld-complete" {
        value 3;
        description
          "EWC controller download complete";
      }
      enum "ewc-ctrl-dwnld-failed" {
        value 4;
        description
          "EWC controller download failed";
      }
      enum "ewc-ap-predwnld-init" {
        value 5;
        description
          "EWC AP predownload initiated";
      }
      enum "ewc-ap-predwnld-inprog" {
        value 6;
        description
          "EWC AP predownload in progress";
      }
      enum "ewc-ap-predwnld-complete" {
        value 7;
        description
          "EWC AP predownload complete";
      }
      enum "ewc-ap-predwnld-unsupp" {
        value 8;
        description
          "EWC AP predownload unsupported";
      }
      enum "ewc-ap-predwnld-failed" {
        value 9;
        description
          "EWC AP predownload failed";
      }
      enum "ewc-ctrl-predwnld-inprog" {
        value 10;
        description
          "EWC controller predownload in progress";
      }
      enum "ewc-ctrl-predwnld-complete" {
        value 11;
        description
          "EWC controller predownload complete";
      }
      enum "ewc-ctrl-predwnld-failed" {
        value 12;
        description
          "EWC controller predownload failed";
      }
      enum "ewc-activated" {
        value 13;
        description
          "EWC predownload activated";
      }
      enum "ewc-act-failed" {
        value 14;
        description
          "EWC predownload activation failed";
      }
    }
    description
      "enumeration for EWC AP pre-download command status";
  }

  typedef enm-ap-end-events {
    type enumeration {
      enum "ev-default" {
        value 0;
        description
          "Default state of the event loop";
      }
      enum "ev-no-event" {
        value 1;
        description
          "NO_EVENT";
      }
      enum "ev-capwap-api-reset" {
        value 2;
        description
          "Reset by API";
      }
      enum "ev-dtls-hwsession-failure" {
        value 3;
        description
          "DTLS session failure";
      }
      enum "ev-reset-resp-msg" {
        value 4;
        description
          "Reset response msg";
      }
      enum "ev-dtls-sess-closed" {
        value 5;
        description
          "DTLS session closed";
      }
      enum "ev-heartbeat-timer-expiry" {
        value 6;
        description
          "Heartbeat timer expiry";
      }
      enum "ev-req-tx-fail" {
        value 7;
        description
          "Message timer expiry";
      }
      enum "ev-image-download-status" {
        value 8;
        description
          "Image download status";
      }
      enum "ev-internal-error" {
        value 9;
        description
          "event loop internal error";
      }
    }
    description
      "Enums specifies the group of AP end events";
  }

  typedef enm-ap-end-transition-states {
    type enumeration {
      enum "default-value" {
        value 0;
        description
          "DEFAULT Value";
      }
      enum "init-phase" {
        value 1;
        description
          "INIT Phase";
      }
      enum "join-wait" {
        value 2;
        description
          "JOIN_WAIT";
      }
      enum "join-process" {
        value 3;
        description
          "Join Process";
      }
      enum "join-auth-wait" {
        value 4;
        description
          "JOIN_AUTH_WAIT";
      }
      enum "joined" {
        value 5;
        description
          "JOINED";
      }
      enum "config-phase1" {
        value 6;
        description
          "CONFIG_PHASE1";
      }
      enum "image-download" {
        value 7;
        description
          "IMAGE_DOWNLOAD";
      }
      enum "change-state-req-processed" {
        value 8;
        description
          "CHANGE_STATE_REQ_PROCESSED";
      }
      enum "data-sess-wait" {
        value 9;
        description
          "DATA_SESS_WAIT";
      }
      enum "run" {
        value 10;
        description
          "RUN STATE";
      }
      enum "reset" {
        value 11;
        description
          "RESET";
      }
      enum "config-status-process" {
        value 12;
        description
          "CONFIG_STATUS_PROCESS";
      }
    }
    description
      "enumeration for AP end transition states";
  }

  typedef spam-ap-reboot-reason {
    type enumeration {
      enum "ap-reboot-reason-none" {
        value 0;
        description
          "unknown reason for AP reboot";
      }
      enum "ap-reboot-reason-11-g-mode" {
        value 1;
        description
          "Reason for AP disconnect - Mode changed to 11g";
      }
      enum "ap-reboot-reason-ip-addr-set" {
        value 2;
        description
          "Reason for AP disconnect - IP addressed set for AP";
      }
      enum "ap-reboot-reason-ip-addr-reset" {
        value 3;
        description
          "Reason for AP reboot/disconnect - AP IP address is reset";
      }
      enum "ap-reboot-reason-reboot-cmd" {
        value 4;
        description
          "Reason for AP reboot/disconnect - AP reboot command specified";
      }
      enum "ap-reboot-reason-dhcp-fallback" {
        value 5;
        description
          "Reason for AP reboot/disconnect - AP could not fallback to dhcp";
      }
      enum "ap-reboot-reason-discovery" {
        value 6;
        description
          "Reason for AP reboot/disconnect - AP could not send discovery";
      }
      enum "ap-reboot-reason-join-resp" {
        value 7;
        description
          "Reason for AP reboot/disconnect - AP did not receive join response";
      }
      enum "ap-reboot-reason-deny-join" {
        value 8;
        description
          "Reason for AP reboot/disconnect - Join denied by the controller";
      }
      enum "ap-reboot-reason-config-resp" {
        value 9;
        description
          "Reason for AP reboot/disconnect - Configuration response denied";
      }
      enum "ap-reboot-reason-config-mwar" {
        value 10;
        description
          "Reason for AP reboot/disconnect - found configured or master mwar";
      }
      enum "ap-reboot-reason-img-upgrade" {
        value 11;
        description
          "Reason for AP reboot/disconnect - AP Image upgraded";
      }
      enum "ap-reboot-reason-img-opcode" {
        value 12;
        description
          "Reason for AP reboot/disconnect - invalid image data opcode in the Image message from the WLC";
      }
      enum "ap-reboot-reason-img-chksum" {
        value 13;
        description
          "Reason for AP reboot/disconnect - invalid image MD5 checksum in the image msg from wlc";
      }
      enum "ap-reboot-reason-img-data" {
        value 14;
        description
          "Reason for AP reboot/disconnect - image data msg timeout";
      }
      enum "ap-reboot-reason-cfgfile" {
        value 15;
        description
          "Reason for AP reboot/disconnect - invalid config file";
      }
      enum "ap-reboot-reason-img-error" {
        value 16;
        description
          "Reason for AP reboot/disconnect - image download process error";
      }
      enum "ap-reboot-reason-ap-reboot-cmd" {
        value 17;
        description
          "Reason for AP reboot disconnect- reboot cmd from AP console";
      }
      enum "ap-reboot-reason-rap-ota-map" {
        value 18;
        description
          "Reason for AP reboot/disconnect - RAP is connected over the air";
      }
      enum "ap-reboot-reason-power-low" {
        value 19;
        description
          "Reason for AP reboot/disconnect - Low power";
      }
      enum "ap-reboot-reason-power-high" {
        value 20;
        description
          "Reason for AP reboot/disconnect - Too high power";
      }
      enum "ap-reboot-reason-power-loss" {
        value 21;
        description
          "Reason for AP reboot/disconnect - power loss";
      }
      enum "ap-reboot-reason-power-chg" {
        value 22;
        description
          "Reason for AP reboot/disconnect - Change of power level";
      }
      enum "ap-reboot-reason-comp-fail" {
        value 23;
        description
          "Reason for AP reboot/disconnect - hardware component failure";
      }
      enum "ap-reboot-reason-watchdog" {
        value 24;
        description
          "Reason for AP reboot/disconnect- HW watchdog timer reboot";
      }
      enum "ap-reboot-reason-lsc-enabled" {
        value 25;
        description
          "Reason for AP reboot/disconnect - LSC enabled";
      }
      enum "ap-reboot-reason-lsc-disabled" {
        value 26;
        description
          "Reason for AP reboot/disconnect - LSC disabled";
      }
      enum "ap-reboot-reason-lsc-provision-timeout" {
        value 27;
        description
          "Reason for AP reboot/disconnect - LSC Provisioning Timeout";
      }
      enum "ap-reboot-reason-lsc-max-prov-retry" {
        value 28;
        description
          "Reason for AP reboot/disconnect - max provision req retries";
      }
      enum "ap-reboot-reason-lsc-load-failure" {
        value 29;
        description
          "Reason for AP reboot/disconnect - LSC load failure";
      }
      enum "ap-reboot-reason-lsc-join-failure" {
        value 30;
        description
          "Reason for AP reboot/disconnect - LSC Join Failure";
      }
      enum "ap-reboot-reason-capwap-timer-failure" {
        value 31;
        description
          "Reason for AP reboot/disconnect - Capwap timer failure";
      }
      enum "ap-reboot-reason-fail-disc-with-dhcp-ip" {
        value 32;
        description
          "Reason for AP reboot/disconnect - Failed to discover WLC after maximum attempt";
      }
      enum "ap-reboot-reason-vlan-tag-failover" {
        value 33;
        description
          "Reason for AP reboot/disconnect - Failed to discover WLC using vlan tag config, fallback to untagged";
      }
      enum "ap-reboot-reason-vlan-tag-retry" {
        value 34;
        description
          "Reason for AP reboot/disconnect - Failed to discover WLC using failover to untagged, retry tagged";
      }
      enum "ap-reboot-reason-ipv6-addr-set" {
        value 35;
        description
          "Reason for AP reboot/disconnect - set static ipv6 address";
      }
      enum "ap-reboot-reason-mode-change" {
        value 36;
        description
          "Reason for AP reboot/disconnect- reboot AP as AP mode changed";
      }
      enum "ap-reboot-reason-ap-type-changed-to-capwap" {
        value 37;
        description
          "Reason for AP reboot/disconnect - reboot AP as AP type is changed from ME to CAPWAP";
      }
      enum "ap-reboot-reason-ap-type-changed-to-me" {
        value 38;
        description
          "Reason for AP reboot/disconnect - reboot AP as AP type is changed from CAPWAP to Embedded Wireless Controller";
      }
      enum "ap-reboot-reason-erase-cfg-cmd" {
        value 39;
        description
          "Reason for AP reboot/disconnect - Config command erased";
      }
      enum "ap-reboot-reason-oeap-mode-cfg-upload" {
        value 40;
        description
          "Reason for AP reboot/disconnect - OEAP Mode Configuration Upload";
      }
      enum "ap-reboot-reason-lag-cfg" {
        value 41;
        description
          "Reason for AP reboot/disconnect - LAG Configuration Change";
      }
      enum "ap-reboot-reason-fips-mode-change" {
        value 42;
        description
          "Reason for AP reboot/disconnect - Change in FIPS or CC Mode";
      }
      enum "ap-reboot-reason-diminished-pwr-change" {
        value 43;
        description
          "Reason for AP reboot/disconnect - Change in Diminished Power";
      }
      enum "ap-reboot-reason-slub-debug" {
        value 44;
        description
          "Reason for AP reboot/disconnect - Slub debug";
      }
      enum "ap-reboot-reason-lsc-mode-capwap" {
        value 45;
        description
          "Reason for AP reboot - LSC for CAPWAP";
      }
      enum "ap-reboot-reason-lsc-mode-dot1x" {
        value 46;
        description
          "Reason for AP reboot - LSC for 802.1x";
      }
      enum "ap-reboot-reason-lsc-mode-all" {
        value 47;
        description
          "Reason for AP reboot - LSC for all";
      }
      enum "ap-reboot-reason-ap-type-changed-to-cloud" {
        value 48;
        description
          "Reason for AP reboot - AP type changed to cloud";
      }
      enum "ap-reboot-reason-dtls-init-failure" {
        value 49;
        description
          "Reason for AP reboot - DTLS init failure";
      }
      enum "ap-reboot-reason-pnp-no-capwap-backoff" {
        value 50;
        description
          "Reason for AP reboot - In no CAPWAP backoff mode for more than 24 hours";
      }
      enum "ap-reboot-reason-day0-config-failure" {
        value 51;
        description
          "Reason for AP reboot - Day 0 config failure";
      }
      enum "ap-reboot-reason-day1-config-failure" {
        value 52;
        description
          "Reason for AP reboot - Day 1 config failure";
      }
      enum "ap-reboot-reason-pnp-triggered-reload" {
        value 53;
        description
          "Reason for AP reboot - Triggered by PnP server";
      }
      enum "ap-reboot-reason-tri-radio-support" {
        value 54;
        description
          "Reason for AP reboot - Tri-radio support change";
      }
      enum "ap-reboot-reason-indoor-deployment" {
        value 55;
        description
          "Reason for AP reboot - Indoor Deployment";
      }
      enum "ap-reboot-reason-ap-type-changed-from-wgb-to-capwap" {
        value 56;
        description
          "Reason for AP reboot - AP type changed from WGB to CAPWAP";
      }
      enum "ap-reboot-reason-ap-type-changed-from-cloud-to-capwap" {
        value 57;
        description
          "Reason for AP reboot - AP type changed from cloud to CAPWAP";
      }
      enum "ap-reboot-reason-ap-type-changed-to-wgb" {
        value 58;
        description
          "Reason for AP reboot - AP type changed from CAPWAP to WGB";
      }
    }
    description
      "enumeration for reboot reason";
  }

  typedef spam-ap-reboot-types {
    type enumeration {
      enum "ap-reboot-link-failure" {
        value 0;
        description
          "ap reboot reason - link failure";
      }
      enum "ap-reboot-spam-initiated" {
        value 1;
        description
          "ap reboot reason - initiated by code";
      }
      enum "ap-reboot-crash" {
        value 2;
        description
          "ap reboot reason - AP crashed";
      }
    }
    description
      "Various reasons for AP reboot";
  }

  typedef spam-ap-disconnect-reason {
    type enumeration {
      enum "unkown" {
        value 0;
        description
          "Unknown reason for disconnect ";
      }
      enum "wtp-post-join-timer-expired" {
        value 1;
        description
          "Join timer expired";
      }
      enum "wtp-wait-dtls-timer-expired" {
        value 2;
        description
          "Dtls time expired";
      }
      enum "wtp-join-response-decode-failed" {
        value 3;
        description
          "Decode failed for join response";
      }
      enum "wtp-img-data-resp-decode-failed" {
        value 4;
        description
          "Decode failed for image data response";
      }
      enum "wtp-config-status-decode-failed" {
        value 5;
        description
          "Decode failed for config status";
      }
      enum "wtp-change-state-report-send-failed" {
        value 6;
        description
          "Failed to send state change report";
      }
      enum "wtp-udi-info-send-failed" {
        value 7;
        description
          "UDI info send failed";
      }
      enum "wtp-data-dtls-init-failed" {
        value 8;
        description
          "Failed to initiate Data DTLS handshake";
      }
      enum "wtp-heartbeat-timer-start-failed" {
        value 9;
        description
          "Failed to start heart beat timer";
      }
      enum "wtp-echo-timer-start-failed" {
        value 10;
        description
          "Failed to start periodic echo timer";
      }
      enum "wtp-max-retransmission-reached" {
        value 11;
        description
          "Max retransmit counter reached";
      }
      enum "wtp-found-master-mwar" {
        value 12;
        description
          "Found master controller";
      }
      enum "wtp-found-configured-primary-mwar" {
        value 13;
        description
          "Found primary WLC";
      }
      enum "wtp-found-configured-secondary-mwar" {
        value 14;
        description
          "Found secondary WLC";
      }
      enum "wtp-found-configured-tertiary-mwar" {
        value 15;
        description
          "Found tertiary WLC";
      }
      enum "wtp-ip-addr-set-to-static" {
        value 16;
        description
          "Static IP address set";
      }
      enum "wtp-ip-addr-reset" {
        value 17;
        description
          "IP address reset";
      }
      enum "wtp-image-error" {
        value 18;
        description
          "AP image error";
      }
      enum "wtp-capwap-sm-restart" {
        value 19;
        description
          "CAPWAP state machine restart";
      }
      enum "wtp-controller-initiated-reason" {
        value 20;
        description
          "WLC initiated";
      }
      enum "wtp-dtls-session-est-fail" {
        value 21;
        description
          "Dtls session establishment failed";
      }
      enum "wtp-wait-dtls-no-join-response" {
        value 22;
        description
          "Join response not received";
      }
      enum "wtp-img-resp-error-image-rejected" {
        value 23;
        description
          "WLC rejected image";
      }
      enum "wtp-img-resp-err-db-entry-fetch-fail" {
        value 24;
        description
          "Image response error. Failed to get database entry";
      }
      enum "wtp-img-req-err-db-entry-fetch-fail" {
        value 25;
        description
          "Image request error. Failed to get database entry";
      }
      enum "wtp-img-req-err-decode-fail" {
        value 26;
        description
          "Unknown reason for AP reboot";
      }
      enum "wtp-img-req-err-img-data-resp-fail" {
        value 27;
        description
          "Failed to send Image data response";
      }
      enum "wtp-img-req-err-predownload-fail" {
        value 28;
        description
          "Image predownload failed";
      }
      enum "wtp-img-req-err-activate-fail" {
        value 29;
        description
          "Image activate fail";
      }
      enum "wtp-reboot-mode-change-11g" {
        value 30;
        description
          "Reboot due to mode change 11G";
      }
      enum "wtp-reboot-mode-change-wgb" {
        value 31;
        description
          "Reboot due to mode change WGB";
      }
      enum "wtp-reboot-mode-change-me" {
        value 32;
        description
          "Reboot due to mode change ME";
      }
      enum "wtp-reboot-mode-change-cloud" {
        value 33;
        description
          "Reboot due to mode change cloud";
      }
      enum "wtp-reboot-mode-change-capwap" {
        value 34;
        description
          "Reboot due to mode change CAPWAP";
      }
      enum "wtp-reboot-image-upgrade" {
        value 35;
        description
          "Image upgrade";
      }
      enum "wtp-reboot-user-cmd" {
        value 36;
        description
          "Reboot due to user command";
      }
      enum "wtp-reboot-erase-cfg-cmd" {
        value 37;
        description
          "Reboot due to erase config command";
      }
      enum "wtp-reboot-dimished-pwr-change" {
        value 38;
        description
          "Reboot due to diminished power change";
      }
      enum "wtp-capwap-cli-restart" {
        value 39;
        description
          "User command CAPWAP restart";
      }
    }
    description
      "Enumeration for AP disconnect reason";
  }

  typedef enm-client-network-preference {
    type enumeration {
      enum "connectivity" {
        value 0;
        description
          "connectivity";
      }
      enum "throughput" {
        value 1;
        description
          "throughput";
      }
      enum "default" {
        value 2;
        description
          "default";
      }
    }
    description
      "Enums specifies the group of client network preferences";
  }

  typedef radio-sub-mode {
    type enumeration {
      enum "radio-sub-mode-none" {
        value 0;
        description
          "Radio sub mode None";
      }
      enum "radio-sub-mode-auto" {
        value 1;
        description
          "Radio sub mode Auto";
      }
      enum "ap-radio-sub-mode-manual" {
        value 2;
        description
          "Radio sub mode Manual";
      }
    }
    description
      "Enum for radio sub mode";
  }

  typedef enm-fra-sensitivity {
    type enumeration {
      enum "fra-sensitivity-high" {
        value 1;
        description
          "high (90%)";
      }
      enum "fra-sensitivity-medium" {
        value 2;
        description
          "medium (95%)";
      }
      enum "fra-sensitivity-low" {
        value 3;
        description
          "low (100%)";
      }
      enum "fra-sensitivity-higher" {
        value 4;
        description
          "higher (85%)";
      }
      enum "fra-sensitivity-even-higher" {
        value 5;
        description
          "even higher (80%)";
      }
      enum "fra-sensitivity-super-high" {
        value 6;
        description
          "super high (50%)";
      }
    }
    description
      "Enums specifies the group of Flexible radio Sensitivity";
  }

  typedef enm-fra-service-priority {
    type enumeration {
      enum "fra-service-priority-coverage" {
        value 0;
        description
          "Configures FRA Service Priority to Coverage";
      }
      enum "fra-service-priority-client-aware" {
        value 1;
        description
          "Configures FRA Service Priority to Client Aware";
      }
      enum "fra-service-priority-service-assurance" {
        value 2;
        description
          "Configures FRA Service Priority to Service Assurance";
      }
    }
    description
      "Enums specifies service priority for XOR radio used by FRA algorithm";
  }

  typedef enm-fra-sensor-coverage-profile {
    type enumeration {
      enum "fra-sensor-coverage-client-priority" {
        value 0;
        description
          "FRA sensor coverage client priority";
      }
      enum "fra-sensor-coverage-client-preferred" {
        value 1;
        description
          "FRA sensor coverage client preferred";
      }
      enum "fra-sensor-coverage-balanced" {
        value 2;
        description
          "FRA sensor coverage balanced";
      }
      enum "fra-sensor-coverage-sensor-preferred" {
        value 3;
        description
          "FRA sensor coverage sensor priority";
      }
      enum "fra-sensor-coverage-sensor-priority" {
        value 4;
        description
          "FRA sensor coverage sensor preferred";
      }
    }
    description
      "Enums specifies sensor coverage for FRA based selection";
  }

  typedef enm-band-switch-reason {
    type enumeration {
      enum "band-switch-reason-none" {
        value 0;
        description
          "Band switch has not happened";
      }
      enum "band-switch-reason-chd" {
        value 1;
        description
          "Band Switch due to CHD";
      }
      enum "band-switch-reason-hyperlocation" {
        value 2;
        description
          "Band Switch due to Hyperlocation";
      }
      enum "band-switch-reason-revert" {
        value 3;
        description
          "Band Switch due to Band Revert";
      }
      enum "band-switch-reason-fra" {
        value 4;
        description
          "Band Switch due to FRA";
      }
      enum "band-switch-reason-manul" {
        value 5;
        description
          "Band Switch due to Manual band change";
      }
      enum "band-switch-reason-sensor" {
        value 6;
        description
          "Band Switch due to Sensor";
      }
      enum "band-switch-reason-client-aware-fra" {
        value 7;
        description
          "Band Switch due to Client Aware FRA";
      }
      enum "band-switch-reason-network-assurance-fra" {
        value 8;
        description
          "Band Switch due to Network Assurance FRA";
      }
    }
    description
      "Set of reasons for Dual band radio band switch";
  }

  typedef ap-role {
    type enumeration {
      enum "ap-role-root" {
        value 1;
        description
          "ap role is root AP";
      }
      enum "ap-role-mesh" {
        value 2;
        description
          "ap role is mesh ap";
      }
    }
    description
      "Enumeration for Role of AP in case of bridge mode AP";
  }

  typedef mesh-security-mode {
    type enumeration {
      enum "mesh-security-mode-eap" {
        value 0;
        description
          "wireless mesh security mode eap";
      }
      enum "mesh-security-mode-psk" {
        value 1;
        description
          "wireless mesh security mode psk";
      }
    }
    description
      "wireless mesh security mode";
  }

  typedef mesh-bhaul-radio-type {
    type enumeration {
      enum "mesh-bhaul-radio-unknown" {
        value 0;
        description
          "Indicates 802.11 interface type of mesh downlink backhaul is unknown";
      }
      enum "mesh-bhaul-radio-24ghz" {
        value 1;
        description
          "Indicates 802.11bg radio interface is used as mesh downlink backhaul";
      }
      enum "mesh-bhaul-radio-5ghz" {
        value 2;
        description
          "Indicates 802.11a radio interface is used as mesh downlink backhaul";
      }
    }
    description
      "Represents 802.11 Radio type of the mesh downlink backhaul";
  }

  typedef mesh-bhaul-data-rate-type {
    type enumeration {
      enum "mesh-bhaul-rate-auto" {
        value 0;
        description
          "Indicates auto data rate is used for mesh backhaul traffic";
      }
      enum "mesh-bhaul-rate-type-dot11abg" {
        value 1;
        description
          "Indicates 802.11abg rate is used for mesh backhaul traffic";
      }
      enum "mesh-bhaul-rate-type-dot11n" {
        value 2;
        description
          "Indicates 802.11n mcs rate is used for mesh backhaul traffic";
      }
      enum "mesh-bhaul-rate-type-dot11ac" {
        value 3;
        description
          "Indicates 802.11ac mcs rate is used for mesh backhaul traffic";
      }
    }
    description
      "Represents transmit data rate type used for mesh backhaul traffic";
  }

  typedef mesh-dot11abg-data-rate {
    type enumeration {
      enum "data-rate-auto" {
        value 0;
        description
          "Indicates data rate used for mesh backhaul traffic is auto";
      }
      enum "data-rate-1mbps" {
        value 1;
        description
          "Indicates data rate used for mesh backhaul traffic is 1 Mbps";
      }
      enum "data-rate-2abpsm" {
        value 2;
        description
          "Indicates data rate used for mesh backhaul traffic is 2 Mbps";
      }
      enum "data-rate-5dot5mbps" {
        value 3;
        description
          "Indicates data rate used for mesh backhaul traffic is 5.5 Mbps";
      }
      enum "data-rate-11mbps" {
        value 4;
        description
          "Indicates data rate used for mesh backhaul traffic is 11 Mbps";
      }
      enum "data-rate-6mbps" {
        value 5;
        description
          "Indicates data rate used for mesh backhaul traffic is 6 Mbps";
      }
      enum "data-rate-9mbps" {
        value 6;
        description
          "Indicates data rate used for mesh backhaul traffic is 9 Mbps";
      }
      enum "data-rate-12mbps" {
        value 7;
        description
          "Indicates data rate used for mesh backhaul traffic is 12 Mbps";
      }
      enum "data-rate-18mbps" {
        value 8;
        description
          "Indicates data rate used for mesh backhaul traffic is 18 Mbps";
      }
      enum "data-rate-24mbps" {
        value 9;
        description
          "Indicates data rate used for mesh backhaul traffic is 24 Mbps";
      }
      enum "data-rate-36mbps" {
        value 10;
        description
          "Indicates data rate used for mesh backhaul traffic is 36 Mbps";
      }
      enum "data-rate-48mbps" {
        value 11;
        description
          "Indicates data rate used for mesh backhaul traffic is 48 Mbps";
      }
      enum "data-rate-54mbps" {
        value 12;
        description
          "Indicates data rate used for mesh backhaul traffic is 54 Mbps";
      }
    }
    description
      "Represents 802.11abg transmit data rate value for mesh backhaul traffic";
  }

  typedef mesh-multicast-mode {
    type enumeration {
      enum "mesh-multicast-mode-regular" {
        value 0;
        description
          "wireless mesh multicast mode regular";
      }
      enum "mesh-multicast-mode-in" {
        value 1;
        description
          "wireless mesh multicast mode in";
      }
      enum "mesh-multicast-mode-inout" {
        value 2;
        description
          "wireless mesh multicast mode inout";
      }
    }
    description
      "wireless mesh multicast mode";
  }

  typedef mesh-convergence-method {
    type enumeration {
      enum "mesh-convergence-standard" {
        value 0;
        description
          "wireless mesh convergence method standard";
      }
      enum "mesh-convergence-fast" {
        value 1;
        description
          "wireless mesh convergence method fast";
      }
      enum "mesh-convergence-veryfast" {
        value 2;
        description
          "wireless mesh convergence method very fast";
      }
      enum "mesh-convergence-noise-tolerant-fast" {
        value 3;
        description
          "wireless mesh convergence method noise tolerant fast";
      }
    }
    description
      "wireless mesh convergence method";
  }

  typedef mesh-adj-state {
    type enumeration {
      enum "mesh-adj-state-uninit" {
        value 0;
        description
          "adjacency state uninitialized";
      }
      enum "mesh-adj-state-scan" {
        value 1;
        description
          "adjacency state scan";
      }
      enum "mesh-adj-state-preseek" {
        value 2;
        description
          "adjacency state pre-seek";
      }
      enum "mesh-adj-state-seek" {
        value 3;
        description
          "adjacency state seek";
      }
      enum "mesh-adj-state-sync" {
        value 4;
        description
          "adjacency state sync";
      }
      enum "mesh-adj-state-maint" {
        value 5;
        description
          "adjacency state maintenance";
      }
    }
    description
      "Mesh adjacency state";
  }

  typedef mesh-bhaul-mode {
    type enumeration {
      enum "mesh-bhaul-mode-select-default" {
        value 0;
        description
          "Represents 802.11 interface type of the backhaul link";
      }
      enum "mesh-bhaul-mode-select-11a" {
        value 1;
        description
          "802.11a radio is used as backhaul link";
      }
      enum "mesh-bhaul-mode-select-11b" {
        value 4;
        description
          "802.11b radio is used as backhaul link";
      }
      enum "mesh-bhaul-mode-select-11g" {
        value 8;
        description
          "802.11g radio is used as backhaul link";
      }
    }
    description
      "Represents 802.11 interface type of the backhaul link";
  }

  typedef mesh-node-pkt-queue-type {
    type enumeration {
      enum "mesh-node-pkt-queue-silver" {
        value 0;
        description
          "queue for Best Effort packets";
      }
      enum "mesh-node-pkt-queue-gold" {
        value 1;
        description
          "queue for Video Application";
      }
      enum "mesh-node-pkt-queue-platinum" {
        value 2;
        description
          "queue for Voice Application";
      }
      enum "mesh-node-pkt-queue-bronze" {
        value 3;
        description
          "queue for Background";
      }
      enum "mesh-node-pkt-queue-mgmt" {
        value 4;
        description
          "queue for management frames";
      }
    }
    description
      "Represents different type of priority queues in a mesh node";
  }

  typedef ethernet-port-type {
    type enumeration {
      enum "port-type-normal" {
        value 0;
        description
          "Port type is normal";
      }
      enum "port-type-access" {
        value 1;
        description
          "Port type is access";
      }
      enum "port-type-trunk" {
        value 2;
        description
          "Port type is trunk";
      }
    }
    description
      "Port type for the ethernet interface of the AP";
  }

  typedef mesh-node-battery-alarm {
    type enumeration {
      enum "mesh-node-battery-overload" {
        value 256;
        description
          "Alarm for battery overload";
      }
      enum "mesh-node-battery-acfail" {
        value 512;
        description
          "Alarm for battery AC Fail";
      }
      enum "mesh-node-battery-low" {
        value 1024;
        description
          "Alarm for low battery";
      }
      enum "mesh-node-battery-replace" {
        value 2048;
        description
          "Alarm for replacing battery";
      }
      enum "mesh-node-battery-unknown" {
        value 4096;
        description
          "Undefined battery alarm";
      }
      enum "mesh-node-battery-missing" {
        value 8192;
        description
          "Alarm for missing battery";
      }
    }
    description
      "Represents different alarms for external battery of Mesh Access Point";
  }

  typedef enm-atf-client-state {
    type enumeration {
      enum "atf-client-state-none" {
        value 0;
        description
          "Client usage by a client on its associated AP radio is unknown";
      }
      enum "atf-client-state-low-usage" {
        value 1;
        description
          "Client usage by a client on its associated AP radio is low";
      }
      enum "atf-client-state-reg-usage" {
        value 2;
        description
          "Client usage by a client on its associated AP radio is regular";
      }
      enum "atf-client-state-over-usage" {
        value 3;
        description
          "Client usage by a client on its associated AP radio is high";
      }
    }
    description
      "Client usage by a client on its associated AP radio";
  }

  typedef enm-atf-mesh-node-role {
    type enumeration {
      enum "atf-mesh-node-role-parent" {
        value 1;
        description
          "AirTime Fairness mesh node role is parent";
      }
      enum "atf-mesh-node-role-child" {
        value 2;
        description
          "AirTime Fairness mesh node role is child";
      }
    }
    description
      "AirTime Fairness mesh node role";
  }

  typedef enm-atf-mesh-link {
    type enumeration {
      enum "atf-mesh-link-universal-client-access" {
        value 1;
        description
          "AirTime Fairness mesh link is universal client access";
      }
      enum "atf-mesh-link-backhaul-access-only" {
        value 2;
        description
          "AirTime Fairness mesh link is backhaul access only";
      }
      enum "atf-mesh-link-client-access-only" {
        value 3;
        description
          "AirTime Fairness mesh link is client access only";
      }
    }
    description
      "AirTime Fairness mesh link";
  }

  typedef mesh-linktest-rate {
    type enumeration {
      enum "ewlc-mesh-linktest-rate-1m" {
        value 1;
        description
          "Indicates data rate used for mesh linktest  is 1 Mbps";
      }
      enum "ewlc-mesh-linktest-rate-2m" {
        value 2;
        description
          "Indicates data rate used for mesh linktest is 2 Mbps";
      }
      enum "ewlc-mesh-linktest-rate-5m" {
        value 5;
        description
          "Indicates data rate used for mesh linktest is 5.5 Mbps";
      }
      enum "ewlc-mesh-linktest-rate-6m" {
        value 6;
        description
          "Indicates data rate used for mesh linktest is 6 Mbps";
      }
      enum "ewlc-mesh-linktest-rate-9m" {
        value 9;
        description
          "Indicates data rate used for mesh linktest is 9 Mbps";
      }
      enum "ewlc-mesh-linktest-rate-11m" {
        value 11;
        description
          "Indicates data rate used for mesh linktest is 11 Mbps";
      }
      enum "ewlc-mesh-linktest-rate-12m" {
        value 12;
        description
          "Indicates data rate used for mesh linktest is 12 Mbps";
      }
      enum "ewlc-mesh-linktest-rate-18m" {
        value 18;
        description
          "Indicates data rate used for mesh linktest is 18 Mbps";
      }
      enum "ewlc-mesh-linktest-rate-24m" {
        value 24;
        description
          "Indicates data rate used for mesh linktest is 24 Mbps";
      }
      enum "ewlc-mesh-linktest-rate-36m" {
        value 36;
        description
          "Indicates data rate used for mesh linktest is 36 Mbps";
      }
      enum "ewlc-mesh-linktest-rate-48m" {
        value 48;
        description
          "Indicates data rate used for mesh linktest is 48 Mbps";
      }
      enum "ewlc-mesh-linktest-rate-54m" {
        value 54;
        description
          "Indicates data rate used for mesh linktest is 54 Mbps";
      }
      enum "ewlc-mesh-linktest-rate-108m" {
        value 108;
        description
          "Indicates data rate used for mesh linktest is 108 Mbps";
      }
      enum "ewlc-mesh-linktest-rate-mcs0" {
        value 256;
        description
          "Indicates data rate used for mesh linktest is mcs0";
      }
      enum "ewlc-mesh-linktest-rate-mcs1" {
        value 257;
        description
          "Indicates data rate used for mesh linktest is mcs1";
      }
      enum "ewlc-mesh-linktest-rate-mcs2" {
        value 258;
        description
          "Indicates data rate used for mesh linktest is mcs2";
      }
      enum "ewlc-mesh-linktest-rate-mcs3" {
        value 259;
        description
          "Indicates data rate used for mesh linktest is mcs3";
      }
      enum "ewlc-mesh-linktest-rate-mcs4" {
        value 260;
        description
          "Indicates data rate used for mesh linktest is mcs4";
      }
      enum "ewlc-mesh-linktest-rate-mcs5" {
        value 261;
        description
          "Indicates data rate used for mesh linktest is mcs5";
      }
      enum "ewlc-mesh-linktest-rate-mcs6" {
        value 262;
        description
          "Indicates data rate used for mesh linktest is mcs6";
      }
      enum "ewlc-mesh-linktest-rate-mcs7" {
        value 263;
        description
          "Indicates data rate used for mesh linktest is mcs7";
      }
      enum "ewlc-mesh-linktest-rate-mcs8" {
        value 264;
        description
          "Indicates data rate used for mesh linktest is mcs8";
      }
      enum "ewlc-mesh-linktest-rate-mcs9" {
        value 265;
        description
          "Indicates data rate used for mesh linktest is mcs9";
      }
      enum "ewlc-mesh-linktest-rate-mcs10" {
        value 266;
        description
          "Indicates data rate used for mesh linktest is mcs10";
      }
      enum "ewlc-mesh-linktest-rate-mcs11" {
        value 267;
        description
          "Indicates data rate used for mesh linktest is mcs11";
      }
      enum "ewlc-mesh-linktest-rate-mcs12" {
        value 268;
        description
          "Indicates data rate used for mesh linktest is mcs12";
      }
      enum "ewlc-mesh-linktest-rate-mcs13" {
        value 269;
        description
          "Indicates data rate used for mesh linktest is mcs13";
      }
      enum "ewlc-mesh-linktest-rate-mcs14" {
        value 270;
        description
          "Indicates data rate used for mesh linktest is mcs14";
      }
      enum "ewlc-mesh-linktest-rate-mcs15" {
        value 271;
        description
          "Indicates data rate used for mesh linktest is mcs15";
      }
    }
    description
      "Represents transmit data rate value for mesh link test";
  }

  typedef mesh-linktest-cfg-status {
    type enumeration {
      enum "mesh-linktest-start" {
        value 0;
        description
          "Mesh link test starts";
      }
      enum "mesh-linktest-free" {
        value 1;
        description
          "Mesh link test is free";
      }
      enum "mesh-linktest-get-results" {
        value 2;
        description
          "Mesh link test collects result";
      }
      enum "mesh-linktest-get-results-sampled" {
        value 3;
        description
          "Mesh link test samples result";
      }
      enum "mesh-linktest-invalid-destination" {
        value 4;
        description
          "Mesh link test destination is invalid ";
      }
      enum "mesh-linktest-starting" {
        value 5;
        description
          "Mesh link test is starting";
      }
      enum "mesh-linktest-in-progress" {
        value 6;
        description
          "Mesh link test in progress";
      }
      enum "mesh-linktest-complete" {
        value 7;
        description
          "Mesh link test completes";
      }
      enum "mesh-linktest-failed" {
        value 8;
        description
          "Mesh link test fails";
      }
    }
    description
      "Enum for mesh link test config status";
  }

  typedef mesh-linktest-rate-idx {
    type enumeration {
      enum "ewlc-mesh-linktest-rate-idx-1" {
        value 1;
        description
          "Indicates data rate index used for mesh linktest  is 1(1 Mbps)";
      }
      enum "ewlc-mesh-linktest-rate-idx-2" {
        value 2;
        description
          "Indicates data rate index used for mesh linktest is 2 (2 Mbps)";
      }
      enum "ewlc-mesh-linktest-rate-idx-3" {
        value 3;
        description
          "Indicates data rate index used for mesh linktest is 3 (5.5 Mbps)";
      }
      enum "ewlc-mesh-linktest-rate-idx-4" {
        value 4;
        description
          "Indicates data rate index used for mesh linktest is 4 (6 Mbps)";
      }
      enum "ewlc-mesh-linktest-rate-idx-5" {
        value 5;
        description
          "Indicates data rate index used for mesh linktest is 5 (9 Mbps)";
      }
      enum "ewlc-mesh-linktest-rate-idx-6" {
        value 6;
        description
          "Indicates data rate index used for mesh linktest is 6 (11 Mbps)";
      }
      enum "ewlc-mesh-linktest-rate-idx-7" {
        value 7;
        description
          "Indicates data rate index used for mesh linktest is 7 (12 Mbps)";
      }
      enum "ewlc-mesh-linktest-rate-idx-8" {
        value 8;
        description
          "Indicates data rate index used for mesh linktest is 8 (18 Mbps)";
      }
      enum "ewlc-mesh-linktest-rate-idx-9" {
        value 9;
        description
          "Indicates data rate index used for mesh linktest is 9 (24 Mbps)";
      }
      enum "ewlc-mesh-linktest-rate-idx-10" {
        value 10;
        description
          "Indicates data rate index used for mesh linktest is 10 (36 Mbps)";
      }
      enum "ewlc-mesh-linktest-rate-idx-11" {
        value 11;
        description
          "Indicates data rate index used for mesh linktest is 11 (48 Mbps)";
      }
      enum "ewlc-mesh-linktest-rate-idx-12" {
        value 12;
        description
          "Indicates data rate index used for mesh linktest is 12 (54 Mbps)";
      }
      enum "ewlc-mesh-linktest-rate-idx-13" {
        value 13;
        description
          "Indicates data rate index used for mesh linktest is 13 (108 Mbps)";
      }
      enum "ewlc-mesh-linktest-rate-idx-14" {
        value 14;
        description
          "Indicates data rate index used for mesh linktest is 14 (mcs0)";
      }
      enum "ewlc-mesh-linktest-rate-idx-15" {
        value 15;
        description
          "Indicates data rate index used for mesh linktest is 15 (mcs1)";
      }
      enum "ewlc-mesh-linktest-rate-idx-16" {
        value 16;
        description
          "Indicates data rate index used for mesh linktest is 16 (mcs2)";
      }
      enum "ewlc-mesh-linktest-rate-idx-17" {
        value 17;
        description
          "Indicates data rate index used for mesh linktest is 17 (mcs3)";
      }
      enum "ewlc-mesh-linktest-rate-idx-18" {
        value 18;
        description
          "Indicates data rate index used for mesh linktest is 18 (mcs4)";
      }
      enum "ewlc-mesh-linktest-rate-idx-19" {
        value 19;
        description
          "Indicates data rate index used for mesh linktest is 19 (mcs5)";
      }
      enum "ewlc-mesh-linktest-rate-idx-20" {
        value 20;
        description
          "Indicates data rate index used for mesh linktest is 20 (mcs6)";
      }
      enum "ewlc-mesh-linktest-rate-idx-21" {
        value 21;
        description
          "Indicates data rate index used for mesh linktest is 21 (mcs7)";
      }
      enum "ewlc-mesh-linktest-rate-idx-22" {
        value 22;
        description
          "Indicates data rate index used for mesh linktest is 22 (mcs8)";
      }
      enum "ewlc-mesh-linktest-rate-idx-23" {
        value 23;
        description
          "Indicates data rate index used for mesh linktest is 23 (mcs9)";
      }
      enum "ewlc-mesh-linktest-rate-idx-24" {
        value 24;
        description
          "Indicates data rate index used for mesh linktest is 24 (mcs10)";
      }
      enum "ewlc-mesh-linktest--rate-idx-25" {
        value 25;
        description
          "Indicates data rate index used for mesh linktest is 25 (mcs11)";
      }
      enum "ewlc-mesh-linktest-rate-idx-26" {
        value 26;
        description
          "Indicates data rate index used for mesh linktest is 26 (mcs12)";
      }
      enum "ewlc-mesh-linktest-rate-idx-27" {
        value 27;
        description
          "Indicates data rate index used for mesh linktest is 27 (mcs13)";
      }
      enum "ewlc-mesh-linktest-rate-idx-28" {
        value 28;
        description
          "Indicates data rate index used for mesh linktest is 28 (mcs14)";
      }
      enum "ewlc-mesh-linktest-rate-idx-295" {
        value 29;
        description
          "Indicates data rate index used for mesh linktest is 29 (mcs15)";
      }
    }
    description
      "Represents transmit data rate index value for mesh link test";
  }

  typedef enm-nas-id-options {
    type enumeration {
      enum "nas-id-not-configured" {
        value 0;
        description
          "NAS-ID not configured";
      }
      enum "nas-id-sys-name" {
        value 1;
        description
          "NAS-ID configured for system name";
      }
      enum "nas-id-sys-ip" {
        value 2;
        description
          "NAS-ID configured for system IP";
      }
      enum "nas-id-sys-mac" {
        value 3;
        description
          "NAS-ID configured for system MAC";
      }
      enum "nas-id-ap-ip" {
        value 4;
        description
          "NAS-ID configured for AP IP";
      }
      enum "nas-id-ap-name" {
        value 5;
        description
          "NAS-ID configured for AP name";
      }
      enum "nas-id-ap-mac" {
        value 6;
        description
          "NAS-ID configured for AP MAC";
      }
      enum "nas-id-ap-eth-mac" {
        value 7;
        description
          "NAS-ID configured of AP ethernet MAC";
      }
      enum "nas-id-ap-policy-tag" {
        value 8;
        description
          "NAS-ID configured for AP policy-tag";
      }
      enum "nas-id-ap-site-tag" {
        value 9;
        description
          "NAS-ID configured for AP site-tag";
      }
      enum "nas-id-ssid" {
        value 10;
        description
          "NAS-ID configured for bssid";
      }
      enum "nas-id-ap-location" {
        value 11;
        description
          "NAS-ID configured for AP location";
      }
    }
    description
      "Enumeration for NAS-ID options";
  }

  typedef enm-radio-frequency {
    type enumeration {
      enum "radio-24-ghz" {
        value 0;
        description
          "Radio frequency is 2.4GHz";
      }
      enum "radio-5-ghz" {
        value 1;
        description
          "Radio frequency is 5GHz";
      }
    }
    description
      "Enum to represent the radio frequency";
  }

  typedef enum-ewlc-lsc-key-size {
    type enumeration {
      enum "lsc-keysize-2048" {
        value 0;
        description
          "CSR key size is 2048";
      }
      enum "lsc-keysize-3072" {
        value 1;
        description
          "CSR key size is 3072";
      }
      enum "lsc-keysize-4096" {
        value 2;
        description
          "CSR key size is 4096";
      }
    }
    description
      "Size of the key with which AP generates a certificate signing request for LSC";
  }

  typedef lsc-prov-status {
    type enumeration {
      enum "lsc-prov-disable" {
        value 0;
        description
          "Disable AP LSC provisioning for all APs";
      }
      enum "lsc-prov-enable-all" {
        value 1;
        description
          "Enable LSC provisioning for all joined APs";
      }
      enum "lsc-prov-enable-provision-list" {
        value 2;
        description
          "Enable LSC provisioning for all APs in the LSC Provision list";
      }
    }
    description
      "LSC Provisioning status that indicates if the provisioning is Disabled/Enabled for all/Enabled to a provision list";
  }

  typedef enm-host-mode {
    type enumeration {
      enum "single-host-mode" {
        value 0;
        description
          "Rlan single host mode";
      }
      enum "multi-host-mode" {
        value 1;
        description
          "Rlan multi host mode";
      }
      enum "multi-domain-mode" {
        value 2;
        description
          "Rlan multi domain mode";
      }
    }
    description
      "Enumeration for rlan host mode";
  }

  typedef enm-violation-mode {
    type enumeration {
      enum "violation-mode-replace" {
        value 0;
        description
          "Rlan replace violation mode";
      }
      enum "violation-mode-shutdown" {
        value 1;
        description
          "Rlan shutdown violation mode";
      }
      enum "violation-mode-protect" {
        value 2;
        description
          "Rlan protect violation mode";
      }
    }
    description
      "Enumeration for rlan violation mode";
  }

  typedef enm-cts-sxp-conn-mode {
    type enumeration {
      enum "cts-sxp-connection-mode-speaker" {
        value 1;
        description
          "Cts sxp config connection mode";
      }
      enum "cts-sxp-connection-mode-listener" {
        value 2;
        description
          "Cts sxp config connection mode";
      }
      enum "cts-sxp-connection-mode-both" {
        value 3;
        description
          "Cts sxp config connection mode";
      }
    }
    description
      "Enumeration for cts sxp configuration";
  }

  typedef enm-cts-sxp-password-type {
    type enumeration {
      enum "cts-sxp-connection-password-none" {
        value 0;
        description
          "Cts sxp config connection password none";
      }
      enum "cts-sxp-connection-password-default" {
        value 2;
        description
          "Cts sxp config connection password default ";
      }
    }
    description
      "Enumeration for cts sxp configuration";
  }

  typedef enum-ewlc-ap-upgrade-config {
    type enumeration {
      enum "ap-staggered-upgrade-percent-5" {
        value 0;
        description
          "AP_UPGRADE 5% AP per iteration";
      }
      enum "ap-staggered-upgrade-percent-15" {
        value 1;
        description
          "AP_UPGRADE 15% AP per iteration";
      }
      enum "ap-staggered-upgrade-percent-25" {
        value 2;
        description
          "AP_UPGRADE 25% AP per iteration";
      }
      enum "ap-staggered-upgrade-one-shot" {
        value 3;
        description
          "AP upgrade in one shot";
      }
    }
    description
      "Staggered AP Upgrade";
  }

  typedef enum-ap-upgrade-type {
    type enumeration {
      enum "ap-upgrade-type-test" {
        value 0;
        description
          "Test AP upgrade";
      }
      enum "ap-upgrade-type-production" {
        value 1;
        description
          "Production AP upgrade";
      }
      enum "ap-upgrade-type-forced" {
        value 2;
        description
          "Forced AP upgrade";
      }
      enum "ap-upgrade-type-production-destination" {
        value 3;
        description
          "Production AP upgrade with destination name and ip";
      }
      enum "ap-upgrade-type-move" {
        value 4;
        description
          "This AP upgrade type just moves APs instead of upgrading APs";
      }
      enum "ap-upgrade-type-move-report" {
        value 5;
        description
          "This AP upgrade type just moves APs based on existing report";
      }
    }
    description
      "Type of the AP upgrade";
  }

  typedef enm-ewlc-dot11-radio-band {
    type enumeration {
      enum "dot11-2-dot-4-ghz-band" {
        value 1;
        description
          "Dot11 2.4 GHz radio band";
      }
      enum "dot11-5-ghz-band" {
        value 2;
        description
          "Dot11 5 GHz radio band";
      }
    }
    description
      "ENUM for dot11 radio band type";
  }

  typedef rx-sen-sop-threshold-level {
    type enumeration {
      enum "rrm-ewlc-rxsensop-threshold-auto" {
        value 0;
        description
          "rrm ewlc rx sensitivity threshold is auto";
      }
      enum "rrm-ewlc-rxsensop-threshold-low" {
        value 1;
        description
          "rrm ewlc rx sensitivity threshold is low";
      }
      enum "rrm-ewlc-rxsensop-threshold-medium" {
        value 2;
        description
          "rrm ewlc rx sensitivity threshold is medium";
      }
      enum "rrm-ewlc-rxsensop-threshold-high" {
        value 3;
        description
          "rrm ewlc rx sensitivity threshold is high";
      }
      enum "rrm-ewlc-rxsensop-threshold-custom" {
        value 4;
        description
          "rrm ewlc rx sensitivity threshold is custom";
      }
    }
    description
      "rx sensitivity threshold level";
  }

  typedef enm-mesh-node-neigh-state {
    type enumeration {
      enum "enm-mesh-node-neigh-state-updated" {
        value 0;
        description
          "Neighbor Mesh AP's state updated";
      }
      enum "enm-mesh-node-neigh-state-needupdate" {
        value 1;
        description
          "Neighbor Mesh AP's state needs update";
      }
      enum "enm-mesh-node-neigh-state-default" {
        value 2;
        description
          "Neighbor Mesh AP's state default";
      }
    }
    description
      "Enumeration for neighbor Mesh AP's neighbor info update state";
  }

  typedef enm-mesh-node-neigh-type {
    type enumeration {
      enum "enm-mesh-node-neigh-type-parent" {
        value 0;
        description
          "Neighbor Mesh AP's role parent";
      }
      enum "enm-mesh-node-neigh-type-tentparent" {
        value 1;
        description
          "Neighbor Mesh AP's role tentative parent";
      }
      enum "enm-mesh-node-neigh-type-neigh" {
        value 2;
        description
          "Neighbor Mesh AP's role neighbor";
      }
      enum "enm-mesh-node-neigh-type-black" {
        value 3;
        description
          "Neighbor Mesh AP's role blacklisted";
      }
      enum "enm-mesh-node-neigh-type-child" {
        value 4;
        description
          "Neighbor Mesh AP's role child";
      }
    }
    description
      "Neighbor Mesh AP's role";
  }

  typedef rrf-silent {
    type enumeration {
      enum "rrf-not-silent" {
        value 0;
        description
          "RRF radio mode set to client serving";
      }
      enum "rrf-silent" {
        value 1;
        description
          "RRF radio mode set to Monitor";
      }
      enum "rrf-silent-invalid" {
        value 199;
        description
          "Invalid RRF Silent State";
      }
    }
    description
      "Radio Role Flexibility(RRF) Silent state";
  }

  typedef rrf-redundant {
    type enumeration {
      enum "rrf-not-redundant" {
        value 0;
        description
          "RRF radio is not redundant";
      }
      enum "rrf-redundant" {
        value 1;
        description
          "RRF radio is marked as redundant";
      }
      enum "rrf-redundancy-invalid" {
        value 199;
        description
          "Invalid RRF Redundancy state";
      }
    }
    description
      "Radio Role Flexibility(RRF) Redundancy state";
  }

  typedef rrf-metric {
    type enumeration {
      enum "rrf-metric-invalid" {
        value 199;
        description
          "Invalid RRF Metric";
      }
      enum "rrf-metric-no-update" {
        value 200;
        description
          "RRF Metric indicating the Radio need not be updated for optimization";
      }
      enum "rrf-metric-radio-disabled" {
        value 249;
        description
          "RRF Metric indicating optimization is disabled for this Radio";
      }
    }
    description
      "Radio Role Flexibility(RRF) metric";
  }

  typedef dca-ewlc-chan-width-cap {
    type enumeration {
      enum "dca-ewlc-chan-width-cap-max" {
        value 0;
        description
          "MAX ALLOWED";
      }
      enum "dca-ewlc-chan-width-cap-20-mhz" {
        value 1;
        description
          "20 MHz";
      }
      enum "dca-ewlc-chan-width-cap-40-mhz" {
        value 2;
        description
          "40 MHz";
      }
      enum "dca-ewlc-chan-width-cap-80-mhz" {
        value 3;
        description
          "80 MHz";
      }
    }
    description
      "enumeration describing channel width";
  }

  typedef tx-power-change-reason {
    type enumeration {
      enum "rrm-txpower-auto" {
        value 0;
        description
          "Tx Power Auto";
      }
      enum "rrm-txpower-auto-default" {
        value 1;
        description
          "Tx Power Auto Default";
      }
      enum "rrm-txpower-auto-max" {
        value 2;
        description
          "Tx Power Auto Max";
      }
      enum "rrm-txpower-static" {
        value 3;
        description
          "Tx Power Auto Static";
      }
      enum "rrm-txpower-chd" {
        value 4;
        description
          "Tx Power CHD";
      }
      enum "rrm-txpower-hd" {
        value 5;
        description
          "Tx Power HD";
      }
      enum "rrm-txpower-unknown" {
        value 6;
        description
          "Tx Power unknown";
      }
    }
    description
      "Enum for tx power change";
  }

  typedef enm-rrm-grp-member-nack-reason {
    type enumeration {
      enum "rrm-member-nack-invalid" {
        value 0;
        description
          "RRM Member NACK Invalid";
      }
      enum "rrm-member-nack-grp-size-exceeded" {
        value 1;
        description
          "RRM Member NACK Group Size Exceeded";
      }
      enum "rrm-member-nack-inv-grp-order" {
        value 2;
        description
          "RRM Member NACK Invalid Group Order";
      }
      enum "rrm-member-nack-unmatch-grp-id" {
        value 3;
        description
          "RRM Member NACK Non-Matching Group ID";
      }
      enum "rrm-member-nack-unexpected-err" {
        value 4;
        description
          "RRM Member NACK Unexpected Error";
      }
      enum "rrm-member-nack-weak-signal-strength" {
        value 5;
        description
          "RRM Member NACK Weak Signal Strength";
      }
      enum "rrm-member-nack-join-pending" {
        value 6;
        description
          "RRM Member NACK Join Pending";
      }
      enum "rrm-member-nack-not-a-manager" {
        value 7;
        description
          "RRM Member NACK not a Manager";
      }
      enum "rrm-member-nack-grping-delayed" {
        value 8;
        description
          "RRM Member NACK Grouping Delayed";
      }
      enum "rrm-member-nack-grping-disabled" {
        value 9;
        description
          "RRM Member NACK Grouping Disabled";
      }
      enum "rrm-member-nack-invalid-version" {
        value 10;
        description
          "RRM Member NACK Invalid Protocol Version";
      }
      enum "rrm-member-nack-country-code-mismatch" {
        value 11;
        description
          "RRM Member NACK Country Code Mismatch";
      }
      enum "rrm-member-nack-invalid-hierarchy" {
        value 12;
        description
          "RRM Member NACK Invalid Hierarchy";
      }
      enum "rrm-member-nack-already-static-leader" {
        value 13;
        description
          "RRM Member NACK Already Static Leader";
      }
      enum "rrm-member-nack-member-of-another-grp" {
        value 14;
        description
          "RRM Member NACK Member of Another Group";
      }
      enum "rrm-member-nack-unconfigured-static-member" {
        value 15;
        description
          "RRM Member NACK Unconfigured Static Member";
      }
      enum "rrm-member-nack-ctrlr-name-ip-mismatch" {
        value 16;
        description
          "RRM Member NACK Controller Name and IP Mismatch";
      }
      enum "rrm-member-nack-unexpected-memory-err" {
        value 17;
        description
          "RRM Member NACK Unexpected Memory Error";
      }
      enum "rrm-member-nack-rf-domain-mismatch" {
        value 18;
        description
          "RRM Member NACK RF Domain Mismatch";
      }
      enum "rrm-member-nack-split-for-invalid-state-req" {
        value 19;
        description
          "RRM Member NACK Split for Invalid State Request";
      }
      enum "rrm-member-nack-split-transit-static-from-auto" {
        value 20;
        description
          "RRM Member NACK Transition to Static From Auto";
      }
      enum "rrm-member-nack-split-on-user-acton" {
        value 21;
        description
          "RRM Member NACK Split due to User Action";
      }
    }
    description
      "RRM group member NACK reason";
  }

  typedef radio-slot-antenna-type {
    type enumeration {
      enum "internal-antenna" {
        value 1;
        description
          "Internal Antenna";
      }
      enum "external-antenna" {
        value 2;
        description
          "External Antenna";
      }
      enum "circular-antenna" {
        value 3;
        description
          "Circular Antenna";
      }
    }
    description
      "Enum for radio slot Antenna type";
  }

  typedef ap-clear-config-op-type {
    type enumeration {
      enum "ap-clear-config" {
        value 0;
        description
          "Clear config on AP";
      }
      enum "ap-clear-config-keep-static-ip" {
        value 1;
        description
          "Clear config on AP but retain static IP address";
      }
    }
    description
      "Enum to represent AP clear config operation type";
  }

  typedef flag-dot11k-rm-capabilities {
    type bits {
      bit link-measurement {
        position 0;
        description
          "Link Measurement capability enabled";
      }
      bit neighbor-report {
        position 1;
        description
          "Neighbor Report capability enabled";
      }
      bit parallel-meas {
        position 2;
        description
          "Parallel Measurements capability enabled";
      }
      bit repeated-meas {
        position 3;
        description
          "Repeated Measurements capability enabled";
      }
      bit meas-mode-passive {
        position 4;
        description
          "Beacon Measurement Mode Passive capability enabled";
      }
      bit meas-mode-active {
        position 5;
        description
          "Beacon Measurement Mode Active capability enabled";
      }
      bit meas-mode-table {
        position 6;
        description
          "Beacon Measurement Mode Table capability enabled";
      }
      bit meas-report-cond {
        position 7;
        description
          "Beacon Measurement Mode Reporting Conditions capability enabled";
      }
      bit frame-measurement {
        position 8;
        description
          "Frame Measurement capability enabled";
      }
      bit channel-load-meas {
        position 9;
        description
          "Channel Load Measurement capability enabled";
      }
      bit noise-histogram-meas {
        position 10;
        description
          "Noise Histogram Measurement capability enabled";
      }
      bit statistics-meas {
        position 11;
        description
          "Statistics Measurement capability enabled";
      }
      bit lci-meas {
        position 12;
        description
          "LCI Measurement capability enabled";
      }
      bit lci-azimuth {
        position 13;
        description
          "LCI Azimuth capability enabled";
      }
      bit tx-stream-meas {
        position 14;
        description
          "Transmit Stream / Category Measurement capability enabled";
      }
      bit trig-tx-stream-meas {
        position 15;
        description
          "Triggered Transmit Stream / Category Measurement capability enabled";
      }
      bit ap-channel-report {
        position 16;
        description
          "AP Channel Report capability enabled";
      }
      bit rm-mib {
        position 17;
        description
          "RM MIB capability enabled";
      }
      bit oper-max-meas-b0 {
        position 18;
        description
          "Operating Channel Max Measurement Duration bit 0";
      }
      bit oper-max-meas-b1 {
        position 19;
        description
          "Operating Channel Max Measurement Duration bit 1";
      }
      bit oper-max-meas-b2 {
        position 20;
        description
          "Operating Channel Max Measurement Duration bit 2";
      }
      bit non-oper-max-meas-b0 {
        position 21;
        description
          "Non-operating Channel Max Measurement Duration bit 0";
      }
      bit non-oper-max-meas-b1 {
        position 22;
        description
          "Non-operating Channel Max Measurement Duration bit 1";
      }
      bit non-oper-max-meas-b2 {
        position 23;
        description
          "Non-operating Channel Max Measurement Duration bit 2";
      }
      bit meas-pilot-bit-0 {
        position 24;
        description
          "Measurement Pilot capability bit 0";
      }
      bit meas-pilot-bit-1 {
        position 25;
        description
          "Measurement Pilot capability bit 1";
      }
      bit meas-pilot-bit-2 {
        position 26;
        description
          "Measurement Pilot capability bit 2";
      }
      bit meas-pilot-trans-info {
        position 27;
        description
          "Measurement Pilot Transmission Info capability enabled";
      }
      bit neigh-tsf-offset {
        position 28;
        description
          "Neighbor Report TSF Offset capability enabled";
      }
      bit rcpi-meas {
        position 29;
        description
          "Received Channel Power Indicator Measurement capability enabled";
      }
      bit rsni-meas {
        position 30;
        description
          "Received Signal to Noise Indicator Measurement capability enabled";
      }
      bit bss-avg-access-delay {
        position 31;
        description
          "BSS Average Access Delay capability enabled";
      }
      bit bss-avail-adm-cap {
        position 32;
        description
          "BSS Available Admission Capacity capability enabled";
      }
      bit antenna-info {
        position 33;
        description
          "Antenna Info capability enabled";
      }
      bit ftm-range-report {
        position 34;
        description
          "Fine Timing Measurement Range Report capability enabled";
      }
      bit civic-location-meas {
        position 35;
        description
          "Civic Location Measurement capability enabled";
      }
    }
    description
      "802.11k Radio Measurement Enabled Capabilities";
  }

  grouping radio-slot-key {
    description
      "Radio slot information";
    leaf wtp-mac {
      type yang:mac-address;
      description
        "Radio mac address of the AP";
    }
    leaf radio-slot-id {
      type uint8;
      description
        "radio slot info";
    }
  }

  grouping radio-wlanid-key {
    description
      "Composite key of wtp-mac, slot-id and wlan-id.";
    leaf wtp-mac {
      type yang:mac-address;
      description
        "AP Radio MAC address";
    }
    leaf slot-id {
      type uint8;
      description
        "Radio slot identifier";
    }
    leaf wlan-id {
      type uint8;
      description
        "WLAN identifier";
    }
  }

  grouping ap-radius-server-key {
    description
      "Composite key of wtp-mac, server-group-name and server-ip.";
    leaf wtp-mac {
      type yang:mac-address;
      description
        "AP Radio MAC address";
    }
    leaf server-group-name {
      type string;
      description
        "RADIUS server group name";
    }
    leaf server-ip {
      type inet:ip-address;
      description
        "RADIUS server IP";
    }
  }

  grouping radio-slot-bssid-key {
    description
      "AP MAC, radio slot and bssid information";
    leaf ap-mac {
      type yang:mac-address;
      description
        "AP radio mac address";
    }
    leaf slot-id {
      type uint32;
      description
        "Radio slot identifier";
    }
    leaf bssid {
      type yang:mac-address;
      description
        "BSSID of the radio";
    }
  }

  grouping version-info {
    description
      "constitutes of the version info of the AP";
    leaf version {
      type uint8;
      description
        "version number of the AP";
    }
    leaf release {
      type uint8;
      description
        "release number of the AP";
    }
    leaf maint {
      type uint8;
      description
        "maintainance version of the AP";
    }
    leaf build {
      type uint8;
      description
        "build version of the AP";
    }
  }

  grouping ipaddr-bgn-channel-key {
    description
      "Represents list of Ip Address bridge group name and channel records learnt from mobility members";
    leaf node-ip {
      type inet:ip-address;
      description
        "Represents IP Address of the mobility member from which the bridge group name and channel is learnt";
    }
    leaf bgn {
      type string;
      description
        "Represents Bridge group name for the access point in the mesh network";
    }
    leaf channel {
      type uint8;
      description
        "Represents the channel number in subset channel list";
    }
  }

  grouping bgn-channel-key {
    description
      "Bridge group name and channel key";
    leaf bgn {
      type string;
      description
        "Represents the bridge group name for the access point in the mesh network";
    }
    leaf channel {
      type uint8;
      description
        "Represents the channel number in subset channel list";
    }
  }

  grouping ap-mac-ssid {
    description
      "AP MAC and SSID information";
    leaf ap-mac {
      type yang:mac-address;
      description
        "AP MAC address";
    }
    leaf wlan-id {
      type uint32;
      description
        "WLAN identifier";
    }
  }

  grouping radio-wlan-key {
    description
      "AirTime Fairness WLAN statistics key information";
    leaf radio-mac {
      type yang:mac-address;
      description
        "Radio mac address of the AP";
    }
    leaf radio-slot-id {
      type uint8;
      description
        "Radio slot ID";
    }
    leaf wlan-profile-name {
      type string;
      description
        "WLAN profile name";
    }
  }

  grouping radio-client-key {
    description
      "AirTime Fairness client statistics key information";
    leaf radio-mac {
      type yang:mac-address;
      description
        "Radio mac address of the AP";
    }
    leaf radio-slot-id {
      type uint8;
      description
        "Radio slot ID";
    }
    leaf wlan-profile-name {
      type string;
      description
        "WLAN profile name";
    }
    leaf client-mac {
      type yang:mac-address;
      description
        "Client mac address";
    }
  }

  grouping radio-neigh-key {
    description
      "AirTime Fairness mesh statistics key information";
    leaf radio-mac {
      type yang:mac-address;
      description
        "Radio mac address of the AP";
    }
    leaf radio-slot-id {
      type uint8;
      description
        "Radio slot ID";
    }
    leaf neigh-mac {
      type yang:mac-address;
      description
        "Mac address of the neighbour AP";
    }
  }

  grouping st-ap-proxy-cfg {
    description
      "HTTP proxy configuration provisioned to this AP";
    leaf hostname {
      type string;
      description
        "HTTP proxy hostname";
    }
    leaf port {
      type uint16 {
        range "0 .. 65535";
      }
      description
        "HTTP proxy port";
    }
    leaf no-proxy-list {
      type string;
      description
        "List of URLs to be excluded from proxying";
    }
  }
}
