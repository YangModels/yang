module Cisco-IOS-XE-isis-oper {
  yang-version 1;
  namespace "http://cisco.com/ns/yang/Cisco-IOS-XE-isis-oper";
  prefix isis-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     ISIS operational data.
     Copyright (c) 2020 by Cisco Systems, Inc.
     All rights reserved.";

  revision 2020-11-01 {
    description
      "Initial revision";
    reference "1.0.0";
    cisco-semver:module-version "1.0.0";
  }

  typedef isis-level-type {
    type enumeration {
      enum "isis-level-1" {
        value 0;
        description
          "Level 1 adjacency";
      }
      enum "isis-level-2" {
        value 1;
        description
          "Level 2 adjacency";
      }
    }
    description
      "Level of ISIS adjacency";
  }

  typedef isis-neighbor-state {
    type enumeration {
      enum "isis-adj-up" {
        value 0;
        description
          "Adjacency is in UP state";
      }
      enum "isis-adj-down" {
        value 1;
        description
          "Adjacency is in DOWN state";
      }
      enum "isis-adj-init" {
        value 2;
        description
          "Adjacency is in INIT state";
      }
      enum "isis-adj-standby" {
        value 3;
        description
          "Adjacency is in STANDBY state";
      }
    }
    description
      "Current state of ISIS adjacency";
  }

  grouping isis-neighbor-key {
    description
      "Compound key that identifies a unique neighbor within an ISIS tag";
    leaf system-id {
      type yang:phys-address;
      description
        "System ID of the neighbor";
    }
    leaf level {
      type isis-ios-xe-oper:isis-level-type;
      description
        "Level of the adjacency formed";
    }
    leaf if-name {
      type string;
      description
        "Interface name on which adjacency is formed";
    }
  }

  grouping isis-neighbor-rec {
    description
      "Details of the adjacency formed";
    leaf ipv4-address {
      type inet:ip-address;
      description
        "IPv4 Address of the neighbor";
    }
    leaf ipv6-address {
      type inet:ip-address;
      description
        "IPv6 Address of the neighbor";
    }
    leaf state {
      type isis-ios-xe-oper:isis-neighbor-state;
      description
        "Current state of the adjacency";
    }
    leaf holdtime {
      type uint32;
      units "seconds";
      description
        "Holdtime of the adjacency";
    }
  }

  grouping isis-tag-type {
    description
      "Each entry contains tag information of single IS-IS instance";
    leaf tag {
      type string;
      description
        "IS-IS router tag";
    }
    list isis-neighbor {
      key "system-id level if-name";
      description
        "List of neighbors for a specific tag";
      uses isis-ios-xe-oper:isis-neighbor-rec;
      uses isis-ios-xe-oper:isis-neighbor-key;
    }
  }

  container isis-oper-data {
    config false;
    description
      "Operational state of the IS-IS subsystem";
    list isis-instance {
      key "tag";
      description
        "List of ISIS routers";
      uses isis-ios-xe-oper:isis-tag-type;
    }
  }
}
