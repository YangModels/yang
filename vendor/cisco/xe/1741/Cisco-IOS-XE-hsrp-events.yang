module Cisco-IOS-XE-hsrp-events {
  yang-version 1;
  namespace "http://cisco.com/ns/yang/Cisco-IOS-XE-hsrp-events";
  prefix hsrp-ios-xe-events;

  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for HSRP State change Notification.
     Copyright (c) 2020 by Cisco Systems, Inc.
     All rights reserved.";

  revision 2020-11-01 {
    description
      "Initial revision";
    reference "1.0.0";
    cisco-semver:module-version "1.0.0";
  }

  typedef hsrp-notification-severity {
    type enumeration {
      enum "critical" {
        value 0;
        description
          "Notification severity - critical";
      }
      enum "major" {
        value 1;
        description
          "Notification severity - major";
      }
      enum "minor" {
        value 2;
        description
          "Notification severity - minor";
      }
    }
    description
      "Notification severity";
  }

  typedef hsrp-ip-addr-type {
    type enumeration {
      enum "hsrp-undefined" {
        value 0;
        description
          "IP Address undefined";
      }
      enum "hsrp-ipv4-address" {
        value 1;
        description
          "IPv4 address";
      }
      enum "hsrp-ipv6-address" {
        value 2;
        description
          "IPv6 address";
      }
    }
    description
      "IP Address type";
  }

  typedef hsrp-notif-proto-state-type {
    type enumeration {
      enum "hsrp-notif-state-invalid" {
        value 0;
        description
          "HSRP state invalid";
      }
      enum "hsrp-notif-state-disabled" {
        value 1;
        description
          "HSRP state disabled";
      }
      enum "hsrp-notif-state-init" {
        value 2;
        description
          "HSRP state init";
      }
      enum "hsrp-notif-state-learn" {
        value 3;
        description
          "HSRP state learn";
      }
      enum "hsrp-notif-state-listen" {
        value 4;
        description
          "HSRP state listen";
      }
      enum "hsrp-notif-state-speak" {
        value 5;
        description
          "HSRP state speak";
      }
      enum "hsrp-notif-state-standby" {
        value 6;
        description
          "HSRP state standby";
      }
      enum "hsrp-notif-state-active" {
        value 7;
        description
          "HSRP state active";
      }
    }
    description
      "HSRP protocol state";
  }

  grouping hsrp-group-state-change-data {
    description
      "HSRP group state change";
    leaf severity {
      type hsrp-ios-xe-events:hsrp-notification-severity;
      description
        "Event severity";
    }
    leaf host-name {
      type string;
      description
        "Host name";
    }
    leaf system-ip {
      type inet:ip-address;
      description
        "IP address";
    }
    leaf group-id {
      type uint16;
      description
        "HSRP Group ID";
    }
    leaf addr-type {
      type hsrp-ios-xe-events:hsrp-ip-addr-type;
      description
        "Address Type";
    }
    leaf if-name {
      type string;
      description
        "Interface Name";
    }
    leaf hsrp-group-state {
      type hsrp-ios-xe-events:hsrp-notif-proto-state-type;
      description
        "HSRP state";
    }
  }

  notification hsrp-group-state-change {
    description
      "HSRP group state change Notification";
    uses hsrp-ios-xe-events:hsrp-group-state-change-data;
  }
}
