module Cisco-IOS-XE-perf-measure-events {
  yang-version 1;
  namespace "http://cisco.com/ns/yang/Cisco-IOS-XE-perf-measure-events";
  prefix perf-measure-ios-xe-events;

  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for performance measure events data.
     Copyright (c) 2020 by Cisco Systems, Inc.
     All rights reserved.";

  revision 2020-07-01 {
    description
      "Initial revision";
    reference "1.0.0";
    cisco-semver:module-version "1.0.0";
  }

  grouping pm-dm-probe-end-notification {
    description
      "Performance measurement delay measurement probe end notification";
    leaf name {
      type string;
      description
        "Name of interface or policy name";
    }
  }

  grouping pm-dm-aggregation-end-notification {
    description
      "Performance measurement delay measurement aggregation end notification";
    leaf name {
      type string;
      description
        "Name of interface or policy name";
    }
  }

  grouping pm-dm-advertisement-event-notification {
    description
      "Performance measurement delay measurement advertisement event notification";
    leaf name {
      type string;
      description
        "Name of interface or policy name";
    }
  }

  notification pm-dm-probe-end-notif {
    description
      "Performance measurement delay measurement probe end notification queue";
    uses perf-measure-ios-xe-events:pm-dm-probe-end-notification;
  }
  notification pm-dm-aggr-end-notif {
    description
      "Performance measurement delay measurement aggregation end notification queue";
    uses perf-measure-ios-xe-events:pm-dm-aggregation-end-notification;
  }
  notification pm-dm-adv-event-notif {
    description
      "Performance measurement delay measurement advertisement event notification queue";
    uses perf-measure-ios-xe-events:pm-dm-advertisement-event-notification;
  }
}
