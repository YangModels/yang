module Cisco-IOS-XE-arp {
  namespace "http://cisco.com/ns/yang/Cisco-IOS-XE-arp";
  prefix ios-arp;


  import ietf-inet-types {
      prefix inet;
  }

  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Access Point (AP) Group Yang model.
     Copyright (c) 2016 by Cisco Systems, Inc.
     All rights reserved.";

  // =========================================================================
  // REVISION
  // =========================================================================
  revision 2017-01-16 {
    description
      "Initial Revision";
  }

  grouping config-arp-grouping {
    container arp {
      description
        "Set a static ARP entry";
      list arp-entry {
        description
          "Configure an arp entry";
        key "ip";
        leaf ip {
          description
	    "IP address of ARP entry";
          type inet:ip-address;
        }
        leaf hardware-address {
          description
            "48-bit hardware address of ARP entry";
          type string;
        }
	leaf arp-type {
	  type enumeration {
	    enum ARPA;
	    enum SAP;
	    enum SMDS;
	    enum SNAP;
	    enum SRP-A;
	    enum SRP-B;
	  }
	}
      }
    }
  }

  /////////////////////////////////////////////////////////
  // native
  /////////////////////////////////////////////////////////
  augment "/ios:native" {
    uses config-arp-grouping;
  } //augment
} //module
