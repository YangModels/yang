module Cisco-IOS-XE-service-routing {
  namespace "http://cisco.com/ns/yang/Cisco-IOS-XE-service-routing";
  prefix ios-sr;

  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Service Routing Yang model.
     Copyright (c) 2016 by Cisco Systems, Inc.
     All rights reserved.";

  // =========================================================================
  // REVISION
  // =========================================================================
  revision 2017-05-09 {
    description
      "add service-routing mdns-sd support";
  }

  revision 2017-02-07 {
    description
      "Initial revision";
  }


  grouping config-service-routing-grouping {
    container service-routing {
      description
        "Configure service-routing";
      leaf capabilities-manager {
        description
          "Service-Routing Capabilities Manager configuration";
        type boolean;
      }
      leaf mdns-sd {
        description
          "Service-Routing MDNS configuration";
        type empty;
      }
    }
  }

  /////////////////////////////////////////////////////////
  // native / servicer-routing
  /////////////////////////////////////////////////////////
  augment "/ios:native" {
    uses config-service-routing-grouping;
  }
} //module
