module Cisco-IOS-XE-object-group {
  namespace "http://cisco.com/ns/yang/Cisco-IOS-XE-object-group";
  prefix ios-og;

  import Cisco-IOS-XE-types {
    prefix ios-types;
  }

  import Cisco-IOS-XE-native {
    prefix ios;
  }


  import ietf-inet-types {
      prefix inet;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Object Group Yang model.
     Copyright (c) 2016 by Cisco Systems, Inc.
     All rights reserved.";

  // =========================================================================
  // REVISION
  // =========================================================================
  revision 2017-02-07 {
    description
      "Initial revision";
  }

  grouping object-group-service-grouping {
    leaf description {
      description
        "Service object group description";
      type string;
    }
    leaf group-object {
      description
        "Nested object group";
      type string;
    }
    choice protocal-choice {
      case protocal-number-case {
        leaf protocal-number {
          type uint8;
        }
      }
      case protocal-name-case {
        leaf ahp {
          description
            "Authentication Header Protocol";
          type empty;
        }
        leaf eigrp {
          description
            "Cisco's EIGRP routing protocol";
          type empty;
        }
        leaf esp {
          description
            "Encapsulation Security Payload";
          type empty;
        }
        leaf gre {
          description
            "Cisco's GRE tunneling";
          type empty;
        }
        container icmp {
          description
            "Internet Control Message Protocol";
          presence "true";
          leaf port-number {
            type uint8;
          }
          leaf alternate-address {
            description
              "Alternate address";
            type empty;
          }
          leaf conversion-error {
            description
              "Datagram conversion";
            type empty;
          }
          leaf echo {
            description
              "Echo (ping)";
            type empty;
          }
          leaf echo-reply {
            description
              "Echo reply";
            type empty;
          }
          leaf information-reply {
            description
              "Information replies";
            type empty;
          }
          leaf information-request {
            description
              "Information requests";
            type empty;
          }
          leaf mask-reply {
            description
              "Mask replies";
            type empty;
          }
          leaf mask-request {
            description
              "Mask requests";
            type empty;
          }
          leaf mobile-redirect {
            description
              "Mobile host redirect";
            type empty;
          }
          leaf parameter-problem {
            description
              "All parameter problems";
            type empty;
          }
          leaf redirect {
            description
              "All redirects";
            type empty;
          }
          leaf router-advertisement {
            description
              "Router discovery advertisements";
            type empty;
          }
          leaf router-solicitation {
            description
              "Router discovery solicitations";
            type empty;
          }
          leaf source-quench {
            description
              "Source quenches";
            type empty;
          }
          leaf time-exceeded {
            description
              "All time exceededs";
            type empty;
          }
          leaf timestamp-reply {
            description
              "Timestamp replies";
            type empty;
          }
          leaf timestamp-request {
            description
              "Timestamp requests";
            type empty;
          }
          leaf traceroute {
            description
              "Traceroute";
            type empty;
          }
          leaf unreachable {
            description
              "All unreachables";
            type empty;
          }
        }
        leaf igmp {
          description
            "Internet Gateway Message Protocol";
          type empty;
        }
        leaf ip {
          description
            "Any Internet Protocol";
          type empty;
        }
        leaf ipinip {
          description
            "IP in IP tunneling";
          type empty;
        }
        leaf nos {
          description
            "KA9Q NOS compatible IP over IP tunneling";
          type empty;
        }
        leaf ospf {
          description
            "OSPF routing protocol";
          type empty;
        }
        leaf pcp {
          description
            "Payload Compression Protocol";
          type empty;
        }
        leaf pim {
          description
            "Protocol Independent Multicast";
          type empty;
        }
        container tcp {
          description
            "Transmission Control Protocol";
          presence "true";
          list tcp-port-list {
            key "tcp-port";
            leaf tcp-port {
              type ios-types:acl-tcp-port-type;
            }
            leaf operator {
              type enumeration {
                enum "eq";
                enum "gt";
                enum "lt";
                enum "range";
              }
            }
            leaf max-tcp-port {
              type ios-types:acl-tcp-port-type;
            }
          }
        }
        container tcp-udp {
          description
            "TCP or UDP protocol";
          presence "true";
          list udp-port-list {
            key "udp-port";
            leaf udp-port {
              type ios-types:acl-udp-port-type;
            }
            leaf operator {
              type enumeration {
                enum "eq";
                enum "gt";
                enum "lt";
                enum "range";
              }
            }
            leaf max-udp-port {
              type ios-types:acl-udp-port-type;
            }
          }
        }
        container udp {
          description
            "User Datagram Protocol";
          presence "true";
          list udp-port-list {
            key "udp-port";
            leaf udp-port {
              type ios-types:acl-udp-port-type;
            }
            leaf operator {
              type enumeration {
                enum "eq";
                enum "gt";
                enum "lt";
                enum "range";
              }
            }
            leaf max-udp-port {
              type ios-types:acl-udp-port-type;
            }
          }
        }
      }
    }
  }

  grouping config-object-group-grouping {
    list network {
      description
        "network group";
      key "name";
      leaf name {
        description
          "WORD;;object-group name";
        type string;
      }
      container obj-Mode-config-network-group {
        list network_address {
          key "ipv4_addr ipv4_mask";
          leaf ipv4_addr {
            description
              "A.B.C.D;;Network address of the group members";
            type inet:ipv4-address;
          }
          leaf ipv4_mask {
            description
              "A.B.C.D;;Network mask";
            type inet:ipv4-address;
          }
        }
        leaf description {
          description
            "Network object group description";
          type string {
            length "1..200";
          }
        }
        leaf group-object {
          description
            "Nested object group";
          type string;
        }
        leaf host {
          description
            "Host address of the object-group member";
          type inet:host;
        }
        container range {
          leaf ip-addr-min {
            description
              "Starting IPv4 Address";
            type inet:ipv4-address;
          }
          leaf ip-addr-max {
            description
              "Ending IPv4 Address";
            type inet:ipv4-address;
          }
        }
      }
    }
    list security {
      description
        "security group";
      key "name";
      leaf name {
        type string;
      }
      container security-group {
        leaf description {
          description
            "Network object group description";
          type string {
            length "1..200";
          }
        }
        leaf group-object {
          description
            "Nested object group";
          type string;
        }
        container security-group {
          description
            "Security Group Tag";
          leaf tag {
            type uint16 {
              range "1..65535";
            }
          }
        }
      }
    }
    list service {
      description
        "service group";
      key "name";
      leaf name {
        type string;
      }
      uses object-group-service-grouping;
    }
  }

  /////////////////////////////////////////////////////////
  // native / object-group
  /////////////////////////////////////////////////////////
  augment "/ios:native/ios:object-group" {
    uses config-object-group-grouping;
  }
} //module
