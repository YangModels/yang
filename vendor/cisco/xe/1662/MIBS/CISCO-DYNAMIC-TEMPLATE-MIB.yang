/*
 * Generated by confdc --mib2yang-std
 * Source: mgmt/dmi/model/common/mib-source/CISCO-DYNAMIC-TEMPLATE-MIB.mib
 */
/*
 * This YANG module has been generated by smidump 0.5.0:
 *
 *      smidump -f yang CISCO-DYNAMIC-TEMPLATE-MIB
 *
 * Do not edit. Edit the source file instead!
 */

module CISCO-DYNAMIC-TEMPLATE-MIB {

  namespace "urn:ietf:params:xml:ns:yang:smiv2:CISCO-DYNAMIC-TEMPLATE-MIB";
  prefix CISCO-DYNAMIC-TEMPLATE-MIB;

  import CISCO-CBP-TC-MIB {
    prefix "cisco-cbp";
  }

  import CISCO-DYNAMIC-TEMPLATE-TC-MIB {
    prefix "cisco-dynamic";
  }

  import CISCO-IP-URPF-MIB {
    prefix "cisco-ip";
  }

  import CISCO-TC {
    prefix "cisco-tc";
  }

  import IF-MIB {
    prefix "if-mib";
  }

  import INET-ADDRESS-MIB {
    prefix "inet-address";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal:  170 W Tasman Drive
    San Jose, CA 95134
    
    Tel:  +1 800 553-NETS
    
    E-mail:  cs-snmp@cisco.com";

  description
   "This MIB defines objects that describe dynamic templates.  A
    dynamic template is a set of configuration attributes that a
    system can dynamically apply to a target.
    
    The target of a dynamic template is the entity configured by the
    system using the configuration attributes contained by a 
    template. At the time of this writing, an interface represents
    the only valid target of a dynamic template.  However, the
    architecture does not prevent other target types, and hence, the
    MIB definition generalizes the notion of a target to allow for
    this.
    
    Generally, the system does not directly apply the attributes
    contained by a dynamic template to an associated
    target.  The system might generate a derived configuration from
    the set of dynamic templates associated with the target.  A
    derived configuration represents the union of the configuration
    attributes contained by each associated dynamic template.  In
    the case of a conflict (i.e., more than one dynamic template
    specifies the same configuration attribute), the system accepts
    the configuration attribute from the dynamic template with the
    highest precedence.";

  revision 2007-09-06 {
    description
     "The initial version of the MIB module.";
  }


  container CISCO-DYNAMIC-TEMPLATE-MIB {
    config false;

    container cdtTemplateTable {
      description
       "This table lists the dynamic templates maintained by the
        system, including those that have been locally-configured on the
        system and those pushed to the system by external policy
        servers.";
      smiv2:oid "1.3.6.1.4.1.9.9.784.1.1.1";

      list cdtTemplateEntry {
        key "cdtTemplateName";
        description
         "An entry describes a dynamic template, which serves as a
          container for configuration attributes.  The configuration
          attributes contained by a dynamic template depends on its type.
          
          The system automatically creates a corresponding entry when a
          dynamic template has been created through another management
          entity (e.g., the system's local console).  Likewise, the system
          automatically destroys a corresponding entry when a dynamic
          template has been destroyed through another management entity.
          
          The system automatically creates a corresponding entry when an
          external policy server pushes a user profile or a service
          profile to the system.
          
          The system automatically creates a corresponding entry when it
          generates a derived configuration.";
        smiv2:oid "1.3.6.1.4.1.9.9.784.1.1.1.1";

        leaf cdtTemplateName {
          type cisco-dynamic:DynamicTemplateName;
          description
           "This object indicates a string-value that uniquely identifies
            the dynamic template.
            
            If the corresponding instance of cdtTemplateSrc is not
            'local', then the system automatically generates the name
            identifying the dynamic template.";
          smiv2:max-access "read-only";
          smiv2:oid "1.3.6.1.4.1.9.9.784.1.1.1.1.1";
        }

        leaf cdtTemplateStatus {
          type snmpv2-tc:RowStatus;
          description
           "This object specifies the status of the dynamic template.  The
            following columns must be valid before activating a dynamic
            template:
            
                - cdtTemplateStorage
                - cdtTemplateType
            
            However, these objects specify a default value.  Thus, it is
            possible to use create-and-go semantics without setting any
            additional columns.
            
            An implementation must allow the EMS/NMS to modify any column
            when this column is 'active', including columns defined in
            tables that have a one-to-one or sparse dependent relationship
            on this table.";
          smiv2:max-access "read-write";
          smiv2:oid "1.3.6.1.4.1.9.9.784.1.1.1.1.2";
        }

        leaf cdtTemplateStorage {
          type snmpv2-tc:StorageType;
          description
           "This object specifies what happens to the dynamic template
            upon restart.
            
            If the corresponding instance of cdtTemplateSrc is not
            'local', then this column must be 'volatile'.";
          smiv2:defval "volatile";
          smiv2:max-access "read-write";
          smiv2:oid "1.3.6.1.4.1.9.9.784.1.1.1.1.3";
        }

        leaf cdtTemplateType {
          type cisco-dynamic:DynamicTemplateType;
          description
           "This object indicates the types of dynamic template.";
          smiv2:defval "other";
          smiv2:max-access "read-write";
          smiv2:oid "1.3.6.1.4.1.9.9.784.1.1.1.1.4";
        }

        leaf cdtTemplateSrc {
          type enumeration {
            enum "other" {
              value "1";
            }
            enum "derived" {
              value "2";
            }
            enum "local" {
              value "3";
            }
            enum "aaaUserProfile" {
              value "4";
            }
            enum "aaaServiceProfile" {
              value "5";
            }
          }
          description
           "This object specifies the source of the dynamic template:
            
            'other'
                The implementation of the MIB module does not recognize the
                source of the dynamic template.
            
            'derived'
                The system created the set of attributes from one or
                more dynamic templates.
            
            'local'
                The dynamic template was locally configured through a
                management entity, such as the local console or a SNMP
                entity.
            
            'aaaUserProfile'
                The dynamic template originated from a user profile
                pushed from an external policy server.
            
            'aaaServiceProfile'
                The dynamic template originated from a service profile
                pushed from an external policy server.";
          smiv2:max-access "read-only";
          smiv2:oid "1.3.6.1.4.1.9.9.784.1.1.1.1.5";
        }

        leaf cdtTemplateUsageCount {
          type uint32 {
            range "0..4294967295";
          }
          description
           "This object specifies the number of targets using a dynamic template";
          smiv2:max-access "read-only";
          smiv2:oid "1.3.6.1.4.1.9.9.784.1.1.1.1.6";
        }
      }
    }

    container cdtTemplateTargetTable {
      description
       "This table contains a list of targets associated with
        one or more dynamic templates.";
      smiv2:oid "1.3.6.1.4.1.9.9.784.1.1.2";

      list cdtTemplateTargetEntry {
        key "cdtTemplateTargetType cdtTemplateTargetId";
        description
         "An entry describes a target associated with one or more
          dynamic templates.
          
          The system automatically creates an entry when it associates a
          dynamic template to a target.  Likewise, the system
          automatically destroys an entry when a target no longer has any
          associated dynamic templates.";
        smiv2:oid "1.3.6.1.4.1.9.9.784.1.1.2.1";

        leaf cdtTemplateTargetType {
          type cisco-dynamic:DynamicTemplateTargetType;
          description
           "This object indicates the type of target.";
          smiv2:max-access "not-accessible";
          smiv2:oid "1.3.6.1.4.1.9.9.784.1.1.2.1.1";
        }

        leaf cdtTemplateTargetId {
          type cisco-dynamic:DynamicTemplateTargetId;
          description
           "This object uniquely identifies the target within the scope of
            its type.";
          smiv2:max-access "not-accessible";
          smiv2:oid "1.3.6.1.4.1.9.9.784.1.1.2.1.2";
        }

        leaf cdtTemplateTargetStatus {
          type snmpv2-tc:RowStatus;
          description
           "This object specifies the status of the dynamic template
            target.  The following columns must be valid before activating a
            subscriber access profile:
            
                - cdtTemplateTargetStorage
            
            However, these objects specify a default value.  Thus, it is
            possible to use create-and-go semantics without setting any
            additional columns.
            
            An implementation must allow the EMS/NMS to modify any column
            when this column is 'active', including columns defined in
            tables that have a one-to-one or sparse dependent relationship
            on this table.";
          smiv2:max-access "read-write";
          smiv2:oid "1.3.6.1.4.1.9.9.784.1.1.2.1.3";
        }

        leaf cdtTemplateTargetStorage {
          type snmpv2-tc:StorageType;
          description
           "This object specifies what happens to the dynamic template
            target upon restart.";
          smiv2:defval "volatile";
          smiv2:max-access "read-write";
          smiv2:oid "1.3.6.1.4.1.9.9.784.1.1.2.1.4";
        }
      }
    }

    container cdtTemplateAssociationTable {
      description
       "This table contains a list of templates associated with each
        target.
        
        This table has an expansion dependent relationship on the
        cdtTemplateTargetTable, containing zero or more rows for each
        target.";
      smiv2:oid "1.3.6.1.4.1.9.9.784.1.1.3";

      list cdtTemplateAssociationEntry {
        key "cdtTemplateTargetType cdtTemplateTargetId cdtTemplateAssociationName";
        description
         "An entry indicates an association of a dynamic template with a
          target.
          
          The system automatically creates an entry when it associates a
          dynamic template to a target.
          
          The system also creates an entry when it derives the
          configuration that it applies to a target.
          
          The system automatically destroys an entry under the following
          circumstances:
          
          1)  The target indicated by the entry no longer exists.
          
          2)  The association between the target and the dynamic template
              no longer exists.";
        smiv2:oid "1.3.6.1.4.1.9.9.784.1.1.3.1";

        leaf cdtTemplateTargetType {
          type leafref {
            path "/CISCO-DYNAMIC-TEMPLATE-MIB:CISCO-DYNAMIC-TEMPLATE-MIB/CISCO-DYNAMIC-TEMPLATE-MIB:cdtTemplateTargetTable/CISCO-DYNAMIC-TEMPLATE-MIB:cdtTemplateTargetEntry/CISCO-DYNAMIC-TEMPLATE-MIB:cdtTemplateTargetType";
          }
        }

        leaf cdtTemplateTargetId {
          type leafref {
            path "/CISCO-DYNAMIC-TEMPLATE-MIB:CISCO-DYNAMIC-TEMPLATE-MIB/CISCO-DYNAMIC-TEMPLATE-MIB:cdtTemplateTargetTable/CISCO-DYNAMIC-TEMPLATE-MIB:cdtTemplateTargetEntry/CISCO-DYNAMIC-TEMPLATE-MIB:cdtTemplateTargetId";
          }
        }

        leaf cdtTemplateAssociationName {
          type cisco-dynamic:DynamicTemplateName;
          description
           "This object indicates the name of the template associated with
            the target.";
          smiv2:max-access "read-only";
          smiv2:oid "1.3.6.1.4.1.9.9.784.1.1.3.1.1";
        }

        leaf cdtTemplateAssociationPrecedence {
          type uint32 {
            range "0..4294967295";
          }
          description
           "This object indicates the relative precedence of the
            associated dynamic template.  Lower values have higher
            precedence than higher values.";
          smiv2:max-access "read-only";
          smiv2:oid "1.3.6.1.4.1.9.9.784.1.1.3.1.2";
        }
      }
    }

    container cdtTemplateUsageTable {
      description
       "This table contains a list of targets using each dynamic
        template.
        
        This table has an expansion dependent relationship on the
        cdtTemplateTable, containing zero or more rows for each
        dynamic template.";
      smiv2:oid "1.3.6.1.4.1.9.9.784.1.1.4";

      list cdtTemplateUsageEntry {
        key "cdtTemplateName cdtTemplateUsageTargetType cdtTemplateUsageTargetId";
        description
         "An entry indicates a target using the dynamic template.
          
          The system automatically creates an entry when it associates a
          dynamic template to a target.
          
          The system also creates an entry when it derives the
          configuration that it applies to a target.
          
          The system automatically destroys an entry under the following
          circumstances:
          
          1)  The target indicated by the entry no longer exists.
          
          2)  The association between the target and the dynamic template
              no longer exists.";
        smiv2:oid "1.3.6.1.4.1.9.9.784.1.1.4.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtTemplateUsageTargetType {
          type cisco-dynamic:DynamicTemplateTargetType;
          description
           "This object indicates the type of target using the
            dynamic template.";
          smiv2:max-access "read-only";
          smiv2:oid "1.3.6.1.4.1.9.9.784.1.1.4.1.1";
        }

        leaf cdtTemplateUsageTargetId {
          type cisco-dynamic:DynamicTemplateTargetId;
          description
           "This object indicates the name of the target using the dynamic
            template";
          smiv2:max-access "read-only";
          smiv2:oid "1.3.6.1.4.1.9.9.784.1.1.4.1.2";
        }
      }
    }

    container cdtTemplateCommonTable {
      description
       "This table contains attributes relating to all dynamic
        templates.  Observe that the type of dynamic templates
        containing these attributes may change with the addition of new
        dynamic template types.
        
        This table has a sparse-dependent relationship on the
        cdtTemplateTable, containing a row for each dynamic template
        having a cdtTemplateType of one of the following values:
        
            'derived'
            'ppp'
            'ethernet'
            'ipSubscriber'
            'service'";
      smiv2:oid "1.3.6.1.4.1.9.9.784.1.1.5";

      list cdtTemplateCommonEntry {
        key "cdtTemplateName";
        description
         "An entry containing attributes relating to any target.
          
          The system automatically creates an entry when the system or the
          EMS/NMS creates a row in the cdtTemplateTable with a
          cdtTemplateType of on the following values:
          
              'derived'
              'ppp'
              'ethernet'
              'ipSubscriber'
              'service'
          
          Likewise, the system automatically destroys an entry when the
          system or the EMS/NMS destroys the corresponding row in the
          cdtTemplateTable.";
        smiv2:oid "1.3.6.1.4.1.9.9.784.1.1.5.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtCommonValid {
          type bits {
            bit descr {
              position "0";
            }
            bit keepalive {
              position "1";
            }
            bit vrf {
              position "2";
            }
            bit addrPool {
              position "3";
            }
            bit ipv4AccessGroup {
              position "4";
            }
            bit ipv4Unreachables {
              position "5";
            }
            bit ipv6AccessGroup {
              position "6";
            }
            bit ipv6Unreachables {
              position "7";
            }
            bit srvSubControl {
              position "8";
            }
            bit srvRedirect {
              position "9";
            }
            bit srvAcct {
              position "10";
            }
            bit srvQos {
              position "11";
            }
            bit srvNetflow {
              position "12";
            }
          }
          description
           "This object specifies which attributes in the dynamic template
            have been configured to valid values.
            
            Each bit in this bit string corresponds to a column in this
            table.  If the bit is '0', then the value of the corresponding
            column is not valid.  If the bit is '1', then the value of the
            corresponding column has been configured to a valid value.
            
            The following list specifies the mappings between bits and the
            columns:
            
                'descr'             => cdtCommonDescr
                'keepaliveInt'      => cdtCommonKeepaliveInt
                'keepaliveRetries'  => cdtCommonKeepaliveRetries
                'vrf'               => cdtCommonVrf
                'addrPool'          => cdtCommonAddrPool
                'ipv4AccessGroup'   => cdtCommonIpv4AccessGroup
                'ipv4Unreachables'  => cdtCommonIpv4Unreachables
                'ipv6AccessGroup'   => cdtCommonIpv6AccessGroup
                'ipv6Unreachables'  => cdtCommonIpv6Unreachables
                'srvSubControl'     => cdtCommonSrvSubControl
                'srvRedirect'       => cdtCommonSrvRedirect
                'srvAcct'           => cdtCommonSrvAcct
                'srvQos'            => cdtCommonSrvQos
                'srvNetflow'        => cdtCommonSrvNetflow";
          smiv2:defval "{}";
          smiv2:max-access "read-write";
          smiv2:oid "1.3.6.1.4.1.9.9.784.1.1.5.1.1";
        }

        leaf cdtCommonDescr {
          type snmp-framework:SnmpAdminString {
            length "0..255";
          }
          description
           "This object specifies a human-readable description for the
            dynamic template.
            
            This column is valid only if the 'descr' bit of the
            corresponding instance of cdtCommonValid is '1'.";
          smiv2:defval "";
          smiv2:max-access "read-write";
          smiv2:oid "1.3.6.1.4.1.9.9.784.1.1.5.1.2";
        }

        leaf cdtCommonKeepaliveInt {
          type uint32 {
            range "1..4294967295";
          }
          units "seconds";
          description
           "This object specifies the interval that the system sends
            keepalive messages to a target.
            
            This column is valid only if the 'keepaliveInterval' bit of the
            corresponding instance of cdtCommonValid is '1'.";
          smiv2:defval "10";
          smiv2:max-access "read-write";
          smiv2:oid "1.3.6.1.4.1.9.9.784.1.1.5.1.3";
        }

        leaf cdtCommonKeepaliveRetries {
          type uint32 {
            range "1..255";
          }
          units "retries";
          description
           "This object specifies the number of times the system will
            resend a keepalive message without a response before it
            transitions a target to an operationally down state.
            
            This column is valid only if the 'keepaliveRetries' bit of the
            corresponding instance of cdtCommonValid is '1'.";
          smiv2:defval "5";
          smiv2:max-access "read-write";
          smiv2:oid "1.3.6.1.4.1.9.9.784.1.1.5.1.4";
        }

        leaf cdtCommonVrf {
          type cisco-tc:CiscoVrfName;
          description
           "This object specifies the name of the VRF with which a target
            has an association.
            
            This column is valid only if the 'vrf' bit of the corresponding
            instance of cdtCommonValid is '1'.";
          smiv2:defval "";
          smiv2:max-access "read-write";
          smiv2:oid "1.3.6.1.4.1.9.9.784.1.1.5.1.5";
        }

        leaf cdtCommonAddrPool {
          type snmp-framework:SnmpAdminString {
            length "0..255";
          }
          description
           "This object specifies the name of the IP address pool the
            system will use to assign an IP address to a peer of a target.
            
            This column is valid only if the 'addrPool' bit of the
            corresponding instance of cdtCommonValid is '1'.";
          smiv2:defval "";
          smiv2:max-access "read-write";
          smiv2:oid "1.3.6.1.4.1.9.9.784.1.1.5.1.6";
        }

        leaf cdtCommonIpv4AccessGroup {
          type snmp-framework:SnmpAdminString {
            length "0..255";
          }
          description
           "This object specifies the name (or number) of the IPv4 ACL
            applied to a target.
            
            This column is valid only if the 'ipv4AccessGroup' bit of the
            corresponding instance of cdtCommonValid is '1'.";
          smiv2:defval "";
          smiv2:max-access "read-write";
          smiv2:oid "1.3.6.1.4.1.9.9.784.1.1.5.1.7";
        }

        leaf cdtCommonIpv4Unreachables {
          type boolean;
          description
           "This object specifies whether a target generates ICMPv4
            unreachable messages.
            
            This column is valid only if the 'ipv4Unreachables' bit of the
            corresponding instance of cdtCommonValid is '1'.";
          smiv2:defval "true";
          smiv2:max-access "read-write";
          smiv2:oid "1.3.6.1.4.1.9.9.784.1.1.5.1.8";
        }

        leaf cdtCommonIpv6AccessGroup {
          type snmp-framework:SnmpAdminString {
            length "0..255";
          }
          description
           "This object specifies the name (or number) of the IPv4 ACL
            applied to a target.
            
            This column is valid only if the 'ipv6AccessGroup' bit of the
            corresponding instance of cdtCommonValid is '1'.";
          smiv2:defval "";
          smiv2:max-access "read-write";
          smiv2:oid "1.3.6.1.4.1.9.9.784.1.1.5.1.9";
        }

        leaf cdtCommonIpv6Unreachables {
          type boolean;
          description
           "This object specifies whether a target generates ICMPv6
            unreachable messages.
            
            This column is valid only if the 'ipv6Unreachables' bit of the
            corresponding instance of cdtCommonValid is '1'.";
          smiv2:defval "true";
          smiv2:max-access "read-write";
          smiv2:oid "1.3.6.1.4.1.9.9.784.1.1.5.1.10";
        }

        leaf cdtCommonSrvSubControl {
          type cisco-cbp:CbpElementName;
          description
           "This object specifies the name of the subscriber control
            policy applied to a target.
            
            The system should assume that the cbpPolicyMapType (defined by
            the CISCO-CBP-BASE-CFG-MIB) of the policy is
            cbpPmtControlSubscriber (defined by the CISCO-CBP-TYPE-OID-MIB).
            
            This column is valid only if the 'srvSubControl' bit of the
            corresponding instance of cdtCommonValid is '1'.";
          smiv2:defval "";
          smiv2:max-access "read-write";
          smiv2:oid "1.3.6.1.4.1.9.9.784.1.1.5.1.11";
        }

        leaf cdtCommonSrvRedirect {
          type cisco-cbp:CbpElementName;
          description
           "This object specifies the name of the traffic redirect policy
            applied to a target.
            
            The system should assume that the cbpPolicyMapType (defined by
            the CISCO-CBP-BASE-CFG-MIB) of the policy is
            cbpPmtTrafficRedirect (defined by the CISCO-CBP-TYPE-OID-MIB).
            
            This column is valid only if the 'srvRedirect' bit of the
            corresponding instance of cdtCommonValid is '1'.";
          smiv2:defval "";
          smiv2:max-access "read-write";
          smiv2:oid "1.3.6.1.4.1.9.9.784.1.1.5.1.12";
        }

        leaf cdtCommonSrvAcct {
          type cisco-cbp:CbpElementName;
          description
           "This object specifies the name of the traffic accounting policy
            applied to a target.
            
            The system should assume that the cbpPolicyMapType (defined by
            the CISCO-CBP-BASE-CFG-MIB) of the policy is
            cbpPmtTrafficAccounting (defined by the CISCO-CBP-TYPE-OID-MIB).
            
            This column is valid only if the 'srvAcct' bit of the
            corresponding instance of cdtCommonValid is '1'.";
          smiv2:defval "";
          smiv2:max-access "read-write";
          smiv2:oid "1.3.6.1.4.1.9.9.784.1.1.5.1.13";
        }

        leaf cdtCommonSrvQos {
          type cisco-cbp:CbpElementName;
          description
           "This object specifies the name of the traffic QoS policy
            applied to a target.
            
            The system should assume that the cbpPolicyMapType (defined by
            the CISCO-CBP-BASE-CFG-MIB) of the policy is cbpPmtQos (defined
            by the CISCO-CBP-TYPE-OID-MIB).
            
            This column is valid only if the 'srvQos' bit of the
            corresponding instance of cdtCommonValid is '1'.";
          smiv2:defval "";
          smiv2:max-access "read-write";
          smiv2:oid "1.3.6.1.4.1.9.9.784.1.1.5.1.14";
        }

        leaf cdtCommonSrvNetflow {
          type cisco-cbp:CbpElementName;
          description
           "This object specifies the name of the NetFlow policy applied to
            a target.
            
            The system should assume that the cbpPolicyMapType (defined by
            the CISCO-CBP-BASE-CFG-MIB) of the policy is
            cbpPmtNetflow (defined by the CISCO-CBP-TYPE-OID-MIB).
            
            This column is valid only if the 'srvNetflow' bit of the
            corresponding instance of cdtCommonValid is '1'.";
          smiv2:defval "";
          smiv2:max-access "read-write";
          smiv2:oid "1.3.6.1.4.1.9.9.784.1.1.5.1.15";
        }
      }
    }

    container cdtIfTemplateTable {
      description
       "This table contains attributes relating to interface
        configuration.
        
        This table has a sparse-dependent relationship on the
        cdtTemplateTable, containing a row for each dynamic template
        having a cdtTemplateType of one of the following values:
        
            'derived'
            'ppp'
            'ethernet'
            'ipSubscriber'";
      smiv2:oid "1.3.6.1.4.1.9.9.784.1.2.1";

      list cdtIfTemplateEntry {
        key "cdtTemplateName";
        description
         "An entry containing attributes relating to interface
          configuration.
          
          The system automatically creates an entry when the system or the
          EMS/NMS creates a row in the cdtTemplateTable with a
          cdtTemplateType of one of the following values:
          
              'derived'
              'ppp'
              'ethernet'
              'ipSubscriber'
          
          Likewise, the system automatically destroys an entry when the
          system or the EMS/NMS destroys the corresponding row in the
          cdtTemplateTable.";
        smiv2:oid "1.3.6.1.4.1.9.9.784.1.2.1.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtIfValid {
          type bits {
            bit mtu {
              position "0";
            }
            bit cdpEnable {
              position "1";
            }
            bit flowMonitor {
              position "2";
            }
            bit ipv4Unnumbered {
              position "3";
            }
            bit ipv4SubEnable {
              position "4";
            }
            bit ipv4Mtu {
              position "5";
            }
            bit ipv4TcpMssAdjust {
              position "6";
            }
            bit ipv4VerifyUniRpf {
              position "7";
            }
            bit ipv4VerifyUniRpfAcl {
              position "8";
            }
            bit ipv4VerifyUniRpfOpts {
              position "9";
            }
            bit ipv6Enable {
              position "10";
            }
            bit ipv6SubEnable {
              position "11";
            }
            bit ipv6TcpMssAdjust {
              position "12";
            }
            bit ipv6VerifyUniRpf {
              position "13";
            }
            bit ipv6VerifyUniRpfAcl {
              position "14";
            }
            bit ipv6VerifyUniRpfOpts {
              position "15";
            }
            bit ipv6NdPrefix {
              position "16";
            }
            bit ipv6NdValidLife {
              position "17";
            }
            bit ipv6NdPreferredLife {
              position "18";
            }
            bit ipv6NdOpts {
              position "19";
            }
            bit ipv6NdDadAttempts {
              position "20";
            }
            bit ipv6NdNsInterval {
              position "21";
            }
            bit ipv6NdReachableTime {
              position "22";
            }
            bit ipv6NdRaIntervalMax {
              position "23";
            }
            bit ipv6NdRaIntervalMin {
              position "24";
            }
            bit ipv6NdRaLife {
              position "25";
            }
            bit ipv6NdRaRouterPreference {
              position "26";
            }
          }
          description
           "This object specifies which attributes in the dynamic template
            have been configured to valid values.
            
            Each bit in this bit string corresponds to a column in this
            table.  If the bit is '0', then the value of the corresponding
            column is not valid.  If the bit is '1', then the value of the
            corresponding column has been configured to a valid value.
            
            The following list specifies the mappings between bits and the
            columns:
            
                'mtu'                     => cdtIfMtu
                'cdpEnable'               => cdtIfCdpEnable
                'flowMonitor'             => cdtIfFlowMonitor
                'ipv4Unnumbered'          => cdtIfIpv4Unnumbered
                'ipv4SubEnable'           => cdtIfIpv4SubEnable
                'ipv4Mtu'                 => cdtIfIpv4Mtu
                'ipv4TcpMssAdjust'        => cdtIfIpv4TcpMssAdjust
                'ipv4VerifyUniRpf'        => cdtIfIpv4VerifyUniRpf
                'ipv4VerifyUniRpfAcl'     => cdtIfIpv4VerifyUniRpfAcl
                'ipv4VerifyUniRpfOpts'    => cdtIfIpv4VerifyUniRpfOpts
                'ipv6Enable'              => cdtIfIpv6Enable
                'ipv6SubEnable'           => cdtIfIpv6SubEnable
                'ipv6TcpMssAdjust'        => cdtIfIpv6TcpMssAdjust
                'ipv6VerifyUniRpf'        => cdtIfIpv6VerifyUniRpf
                'ipv6VerifyUniRpfAcl'     => cdtIfIpv6VerifyUniRpfAcl
                'ipv6VerifyUniRpfOpts'    => cdtIfIpv6VerifyUniRpfOpts
                'ipv6NdPrefix'            => cdtIfIpv6NdPrefix,
                                             cdtIfIpv6NdPrefixLength
                'ipv6NdValidLife'         => cdtIfIpv6NdValidLife
                'ipv6NdPreferredLife'     => cdtIfIpv6NdPreferredLife
                'ipv6NdOpts'              => cdtIfIpv6NdOpts
                'ipv6NdDadAttempts'       => cdtIfIpv6NdDadAttempts
                'ipv6NdNsInterval'        => cdtIfIpv6NdNsInterval
                'ipv6NdReacableTime'      => cdtIfIpv6NdReacableTime
                'ipv6NdRaIntervalMax'     => cdtIfIpv6NdRaIntervalUnits,
                                             cdtIfIpv6NdRaIntervalMax
                'ipv6NdRaIntervalMin'     => cdtIfIpv6NdRaIntervalMin
                'ipv6NdRaLife'            => cdtIfIpv6NdRaLife
                'ipv6NdRouterPreference'' => cdtIfIpv6NdRouterPreference";
          smiv2:defval "{}";
          smiv2:max-access "read-write";
          smiv2:oid "1.3.6.1.4.1.9.9.784.1.2.1.1.1";
        }

        leaf cdtIfMtu {
          type uint32 {
            range "0|64..65535";
          }
          units "octets";
          description
           "This object specifies the Maximum Transfer Unit (MTU) size for
            all packets sent on the target interface.
            
            The value '0' cannot be written to an instance of this object.
            However, it serves as a convenient value when the column is not
            valid.
            
            This column is valid only if the 'mtu' bit of the corresponding
            instance of cdtIfValid is '1'.";
          smiv2:defval "0";
          smiv2:max-access "read-write";
          smiv2:oid "1.3.6.1.4.1.9.9.784.1.2.1.1.2";
        }

        leaf cdtIfCdpEnable {
          type boolean;
          description
           "This object specifies whether the target interface participates
            in the Cisco Discovery Protocol (CDP).
            
            This column is valid only if the 'cdpEnable' bit of the
            corresponding instance of cdtIfValid is '1'.";
          smiv2:defval "false";
          smiv2:max-access "read-write";
          smiv2:oid "1.3.6.1.4.1.9.9.784.1.2.1.1.3";
        }

        leaf cdtIfFlowMonitor {
          type snmp-framework:SnmpAdminString {
            length "0..255";
          }
          description
           "This object specifies the name of the flow monitor associated
            with the target interface.
            
            This column is valid only if the 'flowMonitor' bit of the
            corresponding instance of cdtIfValid is '1'.";
          smiv2:defval "";
          smiv2:max-access "read-write";
          smiv2:oid "1.3.6.1.4.1.9.9.784.1.2.1.1.4";
        }

        leaf cdtIfIpv4Unnumbered {
          type if-mib:InterfaceIndexOrZero;
          description
           "This object specifies the interface of the source address that
            the target interface uses when originating IPv4 packets.
            
            The value '0' cannot be written to an instance of this object.
            However, it serves as a convenient value when the column is
            not valid (e.g., immediately following the creation of an
            instance of the object).
            
            This column is valid only if the 'ipv4Unnumbered' bit of the
            corresponding instance of cdtIfValid is '1'.";
          smiv2:defval "0";
          smiv2:max-access "read-write";
          smiv2:oid "1.3.6.1.4.1.9.9.784.1.2.1.1.5";
        }

        leaf cdtIfIpv4SubEnable {
          type boolean;
          description
           "This object specifies whether the target interface allows IPv4
            subscriber sessions.
            
            This column is valid only if the 'ipv4SubEnable' bit of the
            corresponding instance of cdtIfValid is '1'.";
          smiv2:defval "false";
          smiv2:max-access "read-write";
          smiv2:oid "1.3.6.1.4.1.9.9.784.1.2.1.1.6";
        }

        leaf cdtIfIpv4Mtu {
          type uint32 {
            range "0|128..65535";
          }
          units "octets";
          description
           "This object specifies the Maximum Transfer Unit (MTU) size for
            IPv4 packets sent on the target interface.
            
            The value '0' cannot be written to an instance of this object.
            However, it serves as a convenient value when the column is not
            valid.
            
            This column is valid only if the 'ipv4Mtu' bit of the
            corresponding instance of cdtIfValid is '1'.";
          smiv2:defval "0";
          smiv2:max-access "read-write";
          smiv2:oid "1.3.6.1.4.1.9.9.784.1.2.1.1.7";
        }

        leaf cdtIfIpv4TcpMssAdjust {
          type uint32 {
            range "0|500..1460";
          }
          units "octets";
          description
           "This object specifies the adjustment to the Maximum Segment
            Size (MSS) of TCP SYN packets received by the target interface
            contained in IPv4 datagrams.
            
            The value '0' cannot be written to an instance of this object.
            However, it serves as a convenient value when the column is not
            valid.
            
            This column is valid only if the 'ipv4TcpMssAdjust' bit of the
            corresponding instance of cdtIfValid is '1'.";
          smiv2:defval "0";
          smiv2:max-access "read-write";
          smiv2:oid "1.3.6.1.4.1.9.9.784.1.2.1.1.8";
        }

        leaf cdtIfIpv4VerifyUniRpf {
          type cisco-ip:UnicastRpfType;
          description
           "This object specifies whether the type of unicast RPF the
            system performs on IPv4 packets received by the target
            interface.
            
            This column is valid only if the 'ipv4VerifyUniRpf' bit of the
            corresponding instance of cdtIfValid is '1'.";
          smiv2:defval "disabled";
          smiv2:max-access "read-write";
          smiv2:oid "1.3.6.1.4.1.9.9.784.1.2.1.1.9";
        }

        leaf cdtIfIpv4VerifyUniRpfAcl {
          type snmp-framework:SnmpAdminString {
            length "0..255";
          }
          description
           "This object specifies the name (or number) of the IPv4 ACL
            used to determine whether the system should permit/deny packets
            received by the target interface that fail unicast RPF
            verification.
            
            This column is valid only if the 'ipv4VerifyUniRpfAcl' bit of
            the corresponding instance of cdtIfValid is '1'.";
          smiv2:defval "";
          smiv2:max-access "read-write";
          smiv2:oid "1.3.6.1.4.1.9.9.784.1.2.1.1.10";
        }

        leaf cdtIfIpv4VerifyUniRpfOpts {
          type cisco-ip:UnicastRpfOptions;
          description
           "This object specifies the options that affect how the system
            performs unicast RPF on IPv4 packets received by the target
            interface.
            
            This column is valid only if the 'ipv4VerifyUniRpfOpts' bit of
            the corresponding instance of cdtIfValid is '1'.";
          smiv2:defval "{}";
          smiv2:max-access "read-write";
          smiv2:oid "1.3.6.1.4.1.9.9.784.1.2.1.1.11";
        }

        leaf cdtIfIpv6Enable {
          type boolean;
          description
           "This object specifies whether the system processes IPv6
            packets received by the target interface.
            
            This column is valid only if the 'ipv6Enable' bit of the
            corresponding instance of cdtIfValid is '1'.";
          smiv2:defval "false";
          smiv2:max-access "read-write";
          smiv2:oid "1.3.6.1.4.1.9.9.784.1.2.1.1.12";
        }

        leaf cdtIfIpv6SubEnable {
          type boolean;
          description
           "This object specifies whether the target interface allows IPv6
            subscriber sessions.
            
            This column is valid only if the 'ipv6SubEnable' bit of the
            corresponding instance of cdtIfValid is '1'.";
          smiv2:defval "false";
          smiv2:max-access "read-write";
          smiv2:oid "1.3.6.1.4.1.9.9.784.1.2.1.1.13";
        }

        leaf cdtIfIpv6TcpMssAdjust {
          type uint32 {
            range "0|500..1460";
          }
          units "octets";
          description
           "This object specifies the adjustment to the Maximum Segment
            Size (MSS) of TCP SYN packets received by the target interface
            contained in IPv6 datagrams.
            
            The value '0' cannot be written to an instance of this object.
            However, it serves as a convenient value when the column is not
            valid.
            
            This column is valid only if the 'ipv6TcpMssAdjust' bit of the
            corresponding instance of cdtIfValid is '1'.";
          smiv2:defval "0";
          smiv2:max-access "read-write";
          smiv2:oid "1.3.6.1.4.1.9.9.784.1.2.1.1.14";
        }

        leaf cdtIfIpv6VerifyUniRpf {
          type cisco-ip:UnicastRpfType;
          description
           "This object specifies whether the type of unicast RPF the
            system performs on IPv6 packets received by the target
            interface.
            
            This column is valid only if the 'ipv6VerifyUniRpf' bit of the
            corresponding instance of cdtIfValid is '1'.";
          smiv2:defval "disabled";
          smiv2:max-access "read-write";
          smiv2:oid "1.3.6.1.4.1.9.9.784.1.2.1.1.15";
        }

        leaf cdtIfIpv6VerifyUniRpfAcl {
          type snmp-framework:SnmpAdminString {
            length "0..255";
          }
          description
           "This object specifies the name (or number) of the IPv6 ACL
            used to determine whether the system should permit/deny packets
            received by the target interface that fail unicast RPF
            verification.
            
            This column is valid only if the 'ipv6VerifyUniRpfAcl' bit of
            the corresponding instance of cdtIfValid is '1'.";
          smiv2:defval "";
          smiv2:max-access "read-write";
          smiv2:oid "1.3.6.1.4.1.9.9.784.1.2.1.1.16";
        }

        leaf cdtIfIpv6VerifyUniRpfOpts {
          type cisco-ip:UnicastRpfOptions;
          description
           "This object specifies the options that affect how the system
            performs unicast RPF on IPv6 packets received by the target
            interface.
            
            This column is valid only if the 'ipv6VerifyUniRpfOpts' bit of
            the corresponding instance of cdtIfValid is '1'.";
          smiv2:defval "{}";
          smiv2:max-access "read-write";
          smiv2:oid "1.3.6.1.4.1.9.9.784.1.2.1.1.17";
        }

        leaf cdtIfIpv6NdPrefix {
          type inet-address:InetAddressIPv6;
          description
           "This object specifies the IPv6 network number included in
            IPv6 router advertisements sent on the target interface.
            
            This column is valid only if the 'ipv6NdPrefix' bit of
            the corresponding instance of cdtIfValid is '1'.";
          reference
           "T. Narten, E. Nordmark, W. Simpson, H. Soliman, 'Neighbor
            Discovery for IP version 6 (IPv6)', RFC-4861, September 2007.";
          smiv2:defval "'00000000000000000000000000000000'H";
          smiv2:max-access "read-write";
          smiv2:oid "1.3.6.1.4.1.9.9.784.1.2.1.1.18";
        }

        leaf cdtIfIpv6NdPrefixLength {
          type inet-address:InetAddressPrefixLength;
          description
           "This object specifies the length of the IPv6 prefix specified
            by the corresponding instance of cdtIpv6NdPrefix.
            
            This column is valid only if the 'ipv6NdPrefix' bit of the
            corresponding instance of cdtIfValid is '1'.";
          reference
           "T. Narten, E. Nordmark, W. Simpson, H. Soliman, 'Neighbor
            Discovery for IP version 6 (IPv6)', RFC-4861, September 2007.";
          smiv2:defval "0";
          smiv2:max-access "read-write";
          smiv2:oid "1.3.6.1.4.1.9.9.784.1.2.1.1.19";
        }

        leaf cdtIfIpv6NdValidLife {
          type uint32 {
            range "1..4294967295";
          }
          units "seconds";
          description
           "This object specifies the interval that the system advertises
            the IPv6 prefix (i.e., the corresponding instance of
            cdtIfIpv6NdPrefix) as 'valid' for IPv6 router advertisements
            sent on the target interface.
            
            This column is valid only if the 'ipv6NdValidLife' bit of the
            corresponding instance of cdtIfValid is '1'.";
          reference
           "T. Narten, E. Nordmark, W. Simpson, H. Soliman, 'Neighbor
            Discovery for IP version 6 (IPv6)', RFC-4861, September 2007.";
          smiv2:defval "2592000";
          smiv2:max-access "read-write";
          smiv2:oid "1.3.6.1.4.1.9.9.784.1.2.1.1.20";
        }

        leaf cdtIfIpv6NdPreferredLife {
          type uint32 {
            range "1..4294967295";
          }
          units "seconds";
          description
           "This object specifies the interval that the system advertises
            the IPv6 prefix (i.e., the corresponding instance of
            cdtIfIpv6NdPrefix) as 'preferred' for IPv6 router advertisements
            sent on the target interface.
            
            This column is valid only if the 'ipv6NdPreferredLife' bit of
            the corresponding instance of cdtIfValid is '1'.";
          reference
           "T. Narten, E. Nordmark, W. Simpson, H. Soliman, 'Neighbor
            Discovery for IP version 6 (IPv6)', RFC-4861, September 2007.";
          smiv2:defval "604800";
          smiv2:max-access "read-write";
          smiv2:oid "1.3.6.1.4.1.9.9.784.1.2.1.1.21";
        }

        leaf cdtIfIpv6NdOpts {
          type bits {
            bit advertise {
              position "0";
            }
            bit onlink {
              position "1";
            }
            bit router {
              position "2";
            }
            bit autoConfig {
              position "3";
            }
            bit advertisementInterval {
              position "4";
            }
            bit managedConfigFlag {
              position "5";
            }
            bit otherConfigFlag {
              position "6";
            }
            bit framedIpv6Prefix {
              position "7";
            }
            bit raSuppress {
              position "8";
            }
          }
          description
           "This object specifies options that affect advertisements sent
            on the target interface:
            
                'advertise'
                    This option specifies that the system should advertise
                    the IPv6 prefix (i.e., the corresponding instance of
                    cdtIfIpv6NdPrefix).
            
                'onlink'
                    This option specifies that the IPv6 prefix has been
                    assigned to a link.  If set to '0', the system
                    advertises the IPv6 prefix as 'offlink'.
            
                'router'
                    This option indicates that the router will send the full
                    router address and not set the 'R' bit in prefix
                    advertisements.
            
                'autoConfig'
                    This option indicates to hosts on the local link that
                    the specified prefix supports IPv6 auto-configuration.
            
                'advertisementInterval'
                    This option specifies the advertisement interval option
                    in router advertisements sent on the target interface.
            
                'managedConfigFlag'
                    This option causes the system to set the 'managed
                    address configuration flag' in router advertisements
                    sent on the target interface.
            
                'otherConfigFlag'
                    This option causes the system to set the 'other stateful
                    configuration' flag in router advertisements sent on the
                    target interface.
            
                'frameIpv6Prefix'
                    This option causes the system to add the prefix in a
                    received RADIUS framed IPv6 prefix attribute to the
                    target interface's neighbor discovery prefix queue and
                    includes it in router advertisements sent on the target
                    interface.
            
                'raSupress'
                    This option suppresses the transmission of router
                    advertisements on the target interface.
            
            This column is valid only if the 'ipv6NdOpts' bit of the
            corresponding instance of cdtIfValid is '1'.";
          reference
           "T. Narten, E. Nordmark, W. Simpson, H. Soliman, 'Neighbor
            Discovery for IP version 6 (IPv6)', RFC-4861, September 2007.";
          smiv2:defval "{advertise, onlink, router, autoConfig}";
          smiv2:max-access "read-write";
          smiv2:oid "1.3.6.1.4.1.9.9.784.1.2.1.1.22";
        }

        leaf cdtIfIpv6NdDadAttempts {
          type uint32 {
            range "0..600";
          }
          description
           "This object specifies the number of consecutive neighbor
            solitication messages the system sends on the target interface
            while performing duplicate address detection on unicast IPv6
            addresses on the target interface.  The value '0' disables
            duplicate address detection on the target interface.
            
            This column is valid only if the 'ipv6NdDadAttempts' bit of the
            corresponding instance of cdtIfValid is '1'.";
          reference
           "T. Narten, E. Nordmark, W. Simpson, H. Soliman, 'Neighbor
            Discovery for IP version 6 (IPv6)', RFC-4861, September 2007.";
          smiv2:defval "1";
          smiv2:max-access "read-write";
          smiv2:oid "1.3.6.1.4.1.9.9.784.1.2.1.1.23";
        }

        leaf cdtIfIpv6NdNsInterval {
          type uint32 {
            range "1000..3600000";
          }
          units "milliseconds";
          description
           "This object specifies the interval between neighbor
            solicitation retransmissions on the target interface.
            
            This column is valid only if the 'ipv6NdNsIntervals' bit of the
            corresponding instance of cdtIfValid is '1'.";
          reference
           "T. Narten, E. Nordmark, W. Simpson, H. Soliman, 'Neighbor
            Discovery for IP version 6 (IPv6)', RFC-4861, September 2007.";
          smiv2:defval "1000";
          smiv2:max-access "read-write";
          smiv2:oid "1.3.6.1.4.1.9.9.784.1.2.1.1.24";
        }

        leaf cdtIfIpv6NdReachableTime {
          type uint32 {
            range "0..4294967295";
          }
          units "milliseconds";
          description
           "This object specifies the amount of time the system considers
            a neighbor of the target interface reachable after a
            reachability confirmation event has occurred.  The value '0'
            disables neighbor reachability detection on the target
            interface.
            
            This column is valid only if the 'ipv6NdReachable' bit of the
            corresponding instance of cdtIfValid is '1'.";
          reference
           "T. Narten, E. Nordmark, W. Simpson, H. Soliman, 'Neighbor
            Discovery for IP version 6 (IPv6)', RFC-4861, September 2007.";
          smiv2:defval "0";
          smiv2:max-access "read-write";
          smiv2:oid "1.3.6.1.4.1.9.9.784.1.2.1.1.25";
        }

        leaf cdtIfIpv6NdRaIntervalUnits {
          type enumeration {
            enum "seconds" {
              value "1";
            }
            enum "milliseconds" {
              value "2";
            }
          }
          description
           "This object specifies the units of time for the corresponding
            instances of cdtIfIpv6NdRaIntervalMin and
            cdtIfIpv6NdRaIntervalMax.
            
            This column is valid only if the 'ipv6NdRaInterval' bit of the
            corresponding instance of cdtIfValid is '1'.";
          smiv2:defval "seconds";
          smiv2:max-access "read-write";
          smiv2:oid "1.3.6.1.4.1.9.9.784.1.2.1.1.26";
        }

        leaf cdtIfIpv6NdRaIntervalMax {
          type uint32 {
            range "0..4294967295";
          }
          description
           "This object specifies the maximum interval between IPv6 router
            advertisements sent on the target interface.
            
            The value '0' cannot be written to an instance of this object.
            However, it serves as a convenient value when the column is not
            valid.
            
            This column is valid only if the 'ipv6NdRaInterval' bit of the
            corresponding instance of cdtIfValid is '1'.";
          reference
           "T. Narten, E. Nordmark, W. Simpson, H. Soliman, 'Neighbor
            Discovery for IP version 6 (IPv6)', RFC-4861, September 2007.";
          smiv2:defval "0";
          smiv2:max-access "read-write";
          smiv2:oid "1.3.6.1.4.1.9.9.784.1.2.1.1.27";
        }

        leaf cdtIfIpv6NdRaIntervalMin {
          type uint32 {
            range "0..4294967295";
          }
          description
           "This object specifies the minimum interval between IPv6 router
            advertisements sent on the target interface.  The value of this
            column has the following restrictions:
            
            1)  This value cannot be less than 75% of the value specified
                for cdtIfIpv6NdRaIntervalMax.
            
            2)  If the corresponding instance of cdtIfIpv6NdRaIntervalUnits
                is 'seconds', then this value cannot be less than '3'.
            
            3)  If the corresponding instance of cdtIfIpv6NdRaIntervalUnits
                is 'milliseconds', then this value cannot be less than '30'.
            
            If the target interface template does not specify this value,
            then the system automatically assumes a minimum interval that is
            75% of the corresponding instance of cdtIfIpv6NdRaIntervalMax.
            
            The value '0' cannot be written to an instance of this object.
            However, it serves as a convenient value when the column is not
            valid.
            
            This column is valid only if the 'ipv6NdRaInterval' bit of the
            corresponding instance of cdtIfValid is '1'.";
          reference
           "T. Narten, E. Nordmark, W. Simpson, H. Soliman, 'Neighbor
            Discovery for IP version 6 (IPv6)', RFC-4861, September 2007.";
          smiv2:defval "0";
          smiv2:max-access "read-write";
          smiv2:oid "1.3.6.1.4.1.9.9.784.1.2.1.1.28";
        }

        leaf cdtIfIpv6NdRaLife {
          type uint32 {
            range "0..4294967295";
          }
          units "seconds";
          description
           "This object specifies the router lifetime value in IPv6 router
            advertisements sent on the target interface.  The value '0'
            specifies that neighbors should not consider the router as a
            default router.";
          reference
           "T. Narten, E. Nordmark, W. Simpson, H. Soliman, 'Neighbor
            Discovery for IP version 6 (IPv6)', RFC-4861, September 2007.";
          smiv2:defval "1800";
          smiv2:max-access "read-write";
          smiv2:oid "1.3.6.1.4.1.9.9.784.1.2.1.1.29";
        }

        leaf cdtIfIpv6NdRouterPreference {
          type enumeration {
            enum "high" {
              value "1";
            }
            enum "medium" {
              value "2";
            }
            enum "low" {
              value "3";
            }
          }
          description
           "This object specifies the Default Router Preference (DRP) for
            the router on the target interface.
            
            This column is valid only if the 'ipv6NdRouterPreference' bit of
            the corresponding instance of cdtIfValid is '1'.";
          reference
           "T. Narten, E. Nordmark, W. Simpson, H. Soliman, 'Neighbor
            Discovery for IP version 6 (IPv6)', RFC-4861, September 2007.";
          smiv2:defval "medium";
          smiv2:max-access "read-write";
          smiv2:oid "1.3.6.1.4.1.9.9.784.1.2.1.1.30";
        }
      }
    }

    container cdtPppTemplateTable {
      description
       "This table contains attributes relating to PPP connection
        configuration.
        
        This table has a sparse-dependent relationship on the
        cdtTemplateTable, containing a row for each dynamic template
        having a cdtTemplateType of one of the following values:
        
            'derived'
            'ppp'";
      smiv2:oid "1.3.6.1.4.1.9.9.784.1.3.1";

      list cdtPppTemplateEntry {
        key "cdtTemplateName";
        description
         "An entry containing attributes relating to PPP connection
          configuration.
          
          The system automatically creates an entry when the system or the
          EMS/NMS creates a row in the cdtTemplateTable with a
          cdtTemplateType of one of the following values:
          
              'derived'
              'ppp'
          
          Likewise, the system automatically destroys an entry when the
          system or the EMS/NMS destroys the corresponding row in the
          cdtTemplateTable.";
        smiv2:oid "1.3.6.1.4.1.9.9.784.1.3.1.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtPppValid {
          type bits {
            bit valid {
              position "0";
            }
            bit accounting {
              position "1";
            }
            bit authentication {
              position "2";
            }
            bit autthenticationMethods {
              position "3";
            }
            bit authorization {
              position "4";
            }
            bit loopbackIgnore {
              position "5";
            }
            bit maxBadAuth {
              position "6";
            }
            bit maxConfigure {
              position "7";
            }
            bit maxFailure {
              position "8";
            }
            bit maxTerminate {
              position "9";
            }
            bit timeoutAuthentication {
              position "10";
            }
            bit timeoutRetry {
              position "11";
            }
            bit chapOpts {
              position "12";
            }
            bit chapHostname {
              position "13";
            }
            bit chapPassword {
              position "14";
            }
            bit msChapV1Opts {
              position "15";
            }
            bit msChapV1Hostname {
              position "16";
            }
            bit msChapV1Password {
              position "17";
            }
            bit msChapV2Opts {
              position "18";
            }
            bit msChapV2Hostname {
              position "19";
            }
            bit msChapV2Password {
              position "20";
            }
            bit papOpts {
              position "21";
            }
            bit papUsername {
              position "22";
            }
            bit papPassword {
              position "23";
            }
            bit eapOpts {
              position "24";
            }
            bit eapIdentity {
              position "25";
            }
            bit eapPassword {
              position "26";
            }
            bit ipcpAddrOption {
              position "27";
            }
            bit ipcpDnsOption {
              position "28";
            }
            bit ipcpDnsPrimary {
              position "29";
            }
            bit ipcpDnsSecondary {
              position "30";
            }
            bit ipcpWinsOption {
              position "31";
            }
            bit ipcpWinsPrimary {
              position "32";
            }
            bit ipcpWinsSecondary {
              position "33";
            }
            bit ipcpMaskOption {
              position "34";
            }
            bit ipcpMask {
              position "35";
            }
            bit peerDefIpAddrOpts {
              position "36";
            }
            bit peerDefIpAddrSrc {
              position "37";
            }
            bit peerDefIpAddr {
              position "38";
            }
          }
          description
           "This object specifies which attributes in the dynamic template
            have been configured to valid values.
            
            Each bit in this bit string corresponds to a column in this
            table.  If the bit is '0', then the value of the corresponding
            column is not valid.  If the bit is '1', then the value of the
            corresponding column has been configured to a valid value.
            
            The following list specifies the mappings between bits and the
            columns:
            
                accounting              => cdtPppAccounting
                authentication          => cdtPppAuthentication
                authenticationMethods   => cdtPppAuthenticationMethods
                authorization           => cdtPppAuthorization
                loopbackIgnore          => cdtPppLoopbackIgnore
                maxBadAuth              => cdtPppMaxBadAuth
                maxConfigure            => cdtPppMaxConfigure
                maxFailure              => cdtPppMaxFailure
                maxTerminate            => cdtPppMaxTerminate
                timeoutAuthentication   => cdtPppTimeoutAuthentication
                timeoutRetry            => cdtPppTimeoutRetry
                chapOpts                => cdtPppChapOpts
                chapHostname            => cdtPppChapHostname
                chapPassword            => cdtPppChapPassword
                msChapV1Opts            => cdtPppMsChapV1Opts
                msChapV1Hostname        => cdtPppMsChapV1Hostname
                msChapV1Password        => cdtPppMsChapV1Password
                msChapV2Opts            => cdtPppMsChapV2Opts
                msChapV2Hostname        => cdtPppMsChapV2Hostname
                msChapV2Password        => cdtPppMsChapV2Password
                papOpts                 => cdtPppPapOpts
                papSentUsername         => cdtPppPapUsername
                papSentPassword         => cdtPppPapPassword
                eapOpts                 => cdtPppEapOpts
                eapIdentity             => cdtPppEapIdentity
                eapPassword             => cdtPppEapPassword
                ipcpAddrOption          => cdtPppIpcpAddrOption
                ipcpDnsOption           => cdtPppIpcpDnsOption
                ipcpDnsPrimary          => cdtPppIpcpDnsPrimary
                ipcpDnsSecondary        => cdtPppIpcpDnsSecondary
                ipcpWinsOption          => cdtPppIpcpWinsOption
                ipcpWinsPrimary         => cdtPppIpcpWinsPrimary
                ipcpWinsSecondary       => cdtPppIpcpWinsSecondary
                ipcpMaskOption          => cdtPppIpcpMaskOption
                ipcpMask                => cdtPppIpcpMask
                peerDefIpAddrOpts       => cdtPppPeerOpts
                peerDefIpAddrSrc        => cdtPppPeerDefIpAddrSrc
                peerDefIpAddr           => cdtPppPeerDefIpAddr";
          smiv2:defval "{}";
          smiv2:max-access "read-write";
          smiv2:oid "1.3.6.1.4.1.9.9.784.1.3.1.1.1";
        }

        leaf cdtPppAccounting {
          type boolean;
          description
           "This object specifies whether the system applies accounting
            services to the target PPP connection.
            
            This column is valid only if the 'accounting' bit of the
            corresponding instance of cdtPppValid is '1'.";
          smiv2:defval "false";
          smiv2:max-access "read-write";
          smiv2:oid "1.3.6.1.4.1.9.9.784.1.3.1.1.2";
        }

        leaf cdtPppAuthentication {
          type bits {
            bit chap {
              position "0";
            }
            bit msChap {
              position "1";
            }
            bit msChapV2 {
              position "2";
            }
            bit pap {
              position "3";
            }
            bit eap {
              position "4";
            }
            bit optional {
              position "5";
            }
            bit callin {
              position "6";
            }
            bit oneTime {
              position "7";
            }
          }
          description
           "This object specifies authentication services applied to a
            target PPP connection and other options affecting authentication
            services:
            
                'chap'
                    This option enables the Challenge Handshake Protocol (CHAP)
                    on a target PPP connection.
            
                'msChap'
                    This option enables Microsoft's CHAP on a target PPP
                    connection.
            
                'msChapV2'
                    This option enables version 2 of Microsoft's CHAP on a
                    target PPP connection.
            
                'pap'
                    This option enables Password Authentication Protocol (PAP)
                    on a target PPP connection.
            
                'eap'
                    This option enables Extensible Authentication Protocol (EAP)
                    on a target PPP connection.
            
                'optional'
                    This option specifies that the system accepts the connection
                    even if the peer of a target PPP connection refuses to
                    accept the authentication methods the system has
                    requested.
            
                'callin'
                    This option specifies that authentication should only happen
                    for incoming calls.
            
                'oneTime'
                    This option specifies that the system accepts the username
                    and password in the username field of authentication
                    responses received on a target PPP connection.
            
            This column is valid only if the 'authentication' bit of the
            corresponding instance of cdtPppValid is '1'.";
          smiv2:defval "{}";
          smiv2:max-access "read-write";
          smiv2:oid "1.3.6.1.4.1.9.9.784.1.3.1.1.3";
        }

        leaf cdtPppAuthenticationMethods {
          type snmp-framework:SnmpAdminString {
            length "0..255";
          }
          description
           "This object specifies the name of a list of authentication
            methods used on a target PPP connection.  If the template does
            not include this attribute, then the system uses the default
            method list.
            
            This column is valid only if the 'authentication' bit of the
            corresponding instance of cdtPppValid is '1'.";
          smiv2:defval "";
          smiv2:max-access "read-write";
          smiv2:oid "1.3.6.1.4.1.9.9.784.1.3.1.1.4";
        }

        leaf cdtPppAuthorization {
          type boolean;
          description
           "This object specifies whether the system applies authorization
            services to a target PPP connection.
            
            This column is valid only if the 'authorization' bit of the
            corresponding instance of cditPppValid is '1'.";
          smiv2:defval "false";
          smiv2:max-access "read-write";
          smiv2:oid "1.3.6.1.4.1.9.9.784.1.3.1.1.5";
        }

        leaf cdtPppLoopbackIgnore {
          type boolean;
          description
           "This object specifies whether the system ignores loopback on
            a target PPP connection.  When the system ignores loopback,
            loopback detection is disabled.
            
            This column is valid only if the 'loopbackIgnore' bit of the
            corresponding instance of cdtPppValid is '1'.";
          reference
           "W. Simpson, 'The Point-to-Point Protocol (PPP)', RFC-1661,
            July 1994.";
          smiv2:defval "false";
          smiv2:max-access "read-write";
          smiv2:oid "1.3.6.1.4.1.9.9.784.1.3.1.1.6";
        }

        leaf cdtPppMaxBadAuth {
          type uint32 {
            range "0..4294967295";
          }
          description
           "This object specifies the number of authentication failures
            allowed by the system before a target PPP connection is reset.
            
            The value '0' cannot be written to an instance of this object.
            However, it serves as a convenient value when the column is not
            valid.
            
            This column is valid only if the 'maxBadAuth' bit of the
            corresponding instance of cdtPppValid is '1'.";
          smiv2:defval "0";
          smiv2:max-access "read-write";
          smiv2:oid "1.3.6.1.4.1.9.9.784.1.3.1.1.7";
        }

        leaf cdtPppMaxConfigure {
          type uint32 {
            range "1..4294967295";
          }
          description
           "This object specifies the number of unacknowledged
            Configure-Request messages a target PPP connection can send
            before the system abandons LCP or NCP negotiations.
            
            This column is valid only if the 'maxConfigure' bit of the
            corresponding instance of cdtPppValid is '1'.";
          reference
           "W. Simpson, 'The Point-to-Point Protocol (PPP)', RFC-1661,
            July 1994.";
          smiv2:defval "10";
          smiv2:max-access "read-write";
          smiv2:oid "1.3.6.1.4.1.9.9.784.1.3.1.1.8";
        }

        leaf cdtPppMaxFailure {
          type uint32 {
            range "1..4294967295";
          }
          description
           "This object specifies the number of Configure-Nak messages a
            target PPP connection can receive before the system abandons LCP
            or NCP negotiations.
            
            This column is valid only if the 'maxFailure' bit of the
            corresponding instance of cdtPppValid is '1'.";
          reference
           "W. Simpson, 'The Point-to-Point Protocol (PPP)', RFC-1661,
            July 1994.";
          smiv2:defval "5";
          smiv2:max-access "read-write";
          smiv2:oid "1.3.6.1.4.1.9.9.784.1.3.1.1.9";
        }

        leaf cdtPppMaxTerminate {
          type uint32 {
            range "1..4294967295";
          }
          description
           "This object specifies the number of unacknowledged
            Terminate-Request messages a target PPP connection can send
            before the system abandons LCP or NCP negotiations.
            
            This column is valid only if the 'maxTerminate' bit of the
            corresponding instance of cdtPppValid is '1'.";
          reference
           "W. Simpson, 'The Point-to-Point Protocol (PPP)', RFC-1661,
            July 1994.";
          smiv2:defval "2";
          smiv2:max-access "read-write";
          smiv2:oid "1.3.6.1.4.1.9.9.784.1.3.1.1.10";
        }

        leaf cdtPppTimeoutAuthentication {
          type uint32 {
            range "1..255";
          }
          units "seconds";
          description
           "This objects specifies the maximum time the system will wait
            for a response to an authentication request on a target PPP
            connection.
            
            This column is valid only if the 'timeoutAuthentication' bit of
            the corresponding instance of cdtPppValid is '1'.";
          smiv2:defval "10";
          smiv2:max-access "read-write";
          smiv2:oid "1.3.6.1.4.1.9.9.784.1.3.1.1.11";
        }

        leaf cdtPppTimeoutRetry {
          type uint32 {
            range "1..255";
          }
          units "seconds";
          description
           "This objects specifies the maximum time the system will wait
            for a response to a PPP control packets on a target PPP
            connection.
            
            This column is valid only if the 'timeoutRetry' bit of the
            corresponding instance of cdtPppValid is '1'.";
          reference
           "W. Simpson, 'The Point-to-Point Protocol (PPP)', RFC-1661,
            July 1994.";
          smiv2:defval "3";
          smiv2:max-access "read-write";
          smiv2:oid "1.3.6.1.4.1.9.9.784.1.3.1.1.12";
        }

        leaf cdtPppChapOpts {
          type bits {
            bit refuse {
              position "0";
            }
            bit callin {
              position "1";
            }
            bit wait {
              position "2";
            }
            bit encrypted {
              position "3";
            }
          }
          description
           "This object specifies how the system processes the CHAP on a
            target PPP connection:
            
                'refuse'
                    This option specifies that the system should refuse CHAP
                    requests from peers of a target PPP connection.
            
                'callin'
                    This option specifies that the system should only refuse
                    CHAP requests for incoming calls on a target PPP
                    connection.  This option is only relevant if the
                    'refuse' option is set to '1'.
            
                'wait'
                    This option delays CHAP authentication until after the
                    peer of a target PPP connection has authenticated itself
                    to the system.
            
                'encrypted'
                    This option specifies that the value specified by the
                    corresponding instance of cdtPppChapPassword is already
                    encrypted.
            
            This column is valid only if the 'chapOpts' bit of the
            corresponding instance of cdtPppValid is '1'.";
          reference
           "W. Simpson, 'PPP Challenge Handshake Authentication Protocol
            (CHAP)', RFC-1994, August 1996.";
          smiv2:defval "{wait}";
          smiv2:max-access "read-write";
          smiv2:oid "1.3.6.1.4.1.9.9.784.1.3.1.1.13";
        }

        leaf cdtPppChapHostname {
          type snmp-framework:SnmpAdminString {
            length "0..255";
          }
          description
           "This object specifies the hostname sent in a CHAP response
            on a target PPP connection.  If the template does not include
            this attribute, then the system uses its assigned hostname.
            
            This column is valid only if the 'chapHostname' bit of the
            corresponding instance of cdtPppValid is '1'.";
          reference
           "W. Simpson, 'PPP Challenge Handshake Authentication Protocol
            (CHAP)', RFC-1994, August 1996.";
          smiv2:defval "";
          smiv2:max-access "read-write";
          smiv2:oid "1.3.6.1.4.1.9.9.784.1.3.1.1.14";
        }

        leaf cdtPppChapPassword {
          type snmp-framework:SnmpAdminString {
            length "0..255";
          }
          description
           "This object specifies the password used to construct a CHAP
            response on the target PPP connection.
            
            This column is valid only if the 'chapPassword' bit of the
            corresponding instance of cdtPppValid is '1'.";
          reference
           "W. Simpson, 'PPP Challenge Handshake Authentication Protocol
            (CHAP)', RFC-1994, August 1996.";
          smiv2:defval "";
          smiv2:max-access "read-write";
          smiv2:oid "1.3.6.1.4.1.9.9.784.1.3.1.1.15";
        }

        leaf cdtPppMsChapV1Opts {
          type bits {
            bit refuse {
              position "0";
            }
            bit callin {
              position "1";
            }
            bit wait {
              position "2";
            }
            bit encrypted {
              position "3";
            }
          }
          description
           "This object specifies how the system processes version 1 of
            Microsoft CHAP on a target PPP connection:
            
                'refuse'
                    This option specifies that the system should refuse
                    Microsoft CHAP (v1) requests from peers of a target PPP
                    connection.
            
                'callin'
                    This option specifies that the system should only refuse
                    Microsoft CHAP (v1) requests for incoming calls on a
                    target PPP connection.  This option is only relevant if
                    the 'refuse' option is set to '1'.
            
                'wait'
                    This option delays Microsoft CHAP (v1) authentication
                    until after the peer of a target PPP connection has
                    authenticated itself to the system.
            
                'encrypted'
                    This option specifies that the value specified by the
                    corresponding instance of cdtPppMsChapV1Password is
                    already encrypted.
            
            This column is valid only if the 'msChapV1Opts' bit of the
            corresponding instance of cdtPppValid is '1'.";
          reference
           "G. Zorn, S. Cobb, 'Microsoft PPP CHAP Extensions', RFC-2433,
            October 1998.";
          smiv2:defval "{wait}";
          smiv2:max-access "read-write";
          smiv2:oid "1.3.6.1.4.1.9.9.784.1.3.1.1.16";
        }

        leaf cdtPppMsChapV1Hostname {
          type snmp-framework:SnmpAdminString {
            length "0..255";
          }
          description
           "This object specifies the hostname sent in a Microsoft CHAP
            (v1) response on a target PPP connection.  If the template does
            not include this attribute, then the system uses its assigned
            hostname.
            
            This column is valid only if the 'msChapV1Hostname' bit of the
            corresponding instance of cdtPppValid is '1'.";
          reference
           "G. Zorn, S. Cobb, 'Microsoft PPP CHAP Extensions', RFC-2433,
            October 1998.";
          smiv2:defval "";
          smiv2:max-access "read-write";
          smiv2:oid "1.3.6.1.4.1.9.9.784.1.3.1.1.17";
        }

        leaf cdtPppMsChapV1Password {
          type snmp-framework:SnmpAdminString {
            length "0..255";
          }
          description
           "This object specifies the password used to construct a
            Microsoft CHAP (v1) response on a target PPP connection.
            
            This column is valid only if the 'msChapV1Password' bit of the
            corresponding instance of cdtPppValid is '1'.";
          reference
           "G. Zorn, S. Cobb, 'Microsoft PPP CHAP Extensions', RFC-2433,
            October 1998.";
          smiv2:defval "";
          smiv2:max-access "read-write";
          smiv2:oid "1.3.6.1.4.1.9.9.784.1.3.1.1.18";
        }

        leaf cdtPppMsChapV2Opts {
          type bits {
            bit refuse {
              position "0";
            }
            bit callin {
              position "1";
            }
            bit wait {
              position "2";
            }
            bit encrypted {
              position "3";
            }
          }
          description
           "This object specifies how the system processes version 2 of
            Microsoft CHAP on a target PPP connection:
            
                'refuse'
                    This option specifies that the system should refuse
                    Microsoft CHAP (v2) requests from peers of a target PPP
                    connection.
            
                'callin'
                    This option specifies that the system should only refuse
                    Microsoft CHAP (v2) requests for incoming calls on a
                    target PPP connection.  This option is only relevant if
                    the 'refuse' option is set to '1'.
            
                'wait'
                    This option delays Microsoft CHAP (v2) authentication
                    until after the peer of a target PPP connection has
                    authenticated itself to the system.
            
                'encrypted'
                    This option specifies that the value specified by the
                    corresponding instance of cdtPppMsChapV2Password is
                    already encrypted.
            
            This column is valid only if the 'msChapV2Opts' bit of the
            corresponding instance of cdtPppValid is '1'.";
          reference
           "G. Zorn, 'Microsoft PPP CHAP Extensions, Version 2', RFC-2759,
            January 2000.";
          smiv2:defval "{wait}";
          smiv2:max-access "read-write";
          smiv2:oid "1.3.6.1.4.1.9.9.784.1.3.1.1.19";
        }

        leaf cdtPppMsChapV2Hostname {
          type snmp-framework:SnmpAdminString {
            length "0..255";
          }
          description
           "This object specifies the hostname sent in a Microsoft CHAP
            (v2) response on a target PPP connection.  If the template does
            not include this attribute, then the system uses its assigned
            hostname.
            
            This column is valid only if the 'msChapV2Hostname' bit of the
            corresponding instance of cdtPppValid is '1'.";
          reference
           "G. Zorn, 'Microsoft PPP CHAP Extensions, Version 2', RFC-2759,
            January 2000.";
          smiv2:defval "";
          smiv2:max-access "read-write";
          smiv2:oid "1.3.6.1.4.1.9.9.784.1.3.1.1.20";
        }

        leaf cdtPppMsChapV2Password {
          type snmp-framework:SnmpAdminString {
            length "0..255";
          }
          description
           "This object specifies the password used to construct a
            Microsoft CHAP (v2) response on a target PPP connection.
            
            This column is valid only if the 'msChapV2Password' bit of the
            corresponding instance of cdtPppValid is '1'.";
          reference
           "G. Zorn, 'Microsoft PPP CHAP Extensions, Version 2', RFC-2759,
            January 2000.";
          smiv2:defval "";
          smiv2:max-access "read-write";
          smiv2:oid "1.3.6.1.4.1.9.9.784.1.3.1.1.21";
        }

        leaf cdtPppPapOpts {
          type bits {
            bit refuse {
              position "0";
            }
            bit encrypted {
              position "1";
            }
          }
          description
           "This object specifies how the system processes the PAP on a
            target PPP connection:
            
                'refuse'
                    This option specifies that the system should refuse PAP
                    requests from peers of a target PPP connection.
            
                'encrypted'
                    This option specifies that the value specified by the
                    corresponding instance of cdtPppPapSentPassword is
                    already encrypted.
            
            This column is valid only if the 'papOpts' bit of the
            corresponding instance of cdtPppValid is '1'.";
          reference
           "B. Lloyd and W. Simpson, 'PPP Authentication Protocols',
            RFC-1334, October 1992.";
          smiv2:defval "{}";
          smiv2:max-access "read-write";
          smiv2:oid "1.3.6.1.4.1.9.9.784.1.3.1.1.22";
        }

        leaf cdtPppPapUsername {
          type snmp-framework:SnmpAdminString {
            length "0..255";
          }
          description
           "This object specifies the username sent in a PAP response on
            a target PPP connection.
            
            This column is valid only if the 'papUsername' bit of the
            corresponding instance of cdtPppValid is '1'.";
          reference
           "B. Lloyd and W. Simpson, 'PPP Authentication Protocols',
            RFC-1334, October 1992.";
          smiv2:defval "";
          smiv2:max-access "read-write";
          smiv2:oid "1.3.6.1.4.1.9.9.784.1.3.1.1.23";
        }

        leaf cdtPppPapPassword {
          type snmp-framework:SnmpAdminString {
            length "0..255";
          }
          description
           "This object specifies the username used to construct a PAP
            response on a target PPP connection.
            
            This column is valid only if the 'papPassword' bit of the
            corresponding instance of cdtPppValid is '1'.";
          reference
           "B. Lloyd and W. Simpson, 'PPP Authentication Protocols',
            RFC-1334, October 1992.";
          smiv2:defval "";
          smiv2:max-access "read-write";
          smiv2:oid "1.3.6.1.4.1.9.9.784.1.3.1.1.24";
        }

        leaf cdtPppEapOpts {
          type bits {
            bit refuse {
              position "0";
            }
            bit callin {
              position "1";
            }
            bit wait {
              position "2";
            }
            bit local {
              position "3";
            }
          }
          description
           "This object specifies how the system processes the EAP on a
            target PPP connection:
            
                'refuse'
                    This option specifies that the system should refuse EAP
                    requests from peers of a target PPP connection.
            
                'callin'
                    This option specifies that the system should only refuse EAP
                    requests for incoming calls on a target PPP connection.
                    This option is only relevant if the 'refuse' option is
                    set to '1'.
            
                'wait'
                    This option delays EAP authentication until after the
                    peer of a target PPP connection has authenticated itself
                    to the system.
            
                'local'
                    This option specifies that the system should locally
                    authenticate the peer of a target PPP connection,
                    rather than acting as a proxy to an external AAA server.
            
            This column is valid only if the 'eapOpts' bit of the
            corresponding instance of cdtPppValid is '1'.";
          reference
           "B. Aboba, L. Blunk, J. Vollbrecht, J. Carlson, and H.
            Levkowetz, 'Extensible Authentication Protocol (EAP)',
            RFC-3748, June 2004.";
          smiv2:defval "{}";
          smiv2:max-access "read-write";
          smiv2:oid "1.3.6.1.4.1.9.9.784.1.3.1.1.25";
        }

        leaf cdtPppEapIdentity {
          type snmp-framework:SnmpAdminString {
            length "0..255";
          }
          description
           "This object specifies the identity sent in an EAP response on
            a target PPP connection.
            
            This column is valid only if the 'eapIdentity' bit of the
            corresponding instance of cdtPppValid is '1'.";
          reference
           "B. Aboba, L. Blunk, J. Vollbrecht, J. Carlson, and H.
            Levkowetz, 'Extensible Authentication Protocol (EAP)',
            RFC-3748, June 2004.";
          smiv2:defval "";
          smiv2:max-access "read-write";
          smiv2:oid "1.3.6.1.4.1.9.9.784.1.3.1.1.26";
        }

        leaf cdtPppEapPassword {
          type snmp-framework:SnmpAdminString {
            length "0..255";
          }
          description
           "This object specifies the password used to construct an EAP
            response on a target PPP connection.
            
            This column is valid only if the 'eapPassword' bit of the
            corresponding instance of cdtPppValid is '1'.";
          reference
           "B. Aboba, L. Blunk, J. Vollbrecht, J. Carlson, and H.
            Levkowetz, 'Extensible Authentication Protocol (EAP)',
            RFC-3748, June 2004.";
          smiv2:defval "";
          smiv2:max-access "read-write";
          smiv2:oid "1.3.6.1.4.1.9.9.784.1.3.1.1.27";
        }

        leaf cdtPppIpcpAddrOption {
          type enumeration {
            enum "other" {
              value "1";
            }
            enum "accept" {
              value "2";
            }
            enum "required" {
              value "3";
            }
            enum "unique" {
              value "4";
            }
          }
          description
           "This object specifies the IPCP address option for a target PPP
            connection:
            
                'other'
                    The implementation of this MIB module does not recognize
                    the configured IPCP address option.
            
                'accept'
                    The system accepts any non-zero IP address from the peer
                    of a target PPP connection.
            
                'required'
                    The system disconnects the peer of a target PPP
                    connection if it could not negotiate an IP address.
            
                'unique'
                    The system disconnects the peer of a target PPP
                    connection if the IP address is already in use.
            
            This column is valid only if the 'ipcpAddrOption' bit of the
            corresponding instance of cdtPppValid is '1'.";
          reference
           "G. McGregor, 'The PPP Internet Protocol Control Protocol
            (IPCP)', RFC-1332, May 1992.";
          smiv2:defval "other";
          smiv2:max-access "read-write";
          smiv2:oid "1.3.6.1.4.1.9.9.784.1.3.1.1.28";
        }

        leaf cdtPppIpcpDnsOption {
          type enumeration {
            enum "other" {
              value "1";
            }
            enum "accept" {
              value "2";
            }
            enum "request" {
              value "3";
            }
            enum "reject" {
              value "4";
            }
          }
          description
           "This object specifies the IPCP DNS option for the dynamic
            interface:
            
                'other'
                    The implementation of this MIB module does not recognize
                    the configured DNS option.
            
                'accept'
                    The system accepts any non-zero DNS address form the
                    peer of a target PPP connection.
            
                'request'
                    The system requests the DNS address from the peer of a
                    target PPP connection.
            
                'reject'
                    The system rejects the DNS option from the peer of a
                    target PPP connection.
            
            This column is valid only if the 'ipcpDnsOption' bit of the
            corresponding instance of cdtPppValid is '1'.";
          reference
           "G. McGregor, 'The PPP Internet Protocol Control Protocol
            (IPCP)', RFC-1332, May 1992.";
          smiv2:defval "other";
          smiv2:max-access "read-write";
          smiv2:oid "1.3.6.1.4.1.9.9.784.1.3.1.1.29";
        }

        leaf cdtPppIpcpDnsPrimary {
          type inet-address:InetAddressIPv4;
          description
           "This object specifies the IP address of the primary DNS server
            offered to the peer of a target PPP connection.
            
            This column is valid only if the 'ipcpDnsPrimary' bit of the
            corresponding instance of cdtPppValid is '1'.";
          reference
           "G. McGregor, 'The PPP Internet Protocol Control Protocol
            (IPCP)', RFC-1332, May 1992.";
          smiv2:defval "'00000000'H";
          smiv2:max-access "read-write";
          smiv2:oid "1.3.6.1.4.1.9.9.784.1.3.1.1.30";
        }

        leaf cdtPppIpcpDnsSecondary {
          type inet-address:InetAddressIPv4;
          description
           "This object specifies the IP address of the secondary DNS
            server offered to the peer of a target PPP connection.
            
            This column is valid only if the 'ipcpDnsSecondary' bit of the
            corresponding instance of cdtPppValid is '1'.";
          reference
           "G. McGregor, 'The PPP Internet Protocol Control Protocol
            (IPCP)', RFC-1332, May 1992.";
          smiv2:defval "'00000000'H";
          smiv2:max-access "read-write";
          smiv2:oid "1.3.6.1.4.1.9.9.784.1.3.1.1.31";
        }

        leaf cdtPppIpcpWinsOption {
          type enumeration {
            enum "other" {
              value "1";
            }
            enum "accept" {
              value "2";
            }
            enum "request" {
              value "3";
            }
            enum "reject" {
              value "4";
            }
          }
          description
           "This object specifies the IPCP WINS option for a target PPP
            connection:
            
                'other'
                    The implementation of this MIB module does not recognize
                    the configured WINS option.
            
                'accept'
                    The system accepts any non-zero WINS address from the
                    peer of a target PPP connection.
            
                'request'
                    The system requests the WINS address from the peer of
                    a target PPP connection.
            
                'reject'
                    The system rejects the WINS option from the peer of a
                    target PPP connection.
            
            This column is valid only if the 'ipcpWinsOption' bit of the
            corresponding instance of cdtPppValid is '1'.";
          reference
           "G. McGregor, 'The PPP Internet Protocol Control Protocol
            (IPCP)', RFC-1332, May 1992.";
          smiv2:defval "other";
          smiv2:max-access "read-write";
          smiv2:oid "1.3.6.1.4.1.9.9.784.1.3.1.1.32";
        }

        leaf cdtPppIpcpWinsPrimary {
          type inet-address:InetAddressIPv4;
          description
           "This object specifies the IP address of the primary WINS server
            offered to the peer of a target PPP connection.
            
            This column is valid only if the 'ipcpWinsPrimary' bit of the
            corresponding instance of cdtPppValid is '1'.";
          reference
           "G. McGregor, 'The PPP Internet Protocol Control Protocol
            (IPCP)', RFC-1332, May 1992.";
          smiv2:defval "'00000000'H";
          smiv2:max-access "read-write";
          smiv2:oid "1.3.6.1.4.1.9.9.784.1.3.1.1.33";
        }

        leaf cdtPppIpcpWinsSecondary {
          type inet-address:InetAddressIPv4;
          description
           "This object specifies the IP address of the secondary WINS
            server offered to the peer of a target PPP connection.
            
            This column is valid only if the 'ipcpWinsSecondary' bit of the
            corresponding instance of cdtPppValid is '1'.";
          reference
           "G. McGregor, 'The PPP Internet Protocol Control Protocol
            (IPCP)', RFC-1332, May 1992.";
          smiv2:defval "'00000000'H";
          smiv2:max-access "read-write";
          smiv2:oid "1.3.6.1.4.1.9.9.784.1.3.1.1.34";
        }

        leaf cdtPppIpcpMaskOption {
          type enumeration {
            enum "other" {
              value "1";
            }
            enum "request" {
              value "2";
            }
            enum "reject" {
              value "3";
            }
          }
          description
           "This object specifies the IPCP IP subnet mask option for a
            target PPP connection:
            
                'other'
                    The implementation of this MIB module does not recognize
                    the configured IP subnet mask option.
            
                'request'
                    The system requests the IP subnet mask from the peer of
                    a target PPP connection.
            
                'reject'
                    The system rejects the IP subnet mask option from the
                    peer of a target PPP connection.
            
            This column is valid only if the 'ipcpMaskOption' bit of the
            corresponding instance of cdtPppValid is '1'.";
          reference
           "G. McGregor, 'The PPP Internet Protocol Control Protocol
            (IPCP)', RFC-1332, May 1992.";
          smiv2:defval "other";
          smiv2:max-access "read-write";
          smiv2:oid "1.3.6.1.4.1.9.9.784.1.3.1.1.35";
        }

        leaf cdtPppIpcpMask {
          type inet-address:InetAddressIPv4;
          description
           "This object specifies the IP address mask offered to the peer
            of a target PPP connection.
            
            This column is valid only if the 'ipcpMask' bit of the
            corresponding instance of cdtPppValid is '1'.";
          reference
           "G. McGregor, 'The PPP Internet Protocol Control Protocol
            (IPCP)', RFC-1332, May 1992.";
          smiv2:defval "'00000000'H";
          smiv2:max-access "read-write";
          smiv2:oid "1.3.6.1.4.1.9.9.784.1.3.1.1.36";
        }

        leaf cdtPppPeerDefIpAddrOpts {
          type bits {
            bit ipAddrForced {
              position "0";
            }
            bit matchAaaPools {
              position "1";
            }
            bit staticPool {
              position "2";
            }
          }
          description
           "This object specifies options that affect how the system
            assigns an IP address to the peer of a target PPP connection:
            
                'ipAddrForced'
                    This option forces the system to assign the next
                    available IP address in the pool to the peer of a
                    target PPP connection.  When disabled, the peer may
                    negotiate a specific IP address or the system can assign
                    the peer its previously assigned IP address.
            
                'matchAaaPools'
                    This option specifies that the names of the IP address
                    pools provided by an external AAA server must appear in
                    the corresponding list of IP address pool specified by
                    the cdtPppPeerIpAddrPoolTable.
            
                'backupPools'
                    This option specifies that the corresponding names of
                    the IP address pools specified by the
                    cditPppPeerIpAddrPoolTable serve as backup pools to
                    those provided by an external AAA server.
            
                'staticPools'
                    This option suppresses an attempt to load pools from an
                    external AAA server when the system encounters a missing
                    pool name.
            
            This column is valid only if the 'peerIpAddrOpts' bit of the
            corresponding instance of cdtPppValid is '1'.";
          smiv2:defval "{ipAddrForced}";
          smiv2:max-access "read-write";
          smiv2:oid "1.3.6.1.4.1.9.9.784.1.3.1.1.37";
        }

        leaf cdtPppPeerDefIpAddrSrc {
          type enumeration {
            enum "static" {
              value "1";
            }
            enum "pool" {
              value "2";
            }
            enum "dhcp" {
              value "3";
            }
          }
          description
           "This object specifies how the system assigns an IP address to
            the peer of a target PPP connection:
            
                'static'
                    The system assigns the IP address specified by the
                    corresponding instance of cdtPppPeerDefIpAddr.
            
                'pool'
                    The system allocates the first available IP address from
                    the corresponding list of named pools contained by the
                    cdtPppPeerIpAddrPoolTable.
            
                'dhcp'
                    The system acts as a DHCP proxy-client to obtain an IP
                    address.
            
            This column is valid only if the 'peerDefIpAddrSrc' bit of the
            corresponding instance of cdtPppValid is '1'.";
          smiv2:defval "pool";
          smiv2:max-access "read-write";
          smiv2:oid "1.3.6.1.4.1.9.9.784.1.3.1.1.38";
        }

        leaf cdtPppPeerDefIpAddr {
          type inet-address:InetAddressIPv4;
          description
           "This object specifies the IP address the system assigns to the
            peer of a target PPP connection.
            
            This column is valid only if the 'peerDefIpAddr' bit of the
            corresponding instance of cdtPppValid is '1'.";
          smiv2:defval "'00000000'H";
          smiv2:max-access "read-write";
          smiv2:oid "1.3.6.1.4.1.9.9.784.1.3.1.1.39";
        }
      }
    }

    container cdtPppPeerIpAddrPoolTable {
      description
       "This table contains a prioritized list of named pools for each
        PPP template.  A list corresponding to a PPP template
        specifies the pools the system searches in an attempt to
        assign an IP address to the peer of a target PPP connection.
        The system searches the pools in the order of their priority.
        
        This table has an expansion dependent relationship on the
        cdtPppTemplateTable, containing zero or more rows for each PPP
        template.";
      smiv2:oid "1.3.6.1.4.1.9.9.784.1.3.2";

      list cdtPppPeerIpAddrPoolEntry {
        key "cdtTemplateName cdtPppPeerIpAddrPoolPriority";
        description
         "An entry specifies a named pool in a list of pools associated
          with a PPP template.  A PPP template can only have named
          pools associated with it if it has a cdtPppPeerIpAddrSrc of
          'pool'.
          
          Any attempt to create an entry for a PPP template that does not
          have a cdtPppPeerIpAddrSrc of 'pool' must result in a response
          having an error-status of 'inconsistentValue'.
          
          The system automatically creates a corresponding entry when the
          system associates a named pool with a PPP template through
          another management entity (e.g., the system's local console).
          
          The system automatically destroys an entry under the following
          circumstances:
          
          1)  The system or EMS/NMS destroys the corresponding row in the
              cdtTemplateTable.
          
          2)  The system or EMS/NMS sets the corresponding instance of
              cdtPppPeerIpAddrSrc with a value other than 'pool'.";
        smiv2:oid "1.3.6.1.4.1.9.9.784.1.3.2.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtPppPeerIpAddrPoolPriority {
          type uint32 {
            range "1..4294967295";
          }
          description
           "This object indicates the relative priority of the named pool
            in the list corresponding to a PPP template.  The system
            searches pools in the order of priority, where lower values
            represent higher priority.";
          smiv2:max-access "not-accessible";
          smiv2:oid "1.3.6.1.4.1.9.9.784.1.3.2.1.1";
        }

        leaf cdtPppPeerIpAddrPoolStatus {
          type snmpv2-tc:RowStatus;
          description
           "This object specifies the status of the entry.  The following
            columns must be valid before activating a subscriber access
            profile:
            
                - cdtPppPeerIpAddrPoolStorage
                - cdtPppPeerIpAddrPoolName
            
            However, these objects specify a default value.  Thus, it is
            possible to use create-and-go semantics without setting any
            additional columns.
            
            An implementation must not allow the EMS/NMS to create an entry
            if the corresponding instance of cdtPppPeerIpAddrSrc is not
            'pool'.
            
            An implementation must allow the EMS/NMS to modify any column
            when this column is 'active'.";
          smiv2:max-access "read-write";
          smiv2:oid "1.3.6.1.4.1.9.9.784.1.3.2.1.2";
        }

        leaf cdtPppPeerIpAddrPoolStorage {
          type snmpv2-tc:StorageType;
          description
           "This object specifies what happens to the name pool entry upon
            restart.
            
            If the corresponding instance of cdtTemplateSrc is not 'local',
            then this column must be 'volatile'.";
          smiv2:defval "volatile";
          smiv2:max-access "read-write";
          smiv2:oid "1.3.6.1.4.1.9.9.784.1.3.2.1.3";
        }

        leaf cdtPppPeerIpAddrPoolName {
          type snmp-framework:SnmpAdminString {
            length "0..255";
          }
          description
           "This object specifies the name of the IP address pool
            associated with the PPP template.";
          smiv2:defval "";
          smiv2:max-access "read-write";
          smiv2:oid "1.3.6.1.4.1.9.9.784.1.3.2.1.4";
        }
      }
    }

    container cdtEthernetTemplateTable {
      description
       "This table contains attributes relating to dynamic interfaces
        initiated on Ethernet virtual interfaces (e.g., EoMPLS) or
        automatically created VLANs.
        
        This table has a sparse-dependent relationship on the
        cdtTemplateTable, containing a row for each dynamic template
        having a cdtTemplateType of one of the following values:
        
            'derived'
            'ethernet'";
      smiv2:oid "1.3.6.1.4.1.9.9.784.1.4.1";

      list cdtEthernetTemplateEntry {
        key "cdtTemplateName";
        description
         "An entry containing attributes relating to dynamic interfaces
          initiated on Ethernet virtual interfaces (e.g., EoMPLS) or
          automatically created VLANs.
          
          The system automatically creates an entry when the system or the
          EMS/NMS creates a row in the cdtTemplateTable with a
          cdtTemplateType of one of the following values:
          
              'derived'
              'ethernet'
          
          Likewise, the system automatically destroys an entry when the
          system or the EMS/NMS destroys the corresponding row in the
          cdtTemplateTable.";
        smiv2:oid "1.3.6.1.4.1.9.9.784.1.4.1.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtEthernetValid {
          type bits {
            bit bridgeDomain {
              position "0";
            }
            bit pppoeEnable {
              position "1";
            }
            bit ipv4PointToPoint {
              position "2";
            }
            bit macAddr {
              position "3";
            }
          }
          description
           "This object specifies which attributes in the dynamic template
            have been configured to valid values.
            
            Each bit in this bit string corresponds to a column in this
            table.  If the bit is '0', then the value of the corresponding
            column is not valid.  If the bit is '1', then the value of the
            corresponding column has been configured to a valid value.
            
            The following list specifies the mappings between bits and the
            columns:
            
                bridgeDomain     => cdtEthernetBridgeDomain
                pppoeEnable      => cdtEthernetPppoeEnable
                ipv4PointToPoint => cdtEthernetIpv4PointToPoint
                macAddr          => cdtEthernetMacAddr";
          smiv2:defval "{}";
          smiv2:max-access "read-write";
          smiv2:oid "1.3.6.1.4.1.9.9.784.1.4.1.1.1";
        }

        leaf cdtEthernetBridgeDomain {
          type snmp-framework:SnmpAdminString {
            length "0..255";
          }
          description
           "This object specifies the name of the bridge domain...";
          smiv2:defval "";
          smiv2:max-access "read-write";
          smiv2:oid "1.3.6.1.4.1.9.9.784.1.4.1.1.2";
        }

        leaf cdtEthernetPppoeEnable {
          type boolean;
          description
           "This object specifies whether...";
          smiv2:defval "false";
          smiv2:max-access "read-write";
          smiv2:oid "1.3.6.1.4.1.9.9.784.1.4.1.1.3";
        }

        leaf cdtEthernetIpv4PointToPoint {
          type boolean;
          description
           "This object specifies whether...";
          smiv2:defval "false";
          smiv2:max-access "read-write";
          smiv2:oid "1.3.6.1.4.1.9.9.784.1.4.1.1.4";
        }

        leaf cdtEthernetMacAddr {
          type yang:mac-address;
          description
           "This object specifies the...";
          smiv2:defval "'000000000000'H";
          smiv2:max-access "read-write";
          smiv2:oid "1.3.6.1.4.1.9.9.784.1.4.1.1.5";
        }
      }
    }

    container cdtSrvTemplateTable {
      description
       "This table contains attributes relating to a service.
        
        This table has a sparse-dependent relationship on the
        cdtTemplateTable, containing a row for each dynamic template
        having a cdtTemplateType of one of the following values:
        
            'derived'
            'service'";
      smiv2:oid "1.3.6.1.4.1.9.9.784.1.6.1";

      list cdtSrvTemplateEntry {
        key "cdtTemplateName";
        description
         "An entry containing attributes relating to a service.
          
          The system automatically creates entry when the system or the
          EMS/NMS creates a row in the cdtTemplateTable with a
          cdtTemplateType of one of the following values:
          
              'derived'
              'service'
          
          Likewise, the system automatically destroys an entry when the
          system or the EMS/NMS destroys the corresponding row in the
          cdtTemplateTable.";
        smiv2:oid "1.3.6.1.4.1.9.9.784.1.6.1.1";

        leaf cdtTemplateName {
          type leafref {
            path "/CISCO-DYNAMIC-TEMPLATE-MIB:CISCO-DYNAMIC-TEMPLATE-MIB/CISCO-DYNAMIC-TEMPLATE-MIB:cdtTemplateTable/CISCO-DYNAMIC-TEMPLATE-MIB:cdtTemplateEntry/CISCO-DYNAMIC-TEMPLATE-MIB:cdtTemplateName";
          }
        }

        leaf cdtSrvValid {
          type bits {
            bit networkSrv {
              position "0";
            }
            bit vpdnGroup {
              position "1";
            }
            bit sgSrvGroup {
              position "2";
            }
            bit sgSrvType {
              position "3";
            }
            bit multicast {
              position "4";
            }
          }
          description
           "This object specifies which attributes in the dynamic template
            have been configured to valid values.
            
            Each bit in this bit string corresponds to a column in this
            table.  If the bit is '0', then the value of the corresponding
            column is not valid.  If the bit is '1', then the value of the
            corresponding column has been configured to a valid value.
            
            The following list specifies the mappings between bits and the
            columns:
            
                networkSrv     => cdtSrvNetworkSrv
                vpdnGroup      => cdtSrvVpdnGroup
                sgSrvGroup     => cdtSrvGroup
                sgSrvType      => cdtSrvSgSrvType
                multicast      => cdtSrvMulticast";
          smiv2:defval "{}";
          smiv2:max-access "read-write";
          smiv2:oid "1.3.6.1.4.1.9.9.784.1.6.1.1.1";
        }

        leaf cdtSrvNetworkSrv {
          type enumeration {
            enum "other" {
              value "1";
            }
            enum "none" {
              value "2";
            }
            enum "local" {
              value "3";
            }
            enum "vpdn" {
              value "4";
            }
          }
          description
           "This object specifies the type of network service provided by
            the target service:
            
                'other'
                    The implementation of this MIB module does not recognize
                    the configured network service.
            
                'none'
                    The target subscriber service does not provide a network
                    service to subscribers sessions.
            
                'local'
                    The target subscriber service provides local termination
                    for subscriber sessions.
            
                'vpdn'
                    The target subscriber service provides a Virtual Private
                    Dialup Network service for subscriber sessions.
            
            This column is valid only if the 'networkSrv' bit of the
            corresponding instance of cdtSrvValid is '1'.";
          smiv2:defval "none";
          smiv2:max-access "read-write";
          smiv2:oid "1.3.6.1.4.1.9.9.784.1.6.1.1.2";
        }

        leaf cdtSrvVpdnGroup {
          type snmp-framework:SnmpAdminString {
            length "0..255";
          }
          description
           "This object specifies the name of the VPDN group used to
            configure the network service.
            
            This column is valid only if the 'vpdnGroup' bit of the
            corresponding instance of cdtSrvValid is '1'.";
          smiv2:defval "";
          smiv2:max-access "read-write";
          smiv2:oid "1.3.6.1.4.1.9.9.784.1.6.1.1.3";
        }

        leaf cdtSrvSgSrvGroup {
          type snmp-framework:SnmpAdminString {
            length "0..255";
          }
          description
           "This object specifies the name of the service group with which
            the system associates subscriber sessions.  A service group
            specifies a set of services that may be active simultaneously
            for a given subscriber session.  Typically, a service group
            contains a primary service and one or more secondary services.
            
            This column is valid only if the 'sgSrvGroup' bit of the
            corresponding instance of cdtSrvValid is '1'.";
          smiv2:defval "";
          smiv2:max-access "read-write";
          smiv2:oid "1.3.6.1.4.1.9.9.784.1.6.1.1.4";
        }

        leaf cdtSrvSgSrvType {
          type enumeration {
            enum "primary" {
              value "1";
            }
            enum "secondary" {
              value "2";
            }
          }
          description
           "This object specifies whether the target service specifies a
            network-forwarding policy:
            
                'primary'
                    The target service specifies a network-forwarding
                    policy.  Primary services are mutually exclusive; that
                    is, only one primary service can be activated for any
                    given subscriber session.
            
                'secondary'
                    The target service has a dependence on the primary
                    service in the group specified by the corresponding
                    instance of cdtSuBSrvSgSrvGroup.  After the system
                    activates the primary service, it activates secondary
                    services.  When the system deactivates the primary
                    service, then it deactivates all the secondary services
                    in the service group.
            
            This column is valid only if the 'sgSrvType' bit of the
            corresponding instance of cdtSrvValid is '1'.";
          smiv2:defval "secondary";
          smiv2:max-access "read-write";
          smiv2:oid "1.3.6.1.4.1.9.9.784.1.6.1.1.5";
        }

        leaf cdtSrvMulticast {
          type boolean;
          description
           "This objects specifies whether the system enables multicast
            service for subscriber sessions of the target service.
            
            This column is valid only if the 'sgSrvMcastRoutingIf' bit of
            the corresponding instance of cdtSrvValid is '1'.";
          smiv2:defval "false";
          smiv2:max-access "read-write";
          smiv2:oid "1.3.6.1.4.1.9.9.784.1.6.1.1.6";
        }
      }
    }
  }

  smiv2:alias "ciscoDynamicTemplateMIB" {
    smiv2:oid "1.3.6.1.4.1.9.9.784";
  }

  smiv2:alias "ciscoDynamicTemplateMIBNotifs" {
    smiv2:oid "1.3.6.1.4.1.9.9.784.0";
  }

  smiv2:alias "ciscoDynamicTemplateMIBObjects" {
    smiv2:oid "1.3.6.1.4.1.9.9.784.1";
  }

  smiv2:alias "cdtBase" {
    smiv2:oid "1.3.6.1.4.1.9.9.784.1.1";
  }

  smiv2:alias "cdtCommonIf" {
    smiv2:oid "1.3.6.1.4.1.9.9.784.1.2";
  }

  smiv2:alias "cdtPpp" {
    smiv2:oid "1.3.6.1.4.1.9.9.784.1.3";
  }

  smiv2:alias "cdtEthernet" {
    smiv2:oid "1.3.6.1.4.1.9.9.784.1.4";
  }

  smiv2:alias "cdtIpSubscriber" {
    smiv2:oid "1.3.6.1.4.1.9.9.784.1.5";
  }

  smiv2:alias "cdtService" {
    smiv2:oid "1.3.6.1.4.1.9.9.784.1.6";
  }

  smiv2:alias "cdtSubscriberGroup" {
    smiv2:oid "1.3.6.1.4.1.9.9.784.1.7";
  }

  smiv2:alias "ciscoDynamicTemplateMIBConform" {
    smiv2:oid "1.3.6.1.4.1.9.9.784.2";
  }

  smiv2:alias "ciscoDynamicTemplateMIBCompliances" {
    smiv2:oid "1.3.6.1.4.1.9.9.784.2.1";
  }

  smiv2:alias "ciscoDynamicTemplateMIBGroups" {
    smiv2:oid "1.3.6.1.4.1.9.9.784.2.2";
  }

}
