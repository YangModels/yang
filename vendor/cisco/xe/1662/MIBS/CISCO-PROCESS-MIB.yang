/*
 * Generated by confdc --mib2yang-std
 * Source: mgmt/dmi/model/common/mib-source/hand-processed/CISCO-PROCESS-MIB.mib
 */
/*
 * This YANG module has been generated by smidump 0.5.0:
 *
 *      smidump -f yang CISCO-PROCESS-MIB
 *
 * Do not edit. Edit the source file instead!
 */

module CISCO-PROCESS-MIB {

  namespace "urn:ietf:params:xml:ns:yang:smiv2:CISCO-PROCESS-MIB";
  prefix CISCO-PROCESS-MIB;

  import CISCO-TC {
    prefix "cisco-tc";
  }

  import SNMP-FRAMEWORK-MIB {
    prefix "snmp-framework";
  }

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-snmp@cisco.com";

  description
   "The MIB module to describe active system processes.
    Virtual Machine refers to those OS which can run the 
    code or process of a different executional model OS.
    Virtual Process assume the executional model 
    of a OS which is different from Native OS. Virtual
    Processes are also referred as Tasks.
    Thread is a sequence of instructions to be executed
    within a program. Thread which adhere to POSIX standard
    is referred as a POSIX thread.";

  revision 2011-06-23 {
    description
     "Added new table cpmCoreTable as well as a new optoinal
      compliance group cpmCoreGroup.";
  }

  revision 2010-05-06 {
    description
     "Added the following new objects to the cpmCPUTotalTable.
      cpmCPUMemoryCommitted, cpmCPUMemoryCommittedOvrFlow and
      cpmCPUMemoryHCCommitted.
      
      Added new compliance group cpmCPUTotalMemoryCommitGroup which
      includes Committed memory objects.
      
      Added new compliance cProcessMIBComplianceRev5 which 
      deprecates cProcessMIBComplianceRev4.";
  }

  revision 2009-10-12 {
    description
     "Added TEXTUAL-CONVENTION called CPULoadAverage.
      Added the following new objects to cpmCPUTotalTable.
      cpmCPULoadAvg1min, cpmCPULoadAvg5min, cpmCPULoadAvg15min.
      
      Added new compliance group cpmCPULoadAvgGroup which includes
      load average objects.
      
      Added new compliance cProcessMIBComplianceRev4 which 
      deprecates cProcessMIBComplianceRev3.";
  }

  revision 2009-01-23 {
    description
     "Added the following new objects to cpmCPUTotalTable.
      cpmCPUMemoryUsedOvrflw, cpmCPUMemoryHCUsed,
      cpmCPUMemoryFreeOvrflw, cpmCPUMemoryHCFree,
      cpmCPUMemoryKernelReservedOvrflw, cpmCPUMemoryHCKernelReserved,
      cpmCPUMemoryLowestOvrflw, cpmCPUMemoryHCLowest
      
      Added the following new objects to cpmProcessExtRevTable.
      cpmProcExtMemAllocatedRevOvrflw, cpmProcExtHCMemAllocatedRev,
      cpmProcExtMemFreedRevOvrflw, cpmProcExtHCMemFreedRev,
      cpmProcessTextSegmentSizeOvrflw, cpmProcessHCTextSegmentSize,
      cpmProcessDataSegmentSizeOvrflw, cpmProcessHCDataSegmentSize,
      cpmProcessStackSizeOvrflw, cpmProcessHCStackSize,
      cpmProcessDynamicMemorySizeOvrflw, cpmProcessHCDynamicMemorySize
      
      Added the following new objects to cpmThreadTable.
      cpmThreadStackSizeOvrflw, cpmThreadHCStackSize
      
      Added the following new objects to cpmVirtualProcessTable.
      cpmVirtualProcessMemAllocatedOvrflw,
      cpmVirtualProcessHCMemAllocated,
      cpmVirtualProcessMemFreedOvrflw, cpmVirtualProcessHCMemFreed
      
      Added following new compliance groups.
      cpmCPUTotalOverflowGroup, cpmCPUTotalOverflowGroup,
      cpmProcessExtRevOverflowGroup, cpmProcessExtRevHCGroup,
      cpmThreadOverflowGroup, cpmThreadHCGroup,
      cpmVirtualProcessOverflowGroup, cpmVirtualProcessHCGroup
      
      Added new compliance cProcessMIBComplianceRev3 which deprecates
      cProcessMIBComplianceRev2.";
  }

  revision 2007-03-23 {
    description
     "Added new objects to support POSIX compliant OS. Added
      cpmThread, cpmThreadTable, cpmVirtualProcess, 
      cpmVirtualProcessTable and updated cpmCPUTotalTable, 
      cpmProcessExtRevTable. Added cProcessMIBComplianceRev2
      by deprecating cProcessMIBComplianceRev1. Added 
      cpmCPUPosixMemoryGroup, cpmPosixProcessGroup, 
      cpmThreadGroup, cpmVirtualProcessGroup.";
  }

  revision 2003-01-22 {
    description
     "cpmCPUThresholdTable, cpmCPUHistoryTable,
      cpmCPUProcessHistoryTable are added for CPU thresholding 
      feature.";
  }

  revision 2001-05-18 {
    description
     "The objects cpmProcExtUtil5Sec, cpmProcExtUtil1Min,
      cpmProcExtUtil5Min,cpmCPUTotal5sec, cpmCPUTotal1min 
      and cpmCPUTotal5min are deprecated to increase the
      value range as 0..100. The table cpmProcessExtTable
      is deprecated. The new objects added are 
      cpmProcessExtRevTable, cpmProcExtMemAllocatedRev,
      cpmProcExtMemFreedRev, cpmProcExtInvokedRev, 
      cpmProcExtRuntimeRev, cpmProcExtUtil5SecRev,
      cpmProcExtUtil1MinRev, cpmCPUTotal5MinRev, 
      cpmCPUTotal5secRev, cpmCPUTotal1minRev and 
      cpmCPUTotal5minRev.";
  }

  revision 1998-04-15 {
    description
     "Initial version of this MIB.";
  }

  typedef CPULoadAverage {
    type uint32;
    description
     "The average number of processes in the queue waiting for CPU
      time over the last N minutes, where the N is defined by the 
      object using this TC. This is similar to UNIX/Linux system load
      average. The calculation may vary by different OS kernels, so
      refer  to  the specific system document of your interest.
      The object value, which uses this TC, reflects the average
      number of runnable processes with units of hundredths of
      processes, i.e. a value of 183 indicates the average number of
      runnable processes over the N minutes is 1.83.";
    smiv2:display-hint "d";
  }


  container CISCO-PROCESS-MIB {
    config false;

    container cpmCPUHistory {
      smiv2:oid "1.3.6.1.4.1.9.9.109.1.2.5";

      leaf cpmCPUHistoryThreshold {
        type uint32 {
          range "1..100";
        }
        description
         "The user  configured value of this object gives
          the minimum percent CPU utilization of a process
          in the last cpmCPUMonInterval duration required to be a 
          member of history table. When this object is changed
          the new value will have effect in the next interval.";
        smiv2:max-access "read-write";
        smiv2:oid "1.3.6.1.4.1.9.9.109.1.2.5.1";
      }

      leaf cpmCPUHistorySize {
        type uint32 {
          range "1..4294967295";
        }
        description
         "A value configured by the user which specifies the
          number of reports in the history table. 
          A report contains set of processes which crossed
          the cpmCPUHistoryThreshold 
          in the last cpmCPUMonInterval along with 
          the time at which this report is
          created, total and interrupt CPU utilizations. 
          When this object is changed
          the new value will have effect in the next interval.";
        smiv2:max-access "read-write";
        smiv2:oid "1.3.6.1.4.1.9.9.109.1.2.5.2";
      }
    }

    container cpmCPUTotalTable {
      description
       "A table of overall CPU statistics.";
      smiv2:oid "1.3.6.1.4.1.9.9.109.1.1.1";

      list cpmCPUTotalEntry {
        key "cpmCPUTotalIndex";
        description
         "Overall information about the CPU load. Entries in this
          table come and go as CPUs are added and removed from the
          system.";
        smiv2:oid "1.3.6.1.4.1.9.9.109.1.1.1.1";

        leaf cpmCPUTotalIndex {
          type uint32 {
            range "1..4294967295";
          }
          description
           "An index that uniquely represents a CPU (or group of CPUs)
            whose CPU load information is reported by a row in this table.
            This index is assigned arbitrarily by the engine
            and is not saved over reboots.";
          smiv2:max-access "not-accessible";
          smiv2:oid "1.3.6.1.4.1.9.9.109.1.1.1.1.1";
        }

        leaf cpmCPUTotalPhysicalIndex {
          type cisco-tc:EntPhysicalIndexOrZero;
          description
           "The entPhysicalIndex of the physical entity for which
            the CPU statistics in this entry are maintained.
            The physical entity can be a CPU chip, a group of CPUs,
            a CPU card etc. The exact type of this entity is described by
            its entPhysicalVendorType value. If the CPU statistics
            in this entry correspond to more than one physical entity
            (or to no physical entity), or if the entPhysicalTable is
            not supported on the SNMP agent, the value of this object
            must be zero.";
          smiv2:max-access "read-only";
          smiv2:oid "1.3.6.1.4.1.9.9.109.1.1.1.1.2";
        }

        leaf cpmCPUTotal5sec {
          type yang:gauge32 {
            range "0..100";
          }
          status deprecated;
          description
           "The overall CPU busy percentage in the last 5 second
            period. This object obsoletes the busyPer object from 
            the OLD-CISCO-SYSTEM-MIB. This object is deprecated
            by cpmCPUTotal5secRev which has the changed range of
            value (0..100).";
          smiv2:max-access "read-only";
          smiv2:oid "1.3.6.1.4.1.9.9.109.1.1.1.1.3";
        }

        leaf cpmCPUTotal1min {
          type yang:gauge32 {
            range "0..100";
          }
          status deprecated;
          description
           "The overall CPU busy percentage in the last 1 minute
            period. This object obsoletes the avgBusy1 object from 
            the OLD-CISCO-SYSTEM-MIB. This object is deprecated
            by cpmCPUTotal1minRev which has the changed range
            of value (0..100).";
          smiv2:max-access "read-only";
          smiv2:oid "1.3.6.1.4.1.9.9.109.1.1.1.1.4";
        }

        leaf cpmCPUTotal5min {
          type yang:gauge32 {
            range "0..100";
          }
          status deprecated;
          description
           "The overall CPU busy percentage in the last 5 minute
            period. This object deprecates the avgBusy5 object from 
            the OLD-CISCO-SYSTEM-MIB. This object is deprecated
            by cpmCPUTotal5minRev which has the changed range 
            of value (0..100).";
          smiv2:max-access "read-only";
          smiv2:oid "1.3.6.1.4.1.9.9.109.1.1.1.1.5";
        }

        leaf cpmCPUTotal5secRev {
          type yang:gauge32 {
            range "0..100";
          }
          units "percent";
          status deprecated;
          description
           "The overall CPU busy percentage in the last 5 second
            period. This object deprecates the object cpmCPUTotal5sec 
            and increases the value range to (0..100). This object
            is deprecated by cpmCPUTotalMonIntervalValue";
          smiv2:max-access "read-only";
          smiv2:oid "1.3.6.1.4.1.9.9.109.1.1.1.1.6";
        }

        leaf cpmCPUTotal1minRev {
          type yang:gauge32 {
            range "0..100";
          }
          units "percent";
          description
           "The overall CPU busy percentage in the last 1 minute
            period. This object deprecates the object cpmCPUTotal1min 
            and increases the value range to (0..100).";
          smiv2:max-access "read-only";
          smiv2:oid "1.3.6.1.4.1.9.9.109.1.1.1.1.7";
        }

        leaf cpmCPUTotal5minRev {
          type yang:gauge32 {
            range "0..100";
          }
          units "percent";
          description
           "The overall CPU busy percentage in the last 5 minute
            period. This object deprecates the object cpmCPUTotal5min 
            and increases the value range to (0..100).";
          smiv2:max-access "read-only";
          smiv2:oid "1.3.6.1.4.1.9.9.109.1.1.1.1.8";
        }

        leaf cpmCPUMonInterval {
          type uint32;
          units "seconds";
          description
           "CPU usage monitoring interval. The value of this
            object in seconds indicates the how often the 
            CPU utilization is calculated and monitored.";
          smiv2:max-access "read-only";
          smiv2:oid "1.3.6.1.4.1.9.9.109.1.1.1.1.9";
        }

        leaf cpmCPUTotalMonIntervalValue {
          type yang:gauge32 {
            range "0..100";
          }
          units "percent";
          description
           "The overall CPU busy percentage in the last
            cpmCPUMonInterval period. 
            This object deprecates the object cpmCPUTotal5secRev.";
          smiv2:max-access "read-only";
          smiv2:oid "1.3.6.1.4.1.9.9.109.1.1.1.1.10";
        }

        leaf cpmCPUInterruptMonIntervalValue {
          type yang:gauge32 {
            range "0..100";
          }
          units "percent";
          description
           "The overall CPU busy percentage in the
            interrupt context in the last cpmCPUMonInterval
            period.";
          smiv2:max-access "read-only";
          smiv2:oid "1.3.6.1.4.1.9.9.109.1.1.1.1.11";
        }

        leaf cpmCPUMemoryUsed {
          type yang:gauge32;
          units "kilo-bytes";
          description
           "The overall CPU wide system memory which is currently
            under use.";
          smiv2:max-access "read-only";
          smiv2:oid "1.3.6.1.4.1.9.9.109.1.1.1.1.12";
        }

        leaf cpmCPUMemoryFree {
          type yang:gauge32;
          units "kilo-bytes";
          description
           "The overall CPU wide system memory which is currently
            free.";
          smiv2:max-access "read-only";
          smiv2:oid "1.3.6.1.4.1.9.9.109.1.1.1.1.13";
        }

        leaf cpmCPUMemoryKernelReserved {
          type yang:gauge32;
          units "kilo-bytes";
          description
           "The overall CPU wide system memory which is reserved
            for kernel usage.";
          smiv2:max-access "read-only";
          smiv2:oid "1.3.6.1.4.1.9.9.109.1.1.1.1.14";
        }

        leaf cpmCPUMemoryLowest {
          type yang:gauge32;
          units "bytes";
          description
           "The lowest free memory that has been recorded since
            device has booted.";
          smiv2:max-access "read-only";
          smiv2:oid "1.3.6.1.4.1.9.9.109.1.1.1.1.15";
        }

        leaf cpmCPUMemoryUsedOvrflw {
          type yang:gauge32;
          units "kilo-bytes";
          description
           "This object represents the upper 32-bit of cpmCPUMemoryUsed.
            This object needs to be supported only when the value of
            cpmCPUMemoryUsed exceeds 32-bit, otherwise this object value
            would be set to 0.";
          smiv2:max-access "read-only";
          smiv2:oid "1.3.6.1.4.1.9.9.109.1.1.1.1.16";
        }

        leaf cpmCPUMemoryHCUsed {
          type yang:gauge64;
          units "kilo-bytes";
          description
           "The overall CPU wide system memory which is currently under
            use. This object is a 64-bit version of cpmCPUMemoryUsed.";
          smiv2:max-access "read-only";
          smiv2:oid "1.3.6.1.4.1.9.9.109.1.1.1.1.17";
        }

        leaf cpmCPUMemoryFreeOvrflw {
          type yang:gauge32;
          units "kilo-bytes";
          description
           "This object represents the upper 32-bit of cpmCPUMemoryFree.
            This object needs to be supported only when the value of
            cpmCPUMemoryFree exceeds 32-bit, otherwise this object value
            would be set to 0.";
          smiv2:max-access "read-only";
          smiv2:oid "1.3.6.1.4.1.9.9.109.1.1.1.1.18";
        }

        leaf cpmCPUMemoryHCFree {
          type yang:counter64;
          units "kilo-bytes";
          description
           "The overall CPU wide system memory which is currently free.
            This object is a 64-bit version of cpmCPUMemoryFree.";
          smiv2:max-access "read-only";
          smiv2:oid "1.3.6.1.4.1.9.9.109.1.1.1.1.19";
        }

        leaf cpmCPUMemoryKernelReservedOvrflw {
          type yang:gauge32;
          units "kilo-bytes";
          description
           "This object represents the upper 32-bit of
            cpmCPUMemoryKernelReserved. This object needs 
            to be supported only when the value of 
            cpmCPUMemoryKernelReserved exceeds 32-bit, otherwise
            this object value would be set to 0.";
          smiv2:max-access "read-only";
          smiv2:oid "1.3.6.1.4.1.9.9.109.1.1.1.1.20";
        }

        leaf cpmCPUMemoryHCKernelReserved {
          type yang:gauge64;
          units "kilo-bytes";
          description
           "The overall CPU wide system memory which is reserved
            for kernel usage. This object is a 64-bit version of
            cpmCPUMemoryKernelReserved.";
          smiv2:max-access "read-only";
          smiv2:oid "1.3.6.1.4.1.9.9.109.1.1.1.1.21";
        }

        leaf cpmCPUMemoryLowestOvrflw {
          type yang:gauge32;
          units "kilo-bytes";
          description
           "This object represents the upper 32-bit of cpmCPUMemoryLowest.
            This object needs to be supported only when the value of
            cpmCPUMemoryLowest exceeds 32-bit, otherwise this object value
            would be set to 0.";
          smiv2:max-access "read-only";
          smiv2:oid "1.3.6.1.4.1.9.9.109.1.1.1.1.22";
        }

        leaf cpmCPUMemoryHCLowest {
          type yang:gauge64;
          units "kilo-bytes";
          description
           "The lowest free memory that has been recorded since device has
            booted. This object is a 64-bit version of cpmCPUMemoryLowest.";
          smiv2:max-access "read-only";
          smiv2:oid "1.3.6.1.4.1.9.9.109.1.1.1.1.23";
        }

        leaf cpmCPULoadAvg1min {
          type CISCO-PROCESS-MIB:CPULoadAverage;
          units "hundredths of processes";
          description
           "The overall CPU load Average in the last 1 minute period";
          smiv2:max-access "read-only";
          smiv2:oid "1.3.6.1.4.1.9.9.109.1.1.1.1.24";
        }

        leaf cpmCPULoadAvg5min {
          type CISCO-PROCESS-MIB:CPULoadAverage;
          units "hundredths of processes";
          description
           "The overall CPU load Average in the last 5 minutes period";
          smiv2:max-access "read-only";
          smiv2:oid "1.3.6.1.4.1.9.9.109.1.1.1.1.25";
        }

        leaf cpmCPULoadAvg15min {
          type CISCO-PROCESS-MIB:CPULoadAverage;
          units "hundredths of processes";
          description
           "The overall CPU load Average in the last 15 minutes period";
          smiv2:max-access "read-only";
          smiv2:oid "1.3.6.1.4.1.9.9.109.1.1.1.1.26";
        }

        leaf cpmCPUMemoryCommitted {
          type yang:gauge32;
          description
           "The overall CPU wide system memory which is currently
            Committed.";
          smiv2:max-access "read-only";
          smiv2:oid "1.3.6.1.4.1.9.9.109.1.1.1.1.27";
        }

        leaf cpmCPUMemoryCommittedOvrflw {
          type yang:gauge32;
          description
           "This object represents the upper 32-bit of
            cpmCPUMemoryCommitted.
            This object needs to be supported only when the value of
            cpmCPUMemoryCommitted exceeds 32-bit, otherwise this object
            value would be set to 0.";
          smiv2:max-access "read-only";
          smiv2:oid "1.3.6.1.4.1.9.9.109.1.1.1.1.28";
        }

        leaf cpmCPUMemoryHCCommitted {
          type yang:gauge64;
          description
           "The overall CPU wide system memory which is currently
            committed. This object is a 64-bit version of
            cpmCPUMemoryCommitted";
          smiv2:max-access "read-only";
          smiv2:oid "1.3.6.1.4.1.9.9.109.1.1.1.1.29";
        }
      }
    }

    container cpmCoreTable {
      description
       "A table of per-Core statistics.";
      smiv2:oid "1.3.6.1.4.1.9.9.109.1.1.2";

      list cpmCoreEntry {
        key "cpmCPUTotalIndex cpmCoreIndex";
        description
         "Overall information about the Core load. Entries in this
          table could come and go as Cores go online or offline.";
        smiv2:oid "1.3.6.1.4.1.9.9.109.1.1.2.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmCoreIndex {
          type uint32 {
            range "0..4294967295";
          }
          description
           "An index that uniquely represents a Core (or group of Cores)
            whose Core load information is reported by a row in this table.
            This index is assigned arbitrarily by the engine
            and is not saved over reboots.";
          smiv2:max-access "not-accessible";
          smiv2:oid "1.3.6.1.4.1.9.9.109.1.1.2.1.1";
        }

        leaf cpmCorePhysicalIndex {
          type cisco-tc:EntPhysicalIndexOrZero;
          description
           "The entCorePhysicalIndex of the physical entity for which
            the Core statistics in this entry are maintained.
            The physical entity can be a CPU chip, a group of CPUs,
            a CPU card etc. The exact type of this entity is described by
            its entPhysicalVendorType value. If the Core statistics
            in this entry correspond to more than one physical entity
            (or to no physical entity), or if the entPhysicalTable is
            not supported on the SNMP agent, the value of this object
            must be zero.";
          smiv2:max-access "read-only";
          smiv2:oid "1.3.6.1.4.1.9.9.109.1.1.2.1.2";
        }

        leaf cpmCore5sec {
          type yang:gauge32 {
            range "0..100";
          }
          description
           "The overall Core busy percentage in the last 5 second
            period.";
          smiv2:max-access "read-only";
          smiv2:oid "1.3.6.1.4.1.9.9.109.1.1.2.1.3";
        }

        leaf cpmCore1min {
          type yang:gauge32 {
            range "0..100";
          }
          description
           "The overall Core busy percentage in the last 1 minute
            period.";
          smiv2:max-access "read-only";
          smiv2:oid "1.3.6.1.4.1.9.9.109.1.1.2.1.4";
        }

        leaf cpmCore5min {
          type yang:gauge32 {
            range "0..100";
          }
          description
           "The overall Core busy percentage in the last 5 minute
            period.";
          smiv2:max-access "read-only";
          smiv2:oid "1.3.6.1.4.1.9.9.109.1.1.2.1.5";
        }

        leaf cpmCoreLoadAvg1min {
          type CISCO-PROCESS-MIB:CPULoadAverage;
          units "hundredths of processes";
          description
           "The overall Core load Average in the last 1 minute period";
          smiv2:max-access "read-only";
          smiv2:oid "1.3.6.1.4.1.9.9.109.1.1.2.1.6";
        }

        leaf cpmCoreLoadAvg5min {
          type CISCO-PROCESS-MIB:CPULoadAverage;
          units "hundredths of processes";
          description
           "The overall Core load Average in the last 5 minutes period";
          smiv2:max-access "read-only";
          smiv2:oid "1.3.6.1.4.1.9.9.109.1.1.2.1.7";
        }

        leaf cpmCoreLoadAvg15min {
          type CISCO-PROCESS-MIB:CPULoadAverage;
          units "hundredths of processes";
          description
           "The overall Core load Average in the last 15 minutes period";
          smiv2:max-access "read-only";
          smiv2:oid "1.3.6.1.4.1.9.9.109.1.1.2.1.8";
        }
      }
    }

    container cpmProcessTable {
      description
       "A table of generic information on all active
        processes on this device.";
      smiv2:oid "1.3.6.1.4.1.9.9.109.1.2.1";

      list cpmProcessEntry {
        key "cpmCPUTotalIndex cpmProcessPID";
        description
         "Generic information about an active process on this
          device. Entries in this table come and go as processes are 
          created and destroyed by the device.";
        smiv2:oid "1.3.6.1.4.1.9.9.109.1.2.1.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmProcessPID {
          type uint32;
          description
           "This object contains the process ID. cpmTimeCreated
            should be checked against the last time it was polled,
            and if it has changed the PID has been reused and the
            entire entry should be polled again.";
          smiv2:max-access "read-only";
          smiv2:oid "1.3.6.1.4.1.9.9.109.1.2.1.1.1";
        }

        leaf cpmProcessName {
          type snmpv2-tc:DisplayString {
            length "1..32";
          }
          description
           "The name associated with this process. If the name is
            longer than 32 characters, it will be truncated to the first
            31 characters, and a `*' will be appended as the last
            character to imply this is a truncated process name.";
          smiv2:max-access "read-only";
          smiv2:oid "1.3.6.1.4.1.9.9.109.1.2.1.1.2";
        }

        leaf cpmProcessuSecs {
          type uint32;
          units "microseconds";
          status deprecated;
          description
           "Average elapsed CPU time in microseconds when the
            process was active. This object is deprecated
            by cpmProcessAverageUSecs.";
          smiv2:max-access "read-only";
          smiv2:oid "1.3.6.1.4.1.9.9.109.1.2.1.1.4";
        }

        leaf cpmProcessTimeCreated {
          type yang:timestamp;
          description
           "The time when the process was created. The process ID
            and the time when the process was created, uniquely 
            identifies a process.";
          smiv2:max-access "read-only";
          smiv2:oid "1.3.6.1.4.1.9.9.109.1.2.1.1.5";
        }

        leaf cpmProcessAverageUSecs {
          type uint32;
          units "microseconds";
          description
           "Average elapsed CPU time in microseconds when the
            process was active. This object deprecates the
            object cpmProcessuSecs.";
          smiv2:max-access "read-only";
          smiv2:oid "1.3.6.1.4.1.9.9.109.1.2.1.1.6";
        }
      }
    }

    container cpmProcessExtRevTable {
      description
       "This table contains information that may or may
        not be available on all cisco devices. It contains
        additional objects for the more general
        cpmProcessTable. This object deprecates 
        cpmProcessExtTable.";
      smiv2:oid "1.3.6.1.4.1.9.9.109.1.2.3";

      list cpmProcessExtRevEntry {
        key "cpmCPUTotalIndex cpmProcessPID";
        description
         "An entry containing additional information for
          a particular process. This object deprecates 
          cpmProcessExtEntry.";
        smiv2:oid "1.3.6.1.4.1.9.9.109.1.2.3.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmProcessPID {
          type leafref {
            path "/CISCO-PROCESS-MIB:CISCO-PROCESS-MIB/CISCO-PROCESS-MIB:cpmProcessTable/CISCO-PROCESS-MIB:cpmProcessEntry/CISCO-PROCESS-MIB:cpmProcessPID";
          }
        }

        leaf cpmProcExtMemAllocatedRev {
          type yang:gauge32;
          units "bytes";
          description
           "The sum of all the dynamically allocated memory that
            this process has received from the system. This includes
            memory that may have been returned. The sum of freed
            memory is provided by cpmProcExtMemFreedRev. This object
            deprecates cpmProcExtMemAllocated.";
          smiv2:max-access "read-only";
          smiv2:oid "1.3.6.1.4.1.9.9.109.1.2.3.1.1";
        }

        leaf cpmProcExtMemFreedRev {
          type yang:gauge32;
          units "bytes";
          description
           "The sum of all memory that this process has returned
            to the system. This object  deprecates 
            cpmProcExtMemFreed.";
          smiv2:max-access "read-only";
          smiv2:oid "1.3.6.1.4.1.9.9.109.1.2.3.1.2";
        }

        leaf cpmProcExtInvokedRev {
          type yang:counter32;
          description
           "The number of times since cpmTimeCreated that
            the process has been invoked. This object 
            deprecates cpmProcExtInvoked.";
          smiv2:max-access "read-only";
          smiv2:oid "1.3.6.1.4.1.9.9.109.1.2.3.1.3";
        }

        leaf cpmProcExtRuntimeRev {
          type yang:counter32;
          units "microseconds";
          description
           "The amount of CPU time the process has used, in
            microseconds. This object deprecates
            cpmProcExtRuntime.";
          smiv2:max-access "read-only";
          smiv2:oid "1.3.6.1.4.1.9.9.109.1.2.3.1.4";
        }

        leaf cpmProcExtUtil5SecRev {
          type yang:gauge32 {
            range "0..100";
          }
          units "percent";
          description
           "This object provides a general idea of how busy
            a process caused the processor to be over a 5 
            second period. It is determined as a weighted 
            decaying average of the current idle time over 
            the longest idle time. Note that this information 
            should be used as an estimate only. This object
            deprecates cpmProcExtUtil5Sec and increases the 
            value range to (0..100).";
          smiv2:max-access "read-only";
          smiv2:oid "1.3.6.1.4.1.9.9.109.1.2.3.1.5";
        }

        leaf cpmProcExtUtil1MinRev {
          type yang:gauge32 {
            range "0..100";
          }
          units "percent";
          description
           "This object provides a general idea of how busy
            a process caused the processor to be over a 1 
            minute period. It is determined as a weighted 
            decaying average of the current idle time over the 
            longest idle time. Note that this information 
            should be used as an estimate only. This object 
            deprecates cpmProcExtUtil1Min and increases the value
            range to (0..100).";
          smiv2:max-access "read-only";
          smiv2:oid "1.3.6.1.4.1.9.9.109.1.2.3.1.6";
        }

        leaf cpmProcExtUtil5MinRev {
          type yang:gauge32 {
            range "0..100";
          }
          units "percent";
          description
           "This object provides a general idea of how busy
            a process caused the processor to be over a 5 
            minute period. It is determined as a weighted 
            decaying average of the current idle time over 
            the longest idle time. Note that this information 
            should be used as an estimate only. This object
            deprecates cpmProcExtUtil5Min and increases the
            value range to (0..100).";
          smiv2:max-access "read-only";
          smiv2:oid "1.3.6.1.4.1.9.9.109.1.2.3.1.7";
        }

        leaf cpmProcExtPriorityRev {
          type enumeration {
            enum "critical" {
              value "1";
            }
            enum "high" {
              value "2";
            }
            enum "normal" {
              value "3";
            }
            enum "low" {
              value "4";
            }
            enum "notAssigned" {
              value "5";
            }
          }
          description
           "The priority level at  which the process is
            running. This object deprecates 
            cpmProcExtPriority.";
          smiv2:max-access "read-only";
          smiv2:oid "1.3.6.1.4.1.9.9.109.1.2.3.1.8";
        }

        leaf cpmProcessType {
          type enumeration {
            enum "none" {
              value "0";
            }
            enum "other" {
              value "1";
            }
            enum "posix" {
              value "2";
            }
            enum "ios" {
              value "3";
            }
          }
          description
           "This indicates the kind of process in context.";
          smiv2:max-access "read-only";
          smiv2:oid "1.3.6.1.4.1.9.9.109.1.2.3.1.9";
        }

        leaf cpmProcessRespawn {
          type uint32 {
            range "0..2";
          }
          description
           "This indicates whether respawn of a process is enabled
            or not. If enabled the process in context repawns after
            it has crashed/stopped.";
          smiv2:max-access "read-only";
          smiv2:oid "1.3.6.1.4.1.9.9.109.1.2.3.1.10";
        }

        leaf cpmProcessRespawnCount {
          type yang:counter32;
          description
           "This indicates the number of times the process has
            respawned/restarted.";
          smiv2:max-access "read-only";
          smiv2:oid "1.3.6.1.4.1.9.9.109.1.2.3.1.11";
        }

        leaf cpmProcessRespawnAfterLastPatch {
          type yang:counter32;
          description
           "This indicates the number of times a process has
            restarted after the last patch is applied. This is to 
            determine the stability of the last patch.";
          smiv2:max-access "read-only";
          smiv2:oid "1.3.6.1.4.1.9.9.109.1.2.3.1.12";
        }

        leaf cpmProcessMemoryCore {
          type enumeration {
            enum "none" {
              value "0";
            }
            enum "other" {
              value "1";
            }
            enum "mainmem" {
              value "2";
            }
            enum "mainmemSharedmem" {
              value "3";
            }
            enum "mainmemText" {
              value "4";
            }
            enum "mainmemTextSharedmem" {
              value "5";
            }
            enum "sharedmem" {
              value "6";
            }
            enum "sparse" {
              value "7";
            }
            enum "off" {
              value "8";
            }
          }
          description
           "This indicates the part of process memory to be
            dumped when a process crashes. The process 
            memory is used for debugging purposes to trace the 
            root cause of the crash.
            sparse        - Some operating systems support minimal
                            dump of process core like register
                            info, partial stack, partial memory
                            pages especially for critical process
                            to facilitate faster process restart.";
          smiv2:max-access "read-only";
          smiv2:oid "1.3.6.1.4.1.9.9.109.1.2.3.1.13";
        }

        leaf cpmProcessLastRestartUser {
          type snmp-framework:SnmpAdminString;
          description
           "This indicate the user that has last restarted the
            process or has taken running coredump of the process.";
          smiv2:max-access "read-only";
          smiv2:oid "1.3.6.1.4.1.9.9.109.1.2.3.1.14";
        }

        leaf cpmProcessTextSegmentSize {
          type uint32;
          units "kilo-bytes";
          description
           "This indicates the text memory of a process and all
            its shared objects.";
          smiv2:max-access "read-only";
          smiv2:oid "1.3.6.1.4.1.9.9.109.1.2.3.1.15";
        }

        leaf cpmProcessDataSegmentSize {
          type yang:gauge32;
          units "kilo-bytes";
          description
           "This indicates the data segment of a process and
            all its shared objects.";
          smiv2:max-access "read-only";
          smiv2:oid "1.3.6.1.4.1.9.9.109.1.2.3.1.16";
        }

        leaf cpmProcessStackSize {
          type yang:gauge32;
          units "kilo-bytes";
          description
           "This indicates the amount of stack memory used by the
            process.";
          smiv2:max-access "read-only";
          smiv2:oid "1.3.6.1.4.1.9.9.109.1.2.3.1.17";
        }

        leaf cpmProcessDynamicMemorySize {
          type yang:gauge32;
          units "kilo-bytes";
          description
           "This indicates the amount of dynamic memory being used
            by the process.";
          smiv2:max-access "read-only";
          smiv2:oid "1.3.6.1.4.1.9.9.109.1.2.3.1.18";
        }

        leaf cpmProcExtMemAllocatedRevOvrflw {
          type yang:gauge32;
          units "bytes";
          description
           "This object represents the upper 32-bit of
            cpmProcExtMemAllocatedRev. This object needs
            to be supported only when the value of 
            cpmProcExtMemAllocatedRev exceeds 32-bit, 
            otherwise this object value would be set to 0.";
          smiv2:max-access "read-only";
          smiv2:oid "1.3.6.1.4.1.9.9.109.1.2.3.1.19";
        }

        leaf cpmProcExtHCMemAllocatedRev {
          type yang:gauge64;
          units "bytes";
          description
           "The sum of all the dynamically allocated memory that this
            process has received from the system. This includes memory
            that may have been returned. This object is a 64-bit version
            of cpmProcExtMemAllocatedRev.";
          smiv2:max-access "read-only";
          smiv2:oid "1.3.6.1.4.1.9.9.109.1.2.3.1.20";
        }

        leaf cpmProcExtMemFreedRevOvrflw {
          type yang:gauge32;
          units "bytes";
          description
           "This object represents the upper 32-bit of
            cpmProcExtMemFreedRev. This object needs to 
            be supported only when the value of
            cpmProcExtMemFreedRev exceeds 32-bit,otherwise
            this object value would be set to 0.";
          smiv2:max-access "read-only";
          smiv2:oid "1.3.6.1.4.1.9.9.109.1.2.3.1.21";
        }

        leaf cpmProcExtHCMemFreedRev {
          type yang:gauge64;
          units "bytes";
          description
           "The sum of all memory that this process has returned to the
            system. This object is a 64-bit version of
            cpmProcExtMemFreedRev.";
          smiv2:max-access "read-only";
          smiv2:oid "1.3.6.1.4.1.9.9.109.1.2.3.1.22";
        }

        leaf cpmProcessTextSegmentSizeOvrflw {
          type uint32;
          units "kilo-bytes";
          description
           "This object represents the upper 32-bit of
            cpmProcessTextSegmentSize. This object needs
            to be supported only when the value of 
            cpmProcessTextSegmentSize exceeds 32-bit, 
            otherwise this object value would be set to 0.";
          smiv2:max-access "read-only";
          smiv2:oid "1.3.6.1.4.1.9.9.109.1.2.3.1.23";
        }

        leaf cpmProcessHCTextSegmentSize {
          type cisco-tc:Unsigned64;
          units "kilo-bytes";
          description
           "This indicates the text memory of a process and all
            its shared objects. This object is a 64-bit version
            of cpmProcessTextSegmentSize.";
          smiv2:max-access "read-only";
          smiv2:oid "1.3.6.1.4.1.9.9.109.1.2.3.1.24";
        }

        leaf cpmProcessDataSegmentSizeOvrflw {
          type yang:gauge32;
          units "kilo-bytes";
          description
           "This object represents the upper 32-bit of
            cpmProcessDataSegmentSize. This object needs
            to be supported only when the value of 
            cpmProcessDataSegmentSize exceeds 32-bit, 
            otherwise this object value would be set to 0.";
          smiv2:max-access "read-only";
          smiv2:oid "1.3.6.1.4.1.9.9.109.1.2.3.1.25";
        }

        leaf cpmProcessHCDataSegmentSize {
          type yang:gauge64;
          units "kilo-bytes";
          description
           "This indicates the data segment of a process and
            all its shared objects.. This object is a 64-bit
            version of cpmProcessDataSegmentSize.";
          smiv2:max-access "read-only";
          smiv2:oid "1.3.6.1.4.1.9.9.109.1.2.3.1.26";
        }

        leaf cpmProcessStackSizeOvrflw {
          type yang:gauge32;
          units "kilo-bytes";
          description
           "This object represents the upper 32-bit of cpmProcessStackSize.
            This object needs to be supported only when the value of
            cpmProcessStackSize exceeds 32-bit, otherwise this object value
            would be set to 0.";
          smiv2:max-access "read-only";
          smiv2:oid "1.3.6.1.4.1.9.9.109.1.2.3.1.27";
        }

        leaf cpmProcessHCStackSize {
          type yang:gauge64;
          units "kilo-bytes";
          description
           "This indicates the amount of stack memory used by the process.
            This object is a 64-bit version of cpmProcessStackSize.";
          smiv2:max-access "read-only";
          smiv2:oid "1.3.6.1.4.1.9.9.109.1.2.3.1.28";
        }

        leaf cpmProcessDynamicMemorySizeOvrflw {
          type yang:gauge32;
          units "kilo-bytes";
          description
           "This object represents the upper 32-bit of
            cpmProcessDynamicMemorySize. This object needs
            to be supported only when the value of 
            cpmProcessDynamicMemorySize exceeds 32-bit, 
            otherwise this object value would be set to 0.";
          smiv2:max-access "read-only";
          smiv2:oid "1.3.6.1.4.1.9.9.109.1.2.3.1.29";
        }

        leaf cpmProcessHCDynamicMemorySize {
          type yang:gauge64;
          units "kilo-bytes";
          description
           "This indicates the amount of dynamic memory being used
            by the process. This object is a 64-bit version of
            cpmProcessDynamicMemorySize.";
          smiv2:max-access "read-only";
          smiv2:oid "1.3.6.1.4.1.9.9.109.1.2.3.1.30";
        }
      }
    }

    container cpmCPUThresholdTable {
      description
       "This table contains the information about the
        thresholding values for CPU , configured by the user.";
      smiv2:oid "1.3.6.1.4.1.9.9.109.1.2.4";

      list cpmCPUThresholdEntry {
        key "cpmCPUTotalIndex cpmCPUThresholdClass";
        description
         "An entry containing information about
          CPU thresholding parameters. cpmCPUTotalIndex
          identifies the CPU (or group of CPUs) for which this
          configuration applies.";
        smiv2:oid "1.3.6.1.4.1.9.9.109.1.2.4.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmCPUThresholdClass {
          type enumeration {
            enum "total" {
              value "1";
            }
            enum "interrupt" {
              value "2";
            }
            enum "process" {
              value "3";
            }
          }
          description
           "Value of this object indicates the type of
            utilization, which is monitored. The total(1) indicates
            the total CPU utilization, interrupt(2) indicates the
            the CPU utilization in interrupt context and process(3)
            indicates the CPU utilization in the process level
            execution context.";
          smiv2:max-access "not-accessible";
          smiv2:oid "1.3.6.1.4.1.9.9.109.1.2.4.1.1";
        }

        leaf cpmCPURisingThresholdValue {
          type uint32 {
            range "1..100";
          }
          description
           "The percentage rising threshold value configured by
            the user. The value indicates, 
            if the percentage CPU utilization is equal to or above
            this value for cpmCPURisingThresholdPeriod duration 
            then send a cpmCPURisingThreshold notification to
            the NMS.";
          smiv2:max-access "read-write";
          smiv2:oid "1.3.6.1.4.1.9.9.109.1.2.4.1.2";
        }

        leaf cpmCPURisingThresholdPeriod {
          type uint32 {
            range "5..4294967295";
          }
          units "seconds";
          description
           "This is an observation interval.
            The value of this object indicates that 
            the CPU utilization should be above
            cpmCPURisingThresholdValue for this duration to send a 
            cpmCPURisingThreshold notification to the NMS.";
          smiv2:defval "5";
          smiv2:max-access "read-write";
          smiv2:oid "1.3.6.1.4.1.9.9.109.1.2.4.1.3";
        }

        leaf cpmCPUFallingThresholdValue {
          type uint32 {
            range "1..100";
          }
          description
           "The percentage falling threshold value configured by
            the user. The value indicates, if the percentage 
            CPU utilization is equal to or below this value for 
            cpmCPUFallingThresholdPeriod duration
            then send a cpmCPUFallingThreshold notification 
            to the NMS.";
          smiv2:max-access "read-write";
          smiv2:oid "1.3.6.1.4.1.9.9.109.1.2.4.1.4";
        }

        leaf cpmCPUFallingThresholdPeriod {
          type uint32 {
            range "5..4294967295";
          }
          units "seconds";
          description
           "This is an observation interval. The value of this
            object indicates that CPU utilization should be below
            cpmCPUFallingThresholdValue for this duration to send a 
            cpmCPURisingThreshold notification to the NMS.";
          smiv2:defval "5";
          smiv2:max-access "read-write";
          smiv2:oid "1.3.6.1.4.1.9.9.109.1.2.4.1.5";
        }

        leaf cpmCPUThresholdEntryStatus {
          type snmpv2-tc:RowStatus;
          description
           "The status of this table entry.";
          smiv2:max-access "read-write";
          smiv2:oid "1.3.6.1.4.1.9.9.109.1.2.4.1.6";
        }
      }
    }

    container cpmCPUHistoryTable {
      description
       "A list of CPU utilization history entries.";
      smiv2:oid "1.3.6.1.4.1.9.9.109.1.2.5.3";

      list cpmCPUHistoryEntry {
        key "cpmCPUTotalIndex cpmCPUHistoryReportId";
        description
         "A historical sample of CPU utilization statistics.
          cpmCPUTotalIndex identifies the CPU (or group of CPUs)
          for which this history is collected. 
          When the cpmCPUHistorySize is
          reached the least recent entry is lost.";
        smiv2:oid "1.3.6.1.4.1.9.9.109.1.2.5.3.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmCPUHistoryReportId {
          type uint32;
          description
           "All the entries which are created at the same time
            will have same value for this object. When the
            configured threshold for being a part of History table
            is reached then the qualified processes become the
            part of history table. The entries which became the 
            part of history table at one instant will have
            the same value for this object. When this object
            reaches the max index value then it will wrap around.";
          smiv2:max-access "not-accessible";
          smiv2:oid "1.3.6.1.4.1.9.9.109.1.2.5.3.1.1";
        }

        leaf cpmCPUHistoryReportSize {
          type uint32 {
            range "0..4294967295";
          }
          description
           "The number of process entries in a report.
            This object gives information about how many processes 
            became a part of history table at one instant.";
          smiv2:max-access "read-only";
          smiv2:oid "1.3.6.1.4.1.9.9.109.1.2.5.3.1.2";
        }

        leaf cpmCPUHistoryTotalUtil {
          type yang:gauge32 {
            range "0..100";
          }
          units "percent";
          description
           "Total percentage of CPU utilization
            at cpmCPUHistoryCreated.";
          smiv2:max-access "read-only";
          smiv2:oid "1.3.6.1.4.1.9.9.109.1.2.5.3.1.3";
        }

        leaf cpmCPUHistoryInterruptUtil {
          type yang:gauge32 {
            range "0..100";
          }
          units "percent";
          description
           "Percentage of CPU utilization in the interrupt context
            at cpmCPUHistoryCreated.";
          smiv2:max-access "read-only";
          smiv2:oid "1.3.6.1.4.1.9.9.109.1.2.5.3.1.4";
        }

        leaf cpmCPUHistoryCreatedTime {
          type yang:timestamp;
          description
           "Time stamp with respect to sysUpTime indicating
            the time at which this report is created.";
          smiv2:max-access "read-only";
          smiv2:oid "1.3.6.1.4.1.9.9.109.1.2.5.3.1.5";
        }
      }
    }

    container cpmCPUProcessHistoryTable {
      description
       "A list of process history entries. This table contains
        CPU utilization of processes which crossed the 
        cpmCPUHistoryThreshold.";
      smiv2:oid "1.3.6.1.4.1.9.9.109.1.2.5.4";

      list cpmCPUProcessHistoryEntry {
        key "cpmCPUTotalIndex cpmCPUHistoryReportId cpmCPUProcessHistoryIndex";
        description
         "A historical sample of process utilization
          statistics. The entries in this table will have
          corresponding entires in the cpmCPUHistoryTable.
          The entries in this table get deleted when the entry
          associated with this entry in the cpmCPUHistoryTable 
          gets deleted.";
        smiv2:oid "1.3.6.1.4.1.9.9.109.1.2.5.4.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmCPUHistoryReportId {
          type leafref {
            path "/CISCO-PROCESS-MIB:CISCO-PROCESS-MIB/CISCO-PROCESS-MIB:cpmCPUHistoryTable/CISCO-PROCESS-MIB:cpmCPUHistoryEntry/CISCO-PROCESS-MIB:cpmCPUHistoryReportId";
          }
        }

        leaf cpmCPUProcessHistoryIndex {
          type uint32 {
            range "1..4294967295";
          }
          description
           "An index that uniquely identifies an entry in
            the cmpCPUProcessHistory table among those in the 
            same report. This index is between 1 to N, 
            where N is the cpmCPUHistoryReportSize.";
          smiv2:max-access "not-accessible";
          smiv2:oid "1.3.6.1.4.1.9.9.109.1.2.5.4.1.1";
        }

        leaf cpmCPUHistoryProcId {
          type uint32 {
            range "1..2147483647";
          }
          description
           "The process Id associated with this entry.";
          smiv2:max-access "read-only";
          smiv2:oid "1.3.6.1.4.1.9.9.109.1.2.5.4.1.2";
        }

        leaf cpmCPUHistoryProcName {
          type snmpv2-tc:DisplayString;
          description
           "The process name associated with this entry.";
          smiv2:max-access "read-only";
          smiv2:oid "1.3.6.1.4.1.9.9.109.1.2.5.4.1.3";
        }

        leaf cpmCPUHistoryProcCreated {
          type yang:timestamp;
          description
           "The time when the process was created. The process ID
            and the time when the process was created, uniquely 
            identifies a process.";
          smiv2:max-access "read-only";
          smiv2:oid "1.3.6.1.4.1.9.9.109.1.2.5.4.1.4";
        }

        leaf cpmCPUHistoryProcUtil {
          type yang:gauge32 {
            range "0..100";
          }
          units "percent";
          description
           "The percentage CPU utilization of a process at
            cpmCPUHistoryCreatedTime.";
          smiv2:max-access "read-only";
          smiv2:oid "1.3.6.1.4.1.9.9.109.1.2.5.4.1.5";
        }
      }
    }

    container cpmThreadTable {
      description
       "This table contains generic information about
        POSIX threads in the device.";
      smiv2:oid "1.3.6.1.4.1.9.9.109.1.3.1";

      list cpmThreadEntry {
        key "cpmCPUTotalIndex cpmProcessPID cpmThreadID";
        description
         "An entry containing the general statistics
          of a POSIX thread.";
        smiv2:oid "1.3.6.1.4.1.9.9.109.1.3.1.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmProcessPID {
          type leafref {
            path "/CISCO-PROCESS-MIB:CISCO-PROCESS-MIB/CISCO-PROCESS-MIB:cpmProcessTable/CISCO-PROCESS-MIB:cpmProcessEntry/CISCO-PROCESS-MIB:cpmProcessPID";
          }
        }

        leaf cpmThreadID {
          type uint32;
          description
           "This object contains the thread ID. ThreadID is
            Unique per process.";
          smiv2:max-access "not-accessible";
          smiv2:oid "1.3.6.1.4.1.9.9.109.1.3.1.1.1";
        }

        leaf cpmThreadName {
          type snmp-framework:SnmpAdminString;
          description
           "This object represents the name of the thread.
            Thread names need not be unique. Hence statistics 
            should be analyzed against thread ID.";
          smiv2:max-access "read-only";
          smiv2:oid "1.3.6.1.4.1.9.9.109.1.3.1.1.2";
        }

        leaf cpmThreadPriority {
          type uint32 {
            range "0..63";
          }
          description
           "This object indicates the priority of a POSIX thread.
            The higher the number, the higher the priority of the 
            thread over other threads.";
          smiv2:max-access "read-only";
          smiv2:oid "1.3.6.1.4.1.9.9.109.1.3.1.1.3";
        }

        leaf cpmThreadState {
          type enumeration {
            enum "other" {
              value "1";
            }
            enum "dead" {
              value "2";
            }
            enum "running" {
              value "3";
            }
            enum "ready" {
              value "4";
            }
            enum "stopped" {
              value "5";
            }
            enum "send" {
              value "6";
            }
            enum "receive" {
              value "7";
            }
            enum "reply" {
              value "8";
            }
            enum "stack" {
              value "9";
            }
            enum "waitpage" {
              value "10";
            }
            enum "sigsuspend" {
              value "11";
            }
            enum "sigwaitinfo" {
              value "12";
            }
            enum "nanosleep" {
              value "13";
            }
            enum "mutex" {
              value "14";
            }
            enum "condvar" {
              value "15";
            }
            enum "join" {
              value "16";
            }
            enum "intr" {
              value "17";
            }
            enum "sem" {
              value "18";
            }
          }
          description
           "This object indicates the current state of a thread.
            Running state means that the thread is actively 
            consumig CPU. All the other states are just waiting 
            states. The valid states are:
            other         - Any other state apart from the listed 
                            ones.
            dead          - Kernel is waiting to release the 
                            thread's resources.
            running       - Actively running on a CPU.
            ready         - Not running on a CPU, but is ready to 
                            run (one or more higher or equal 
                            priority threads are running).
            stopped       - Suspended (SIGSTOP signal).
            send          - Waiting for a server to receive 
                            a message.
            receive       - Waiting for a client to send a message.
            reply         - Waiting for a server to reply to a 
                            message.
            stack         - Waiting for more stack to be allocated.
            waitpage      - Waiting for process manager to 
                            resolve a fault on a page.
            sigsuspend    - Suspended for a signal.
            sigwaitinfo   - Waiting for a signal.
            nanosleep     - Sleeping for a period of time.
            mutex         - Waiting to acquire a mutex
            condvar       - Waiting for a condition variable to be 
                            signalled.
            join          - Waiting for the completion of another 
                            thread.
            intr          - Waiting for an interrupt.
            sem           - Waiting to acquire a semaphore.";
          smiv2:max-access "read-only";
          smiv2:oid "1.3.6.1.4.1.9.9.109.1.3.1.1.4";
        }

        leaf cpmThreadBlockingProcess {
          type snmpv2-tc:RowPointer;
          description
           "This object identifies the process on which the
            current thread is blocked on. This points to the 
            cpmProcessTable of the process on which the thread 
            in context is blocked. This is valid only to threads
            which are either in send/reply states. For the 
            rest of the threads it is returned as 0.0";
          smiv2:max-access "read-only";
          smiv2:oid "1.3.6.1.4.1.9.9.109.1.3.1.1.5";
        }

        leaf cpmThreadCpuUtilization {
          type yang:gauge32;
          units "milliseconds";
          description
           "This object provides a general idea on how busy
            the thread in context caused the processor to be.";
          smiv2:max-access "read-only";
          smiv2:oid "1.3.6.1.4.1.9.9.109.1.3.1.1.6";
        }

        leaf cpmThreadStackSize {
          type yang:gauge32;
          units "bytes";
          description
           "This object indicates the stack size allocated to
            the thread in context.";
          smiv2:max-access "read-only";
          smiv2:oid "1.3.6.1.4.1.9.9.109.1.3.1.1.7";
        }

        leaf cpmThreadStackSizeOvrflw {
          type yang:gauge32;
          units "bytes";
          description
           "This object represents the upper 32-bit of cpmThreadStackSize.
            This object needs to be supported only when the value of
            cpmThreadStackSize exceeds 32-bit, otherwise this object value
            would be set to 0.";
          smiv2:max-access "read-only";
          smiv2:oid "1.3.6.1.4.1.9.9.109.1.3.1.1.8";
        }

        leaf cpmThreadHCStackSize {
          type yang:gauge64;
          units "bytes";
          description
           "This object indicates the stack size allocated to the
            thread in context. This object is a 64-bit version of
            cpmThreadStackSize.";
          smiv2:max-access "read-only";
          smiv2:oid "1.3.6.1.4.1.9.9.109.1.3.1.1.9";
        }
      }
    }

    container cpmVirtualProcessTable {
      description
       "This table contains information about virtual
        processes in a virtual machine.";
      smiv2:oid "1.3.6.1.4.1.9.9.109.1.4.1";

      list cpmVirtualProcessEntry {
        key "cpmCPUTotalIndex cpmProcessPID cpmVirtualProcessID";
        description
         "An entry containing the general statistics of a
          virtual process in a virtual machine.";
        smiv2:oid "1.3.6.1.4.1.9.9.109.1.4.1.1";

        leaf cpmCPUTotalIndex {
          type leafref {
            path "/CISCO-PROCESS-MIB:CISCO-PROCESS-MIB/CISCO-PROCESS-MIB:cpmCPUTotalTable/CISCO-PROCESS-MIB:cpmCPUTotalEntry/CISCO-PROCESS-MIB:cpmCPUTotalIndex";
          }
        }

        leaf cpmProcessPID {
          type leafref {
            path "/CISCO-PROCESS-MIB:CISCO-PROCESS-MIB/CISCO-PROCESS-MIB:cpmProcessTable/CISCO-PROCESS-MIB:cpmProcessEntry/CISCO-PROCESS-MIB:cpmProcessPID";
          }
        }

        leaf cpmVirtualProcessID {
          type uint32;
          description
           "This object indicates the process ID of a virtual
            process. PID is unique only inside one address space.
            Virtual process PID should be considered along with 
            Parent process cpmProcessPID.";
          smiv2:max-access "not-accessible";
          smiv2:oid "1.3.6.1.4.1.9.9.109.1.4.1.1.1";
        }

        leaf cpmVirtualProcessName {
          type snmp-framework:SnmpAdminString {
            length "1..32";
          }
          description
           "This object indicates the name of a virtual process.
            If the name is longer than 32 characters, it will be
            truncated to the first 31 characters, and a `*' will be
            appended as the last character to imply this is a
            truncated process name.";
          smiv2:max-access "read-only";
          smiv2:oid "1.3.6.1.4.1.9.9.109.1.4.1.1.2";
        }

        leaf cpmVirtualProcessUtil5Sec {
          type yang:gauge32 {
            range "0..100";
          }
          units "percent";
          description
           "This indicates an estimated CPU utilization by
            a virtual process over the last 5 seconds.";
          smiv2:max-access "read-only";
          smiv2:oid "1.3.6.1.4.1.9.9.109.1.4.1.1.3";
        }

        leaf cpmVirtualProcessUtil1Min {
          type yang:gauge32 {
            range "0..100";
          }
          units "percent";
          description
           "This indicates an estimated CPU utilization by
            a virtual process over the last one minute.";
          smiv2:max-access "read-only";
          smiv2:oid "1.3.6.1.4.1.9.9.109.1.4.1.1.4";
        }

        leaf cpmVirtualProcessUtil5Min {
          type yang:gauge32 {
            range "0..100";
          }
          units "percent";
          description
           "This indicates an estimated CPU utilization by
            a virtual process over the last 5 minutes.";
          smiv2:max-access "read-only";
          smiv2:oid "1.3.6.1.4.1.9.9.109.1.4.1.1.5";
        }

        leaf cpmVirtualProcessMemAllocated {
          type yang:gauge32;
          units "bytes";
          description
           "This object indicates the memory allocated by the
            virtual process inside the address space of a 
            process running on Native OS.";
          smiv2:max-access "read-only";
          smiv2:oid "1.3.6.1.4.1.9.9.109.1.4.1.1.6";
        }

        leaf cpmVirtualProcessMemFreed {
          type yang:gauge32;
          units "bytes";
          description
           "This object indicates the memory freed by the virtual
            process inside the address space of a process running 
            on Native OS.";
          smiv2:max-access "read-only";
          smiv2:oid "1.3.6.1.4.1.9.9.109.1.4.1.1.7";
        }

        leaf cpmVirtualProcessInvokeCount {
          type yang:counter32;
          description
           "The number of times a virtual process is invoked.";
          smiv2:max-access "read-only";
          smiv2:oid "1.3.6.1.4.1.9.9.109.1.4.1.1.8";
        }

        leaf cpmVirtualProcessRuntime {
          type yang:counter32;
          units "microseconds";
          description
           "The amount of CPU time a virtual process has used in
            microseconds.";
          smiv2:max-access "read-only";
          smiv2:oid "1.3.6.1.4.1.9.9.109.1.4.1.1.9";
        }

        leaf cpmVirtualProcessMemAllocatedOvrflw {
          type yang:gauge32;
          units "bytes";
          description
           "This object represents the upper 32-bit of
            cpmVirtualProcessMemAllocated. This object 
            needs to be supported only when the value of
            cpmVirtualProcessMemAllocated exceeds 32-bit,
            otherwise this object value would be set to 0.";
          smiv2:max-access "read-only";
          smiv2:oid "1.3.6.1.4.1.9.9.109.1.4.1.1.10";
        }

        leaf cpmVirtualProcessHCMemAllocated {
          type yang:gauge64;
          units "bytes";
          description
           "This object indicates the memory allocated by the
            virtual process inside the address space of a process
            running on Native OS. This object is a 64-bit version
            of cpmVirtualProcessMemAllocated.";
          smiv2:max-access "read-only";
          smiv2:oid "1.3.6.1.4.1.9.9.109.1.4.1.1.11";
        }

        leaf cpmVirtualProcessMemFreedOvrflw {
          type yang:gauge32;
          units "bytes";
          description
           "This object represents the upper 32-bit of
            cpmVirtualProcessMemFreed. This object needs
            to be supported only when the value of 
            cpmVirtualProcessMemFreed exceeds 32-bit, 
            otherwise this object value would be set to 0.";
          smiv2:max-access "read-only";
          smiv2:oid "1.3.6.1.4.1.9.9.109.1.4.1.1.12";
        }

        leaf cpmVirtualProcessHCMemFreed {
          type yang:gauge64;
          units "bytes";
          description
           "This object indicates the memory freed by the virtual process
            inside the address space of a process running on Native OS.This
            object is a 64-bit version of cpmVirtualProcessMemAllocated.";
          smiv2:max-access "read-only";
          smiv2:oid "1.3.6.1.4.1.9.9.109.1.4.1.1.13";
        }
      }
    }
  }

  smiv2:alias "cpmProcessExtTable" {
    status deprecated;
    description
     "This table contains information that may or may
      not be available on all cisco devices. It contains
      additional objects for the more general
      cpmProcessTable. This object is deprecated by
      cpmProcessExtRevTable.";
    smiv2:oid "1.3.6.1.4.1.9.9.109.1.2.2";
  }

  smiv2:alias "cpmProcessExtEntry" {
    status deprecated;
    description
     "An entry containing additional information for
      a particular process. This object is deprecated by
      cpmProcessExtRevEntry.";
    smiv2:oid "1.3.6.1.4.1.9.9.109.1.2.2.1";
  }

  augment "/CISCO-PROCESS-MIB:CISCO-PROCESS-MIB/CISCO-PROCESS-MIB:cpmProcessTable/CISCO-PROCESS-MIB:cpmProcessEntry" {
    status deprecated;
    description
     "An entry containing additional information for
      a particular process. This object is deprecated by
      cpmProcessExtRevEntry.";
    smiv2:oid "1.3.6.1.4.1.9.9.109.1.2.2.1";

    leaf cpmProcExtMemAllocated {
      type yang:gauge32;
      units "bytes";
      status deprecated;
      description
       "The sum of all the dynamically allocated memory that
        this process has received from the system. This includes
        memory that may have been returned. The sum of freed
        memory is provided by cpmProcExtMemFreed. This object
        is deprecated by cpmProcExtMemAllocatedRev.";
      smiv2:max-access "read-only";
      smiv2:oid "1.3.6.1.4.1.9.9.109.1.2.2.1.1";
    }

    leaf cpmProcExtMemFreed {
      type yang:gauge32;
      units "bytes";
      status deprecated;
      description
       "The sum of all memory that this process has returned
        to the system. This object is deprecated by 
        cpmProcExtMemFreedRev.";
      smiv2:max-access "read-only";
      smiv2:oid "1.3.6.1.4.1.9.9.109.1.2.2.1.2";
    }

    leaf cpmProcExtInvoked {
      type yang:counter32;
      status deprecated;
      description
       "The number of times since cpmTimeCreated that
        the process has been invoked. This object is
        deprecated by cpmProcExtInvokedRev.";
      smiv2:max-access "read-only";
      smiv2:oid "1.3.6.1.4.1.9.9.109.1.2.2.1.3";
    }

    leaf cpmProcExtRuntime {
      type yang:counter32;
      units "microseconds";
      status deprecated;
      description
       "The amount of CPU time the process has used, in
        microseconds. This object is deprecated by
        cpmProcExtRuntimeRev.";
      smiv2:max-access "read-only";
      smiv2:oid "1.3.6.1.4.1.9.9.109.1.2.2.1.4";
    }

    leaf cpmProcExtUtil5Sec {
      type yang:gauge32 {
        range "0..100";
      }
      status deprecated;
      description
       "This object provides a general idea of how busy
        a process caused the processor to be over a 5 
        second period. It is determined as a weighted 
        decaying average of the current idle time over 
        the longest idle time. Note that this information 
        should be used as an estimate only. This object is 
        deprecated by cpmProcExtUtil5SecRev which has the 
        changed range of value (0..100).";
      smiv2:max-access "read-only";
      smiv2:oid "1.3.6.1.4.1.9.9.109.1.2.2.1.5";
    }

    leaf cpmProcExtUtil1Min {
      type yang:gauge32 {
        range "0..100";
      }
      status deprecated;
      description
       "This object provides a general idea of how busy
        a process caused the processor to be over a 1 
        minute period. It is determined as a weighted 
        decaying average of the current idle time over the 
        longest idle time. Note that this information 
        should be used as an estimate only. This object is 
        deprecated by cpmProcExtUtil1MinRev which has
        the changed range of value (0..100).";
      smiv2:max-access "read-only";
      smiv2:oid "1.3.6.1.4.1.9.9.109.1.2.2.1.6";
    }

    leaf cpmProcExtUtil5Min {
      type yang:gauge32 {
        range "0..100";
      }
      status deprecated;
      description
       "This object provides a general idea of how busy
        a process caused the processor to be over a 5 
        minute period. It is determined as a weighted 
        decaying average of the current idle time over 
        the longest idle time. Note that this information 
        should be used as an estimate only. This object
        is deprecated by cpmProcExtUtil5MinRev which
        has the changed range of value (0..100).";
      smiv2:max-access "read-only";
      smiv2:oid "1.3.6.1.4.1.9.9.109.1.2.2.1.7";
    }

    leaf cpmProcExtPriority {
      type enumeration {
        enum "critical" {
          value "1";
        }
        enum "high" {
          value "2";
        }
        enum "normal" {
          value "3";
        }
        enum "low" {
          value "4";
        }
        enum "notAssigned" {
          value "5";
        }
      }
      status deprecated;
      description
       "The priority level at which the process is
        running. This object is deprecated by
        cpmProcExtPriorityRev.";
      smiv2:max-access "read-write";
      smiv2:oid "1.3.6.1.4.1.9.9.109.1.2.2.1.8";
    }
  }

  notification cpmCPURisingThreshold {
    description
     "A cpmCPURisingThreshold notification is sent
      when configured rising CPU utilization threshold
      (cpmCPURisingThresholdValue) is reached and
      CPU utilization remained above the threshold 
      for configured interval(cpmCPURisingThresholdPeriod)
      and such a notification is requested. 
      The cpmProcExtUtil5SecRev and cpmProcessTimeCreated 
      objects can be repeated multiple times
      in a notification indicating the top users of CPU.";
    smiv2:oid "1.3.6.1.4.1.9.9.109.2.0.1";

    container object-1 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmCPUThresholdClass {
        type leafref {
          path "/CISCO-PROCESS-MIB:CISCO-PROCESS-MIB/CISCO-PROCESS-MIB:cpmCPUThresholdTable/CISCO-PROCESS-MIB:cpmCPUThresholdEntry/CISCO-PROCESS-MIB:cpmCPUThresholdClass";
        }
      }

      leaf cpmCPURisingThresholdValue {
        type leafref {
          path "/CISCO-PROCESS-MIB:CISCO-PROCESS-MIB/CISCO-PROCESS-MIB:cpmCPUThresholdTable/CISCO-PROCESS-MIB:cpmCPUThresholdEntry/CISCO-PROCESS-MIB:cpmCPURisingThresholdValue";
        }
      }
    }

    container object-2 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmCPUTotalMonIntervalValue {
        type leafref {
          path "/CISCO-PROCESS-MIB:CISCO-PROCESS-MIB/CISCO-PROCESS-MIB:cpmCPUTotalTable/CISCO-PROCESS-MIB:cpmCPUTotalEntry/CISCO-PROCESS-MIB:cpmCPUTotalMonIntervalValue";
        }
      }
    }

    container object-3 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmCPUInterruptMonIntervalValue {
        type leafref {
          path "/CISCO-PROCESS-MIB:CISCO-PROCESS-MIB/CISCO-PROCESS-MIB:cpmCPUTotalTable/CISCO-PROCESS-MIB:cpmCPUTotalEntry/CISCO-PROCESS-MIB:cpmCPUInterruptMonIntervalValue";
        }
      }
    }

    container object-4 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmProcessPID {
        type leafref {
          path "/CISCO-PROCESS-MIB:CISCO-PROCESS-MIB/CISCO-PROCESS-MIB:cpmProcessTable/CISCO-PROCESS-MIB:cpmProcessEntry/CISCO-PROCESS-MIB:cpmProcessPID";
        }
      }

      leaf cpmProcExtUtil5SecRev {
        type leafref {
          path "/CISCO-PROCESS-MIB:CISCO-PROCESS-MIB/CISCO-PROCESS-MIB:cpmProcessExtRevTable/CISCO-PROCESS-MIB:cpmProcessExtRevEntry/CISCO-PROCESS-MIB:cpmProcExtUtil5SecRev";
        }
      }
    }

    container object-5 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmProcessPID {
        type leafref {
          path "/CISCO-PROCESS-MIB:CISCO-PROCESS-MIB/CISCO-PROCESS-MIB:cpmProcessTable/CISCO-PROCESS-MIB:cpmProcessEntry/CISCO-PROCESS-MIB:cpmProcessPID";
        }
      }

      leaf cpmProcessTimeCreated {
        type leafref {
          path "/CISCO-PROCESS-MIB:CISCO-PROCESS-MIB/CISCO-PROCESS-MIB:cpmProcessTable/CISCO-PROCESS-MIB:cpmProcessEntry/CISCO-PROCESS-MIB:cpmProcessTimeCreated";
        }
      }
    }
  }

  notification cpmCPUFallingThreshold {
    description
     "A cpmCPUFallingThresholdTrap is sent when the
      configured falling threshold
      (cpmCPURisingThresholdValue) 
      is reached and CPU utilization remained under 
      threshold for configured 
      interval (cpmCPUFallingThresholdPeriod) 
      and such a notification is requested.";
    smiv2:oid "1.3.6.1.4.1.9.9.109.2.0.2";

    container object-1 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmCPUThresholdClass {
        type leafref {
          path "/CISCO-PROCESS-MIB:CISCO-PROCESS-MIB/CISCO-PROCESS-MIB:cpmCPUThresholdTable/CISCO-PROCESS-MIB:cpmCPUThresholdEntry/CISCO-PROCESS-MIB:cpmCPUThresholdClass";
        }
      }

      leaf cpmCPUFallingThresholdValue {
        type leafref {
          path "/CISCO-PROCESS-MIB:CISCO-PROCESS-MIB/CISCO-PROCESS-MIB:cpmCPUThresholdTable/CISCO-PROCESS-MIB:cpmCPUThresholdEntry/CISCO-PROCESS-MIB:cpmCPUFallingThresholdValue";
        }
      }
    }

    container object-2 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmCPUTotalMonIntervalValue {
        type leafref {
          path "/CISCO-PROCESS-MIB:CISCO-PROCESS-MIB/CISCO-PROCESS-MIB:cpmCPUTotalTable/CISCO-PROCESS-MIB:cpmCPUTotalEntry/CISCO-PROCESS-MIB:cpmCPUTotalMonIntervalValue";
        }
      }
    }

    container object-3 {

      leaf cpmCPUTotalIndex {
        type leafref {
          path "/CISCO-PROCESS-MIB:CISCO-PROCESS-MIB/CISCO-PROCESS-MIB:cpmCPUTotalTable/CISCO-PROCESS-MIB:cpmCPUTotalEntry/CISCO-PROCESS-MIB:cpmCPUTotalIndex";
        }
      }

      leaf cpmCPUInterruptMonIntervalValue {
        type leafref {
          path "/CISCO-PROCESS-MIB:CISCO-PROCESS-MIB/CISCO-PROCESS-MIB:cpmCPUTotalTable/CISCO-PROCESS-MIB:cpmCPUTotalEntry/CISCO-PROCESS-MIB:cpmCPUInterruptMonIntervalValue";
        }
      }
    }
  }

  smiv2:alias "ciscoProcessMIB" {
    smiv2:oid "1.3.6.1.4.1.9.9.109";
  }

  smiv2:alias "ciscoProcessMIBObjects" {
    smiv2:oid "1.3.6.1.4.1.9.9.109.1";
  }

  smiv2:alias "cpmCPU" {
    smiv2:oid "1.3.6.1.4.1.9.9.109.1.1";
  }

  smiv2:alias "cpmProcess" {
    smiv2:oid "1.3.6.1.4.1.9.9.109.1.2";
  }

  smiv2:alias "cpmCPUHistory" {
    smiv2:oid "1.3.6.1.4.1.9.9.109.1.2.5";
  }

  smiv2:alias "cpmThread" {
    smiv2:oid "1.3.6.1.4.1.9.9.109.1.3";
  }

  smiv2:alias "cpmVirtualProcess" {
    smiv2:oid "1.3.6.1.4.1.9.9.109.1.4";
  }

  smiv2:alias "ciscoProcessMIBNotifPrefix" {
    smiv2:oid "1.3.6.1.4.1.9.9.109.2";
  }

  smiv2:alias "ciscoProcessMIBNotifs" {
    smiv2:oid "1.3.6.1.4.1.9.9.109.2.0";
  }

  smiv2:alias "ciscoProcessMIBConformance" {
    smiv2:oid "1.3.6.1.4.1.9.9.109.3";
  }

  smiv2:alias "cpmCompliances" {
    smiv2:oid "1.3.6.1.4.1.9.9.109.3.1";
  }

  smiv2:alias "cpmGroups" {
    smiv2:oid "1.3.6.1.4.1.9.9.109.3.2";
  }

}
