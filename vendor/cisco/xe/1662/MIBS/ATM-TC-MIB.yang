/*
 * Generated by confdc --mib2yang-std
 * Source: mgmt/dmi/model/common/mib-source/ATM-TC-MIB.mib
 */
/*
 * This YANG module has been generated by smidump 0.5.0:
 *
 *      smidump -f yang ATM-TC-MIB
 *
 * Do not edit. Edit the source file instead!
 */

module ATM-TC-MIB {

  namespace "urn:ietf:params:xml:ns:yang:smiv2:ATM-TC-MIB";
  prefix ATM-TC-MIB;

  import ietf-yang-smiv2 {
    prefix "smiv2";
  }

  import ietf-yang-types {
    prefix "yang";
  }

  organization
   "IETF AToMMIB Working Group";

  contact
   "          Michael Noto
    Postal:  3Com Corporation
             5400 Bayfront Plaza, M/S 3109
             Santa Clara, CA 95052
             USA
    Tel:     +1 408 326 2218
    E-mail:  mike_noto@3com.com
    
             Ethan Mickey Spiegel
    Postal:  Cisco Systems
             170 W. Tasman Dr.
             San Jose, CA 95134
             USA
    Tel:     +1 408 526 6408
    E-mail:  mspiegel@cisco.com
    
             Kaj Tesink
    Postal:  Bellcore
             331 Newman Springs Road
             Red Bank, NJ 07701
             USA
    Tel:     +1 732 758 5254
    Fax:     +1 732 758 4177
    E-mail:  kaj@bellcore.com";

  description
   "This MIB Module provides Textual Conventions
    and OBJECT-IDENTITY Objects to be used by
    ATM systems.";

  revision 1998-10-19 {
    description
     "[Revision added by libsmi due to a LAST-UPDATED clause.]";
  }

  typedef AtmAddr {
    type string;
    description
     "An ATM address. The semantics are implied by
      the length. The address types are: - no
      address (0 octets) - E.164 (8 octets) - NSAP
      (20 octets) In addition, when subaddresses
      are used the AtmAddr may represent the
      concatenation of address and subaddress. The
      associated address types are: - E.164, E.164
      (16 octets) - E.164, NSAP (28 octets) - NSAP,
      NSAP (40 octets) Address lengths other than
      defined in this definition imply address
      types defined elsewhere.  Note: The E.164
      address is encoded in BCD format.";
    smiv2:display-hint "1x";
  }

  typedef AtmConnCastType {
    type enumeration {
      enum "p2p" {
        value "1";
      }
      enum "p2mpRoot" {
        value "2";
      }
      enum "p2mpLeaf" {
        value "3";
      }
    }
    description
     "The type of topology of a connection (point-
      to-point, point-to-multipoint). In the case
      of point-to-multipoint, the orientation of
      this VPL or VCL in the connection.
      On a host:
      - p2mpRoot indicates that the host
        is the root of the p2mp connection.
      - p2mpLeaf indicates that the host
        is a leaf of the p2mp connection.
      On a switch interface:
      - p2mpRoot indicates that cells received
        by the switching fabric from the interface
        are from the root of the p2mp connection.
      - p2mpLeaf indicates that cells transmitted
        to the interface from the switching fabric
        are to the leaf of the p2mp connection.";
  }

  typedef AtmConnKind {
    type enumeration {
      enum "pvc" {
        value "1";
      }
      enum "svcIncoming" {
        value "2";
      }
      enum "svcOutgoing" {
        value "3";
      }
      enum "spvcInitiator" {
        value "4";
      }
      enum "spvcTarget" {
        value "5";
      }
    }
    description
     "The type of call control used for an ATM
      connection at a particular interface. The use
      is as follows:
         pvc(1)
            Virtual link of a PVC. Should not be
            used for an PVC/SVC (i.e., Soft PVC)
            crossconnect.
         svcIncoming(2)
            Virtual link established after a
            received signaling request to setup
            an SVC.
         svcOutgoing(3)
            Virtual link established after a
            transmitted or forwarded signaling
            request to setup an SVC.
         spvcInitiator(4)
            Virtual link at the PVC side of an
            SVC/PVC crossconnect, where the
            switch is the initiator of the Soft PVC
            setup.
         spvcTarget(5)
            Virtual link at the PVC side of an
            SVC/PVC crossconnect, where the
            switch is the target of the Soft PVC
            setup.
      
      For PVCs, a pvc virtual link is always cross-
      connected to a pvc virtual link.
      
      For SVCs, an svcIncoming virtual link is always cross-
      connected to an svcOutgoing virtual link.
      
      For Soft PVCs, an spvcInitiator is either cross-connected to
      an svcOutgoing or an spvcTarget, and an spvcTarget is either
      cross-connected to an svcIncoming or an spvcInitiator.";
  }

  typedef AtmIlmiNetworkPrefix {
    type binary {
      length "8|13";
    }
    description
     "A network prefix used for ILMI address
      registration.  In the case of ATM endsystem
      addresses (AESAs), the network prefix is the first
      13 octets of the address which includes the AFI,
      IDI, and HO-DSP fields.  In the case of native
      E.164 addresses, the network prefix is the entire
      E.164 address encoded in 8 octets, as if it were
      an E.164 IDP in an ATM endsystem address
      structure.";
    reference
     "ATM Forum, Integrated Local Management Interface
      (ILMI) Specification, Version 4.0,
      af-ilmi-0065.000, September 1996, Section 9
      ATM Forum, ATM User-Network Interface Signalling
      Specification, Version 4.0 (UNI 4.0),
      af-sig-0061.000, June 1996, Section 3";
  }

  typedef AtmInterfaceType {
    type enumeration {
      enum "other" {
        value "1";
      }
      enum "autoConfig" {
        value "2";
      }
      enum "ituDss2" {
        value "3";
      }
      enum "atmfUni3Dot0" {
        value "4";
      }
      enum "atmfUni3Dot1" {
        value "5";
      }
      enum "atmfUni4Dot0" {
        value "6";
      }
      enum "atmfIispUni3Dot0" {
        value "7";
      }
      enum "atmfIispUni3Dot1" {
        value "8";
      }
      enum "atmfIispUni4Dot0" {
        value "9";
      }
      enum "atmfPnni1Dot0" {
        value "10";
      }
      enum "atmfBici2Dot0" {
        value "11";
      }
      enum "atmfUniPvcOnly" {
        value "12";
      }
      enum "atmfNniPvcOnly" {
        value "13";
      }
    }
    description
     "The connection setup procedures used for the
      identified interface.
      
      Other: Connection setup procedures other than
         those listed below.
      
      Auto-configuration:
         Indicates that the connection setup
         procedures are to be determined dynamically,
         or that determination has not yet been
         completed. One such mechanism is via ATM
         Forum ILMI auto-configuration procedures.
      
      ITU-T DSS2:
      -  ITU-T Recommendation Q.2931, Broadband
         Integrated Service Digital Network (B-ISDN)
         Digital Subscriber Signalling System No.2
         (DSS2) User-Network Interface (UNI) Layer 3
         Specification for Basic Call/Connection
         Control (September 1994)
      -  ITU-T Draft Recommendation Q.2961,
         B-ISDN DSS 2 Support of Additional Traffic
         Parameters (May 1995)
      
      -  ITU-T Draft Recommendation Q.2971,
         B-ISDN DSS 2 User Network Interface Layer 3
         Specification for Point-to-multipoint
         Call/connection Control (May 1995)
      
      ATM Forum UNI 3.0:
         ATM Forum, ATM User-Network Interface,
         Version 3.0 (UNI 3.0) Specification,
         (1994).
      
      ATM Forum UNI 3.1:
         ATM Forum, ATM User-Network Interface,
         Version 3.1 (UNI 3.1) Specification,
         (November 1994).
      
      ATM Forum UNI Signalling 4.0:
         ATM Forum, ATM User-Network Interface (UNI)
         Signalling Specification Version 4.0,
         af-sig-0061.000 (June 1996).
      
      ATM Forum IISP (based on UNI 3.0 or UNI 3.1) :
         Interim Inter-switch Signaling Protocol
         (IISP) Specification, Version 1.0,
         af-pnni-0026.000, (December 1994).
      
      ATM Forum PNNI 1.0 :
         ATM Forum, Private Network-Network Interface
         Specification, Version 1.0, af-pnni-0055.000,
         (March 1996).
      
      ATM Forum B-ICI:
         ATM Forum, B-ICI Specification, Version 2.0,
         af-bici-0013.002, (November 1995).
      
      ATM Forum UNI PVC Only:
         An ATM Forum compliant UNI with the
         signalling disabled.
      ATM Forum NNI PVC Only:
         An ATM Forum compliant NNI with the
         signalling disabled.";
  }

  typedef AtmServiceCategory {
    type enumeration {
      enum "other" {
        value "1";
      }
      enum "cbr" {
        value "2";
      }
      enum "rtVbr" {
        value "3";
      }
      enum "nrtVbr" {
        value "4";
      }
      enum "abr" {
        value "5";
      }
      enum "ubr" {
        value "6";
      }
    }
    description
     "The service category for a connection.";
    reference
     "ATM Forum Traffic Management Specification,
      Version 4.0, af-tm-0056.000, June 1996.";
  }

  typedef AtmSigDescrParamIndex {
    type int32 {
      range "0..2147483647";
    }
    description
     "The value of this object identifies a row in the
      atmSigDescrParamTable. The value 0 signifies that
      none of the signalling parameters defined in the
      atmSigDescrParamTable are applicable.";
  }

  typedef AtmTrafficDescrParamIndex {
    type int32 {
      range "0..2147483647";
    }
    description
     "The value of this object identifies a row in the
      atmTrafficDescrParamTable.  The value 0 signifies
      that no row has been identified.";
  }

  typedef AtmVcIdentifier {
    type int32 {
      range "0..65535";
    }
    description
     "The VCI value for a VCL. The maximum VCI value
      cannot exceed the value allowable by
      atmInterfaceMaxVciBits defined in ATM-MIB.";
  }

  typedef AtmVpIdentifier {
    type int32 {
      range "0..4095";
    }
    description
     "The VPI value for a VPL or VCL. The value VPI=0
      is only allowed for a VCL. For ATM UNIs supporting
      VPCs the VPI value ranges from 0 to 255.  The VPI
      value 0 is supported for ATM UNIs conforming to
      the ATM Forum UNI 4.0 Annex 8 (Virtual UNIs)
      specification. For ATM UNIs supporting VCCs the
      VPI value ranges from 0 to 255.  For ATM NNIs the
      VPI value ranges from 0 to 4095.  The maximum VPI
      value cannot exceed the value allowable by
      atmInterfaceMaxVpiBits defined in ATM-MIB.";
  }

  typedef AtmVorXAdminStatus {
    type enumeration {
      enum "up" {
        value "1";
      }
      enum "down" {
        value "2";
      }
    }
    description
     "The value determines the desired administrative
      status of a virtual link or cross-connect. The up
      and down states indicate that the traffic flow is
      enabled or disabled respectively on the virtual
      link or cross-connect.";
  }

  typedef AtmVorXLastChange {
    type yang:timeticks;
    description
     "The value of MIB II's sysUpTime at the time a
      virtual link or cross-connect entered its current
      operational state. If the current state was
      entered prior to the last re-initialization of the
      agent then this object contains a zero value.";
  }

  typedef AtmVorXOperStatus {
    type enumeration {
      enum "up" {
        value "1";
      }
      enum "down" {
        value "2";
      }
      enum "unknown" {
        value "3";
      }
    }
    description
     "The value determines the operational status of a
      virtual link or cross-connect. The up and down
      states indicate that the traffic flow is enabled
      or disabled respectively on the virtual link or
      cross-connect. The unknown state indicates that
      the state of it cannot be determined. The state
      will be down or unknown if the supporting ATM
      interface(s) is down or unknown respectively.";
  }

  identity atmNoTrafficDescriptor {
    base smiv2:object-identity;
    status deprecated;
    description
     "This identifies the no ATM traffic
      descriptor type.  Parameters 1, 2, 3, 4,
      and 5 are not used.  This traffic descriptor
      type can be used for best effort traffic.";
    smiv2:oid "1.3.6.1.2.1.37.1.1.1";
  }

  identity atmNoClpNoScr {
    base smiv2:object-identity;
    description
     "This traffic descriptor type is for no CLP
      and no Sustained Cell Rate.  The use of the
      parameter vector for this type:
      Parameter 1: peak cell rate in cells/second
                   for CLP=0+1 traffic
      Parameter 2: not used
      Parameter 3: not used
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.2";
  }

  identity atmClpNoTaggingNoScr {
    base smiv2:object-identity;
    status deprecated;
    description
     "This traffic descriptor is for CLP without
      tagging and no Sustained Cell Rate.  The use
      of the parameter vector for this type:
      Parameter 1: peak cell rate in cells/second
                   for CLP=0+1 traffic
      Parameter 2: peak cell rate in cells/second
                   for CLP=0 traffic
      Parameter 3: not used
      Parameter 4: not used
      Parameter 5: not used.";
    smiv2:oid "1.3.6.1.2.1.37.1.1.3";
  }

  identity atmClpTaggingNoScr {
    base smiv2:object-identity;
    status deprecated;
    description
     "This traffic descriptor is for CLP with
      tagging and no Sustained Cell Rate.  The use
      of the parameter vector for this type:
      Parameter 1: peak cell rate in cells/second
                   for CLP=0+1 traffic
      Parameter 2: peak cell rate in cells/second
                   for CLP=0 traffic, excess
                   tagged as CLP=1
      Parameter 3: not used
      Parameter 4: not used
      Parameter 5: not used.";
    smiv2:oid "1.3.6.1.2.1.37.1.1.4";
  }

  identity atmNoClpScr {
    base smiv2:object-identity;
    description
     "This traffic descriptor type is for no CLP
      with Sustained Cell Rate.  The use of the
      parameter vector for this type:
      Parameter 1: peak cell rate in cells/second
                   for CLP=0+1 traffic
      Parameter 2: sustainable cell rate in cells/second
                   for CLP=0+1 traffic
      Parameter 3: maximum burst size in cells
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.5";
  }

  identity atmClpNoTaggingScr {
    base smiv2:object-identity;
    description
     "This traffic descriptor type is for CLP with
      Sustained Cell Rate and no tagging.  The use
      of the parameter vector for this type:
      Parameter 1: peak cell rate in cells/second
                   for CLP=0+1 traffic
      Parameter 2: sustainable cell rate in cells/second
                   for CLP=0 traffic
      Parameter 3: maximum burst size in cells
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.6";
  }

  identity atmClpTaggingScr {
    base smiv2:object-identity;
    description
     "This traffic descriptor type is for CLP with
      tagging and Sustained Cell Rate.  The use of
      the parameter vector for this type:
      Parameter 1: peak cell rate in cells/second
                   for CLP=0+1 traffic
      Parameter 2: sustainable cell rate in cells/second
                   for CLP=0 traffic, excess tagged as
                   CLP=1
      Parameter 3: maximum burst size in cells
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.7";
  }

  identity atmClpNoTaggingMcr {
    base smiv2:object-identity;
    description
     "This traffic descriptor type is for CLP with
      Minimum Cell Rate and no tagging.  The use of
      the parameter vector for this type:
      Parameter 1: peak cell rate in cells/second
                   for CLP=0+1 traffic
      Parameter 2: CDVT in tenths of microseconds
      Parameter 3: minimum cell rate in cells/second
      Parameter 4: unused
      Parameter 5: unused.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.8";
  }

  identity atmClpTransparentNoScr {
    base smiv2:object-identity;
    description
     "This traffic descriptor type is for the CLP-
      transparent model and no Sustained Cell Rate.
      The use of the parameter vector for this type:
      Parameter 1: peak cell rate in cells/second
                   for CLP=0+1 traffic
      Parameter 2: CDVT in tenths of microseconds
      Parameter 3: not used
      Parameter 4: not used
      Parameter 5: not used.
      
      This traffic descriptor type is applicable to
      connections following the CBR.1 conformance
      definition.
      
      Connections specifying this traffic descriptor
      type will be rejected at UNI 3.0 or UNI 3.1
      interfaces.  For a similar traffic descriptor
      type that can be accepted at UNI 3.0 and
      UNI 3.1 interfaces, see atmNoClpNoScr.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.9";
  }

  identity atmClpTransparentScr {
    base smiv2:object-identity;
    description
     "This traffic descriptor type is for the CLP-
      transparent model with Sustained Cell Rate.
      The use of the parameter vector for this type:
      Parameter 1: peak cell rate in cells/second
                   for CLP=0+1 traffic
      Parameter 2: sustainable cell rate in cells/second
                   for CLP=0+1 traffic
      Parameter 3: maximum burst size in cells
      Parameter 4: CDVT in tenths of microseconds
      Parameter 5: not used.
      
      This traffic descriptor type is applicable to
      connections following the VBR.1 conformance
      definition.
      
      Connections specifying this traffic descriptor
      type will be rejected at UNI 3.0 or UNI 3.1
      interfaces.  For a similar traffic descriptor
      type that can be accepted at UNI 3.0 and
      UNI 3.1 interfaces, see atmNoClpScr.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.10";
  }

  identity atmNoClpTaggingNoScr {
    base smiv2:object-identity;
    description
     "This traffic descriptor type is for no CLP
      with tagging and no Sustained Cell Rate.  The
      use of the parameter vector for this type:
      Parameter 1: peak cell rate in cells/second
                   for CLP=0+1 traffic
      Parameter 2: CDVT in tenths of microseconds
      Parameter 3: not used
      Parameter 4: not used
      Parameter 5: not used.
      
      This traffic descriptor type is applicable to
      connections following the UBR.2 conformance
      definition .";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.11";
  }

  identity atmNoClpNoScrCdvt {
    base smiv2:object-identity;
    description
     "This traffic descriptor type is for no CLP
      and no Sustained Cell Rate.  The use of the
      parameter vector for this type:
      Parameter 1: peak cell rate in cells/second
                   for CLP=0+1 traffic
      Parameter 2: CDVT in tenths of microseconds
      Parameter 3: not used
      Parameter 4: not used
      Parameter 5: not used.
      
      This traffic descriptor type is applicable to
      CBR connections following the UNI 3.0/3.1
      conformance definition for PCR CLP=0+1.
      These CBR connections differ from CBR.1
      connections in that the CLR objective
      applies only to the CLP=0 cell flow.
      
      This traffic descriptor type is also
      applicable to connections following the UBR.1
      conformance definition.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.12";
  }

  identity atmNoClpScrCdvt {
    base smiv2:object-identity;
    description
     "This traffic descriptor type is for no CLP
      with Sustained Cell Rate.  The use of the
      parameter vector for this type:
      Parameter 1: peak cell rate in cells/second
                   for CLP=0+1 traffic
      Parameter 2: sustainable cell rate in cells/second
                   for CLP=0+1 traffic
      Parameter 3: maximum burst size in cells
      Parameter 4: CDVT in tenths of microseconds
      Parameter 5: not used.
      
      This traffic descriptor type is applicable
      to VBR connections following the UNI 3.0/3.1
      conformance definition for PCR CLP=0+1 and
      SCR CLP=0+1.  These VBR connections
      differ from VBR.1 connections in that
      the CLR objective applies only to the CLP=0
      cell flow.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.13";
  }

  identity atmClpNoTaggingScrCdvt {
    base smiv2:object-identity;
    description
     "This traffic descriptor type is for CLP with
      Sustained Cell Rate and no tagging.  The use
      of the parameter vector for this type:
      Parameter 1: peak cell rate in cells/second
                   for CLP=0+1 traffic
      Parameter 2: sustainable cell rate in cells/second
                   for CLP=0 traffic
      Parameter 3: maximum burst size in cells
      Parameter 4: CDVT in tenths of microseconds
      Parameter 5: not used.
      
      This traffic descriptor type is applicable to
      connections following the VBR.2 conformance
      definition.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.14";
  }

  identity atmClpTaggingScrCdvt {
    base smiv2:object-identity;
    description
     "This traffic descriptor type is for CLP with
      tagging and Sustained Cell Rate.  The use of
      the parameter vector for this type:
      Parameter 1: peak cell rate in cells/second
                   for CLP=0+1 traffic
      Parameter 2: sustainable cell rate in cells/second
                   for CLP=0 traffic, excess tagged as
                   CLP=1
      Parameter 3: maximum burst size in cells
      Parameter 4: CDVT in tenths of microseconds
      Parameter 5: not used.
      
      This traffic descriptor type is applicable to
      connections following the VBR.3 conformance
      definition.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.15";
  }

  smiv2:alias "atmTrafficDescriptorTypes" {
    smiv2:oid "1.3.6.1.2.1.37.1.1";
  }

  smiv2:alias "atmNoTrafficDescriptor" {
    status deprecated;
    description
     "This identifies the no ATM traffic
      descriptor type.  Parameters 1, 2, 3, 4,
      and 5 are not used.  This traffic descriptor
      type can be used for best effort traffic.";
    smiv2:oid "1.3.6.1.2.1.37.1.1.1";
  }

  smiv2:alias "atmNoClpNoScr" {
    description
     "This traffic descriptor type is for no CLP
      and no Sustained Cell Rate.  The use of the
      parameter vector for this type:
      Parameter 1: peak cell rate in cells/second
                   for CLP=0+1 traffic
      Parameter 2: not used
      Parameter 3: not used
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.2";
  }

  smiv2:alias "atmClpNoTaggingNoScr" {
    status deprecated;
    description
     "This traffic descriptor is for CLP without
      tagging and no Sustained Cell Rate.  The use
      of the parameter vector for this type:
      Parameter 1: peak cell rate in cells/second
                   for CLP=0+1 traffic
      Parameter 2: peak cell rate in cells/second
                   for CLP=0 traffic
      Parameter 3: not used
      Parameter 4: not used
      Parameter 5: not used.";
    smiv2:oid "1.3.6.1.2.1.37.1.1.3";
  }

  smiv2:alias "atmClpTaggingNoScr" {
    status deprecated;
    description
     "This traffic descriptor is for CLP with
      tagging and no Sustained Cell Rate.  The use
      of the parameter vector for this type:
      Parameter 1: peak cell rate in cells/second
                   for CLP=0+1 traffic
      Parameter 2: peak cell rate in cells/second
                   for CLP=0 traffic, excess
                   tagged as CLP=1
      Parameter 3: not used
      Parameter 4: not used
      Parameter 5: not used.";
    smiv2:oid "1.3.6.1.2.1.37.1.1.4";
  }

  smiv2:alias "atmNoClpScr" {
    description
     "This traffic descriptor type is for no CLP
      with Sustained Cell Rate.  The use of the
      parameter vector for this type:
      Parameter 1: peak cell rate in cells/second
                   for CLP=0+1 traffic
      Parameter 2: sustainable cell rate in cells/second
                   for CLP=0+1 traffic
      Parameter 3: maximum burst size in cells
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.5";
  }

  smiv2:alias "atmClpNoTaggingScr" {
    description
     "This traffic descriptor type is for CLP with
      Sustained Cell Rate and no tagging.  The use
      of the parameter vector for this type:
      Parameter 1: peak cell rate in cells/second
                   for CLP=0+1 traffic
      Parameter 2: sustainable cell rate in cells/second
                   for CLP=0 traffic
      Parameter 3: maximum burst size in cells
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.6";
  }

  smiv2:alias "atmClpTaggingScr" {
    description
     "This traffic descriptor type is for CLP with
      tagging and Sustained Cell Rate.  The use of
      the parameter vector for this type:
      Parameter 1: peak cell rate in cells/second
                   for CLP=0+1 traffic
      Parameter 2: sustainable cell rate in cells/second
                   for CLP=0 traffic, excess tagged as
                   CLP=1
      Parameter 3: maximum burst size in cells
      Parameter 4: not used
      Parameter 5: not used.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.7";
  }

  smiv2:alias "atmClpNoTaggingMcr" {
    description
     "This traffic descriptor type is for CLP with
      Minimum Cell Rate and no tagging.  The use of
      the parameter vector for this type:
      Parameter 1: peak cell rate in cells/second
                   for CLP=0+1 traffic
      Parameter 2: CDVT in tenths of microseconds
      Parameter 3: minimum cell rate in cells/second
      Parameter 4: unused
      Parameter 5: unused.";
    reference
     "ATM Forum,ATM User-Network Interface,
      Version 3.0 (UNI 3.0) Specification, 1994.
      ATM Forum, ATM User-Network Interface,
      Version 3.1 (UNI 3.1) Specification,
      November 1994.";
    smiv2:oid "1.3.6.1.2.1.37.1.1.8";
  }

  smiv2:alias "atmClpTransparentNoScr" {
    description
     "This traffic descriptor type is for the CLP-
      transparent model and no Sustained Cell Rate.
      The use of the parameter vector for this type:
      Parameter 1: peak cell rate in cells/second
                   for CLP=0+1 traffic
      Parameter 2: CDVT in tenths of microseconds
      Parameter 3: not used
      Parameter 4: not used
      Parameter 5: not used.
      
      This traffic descriptor type is applicable to
      connections following the CBR.1 conformance
      definition.
      
      Connections specifying this traffic descriptor
      type will be rejected at UNI 3.0 or UNI 3.1
      interfaces.  For a similar traffic descriptor
      type that can be accepted at UNI 3.0 and
      UNI 3.1 interfaces, see atmNoClpNoScr.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.9";
  }

  smiv2:alias "atmClpTransparentScr" {
    description
     "This traffic descriptor type is for the CLP-
      transparent model with Sustained Cell Rate.
      The use of the parameter vector for this type:
      Parameter 1: peak cell rate in cells/second
                   for CLP=0+1 traffic
      Parameter 2: sustainable cell rate in cells/second
                   for CLP=0+1 traffic
      Parameter 3: maximum burst size in cells
      Parameter 4: CDVT in tenths of microseconds
      Parameter 5: not used.
      
      This traffic descriptor type is applicable to
      connections following the VBR.1 conformance
      definition.
      
      Connections specifying this traffic descriptor
      type will be rejected at UNI 3.0 or UNI 3.1
      interfaces.  For a similar traffic descriptor
      type that can be accepted at UNI 3.0 and
      UNI 3.1 interfaces, see atmNoClpScr.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.10";
  }

  smiv2:alias "atmNoClpTaggingNoScr" {
    description
     "This traffic descriptor type is for no CLP
      with tagging and no Sustained Cell Rate.  The
      use of the parameter vector for this type:
      Parameter 1: peak cell rate in cells/second
                   for CLP=0+1 traffic
      Parameter 2: CDVT in tenths of microseconds
      Parameter 3: not used
      Parameter 4: not used
      Parameter 5: not used.
      
      This traffic descriptor type is applicable to
      connections following the UBR.2 conformance
      definition .";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.11";
  }

  smiv2:alias "atmNoClpNoScrCdvt" {
    description
     "This traffic descriptor type is for no CLP
      and no Sustained Cell Rate.  The use of the
      parameter vector for this type:
      Parameter 1: peak cell rate in cells/second
                   for CLP=0+1 traffic
      Parameter 2: CDVT in tenths of microseconds
      Parameter 3: not used
      Parameter 4: not used
      Parameter 5: not used.
      
      This traffic descriptor type is applicable to
      CBR connections following the UNI 3.0/3.1
      conformance definition for PCR CLP=0+1.
      These CBR connections differ from CBR.1
      connections in that the CLR objective
      applies only to the CLP=0 cell flow.
      
      This traffic descriptor type is also
      applicable to connections following the UBR.1
      conformance definition.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.12";
  }

  smiv2:alias "atmNoClpScrCdvt" {
    description
     "This traffic descriptor type is for no CLP
      with Sustained Cell Rate.  The use of the
      parameter vector for this type:
      Parameter 1: peak cell rate in cells/second
                   for CLP=0+1 traffic
      Parameter 2: sustainable cell rate in cells/second
                   for CLP=0+1 traffic
      Parameter 3: maximum burst size in cells
      Parameter 4: CDVT in tenths of microseconds
      Parameter 5: not used.
      
      This traffic descriptor type is applicable
      to VBR connections following the UNI 3.0/3.1
      conformance definition for PCR CLP=0+1 and
      SCR CLP=0+1.  These VBR connections
      differ from VBR.1 connections in that
      the CLR objective applies only to the CLP=0
      cell flow.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.13";
  }

  smiv2:alias "atmClpNoTaggingScrCdvt" {
    description
     "This traffic descriptor type is for CLP with
      Sustained Cell Rate and no tagging.  The use
      of the parameter vector for this type:
      Parameter 1: peak cell rate in cells/second
                   for CLP=0+1 traffic
      Parameter 2: sustainable cell rate in cells/second
                   for CLP=0 traffic
      Parameter 3: maximum burst size in cells
      Parameter 4: CDVT in tenths of microseconds
      Parameter 5: not used.
      
      This traffic descriptor type is applicable to
      connections following the VBR.2 conformance
      definition.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.14";
  }

  smiv2:alias "atmClpTaggingScrCdvt" {
    description
     "This traffic descriptor type is for CLP with
      tagging and Sustained Cell Rate.  The use of
      the parameter vector for this type:
      Parameter 1: peak cell rate in cells/second
                   for CLP=0+1 traffic
      Parameter 2: sustainable cell rate in cells/second
                   for CLP=0 traffic, excess tagged as
                   CLP=1
      Parameter 3: maximum burst size in cells
      Parameter 4: CDVT in tenths of microseconds
      Parameter 5: not used.
      
      This traffic descriptor type is applicable to
      connections following the VBR.3 conformance
      definition.";
    reference
     "ATM Forum,ATM User-Network Interface,
      Version 3.0 (UNI 3.0) Specification, 1994.
      ATM Forum, ATM User-Network Interface,
      Version 3.1 (UNI 3.1) Specification,
      November 1994.
      ATM Forum, Traffic Management Specification,
      Version 4.0, af-tm-0056.000, June 1996.";
    smiv2:oid "1.3.6.1.2.1.37.1.1.15";
  }

  smiv2:alias "atmTCMIB" {
    smiv2:oid "1.3.6.1.2.1.37.3";
  }

  smiv2:alias "atmObjectIdentities" {
    smiv2:oid "1.3.6.1.2.1.37.3.1";
  }

}
