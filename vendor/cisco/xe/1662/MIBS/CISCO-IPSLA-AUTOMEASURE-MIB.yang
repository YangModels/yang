/*
 * Generated by confdc --mib2yang-std
 * Source: mgmt/dmi/model/common/mib-source/CISCO-IPSLA-AUTOMEASURE-MIB.mib
 */
/*
 * This YANG module has been generated by smidump 0.5.0:
 *
 *      smidump -f yang CISCO-IPSLA-AUTOMEASURE-MIB
 *
 * Do not edit. Edit the source file instead!
 */

module CISCO-IPSLA-AUTOMEASURE-MIB {

  namespace "urn:ietf:params:xml:ns:yang:smiv2:CISCO-IPSLA-AUTOMEASURE-MIB";
  prefix CISCO-IPSLA-AUTOMEASURE-MIB;

  import CISCO-IPSLA-TC-MIB {
    prefix "cisco-ipsla";
  }

  import INET-ADDRESS-MIB {
    prefix "inet-address";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  organization
   "Cisco Systems, Inc.";

  contact
   "Cisco Systems, Inc.
    Customer Service
    
    Postal: 170 W Tasman Drive
    San Jose, CA 95134
    
    Tel: +1 800 553 NETS
    Email: cs-ipsla@cisco.com";

  description
   "This module defines the MIB for IP SLA Automation. IP SLA
    Automation consists of the following:
    1. Use of grouping - Group is an aggregation of operations 
       sharing the same type, for example UDP jitter type, with 
       common characteristics like frequency, interval etc.  
       Groups are formed by policies dictated either per customer, 
       or by service level or any other requirements.  So, for 
       example, there could be separate groups for customers named 
       Customer A, Customer B etc, or service levels named 
       Gold-service, Silver-service etc.  A single group will contain 
       one and only one IP SLA operation definition or reference a 
       single template.
    2. Use of templates - It has been observed that operations can be 
       configured quickly if the variants such as IP address and 
       ports can be configured separately and then combined with a 
       template  consisting of invariants.  This allows for re-use of 
       the invariant template with various combinations of destination 
       addresses and ports, the benefits for which are multiplied when 
       considering groupings.
    3. Auto operations - With this feature the software will try to 
       automatically kickstart operations by making intelligent 
       assumptions.  For example, if no specific operation is referenced 
       by the group configuration then an ICMP jitter operation is 
       assumed by default.";

  revision 2007-06-13 {
    description
     "Initial version of this MIB module.";
  }


  container CISCO-IPSLA-AUTOMEASURE-MIB {
    config false;

    container cipslaAutoGroupTable {
      description
       "A table that contains IP SLA auto measure group definitions.";
      smiv2:oid "1.3.6.1.4.1.9.9.633.1.1";

      list cipslaAutoGroupEntry {
        key "cipslaAutoGroupName";
        description
         "An entry containing the configurations for a particular
          auto measure group.";
        smiv2:oid "1.3.6.1.4.1.9.9.633.1.1.1";

        leaf cipslaAutoGroupName {
          type snmp-framework:SnmpAdminString {
            length "1..64";
          }
          description
           "A group name which is used by a management application
            to identify the group.";
          smiv2:max-access "not-accessible";
          smiv2:oid "1.3.6.1.4.1.9.9.633.1.1.1.1";
        }

        leaf cipslaAutoGroupDescription {
          type snmp-framework:SnmpAdminString {
            length "0..128";
          }
          description
           "This field is used to provide description for the group.";
          smiv2:defval "";
          smiv2:max-access "read-write";
          smiv2:oid "1.3.6.1.4.1.9.9.633.1.1.1.2";
        }

        leaf cipslaAutoGroupDestinationName {
          type snmp-framework:SnmpAdminString {
            length "0..64";
          }
          description
           "This object refers to the cipslaAutoGroupDestName
            in cipslaAutoGroupDestTable. If the name entered 
            is not present in cipslaAutoGroupDestTable, then when 
            group is scheduled, no ip sla operations will be created.";
          smiv2:defval "";
          smiv2:max-access "read-write";
          smiv2:oid "1.3.6.1.4.1.9.9.633.1.1.1.3";
        }

        leaf cipslaAutoGroupADDestPort {
          type inet:port-number;
          description
           "This object represents the destination port number
            for auto discovery use.";
          smiv2:defval "0";
          smiv2:max-access "read-write";
          smiv2:oid "1.3.6.1.4.1.9.9.633.1.1.1.4";
        }

        leaf cipslaAutoGroupOperTemplateName {
          type snmp-framework:SnmpAdminString {
            length "0..64";
          }
          description
           "A string which is used by a management application to
            identify the template which is associated with the group.
            Depends on cipslaAutoGroupOperType, this object refers to
            cipslaIcmpEchoTmplName in cipslaIcmpEchoTmplTable, or
            cipslaUdpEchoTmplName in cipslaUdpEchoTmplTable, or
            cipslaTcpConnTmplName in cipslaTcpConnTmplTable, or
            cipslaIcmpJitterTmplName in cipslaIcmpJitterTmplTable, or
            ciscoIpSlaUdpJitterTmplName in ciscoIpSlaUdpJitterTmplTable.";
          smiv2:max-access "read-write";
          smiv2:oid "1.3.6.1.4.1.9.9.633.1.1.1.5";
        }

        leaf cipslaAutoGroupSchedulerId {
          type snmp-framework:SnmpAdminString {
            length "0..64";
          }
          description
           "This object refers to the cipslaAutoGroupSchedId in
            cipslaAutoGroupSchedTable, and is used to schedule 
            this group.";
          smiv2:defval "";
          smiv2:max-access "read-write";
          smiv2:oid "1.3.6.1.4.1.9.9.633.1.1.1.6";
        }

        leaf cipslaAutoGroupQoSEnable {
          type boolean;
          description
           "When this object is set to true, QoS is enabled for this
            group and this group is linked to policy map. The 
            restriction is that after QoS is enabled, it can not be 
            disabled for this group.";
          smiv2:defval "false";
          smiv2:max-access "read-write";
          smiv2:oid "1.3.6.1.4.1.9.9.633.1.1.1.7";
        }

        leaf cipslaAutoGroupOperType {
          type cisco-ipsla:IpSlaOperType;
          description
           "This object specifies the type of IP SLA operation.
            When operation type is not ICMP jitter, then 
            cipslaAutoGroupOperTemplateName must be specified.";
          smiv2:max-access "read-write";
          smiv2:oid "1.3.6.1.4.1.9.9.633.1.1.1.8";
        }

        leaf cipslaAutoGroupDestIPADEnable {
          type boolean;
          description
           "When this object is set to true, destination IP address
            is populated through auto-discovery.";
          smiv2:defval "false";
          smiv2:max-access "read-write";
          smiv2:oid "1.3.6.1.4.1.9.9.633.1.1.1.9";
        }

        leaf cipslaAutoGroupADMeasureRetry {
          type uint32 {
            range "1..65536";
          }
          description
           "This object specifies number of measurement retries to
            be attempted for the discovered end point after the 
            connection to the end point is broken. If there is no 
            re-registration message received, the end point will be 
            in inactive state.
            
            When the value of cipslaAutoGroupDestIPADEnable is 
            'false', the value of this object has no effect.";
          smiv2:defval "3";
          smiv2:max-access "read-write";
          smiv2:oid "1.3.6.1.4.1.9.9.633.1.1.1.10";
        }

        leaf cipslaAutoGroupADDestIPAgeout {
          type uint32 {
            range "0..65536";
          }
          units "seconds";
          description
           "This object represents the ageout time for the discovered
            end point.  If the end point becomes inactive for the period 
            of ageout time, the end point will be removed from the 
            discovered end point list.
            
            When the value of cipslaAutoGroupDestIPADEnable is 
            'false', the value of this object has no effect.";
          smiv2:defval "3600";
          smiv2:max-access "read-write";
          smiv2:oid "1.3.6.1.4.1.9.9.633.1.1.1.11";
        }

        leaf cipslaAutoGroupStorageType {
          type snmpv2-tc:StorageType;
          description
           "The storage type of this conceptual row.";
          smiv2:defval "nonVolatile";
          smiv2:max-access "read-write";
          smiv2:oid "1.3.6.1.4.1.9.9.633.1.1.1.12";
        }

        leaf cipslaAutoGroupRowStatus {
          type snmpv2-tc:RowStatus;
          description
           "The status of the conceptual group control row.
            
            When the status is active, the other writable objects
            may be modified unless the scheduler with name 
            specified by cipslaAutoGroupSchedulerId is scheduled.";
          smiv2:max-access "read-write";
          smiv2:oid "1.3.6.1.4.1.9.9.633.1.1.1.13";
        }
      }
    }

    container cipslaAutoGroupDestTable {
      description
       "A table contains the list of destination IP
        addresses and ports associated to the auto measure
        group destination name.";
      smiv2:oid "1.3.6.1.4.1.9.9.633.1.2";

      list cipslaAutoGroupDestEntry {
        key "cipslaAutoGroupDestName cipslaAutoGroupDestIpAddrType cipslaAutoGroupDestIpAddr cipslaAutoGroupDestPort";
        description
         "An entry containing the destination IP addresses
          and port configurations associated to auto measure
          group destination name.";
        smiv2:oid "1.3.6.1.4.1.9.9.633.1.2.1";

        leaf cipslaAutoGroupDestName {
          type snmp-framework:SnmpAdminString {
            length "1..64";
          }
          description
           "This is the name for an auto measure group destination.";
          smiv2:max-access "not-accessible";
          smiv2:oid "1.3.6.1.4.1.9.9.633.1.2.1.1";
        }

        leaf cipslaAutoGroupDestIpAddrType {
          type inet-address:InetAddressType;
          description
           "The type of the internet address of a destination
            for an auto measure group.";
          smiv2:max-access "not-accessible";
          smiv2:oid "1.3.6.1.4.1.9.9.633.1.2.1.2";
        }

        leaf cipslaAutoGroupDestIpAddr {
          type inet-address:InetAddress;
          description
           "The internet address of a destination for an auto
            measure group. The type of this address is determined
            by the value of cipslaAutoGroupDestIpAddrType.";
          smiv2:max-access "not-accessible";
          smiv2:oid "1.3.6.1.4.1.9.9.633.1.2.1.3";
        }

        leaf cipslaAutoGroupDestPort {
          type inet:port-number;
          description
           "This object represents the destination port number.
            For ICMP echo and ICMP jitter, the suggested value is 
            '0'.";
          smiv2:max-access "not-accessible";
          smiv2:oid "1.3.6.1.4.1.9.9.633.1.2.1.4";
        }

        leaf cipslaAutoGroupDestStorageType {
          type snmpv2-tc:StorageType;
          description
           "The storage type of this conceptual row.
            
            By default the entry will be saved into non-volatile
            memory.";
          smiv2:defval "nonVolatile";
          smiv2:max-access "read-write";
          smiv2:oid "1.3.6.1.4.1.9.9.633.1.2.1.5";
        }

        leaf cipslaAutoGroupDestRowStatus {
          type snmpv2-tc:RowStatus;
          description
           "The status of the conceptual destination table control row.
            No other objects in this row need to be set before this object
            can become active.
            
            During 'destroy', when cipslaAutoGroupDestIpAddr is specified 
            as '0.0.0.0' and cipslaAutoGroupDestPort is specified as '0', 
            then all the rows with same cipslaAutoGroupDestName will be 
            deleted.";
          smiv2:max-access "read-write";
          smiv2:oid "1.3.6.1.4.1.9.9.633.1.2.1.6";
        }
      }
    }

    container cipslaReactTable {
      description
       "A table that contains reaction configurations for templates.
        Each conceptual row in cipslaReactTable corresponds 
        to a reaction configured for one template.
        
        Each template can have multiple reactions and hence there can be 
        multiple rows for a particular template. Different template
        types can have different reactions. The reaction type is 
        specified as cipslaReactVar based upon template type as some 
        reaction types are applicable just for specific template types.";
      smiv2:oid "1.3.6.1.4.1.9.9.633.1.3";

      list cipslaReactEntry {
        key "cipslaAutoGroupOperType cipslaReactConfigIndex cipslaAutoGroupOperTemplateName";
        description
         "A base list of objects that define a conceptual reaction
          configuration control row.";
        smiv2:oid "1.3.6.1.4.1.9.9.633.1.3.1";

        leaf cipslaAutoGroupOperType {
          type leafref {
            path "/CISCO-IPSLA-AUTOMEASURE-MIB:CISCO-IPSLA-AUTOMEASURE-MIB/CISCO-IPSLA-AUTOMEASURE-MIB:cipslaAutoGroupTable/CISCO-IPSLA-AUTOMEASURE-MIB:cipslaAutoGroupEntry/CISCO-IPSLA-AUTOMEASURE-MIB:cipslaAutoGroupOperType";
          }
        }

        leaf cipslaAutoGroupOperTemplateName {
          type leafref {
            path "/CISCO-IPSLA-AUTOMEASURE-MIB:CISCO-IPSLA-AUTOMEASURE-MIB/CISCO-IPSLA-AUTOMEASURE-MIB:cipslaAutoGroupTable/CISCO-IPSLA-AUTOMEASURE-MIB:cipslaAutoGroupEntry/CISCO-IPSLA-AUTOMEASURE-MIB:cipslaAutoGroupOperTemplateName";
          }
        }

        leaf cipslaReactConfigIndex {
          type uint32 {
            range "1..2147483647";
          }
          description
           "This object along with cipslaAutoGroupOperType and
            cipslaAutoGroupOperTemplateName identifies
            a particular reaction-configuration for one IP SLA 
            template.
            
            This number is persistent across reboots.";
          smiv2:max-access "not-accessible";
          smiv2:oid "1.3.6.1.4.1.9.9.633.1.3.1.1";
        }

        leaf cipslaReactVar {
          type cisco-ipsla:IpSlaReactVar;
          description
           "This object specifies the type of reaction configured for an
            IP SLA template. Default value is 'rtt' for ICMP echo, UDP echo
            and TCP connect. Default value is 'jitterAvg' for UDP jitter and 
            ICMP jitter.
            
            The reaction types 'rtt', 'timeout', 'connectionLoss' and
            'verifyError' can be configured for all template types.
            
            The reaction types 'jitterSDAvg', 'jitterDSAvg', 'jitterAvg', 
            'packetLateArrival', 'packetOutOfSequence', 
            'maxOfPositiveSD', 'maxOfNegativeSD', 'maxOfPositiveDS'
            'maxOfNegativeDS', 'mos' and 'icpif' can be configured for 
            UDP jitter and ICMP jitter types only.
            
            The reaction types 'packetLossDS', 'packetLossSD' and 
            'packetMIA' can be configured for UDP jitter type only.
            
            The reaction types 'successivePacketLoss', 'maxOfLatencyDS', 
            'maxOfLatencySD', 'latencyDSAvg', 'latencySDAvg' and 
            'packetLoss' can be configured for ICMP jitter type only.";
          smiv2:max-access "read-write";
          smiv2:oid "1.3.6.1.4.1.9.9.633.1.3.1.2";
        }

        leaf cipslaReactThresholdType {
          type enumeration {
            enum "never" {
              value "1";
            }
            enum "immediate" {
              value "2";
            }
            enum "consecutive" {
              value "3";
            }
            enum "xOfy" {
              value "4";
            }
            enum "average" {
              value "5";
            }
          }
          description
           "This object specifies the conditions under which
            a notification ( trap ) is sent. The rttMonReactOccurred
            object defined in rttMonReactTable in CISCO-RTTMON-MIB will
            change accordingly:
            
            never(1)       - rttMonReactOccurred is never set
            
            immediate(2)   - rttMonReactOccurred is set to 'true' when the
                             value of parameter for which reaction is
                             configured ( e.g rtt, jitterAvg, packetLossSD,
                             mos etc ) violates the threshold.
                             Conversely, rttMonReactOccurred is set to 'false'
                             when the parameter ( e.g rtt, jitterAvg,
                             packetLossSD, mos etc ) is below the threshold
                             limits.
            
            consecutive(3) - rttMonReactOccurred is set to true when the value
                             of parameter for which reaction is configured
                             ( e.g rtt, jitterAvg, packetLossSD, mos etc )
                             violates the threshold for configured consecutive
                             times.
                             Conversely, rttMonReactOccurred is set to false
                             when the value of parameter ( e.g rtt, jitterAvg
                             packetLossSD, mos etc ) is below the threshold
                             limits for the same number of consecutive
                             operations.
            
            xOfy(4)        - rttMonReactOccurred is set to true when x
                             ( as specified by cipslaReactThresholdCountX )
                             out of the last y ( as specified by
                             cipslaReacthresholdCountY ) times the value of
                             parameter for which the reaction is configured
                             ( e.g rtt, jitterAvg, packetLossSD, mos etc )
                             violates the threshold.
                             Conversely, it is set to false when x, out of the
                             last y times the value of parameter
                             ( e.g rtt, jitterAvg, packetLossSD, mos ) is
                             below the threshold limits.
                             NOTE: If x > y, this will never
                                  generate a reaction.
            
            average(5)    - rttMonReactOccurred is set to true when the
                            average ( cipslaReactThresholdCountX times )
                            value of parameter for which reaction is 
                            configured ( e.g rtt, jitterAvg, packetLossSD,
                            mos etc ) violates the threshold condition.
                            Conversely, it is set to false when the
                            average value of parameter ( e.g rtt, jitterAvg,
                            packetLossSD, mos etc ) is below the threshold
                            limits.
            
            If this value is changed by a management station,
            rttMonReactOccurred is set to false, but
            no reaction is generated if the prior value of
            rttMonReactOccurred was true.";
          smiv2:defval "never";
          smiv2:max-access "read-write";
          smiv2:oid "1.3.6.1.4.1.9.9.633.1.3.1.3";
        }

        leaf cipslaReactActionType {
          type enumeration {
            enum "none" {
              value "1";
            }
            enum "notificationOnly" {
              value "2";
            }
          }
          description
           "Specifies what type, if any, of reaction to
            generate if one of the watched
            (reaction-configuration ) conditions is satisfied:
            
            none(1)                - no reaction is generated
            notificationOnly(2)    - a notification is generated";
          smiv2:defval "none";
          smiv2:max-access "read-write";
          smiv2:oid "1.3.6.1.4.1.9.9.633.1.3.1.4";
        }

        leaf cipslaReactThresholdRising {
          type uint32;
          description
           "This object defines the higher threshold limit.
            If the value ( e.g rtt, jitterAvg, packetLossSD etc ) rises
            above this limit and if the condition specified in
            cipslaReactThresholdType is satisfied, a notification is 
            generated.
            
            Default value of cipslaReactThresholdRising for
               'rtt' is 5000
               'jitterAvg' is 100.
               'jitterSDAvg' is 100.
               'jitterDSAvg' 100.
               'packetLossSD' is 10000.
               'packetLossDS' is 10000.
               'mos' is 500.
               'icpif' is 93.
               'packetMIA' is 10000.
               'packetLateArrival' is 10000.
               'packetOutOfSequence' is 10000.
               'maxOfPositiveSD' is 10000.
               'maxOfNegativeSD' is 10000.
               'maxOfPositiveDS' is 10000.
               'maxOfNegativeDS' is 10000.
               'successivePacketLoss' is 1000.
               'maxOfLatencyDS' is 5000.
               'maxOfLatencySD' is 5000.
               'latencyDSAvg' is 5000.
               'latencySDAvg' is 5000.
               'packetLoss' is 10000.
            
            This object is not applicable if the cipslaReactVar is
            'timeout', 'connectionLoss' or 'verifyError'. For 'timeout',
            'connectionLoss' and 'verifyError' default value of 
            cipslaReactThresholdRising will be 0.";
          smiv2:max-access "read-write";
          smiv2:oid "1.3.6.1.4.1.9.9.633.1.3.1.5";
        }

        leaf cipslaReactThresholdFalling {
          type uint32;
          description
           "This object defines a lower threshold limit. If the
            value ( e.g rtt, jitterAvg, packetLossSD etc ) falls
            below this limit and if the condition specified in
            cipslaReactThresholdType is satisfied, a notification 
            is generated. This object value can not bigger than
            cipslaReactThresholdRising value.
            
            Default value of cipslaReactThresholdFalling
               'rtt' is 3000
               'jitterAvg' is 100.
               'jitterSDAvg' is 100.
               'jitterDSAvg' 100.
               'packetLossSD' is 10000.
               'packetLossDS' is 10000.
               'mos' is 500.
               'icpif' is 93.
               'packetMIA' is 10000.
               'packetLateArrival' is 10000.
               'packetOutOfSequence' is 10000.
               'maxOfPositiveSD' is 10000.
               'maxOfNegativeSD' is 10000.
               'maxOfPositiveDS' is 10000.
               'maxOfNegativeDS' is 10000.
               'successivePacketLoss' is 1000.
               'maxOfLatencyDS' is 3000.
               'maxOfLatencySD' is 3000.
               'latencyDSAvg' is 3000.
               'latencySDAvg' is 3000.
               'packetLoss' is 10000.
            
            This object is not applicable if the cipslaReactVar is
            'timeout', 'connectionLoss' or 'verifyError'. For 'timeout',
            'connectionLoss' and 'verifyError', default value of
            cipslaReactThresholdFalling will be 0.";
          smiv2:max-access "read-write";
          smiv2:oid "1.3.6.1.4.1.9.9.633.1.3.1.6";
        }

        leaf cipslaReactThresholdCountX {
          type uint32 {
            range "1..16";
          }
          description
           "If cipslaReactThresholdType value is 'xOfy', this object
            defines the 'x' value.
            
            If cipslaReactThresholdType value is 'consecutive'
            this object defines the number of consecutive occurrences
            that needs threshold violation before setting 
            cipslaReactOccurred as true.
            
            If cipslaReactThresholdType value is 'average' this object
            defines the number of samples that needs be considered for
            calculating average.
            
            This object has no meaning if cipslaReactThresholdType has
            value of 'never' and 'immediate'.";
          smiv2:defval "5";
          smiv2:max-access "read-write";
          smiv2:oid "1.3.6.1.4.1.9.9.633.1.3.1.7";
        }

        leaf cipslaReactThresholdCountY {
          type uint32 {
            range "1..16";
          }
          description
           "This object defines the 'y' value of the xOfy condition
            if cipslaReactThresholdType is 'xOfy'. The default for the 
            'y' value is 5.
            
            For other values of cipslaReactThresholdType, this object
            is not applicable.";
          smiv2:max-access "read-write";
          smiv2:oid "1.3.6.1.4.1.9.9.633.1.3.1.8";
        }

        leaf cipslaReactStorageType {
          type snmpv2-tc:StorageType;
          description
           "The storage type of this conceptual row.
            
            By default the entry will be saved into non-volatile
            memory.";
          smiv2:defval "nonVolatile";
          smiv2:max-access "read-write";
          smiv2:oid "1.3.6.1.4.1.9.9.633.1.3.1.9";
        }

        leaf cipslaReactRowStatus {
          type snmpv2-tc:RowStatus;
          description
           "This objects indicates the status of the conceptual
            Reaction Control Row. 
            
            When this object moves to active state, the conceptual row 
            is monitored and notifications are generated when threshold 
            violation takes place.
            
            In order for this object to become active cipslaReactVar must
            be defined. All other objects assume default values.  When the 
            status is active, the following objects in that row can be 
            modified.
             cipslaReactThresholdType,
             cipslaReactActionType,
             cipslaReactThresholdRising,
             cipslaReactThresholdFalling,
             cipslaReactThresholdCountX,
             cipslaReactThresholdCountY,
             cipslaReactStorageType
            
            This object can be set to 'destroy' from any value at any time.
            When this object is set to 'destroy' no reaction configuration
            would exist. The reaction configuration for the template is 
            removed.";
          smiv2:max-access "read-write";
          smiv2:oid "1.3.6.1.4.1.9.9.633.1.3.1.10";
        }
      }
    }

    container cipslaAutoGroupSchedTable {
      description
       "A table of group scheduling definitions.";
      smiv2:oid "1.3.6.1.4.1.9.9.633.1.4";

      list cipslaAutoGroupSchedEntry {
        key "cipslaAutoGroupSchedId";
        description
         "A list of objects that define specific configuration for
          group scheduling.";
        smiv2:oid "1.3.6.1.4.1.9.9.633.1.4.1";

        leaf cipslaAutoGroupSchedId {
          type snmp-framework:SnmpAdminString {
            length "1..64";
          }
          description
           "This string uniquely identifies a row in the
            cipslaAutoGroupSchedTable.";
          smiv2:max-access "not-accessible";
          smiv2:oid "1.3.6.1.4.1.9.9.633.1.4.1.1";
        }

        leaf cipslaAutoGroupSchedPeriod {
          type uint32 {
            range "100..99000";
          }
          units "seconds";
          description
           "Specifies the time duration between initiating two
            IP SLA operations generated via the auto measure group.";
          smiv2:defval "1000";
          smiv2:max-access "read-write";
          smiv2:oid "1.3.6.1.4.1.9.9.633.1.4.1.2";
        }

        leaf cipslaAutoGroupSchedInterval {
          type uint32 {
            range "1..604800";
          }
          units "seconds";
          description
           "Specifies the duration between initiating each RTT
            operation for one IP SLA operation generated via the auto 
            measure group.
            
            The value of this object is only effective when both
            cipslaAutoGroupSchedMaxInterval and 
            cipslaAutoGroupSchedMinInterval have zero values.";
          smiv2:defval "60";
          smiv2:max-access "read-write";
          smiv2:oid "1.3.6.1.4.1.9.9.633.1.4.1.3";
        }

        leaf cipslaAutoGroupSchedLife {
          type uint32 {
            range "0..2147483647";
          }
          units "seconds";
          description
           "This object specifies the life of all the operations that are
            getting group scheduled. This value will be placed into
            cipslaAutoGroupSchedRttLife object when this conceptual control
            row becomes 'active'.
            
            The value 2147483647 has a special meaning. When this object is
            set to 2147483647, the rttMonCtrlOperRttLife object for all the
            operations will not decrement, and thus the life time of the 
            operation will never end.";
          smiv2:defval "3600";
          smiv2:max-access "read-write";
          smiv2:oid "1.3.6.1.4.1.9.9.633.1.4.1.4";
        }

        leaf cipslaAutoGroupSchedAgeout {
          type uint32 {
            range "0..2073600";
          }
          units "seconds";
          description
           "This object specifies the ageout value of the operations that are
            getting group scheduled. This value will be placed into
            rttMonSchedAdminConceptRowAgeout object for each of the
            operations in the group when this conceptual control row becomes 
            'active'.
            
            When this value is set to zero, the operations will never ageout.";
          smiv2:defval "3600";
          smiv2:max-access "read-write";
          smiv2:oid "1.3.6.1.4.1.9.9.633.1.4.1.5";
        }

        leaf cipslaAutoGroupSchedMaxInterval {
          type uint32 {
            range "0..604800";
          }
          units "seconds";
          description
           "Specifies the max duration between initiating each RTT
            operation for one IP SLA operation in the group.";
          smiv2:defval "0";
          smiv2:max-access "read-write";
          smiv2:oid "1.3.6.1.4.1.9.9.633.1.4.1.6";
        }

        leaf cipslaAutoGroupSchedMinInterval {
          type uint32 {
            range "0..604800";
          }
          units "seconds";
          description
           "Specifies the min duration between initiating each RTT
            operation for one IP SLA operation in the group.
            
            The value of this object should be lower than the value of
            cipslaAutoGroupSchedMaxInterval.";
          smiv2:defval "0";
          smiv2:max-access "read-write";
          smiv2:oid "1.3.6.1.4.1.9.9.633.1.4.1.7";
        }

        leaf cipslaAutoGroupSchedStartTime {
          type uint32 {
            range "0..604800";
          }
          units "seconds";
          description
           "This is the time in seconds after which the operations of
            the associated groups  will take transition to active state.
            When set to the value other than '1' (pending), then all 
            objects in this row cannot be modified.";
          smiv2:defval "1";
          smiv2:max-access "read-write";
          smiv2:oid "1.3.6.1.4.1.9.9.633.1.4.1.8";
        }

        leaf cipslaAutoGroupSchedStorageType {
          type snmpv2-tc:StorageType;
          description
           "The storage type of this conceptual row.
            
            By default the entry will be saved into non-volatile
            memory.";
          smiv2:defval "nonVolatile";
          smiv2:max-access "read-write";
          smiv2:oid "1.3.6.1.4.1.9.9.633.1.4.1.9";
        }

        leaf cipslaAutoGroupSchedRowStatus {
          type snmpv2-tc:RowStatus;
          description
           "The status of the conceptual group schedule control row.
            
            When the status is active and the value of 
            cipslaAutoGroupSchedStartTime is '1', the other writable 
            objects may be modified.
            
            This object can be set to 'destroy' from any value at any time.
            When this object is set to 'destroy' it will stop all the 
            operations which had been group scheduled by it earlier, 
            before destroying the group schedule control row.";
          smiv2:max-access "read-write";
          smiv2:oid "1.3.6.1.4.1.9.9.633.1.4.1.10";
        }
      }
    }
  }

  smiv2:alias "ciscoIpSlaAutoMIB" {
    smiv2:oid "1.3.6.1.4.1.9.9.633";
  }

  smiv2:alias "ciscoIpSlaAutoMIBNotifs" {
    smiv2:oid "1.3.6.1.4.1.9.9.633.0";
  }

  smiv2:alias "ciscoIpSlaAutoMIBObjects" {
    smiv2:oid "1.3.6.1.4.1.9.9.633.1";
  }

  smiv2:alias "ciscoIpSlaAutoMIBConform" {
    smiv2:oid "1.3.6.1.4.1.9.9.633.2";
  }

  smiv2:alias "ciscoIpSlaAutoMIBCompliances" {
    smiv2:oid "1.3.6.1.4.1.9.9.633.2.1";
  }

  smiv2:alias "ciscoIpSlaAutoMIBGroups" {
    smiv2:oid "1.3.6.1.4.1.9.9.633.2.2";
  }

}
