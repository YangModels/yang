/*
 * Generated by confdc --mib2yang-std
 * Source: mgmt/dmi/model/common/mib-source/CISCO-FTP-CLIENT-MIB.mib
 */
/*
 * This YANG module has been generated by smidump 0.5.0:
 *
 *      smidump -f yang CISCO-FTP-CLIENT-MIB
 *
 * Do not edit. Edit the source file instead!
 */

module CISCO-FTP-CLIENT-MIB {

  namespace "urn:ietf:params:xml:ns:yang:smiv2:CISCO-FTP-CLIENT-MIB";
  prefix CISCO-FTP-CLIENT-MIB;

  import SNMPv2-TC {
    prefix "snmpv2-tc";
  }

  import ietf-yang-smiv2 {
    prefix "smiv2";
  }

  import ietf-yang-types {
    prefix "yang";
  }

  organization
   "Cisco Systems, Inc.";

  contact
   "Cisco Systems
    Customer Service
    
    Postal: 170 W Tasman Drive
    San Jose, CA  95134
    USA
    
    Tel: +1 800 553-NETS
    
    E-mail: cs-snmp@cisco.com";

  description
   "The MIB module for invoking Internet File Transfer Protocol
    (FTP) operations for network management purposes.";

  revision 2006-03-31 {
    description
     "Updated the imports such that Unsigned32 is imported from
      SNMPv2-SMI instead of CISCO-TC.";
  }

  revision 1997-10-09 {
    description
     "Initial version.";
  }


  container CISCO-FTP-CLIENT-MIB {
    config false;

    container cfcRequest {
      smiv2:oid "1.3.6.1.4.1.9.9.80.1.1";

      leaf cfcRequestMaximum {
        type uint32 {
          range "0..4294967295";
        }
        description
         "The maximum number of requests this system can hold in
          cfcRequestTable.  A value of 0 indicates no configured limit.
          
          This object may be read-only on some systems.
          
          When an attempt is made to create a new entry but the table
          is full, the oldest completed entry is bumped out and
          cfcRequestsBumped is incremented.
          
          Changing this number does not disturb existing requests that
          are not completed and bumps completed requests as necessary.";
        smiv2:max-access "read-write";
        smiv2:oid "1.3.6.1.4.1.9.9.80.1.1.1";
      }

      leaf cfcRequests {
        type yang:gauge32;
        description
         "The current number of requests in cfcRequestTable.";
        smiv2:max-access "read-only";
        smiv2:oid "1.3.6.1.4.1.9.9.80.1.1.2";
      }

      leaf cfcRequestsHigh {
        type yang:gauge32;
        description
         "The highest number of requests in cfcRequestTable since this
          system was last initialized.";
        smiv2:max-access "read-only";
        smiv2:oid "1.3.6.1.4.1.9.9.80.1.1.3";
      }

      leaf cfcRequestsBumped {
        type yang:counter32;
        description
         "The number of requests in cfcRequestTable that were bumped
          out to make room for a new request.";
        smiv2:max-access "read-only";
        smiv2:oid "1.3.6.1.4.1.9.9.80.1.1.4";
      }
    }

    container cfcRequestTable {
      description
       "A table of FTP client requests.";
      smiv2:oid "1.3.6.1.4.1.9.9.80.1.1.5";

      list cfcRequestEntry {
        key "cfcRequestIndex";
        description
         "Information about an FTP client request.  Management applications
          use cfcRequestEntryStatus to control entry modification, creation,
          and deletion.
          
          Setting cfcRequestEntryStatus to 'active' from any state including
          'active' causes the operation to be started.
          
          The entry may be modified only when cfcRequestOperationState is
          'stopped'.
          
          The value of cfcRequestEntryStatus may be set to 'destroy' at any
          time.  Doing so will abort a running request.
          
          Entries may not be created without explicitly setting
          cfcRequestEntryStatus to either 'createAndGo' or 'createAndWait'.";
        smiv2:oid "1.3.6.1.4.1.9.9.80.1.1.5.1";

        leaf cfcRequestIndex {
          type uint32 {
            range "1..4294967295";
          }
          description
           "An arbitrary integer to uniquely identify this entry.  To
            create an entry a management application should pick a
            random number.";
          smiv2:max-access "not-accessible";
          smiv2:oid "1.3.6.1.4.1.9.9.80.1.1.5.1.1";
        }

        leaf cfcRequestOperation {
          type enumeration {
            enum "putBinary" {
              value "1";
            }
            enum "putASCII" {
              value "2";
            }
          }
          description
           "The FTP operation to be performed.";
          smiv2:defval "putBinary";
          smiv2:max-access "read-write";
          smiv2:oid "1.3.6.1.4.1.9.9.80.1.1.5.1.2";
        }

        leaf cfcRequestLocalFile {
          type snmpv2-tc:DisplayString {
            length "1..255";
          }
          description
           "The local file on which the operation is to be performed.";
          smiv2:max-access "read-write";
          smiv2:oid "1.3.6.1.4.1.9.9.80.1.1.5.1.3";
        }

        leaf cfcRequestRemoteFile {
          type snmpv2-tc:DisplayString {
            length "1..255";
          }
          description
           "The remote file on which the operation is to be performed.";
          smiv2:max-access "read-write";
          smiv2:oid "1.3.6.1.4.1.9.9.80.1.1.5.1.4";
        }

        leaf cfcRequestServer {
          type snmpv2-tc:DisplayString {
            length "1..64";
          }
          description
           "The domain name or IP address of the FTP server to use.";
          smiv2:max-access "read-write";
          smiv2:oid "1.3.6.1.4.1.9.9.80.1.1.5.1.5";
        }

        leaf cfcRequestUser {
          type snmpv2-tc:DisplayString {
            length "1..32";
          }
          description
           "The user name to use at the FTP server.";
          smiv2:max-access "read-write";
          smiv2:oid "1.3.6.1.4.1.9.9.80.1.1.5.1.6";
        }

        leaf cfcRequestPassword {
          type snmpv2-tc:DisplayString {
            length "0..16";
          }
          description
           "The password to use at the FTP server.
            
            When read this object always returns a zero-length string.";
          smiv2:defval "";
          smiv2:max-access "read-write";
          smiv2:oid "1.3.6.1.4.1.9.9.80.1.1.5.1.7";
        }

        leaf cfcRequestResult {
          type enumeration {
            enum "pending" {
              value "1";
            }
            enum "success" {
              value "2";
            }
            enum "aborted" {
              value "3";
            }
            enum "fileOpenFailLocal" {
              value "4";
            }
            enum "fileOpenFailRemote" {
              value "5";
            }
            enum "badDomainName" {
              value "6";
            }
            enum "unreachableIpAddress" {
              value "7";
            }
            enum "linkFailed" {
              value "8";
            }
            enum "fileReadFailed" {
              value "9";
            }
            enum "fileWriteFailed" {
              value "10";
            }
          }
          description
           "The result of the FTP operation.";
          smiv2:max-access "read-only";
          smiv2:oid "1.3.6.1.4.1.9.9.80.1.1.5.1.8";
        }

        leaf cfcRequestCompletionTime {
          type yang:timestamp;
          description
           "The value of sysUpTime when the operation completed.  For
            an incomplete operation this value is zero.";
          smiv2:max-access "read-only";
          smiv2:oid "1.3.6.1.4.1.9.9.80.1.1.5.1.9";
        }

        leaf cfcRequestStop {
          type enumeration {
            enum "ready" {
              value "1";
            }
            enum "stop" {
              value "2";
            }
          }
          description
           "The action control to stop a running request.  Setting this to
            'stop' will begin the process of stopping the request.  Setting
            it to 'ready' or setting it to 'stop' more than once have no
            effect.  When read this object always returns ready.";
          smiv2:max-access "read-write";
          smiv2:oid "1.3.6.1.4.1.9.9.80.1.1.5.1.10";
        }

        leaf cfcRequestOperationState {
          type enumeration {
            enum "running" {
              value "1";
            }
            enum "stopping" {
              value "2";
            }
            enum "stopped" {
              value "3";
            }
          }
          description
           "The operational state of the file transfer.  To short-terminate
            the transfer set cfcRequestStop to 'stop'.";
          smiv2:max-access "read-only";
          smiv2:oid "1.3.6.1.4.1.9.9.80.1.1.5.1.11";
        }

        leaf cfcRequestEntryStatus {
          type snmpv2-tc:RowStatus;
          description
           "The control that allows modification, creation, and deletion
            of entries.  For detailed rules see the DESCRIPTION for
            cfcRequestEntry.";
          smiv2:max-access "read-write";
          smiv2:oid "1.3.6.1.4.1.9.9.80.1.1.5.1.12";
        }
      }
    }
  }

  smiv2:alias "ciscoFtpClientMIB" {
    smiv2:oid "1.3.6.1.4.1.9.9.80";
  }

  smiv2:alias "ciscoFtpClientMIBObjects" {
    smiv2:oid "1.3.6.1.4.1.9.9.80.1";
  }

  smiv2:alias "cfcRequest" {
    smiv2:oid "1.3.6.1.4.1.9.9.80.1.1";
  }

  smiv2:alias "ciscoFtpClientMIBConformance" {
    smiv2:oid "1.3.6.1.4.1.9.9.80.3";
  }

  smiv2:alias "ciscoFtpClientMIBCompliances" {
    smiv2:oid "1.3.6.1.4.1.9.9.80.3.1";
  }

  smiv2:alias "ciscoFtpClientMIBGroups" {
    smiv2:oid "1.3.6.1.4.1.9.9.80.3.2";
  }

}
