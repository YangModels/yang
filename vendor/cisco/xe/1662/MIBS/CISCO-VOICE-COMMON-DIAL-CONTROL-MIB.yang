/*
 * Generated by confdc --mib2yang-std
 * Source: mgmt/dmi/model/common/mib-source/CISCO-VOICE-COMMON-DIAL-CONTROL-MIB.mib
 */
/*
 * This YANG module has been generated by smidump 0.5.0:
 *
 *      smidump -f yang CISCO-VOICE-COMMON-DIAL-CONTROL-MIB
 *
 * Do not edit. Edit the source file instead!
 */

module CISCO-VOICE-COMMON-DIAL-CONTROL-MIB {

  namespace "urn:ietf:params:xml:ns:yang:smiv2:CISCO-VOICE-COMMON-DIAL-CONTROL-MIB";
  prefix CISCO-VOICE-COMMON-DIAL-CONTROL-MIB;

  import CISCO-DIAL-CONTROL-MIB {
    prefix "cisco-dial";
  }

  import DIAL-CONTROL-MIB {
    prefix "dial-control";
  }

  import SNMP-FRAMEWORK-MIB {
    prefix "snmp-framework";
  }

  import ietf-yang-smiv2 {
    prefix "smiv2";
  }

  import ietf-yang-types {
    prefix "yang";
  }

  organization
   "Cisco Systems, Inc.";

  contact
   "Cisco Systems
    Customer Service
    
    Postal: 170 W. Tasman Drive
    San Jose, CA  95134
    USA
    
    Tel: +1 800 553-NETS
    
    E-mail: cs-voice@cisco.com";

  description
   "This MIB module contains voice related objects that
    are common across more than one network
    encapsulation i.e VoIP, VoATM and VoFR.
    
    *** ABBREVIATIONS, ACRONYMS AND SYMBOLS ***
    
    GSM    - Global System for Mobile Communication
    
    AMR-NB - Adaptive Multi Rate - Narrow Band
    
    iLBC   - internet Low Bitrate Codec
    
    iSAC   - internet Speech Audio Codec";

  revision 2010-06-30 {
    description
     "Added CvcCallReferenceIdOrZero textual convention.
      Added aaclc and aacld enum to CvcCoderTypeRate and
      CvcSpeechCoderRate textual conventions.";
  }

  revision 2009-03-18 {
    description
     "[1] Added acronym for iSAC codec
      [2] Added iSAC enum to CvcSpeechCoderRate and CvcCoderTypeRate  
          textual conventions.";
  }

  revision 2008-07-02 {
    description
     "[1] Added '-- obsolete' to description of 'g722'
      enum from CvcCoderTypeRate.
      [2] Added new enum values 'g722r4800', 'g722r5600'
      and 'g722r6400' to CvcCoderTypeRate.
      [3] Added new enum values 'g722r4800', 'g722r5600'
      and 'g722r6400' to CvcSpeechCoderRate.";
  }

  revision 2007-06-26 {
    description
     "[1] Imported TEXTUAL-CONVENTION from SNMPv2-TC.
      [2] Added acronyms for GSM AMR-NB and iLBC codecs
      [3] Added llcc, gsmAmrNb, iLBC, iLBCr15200 and iLBCr13330
          enums to CvcSpeechCoderRate textual conventions.
      [4] Added llcc, gsmAmrNb, g722, iLBC, iLBCr15200 and iLBCr13330 
          enums to CvcCoderTypeRate textual conventions.
      [5] Added REFERENCE clause to CvcSpeechCoderRate and
          CvcCoderTypeRate textual conventions for GSM AMR-NB and
          iLBC codecs.";
  }

  revision 2005-08-16 {
    description
     "Added CvcH320CallType and CvcVideoCoderRate objects.
      Added g722 enum to CvcCoderTypeRate textual conventions.";
  }

  revision 2005-03-06 {
    description
     "Added gsmAmrNb enum to CvcSpeechCoderRate and CvcCoderTypeRate
      textual conventions.";
  }

  revision 2003-03-11 {
    description
     "Added new enum value 'llcc', to CvcSpeechCoderRate
      and CvcCoderTypeRate textual-conventions.";
  }

  revision 2001-10-06 {
    description
     "[1] Added new enum value 'g726r40000',to CvcSpeechCoderRate's
      and CvcCoderTypeRate's textual-conventions.
      [2] Replaced 'clearch' enum with 'clearChannel' enum.
      [3] Replaced 'codec is disabled' comment for clearChannel enum
      with 'CLEAR channel codec'.";
  }

  revision 2001-09-05 {
    description
     "[1] Added new enum value, 'clearch,' to CvcSpeechCoderRate's
      and CvcCoderTypeRate's textual-conventions. 
      [2] Added new enum value, 'gr303,' to CvcInBandSignaling's
      textual-conventions
      [3] Modified cvCommonDcCallActiveInBandSignaling's and
      cvCommonDcCallHistoryInBandSignaling's description
      to indicate value is valid only for Connection Trunk calls.";
  }

  revision 2000-07-22 {
    description
     "Add new objects for handling the following features:
      [1] Calling Name display for call active and history table.
      [2] Caller ID Block, which indicates whether the Caller ID
          feature is in using,  for call active and history table.";
  }

  typedef CvcSpeechCoderRate {
    type enumeration {
      enum "g729r8000" {
        value "1";
      }
      enum "g729Ar8000" {
        value "2";
      }
      enum "g726r16000" {
        value "3";
      }
      enum "g726r24000" {
        value "4";
      }
      enum "g726r32000" {
        value "5";
      }
      enum "g711ulawr64000" {
        value "6";
      }
      enum "g711Alawr64000" {
        value "7";
      }
      enum "g728r16000" {
        value "8";
      }
      enum "g723r6300" {
        value "9";
      }
      enum "g723r5300" {
        value "10";
      }
      enum "gsmr13200" {
        value "11";
      }
      enum "g729Br8000" {
        value "12";
      }
      enum "g729ABr8000" {
        value "13";
      }
      enum "g723Ar6300" {
        value "14";
      }
      enum "g723Ar5300" {
        value "15";
      }
      enum "g729IETFr8000" {
        value "16";
      }
      enum "gsmeEr12200" {
        value "17";
      }
      enum "clearChannel" {
        value "18";
      }
      enum "g726r40000" {
        value "19";
      }
      enum "llcc" {
        value "20";
      }
      enum "gsmAmrNb" {
        value "21";
      }
      enum "iLBC" {
        value "22";
      }
      enum "iLBCr15200" {
        value "23";
      }
      enum "iLBCr13330" {
        value "24";
      }
      enum "g722r4800" {
        value "25";
      }
      enum "g722r5600" {
        value "26";
      }
      enum "g722r6400" {
        value "27";
      }
      enum "iSAC" {
        value "28";
      }
      enum "aaclc" {
        value "29";
      }
      enum "aacld" {
        value "30";
      }
    }
    description
     "This object specifies the most desirable codec of
      speech for the VoIP, VoATM or VoFR peer.
      g729r8000      - pre-IETF G.729 8000  bps
      g729Ar8000     - G.729 ANNEX-A 8000  bps
      g726r16000     - G.726 16000 bps
      g726r24000     - G.726 24000 bps
      g726r32000     - G.726 32000 bps
      g711ulawr64000 - G.711 u-Law 64000 bps
      g711Alawr64000 - G.711 A-Law 64000 bps
      g728r16000     - G.728 16000 bps
      g723r6300      - G.723.1 6300 bps
      g723r5300      - G.723.1 5300 bps
      gsmr13200      - GSM Full rate 13200 bps
      g729Br8000     - G.729 ANNEX-B 8000  bps
      g729ABr8000    - G.729 ANNEX-A & B 8000 bps
      g723Ar6300     - G723.1 Annex A 6300 bps              
      g723Ar5300     - G723.1 Annex A 5300 bps               
      g729IETFr8000  - IETF G.729 8000  bps
      gsmeEr12200    - GSM Enhanced Full Rate 12200 bps
      clearChannel   - CLEAR Channel codec
      g726r40000     - G.726 40000 bps
      llcc           - Lossless compression codec
      gsmAmrNb       - GSM AMR-NB 4750 - 12200 bps
      iLBC           - iILBC 13330 or 15200 bps
      iLBCr15200     - iLBC 15200 bps
      iLBCr13330     - iLBC 13330 bps
      g722r4800      - G.722 (modes 1, 2, 3)
      g722r5600      - G.722 (modes 1, 2)
      g722r6400      - G.722 (mode 1)
      iSAC           - iSAC (10 to 32 kbps)
      aaclc          - AAC-LC Advanced Audio Coding Low Complexity
      aacld          - AAC-LD MPEG-4 Low Delay Audio Coder";
    reference
     "[1] RFC 3267: For introduction about GSM AMR-NB codec,
      section 3.1
          [2] RFC 3952: For introduction about iLBC codec,
      section 2";
  }

  typedef CvcFaxTransmitRate {
    type enumeration {
      enum "none" {
        value "1";
      }
      enum "voiceRate" {
        value "2";
      }
      enum "fax2400" {
        value "3";
      }
      enum "fax4800" {
        value "4";
      }
      enum "fax7200" {
        value "5";
      }
      enum "fax9600" {
        value "6";
      }
      enum "fax14400" {
        value "7";
      }
      enum "fax12000" {
        value "8";
      }
    }
    description
     "This object specifies the default transmit rate of FAX
      for the VoIP, VoATM or VOFR peer. If the value of this
      object is 'none', then the Fax relay feature is disabled         
      ; otherwise the Fax relay feature is enabled.
      
      none      - Fax relay is disabled.
      voiceRate - the fastest possible fax rate not exceed
                  the configured voice rate.
      fax2400   - 2400  bps FAX transmit rate.
      fax4800   - 4800  bps FAX transmit rate.
      fax7200   - 7200  bps FAX transmit rate.
      fax9600   - 9600  bps FAX transmit rate.
      fax14400  - 14400 bps FAX transmit rate.
      fax12000  - 12000 bps FAX transmit rate.";
  }

  typedef CvcCoderTypeRate {
    type enumeration {
      enum "other" {
        value "1";
      }
      enum "fax2400" {
        value "2";
      }
      enum "fax4800" {
        value "3";
      }
      enum "fax7200" {
        value "4";
      }
      enum "fax9600" {
        value "5";
      }
      enum "fax14400" {
        value "6";
      }
      enum "fax12000" {
        value "7";
      }
      enum "g729r8000" {
        value "10";
      }
      enum "g729Ar8000" {
        value "11";
      }
      enum "g726r16000" {
        value "12";
      }
      enum "g726r24000" {
        value "13";
      }
      enum "g726r32000" {
        value "14";
      }
      enum "g711ulawr64000" {
        value "15";
      }
      enum "g711Alawr64000" {
        value "16";
      }
      enum "g728r16000" {
        value "17";
      }
      enum "g723r6300" {
        value "18";
      }
      enum "g723r5300" {
        value "19";
      }
      enum "gsmr13200" {
        value "20";
      }
      enum "g729Br8000" {
        value "21";
      }
      enum "g729ABr8000" {
        value "22";
      }
      enum "g723Ar6300" {
        value "23";
      }
      enum "g723Ar5300" {
        value "24";
      }
      enum "ietfg729r8000" {
        value "25";
      }
      enum "gsmeEr12200" {
        value "26";
      }
      enum "clearChannel" {
        value "27";
      }
      enum "g726r40000" {
        value "28";
      }
      enum "llcc" {
        value "29";
      }
      enum "gsmAmrNb" {
        value "30";
      }
      enum "g722" {
        value "31";
      }
      enum "iLBC" {
        value "32";
      }
      enum "iLBCr15200" {
        value "33";
      }
      enum "iLBCr13330" {
        value "34";
      }
      enum "g722r4800" {
        value "35";
      }
      enum "g722r5600" {
        value "36";
      }
      enum "g722r6400" {
        value "37";
      }
      enum "iSAC" {
        value "38";
      }
      enum "aaclc" {
        value "39";
      }
      enum "aacld" {
        value "40";
      }
    }
    description
     "Represents the coder type-rate for voice/fax compression
      used during a call.
      
      *** ABBREVIATIONS, ACRONYMS AND SYMBOLS ***
      
      GSM    - Global System for Mobile Communication
      
      AMR-NB - Adaptive Multi Rate - Narrow Band
      
      iLBC   - internet Low Bitrate Codec
      
      iSAC   - internet Speech Audio Codec
      
      other          - none of the following.
      fax2400        - FAX   2400  bps 
      fax4800        - FAX   4800  bps 
      fax7200        - FAX   7200  bps 
      fax9600        - FAX   9600  bps
      fax14400       - FAX   14400 bps  
      fax12000       - FAX   12000 bps  
      g729r8000      - G.729 8000  bps (pre-IETF bit ordering)
      g729Ar8000     - G.729 ANNEX-A 8000  bps
      g726r16000     - G.726 16000 bps
      g726r24000     - G.726 24000 bps
      g726r32000     - G.726 32000 bps
      g711ulawr64000 - G.711 u-Law 64000 bps
      g711Alawr64000 - G.711 A-Law 64000 bps
      g728r16000     - G.728 16000 bps
      g723r6300      - G.723.1 6300 bps
      g723r5300      - G.723.1 5300 bps
      gsmr13200      - GSM full rate 13200 bps
      g729Br8000     - G.729 ANNEX-B 8000  bps
      g729ABr8000    - G.729 ANNEX-A & B 8000 bps
      g723Ar6300     - G723.1 Annex A 6300 bps              
      g723Ar5300     - G723.1 Annex A 5300 bps               
      ietfg729r8000  - G.729 8000 bps (IETF bit ordering)
      gsmeEr12200    - GSM Enhanced Full Rate 12200 bps
      clearChannel   - CLEAR channel codec
      g726r40000     - G.726 40000 bps 
      llcc           - Lossless compression codec
      gsmAmrNb       - GSM AMR-NB 4750 - 12200 bps
      g722           - G.722 2400 - 6400 bps
      iLBC           - iILBC 13330 or 15200 bps
      iLBCr15200     - iLBC 15200 bps
      iLBCr13330     - iLBC 13330 bps
      g722r4800      - G.722 (modes 1, 2, 3)
      g722r5600      - G.722 (modes 1, 2)
      g722r6400      - G.722 (mode 1)
      iSAC           - iSAC (10 to 32 kbps)
      aaclc          - AAC-LC Advanced Audio Coding Low Complexity
      aacld          - AAC-LD MPEG-4 Low Delay Audio Coder";
    reference
     "[1] RFC 3267: For introduction about GSM AMR-NB codec,
      section 3.1
          [2] RFC 3952: For introduction about iLBC codec,
      section 2";
  }

  typedef CvcGUid {
    type binary {
      length "0..16";
    }
    description
     "Represents a Global Call Identifier.
      The global call identifier is used as an unique identifier
      for an end-to-end call.
      A zero length CvcGUid indicates no value for the global call
      identifier.";
  }

  typedef CvcInBandSignaling {
    type enumeration {
      enum "cas" {
        value "1";
      }
      enum "none" {
        value "2";
      }
      enum "cept" {
        value "3";
      }
      enum "transparent" {
        value "4";
      }
      enum "gr303" {
        value "5";
      }
    }
    description
     "Represents the type of in-band signaling used between
      the two end points of the call and is used to inform the
      router how interpret the ABCD signaling data bits passed
      as part of the voice payload data.
      
      cas         - specifies interpret the signaling bits as
                    North American Channel Associated signaling.        
      none        - specifies no in-band signaling or signaling
                    is being done via an external method (e.g
                    CCS).
      cept        - specifies interpret the signaling bits as
                    MELCAS
      transparent - specifies do not interpret or translate the
                    signaling bits.
      gr303       - specifies interpret the signaling bits as
                    GR303";
  }

  typedef CvcCallReferenceIdOrZero {
    type uint32;
    description
     "A call reference ID correlates the video and audio call entries
      that belong to the same endpoint.  In other words, if an audio
      call entry and a video call entry have the same call reference
      ID, these entries belong to the same endpoint.  
      Because an audio-only endpoint creates only one call entry, call
      reference ID is not necessary and is set to zero.
      A call reference ID with value greater than zero signifies a
      video call, the value zero is object-specific and must therefore
      be defined as part of the description of any object which uses
      this syntax.  Examples of the usage of zero include audio calls.";
  }

  typedef CvcH320CallType {
    type enumeration {
      enum "none" {
        value "0";
      }
      enum "primary" {
        value "1";
      }
      enum "secondary" {
        value "2";
      }
    }
    description
     "This object specifies the H320 call type of a voice call.";
  }

  typedef CvcVideoCoderRate {
    type enumeration {
      enum "none" {
        value "0";
      }
      enum "h261" {
        value "1";
      }
      enum "h263" {
        value "2";
      }
      enum "h263plus" {
        value "3";
      }
      enum "h264" {
        value "4";
      }
    }
    description
     "This object specifies the encoding type used to compress
      the video data of the voice call.";
  }


  container CISCO-VOICE-COMMON-DIAL-CONTROL-MIB {
    config false;

    container cvCommonDcCallActiveTable {
      description
       "This table is a common extension to the call active
        table of IETF Dial Control MIB. It contains common call 
        leg information about a network call leg.";
      smiv2:oid "1.3.6.1.4.1.9.10.55.1.1.1";

      list cvCommonDcCallActiveEntry {
        key "callActiveSetupTime callActiveIndex";
        description
         "The common information regarding a single network call
          leg. The call leg entry is identified by using the same 
          index objects that are used by Call Active table of IETF 
          Dial Control MIB to identify the call.
          An entry of this table is created when its associated 
          call active entry in the IETF Dial Control MIB is created
          and the call active entry contains information for the 
          call establishment to a network dialpeer.             
          The entry is deleted when its associated call active entry 
          in the IETF Dial Control MIB is deleted.";
        smiv2:oid "1.3.6.1.4.1.9.10.55.1.1.1.1";

        leaf callActiveSetupTime {
          type leafref {
            path "/dial-control:DIAL-CONTROL-MIB/dial-control:callActiveTable/dial-control:callActiveEntry/dial-control:callActiveSetupTime";
          }
        }

        leaf callActiveIndex {
          type leafref {
            path "/dial-control:DIAL-CONTROL-MIB/dial-control:callActiveTable/dial-control:callActiveEntry/dial-control:callActiveIndex";
          }
        }

        leaf cvCommonDcCallActiveConnectionId {
          type CISCO-VOICE-COMMON-DIAL-CONTROL-MIB:CvcGUid;
          description
           "The global call identifier for the network call.";
          smiv2:max-access "read-only";
          smiv2:oid "1.3.6.1.4.1.9.10.55.1.1.1.1.1";
        }

        leaf cvCommonDcCallActiveVADEnable {
          type boolean;
          description
           "The object indicates whether or not the VAD (Voice
            Activity Detection) is enabled for the voice call.";
          smiv2:max-access "read-only";
          smiv2:oid "1.3.6.1.4.1.9.10.55.1.1.1.1.2";
        }

        leaf cvCommonDcCallActiveCoderTypeRate {
          type CISCO-VOICE-COMMON-DIAL-CONTROL-MIB:CvcCoderTypeRate;
          description
           "The negotiated coder rate. It specifies the transmit
            rate of voice/fax compression to its associated call leg 
            for the call.
            This rate is different from the configuration rate 
            because of rate negotiation during the call.";
          smiv2:max-access "read-only";
          smiv2:oid "1.3.6.1.4.1.9.10.55.1.1.1.1.3";
        }

        leaf cvCommonDcCallActiveCodecBytes {
          type int32 {
            range "10..255";
          }
          description
           "Specifies the payload size of the voice packet.";
          smiv2:max-access "read-only";
          smiv2:oid "1.3.6.1.4.1.9.10.55.1.1.1.1.4";
        }

        leaf cvCommonDcCallActiveInBandSignaling {
          type CISCO-VOICE-COMMON-DIAL-CONTROL-MIB:CvcInBandSignaling;
          description
           "Specifies the type of in-band signaling being used on
            the call.  This object is instantiated only for 
            Connection Trunk calls.";
          smiv2:max-access "read-only";
          smiv2:oid "1.3.6.1.4.1.9.10.55.1.1.1.1.5";
        }

        leaf cvCommonDcCallActiveCallingName {
          type snmp-framework:SnmpAdminString {
            length "0..64";
          }
          description
           "The calling party name this call is connected to. If the
            name is not available, then it will have a length of zero.";
          smiv2:max-access "read-only";
          smiv2:oid "1.3.6.1.4.1.9.10.55.1.1.1.1.6";
        }

        leaf cvCommonDcCallActiveCallerIDBlock {
          type boolean;
          description
           "The object indicates whether or not the caller ID feature
            is blocked for this voice call.";
          smiv2:max-access "read-only";
          smiv2:oid "1.3.6.1.4.1.9.10.55.1.1.1.1.7";
        }
      }
    }

    container cvCommonDcCallHistoryTable {
      description
       "This table is the Common extension to the call history
        table of IETF Dial Control MIB. It contains Common call 
        leg information about a network call leg.";
      smiv2:oid "1.3.6.1.4.1.9.10.55.1.2.1";

      list cvCommonDcCallHistoryEntry {
        key "cCallHistoryIndex";
        description
         "The common information regarding a single network call
          leg. The call leg entry is identified by using the same 
          index objects that are used by Call Active table of IETF 
          Dial Control MIB to identify the call.
          An entry of this table is created when its associated 
          call history entry in the IETF Dial Control MIB is 
          created and the call history entry contains information 
          for the call establishment to a network dialpeer.
          The entry is deleted when its associated call history 
          entry in the IETF Dial Control MIB is deleted.";
        smiv2:oid "1.3.6.1.4.1.9.10.55.1.2.1.1";

        leaf cCallHistoryIndex {
          type leafref {
            path "/cisco-dial:CISCO-DIAL-CONTROL-MIB/cisco-dial:cCallHistoryTable/cisco-dial:cCallHistoryEntry/cisco-dial:cCallHistoryIndex";
          }
        }

        leaf cvCommonDcCallHistoryConnectionId {
          type CISCO-VOICE-COMMON-DIAL-CONTROL-MIB:CvcGUid;
          description
           "The global call identifier for the gateway call.";
          smiv2:max-access "read-only";
          smiv2:oid "1.3.6.1.4.1.9.10.55.1.2.1.1.1";
        }

        leaf cvCommonDcCallHistoryVADEnable {
          type boolean;
          description
           "The object indicates whether or not the VAD (Voice
            Activity Detection) was enabled for the voice call.";
          smiv2:max-access "read-only";
          smiv2:oid "1.3.6.1.4.1.9.10.55.1.2.1.1.2";
        }

        leaf cvCommonDcCallHistoryCoderTypeRate {
          type CISCO-VOICE-COMMON-DIAL-CONTROL-MIB:CvcCoderTypeRate;
          description
           "The negotiated coder rate. It specifies the transmit rate
            of voice/fax compression to its associated call leg for 
            the call.
            This rate is different from the configuration rate 
            because of rate negotiation during the call.";
          smiv2:max-access "read-only";
          smiv2:oid "1.3.6.1.4.1.9.10.55.1.2.1.1.3";
        }

        leaf cvCommonDcCallHistoryCodecBytes {
          type int32 {
            range "10..255";
          }
          description
           "Specifies the payload size of the voice packet.";
          smiv2:max-access "read-only";
          smiv2:oid "1.3.6.1.4.1.9.10.55.1.2.1.1.4";
        }

        leaf cvCommonDcCallHistoryInBandSignaling {
          type CISCO-VOICE-COMMON-DIAL-CONTROL-MIB:CvcInBandSignaling;
          description
           "Specifies the type of in-band signaling used on the
            call.  This object is instantiated only for 
            Connection Trunk calls.";
          smiv2:max-access "read-only";
          smiv2:oid "1.3.6.1.4.1.9.10.55.1.2.1.1.5";
        }

        leaf cvCommonDcCallHistoryCallingName {
          type snmp-framework:SnmpAdminString {
            length "0..64";
          }
          description
           "The calling party name this call is connected to. If
            the name is not available, then it will have a length 
            of zero.";
          smiv2:max-access "read-only";
          smiv2:oid "1.3.6.1.4.1.9.10.55.1.2.1.1.6";
        }

        leaf cvCommonDcCallHistoryCallerIDBlock {
          type boolean;
          description
           "The object indicates whether or not the caller ID
            feature is blocked for this voice call.";
          smiv2:max-access "read-only";
          smiv2:oid "1.3.6.1.4.1.9.10.55.1.2.1.1.7";
        }
      }
    }
  }

  smiv2:alias "ciscoVoiceCommonDialControlMIB" {
    smiv2:oid "1.3.6.1.4.1.9.10.55";
  }

  smiv2:alias "cvCommonDcMIBObjects" {
    smiv2:oid "1.3.6.1.4.1.9.10.55.1";
  }

  smiv2:alias "cvCommonDcCallActive" {
    smiv2:oid "1.3.6.1.4.1.9.10.55.1.1";
  }

  smiv2:alias "cvCommonDcCallHistory" {
    smiv2:oid "1.3.6.1.4.1.9.10.55.1.2";
  }

  smiv2:alias "cvCommonDcMIBNotificationPrefix" {
    smiv2:oid "1.3.6.1.4.1.9.10.55.2";
  }

  smiv2:alias "cvCommonDcMIBNotifications" {
    smiv2:oid "1.3.6.1.4.1.9.10.55.2.0";
  }

  smiv2:alias "cvCommonDcMIBConformance" {
    smiv2:oid "1.3.6.1.4.1.9.10.55.3";
  }

  smiv2:alias "cvCommonDcMIBCompliances" {
    smiv2:oid "1.3.6.1.4.1.9.10.55.3.1";
  }

  smiv2:alias "cvCommonDcMIBGroups" {
    smiv2:oid "1.3.6.1.4.1.9.10.55.3.2";
  }

}
