/*
 * Generated by confdc --mib2yang-std
 * Source: mgmt/dmi/model/common/mib-source/IPMROUTE-STD-MIB.mib
 */
/*
 * This YANG module has been generated by smidump 0.5.0:
 *
 *      smidump -f yang IPMROUTE-STD-MIB
 *
 * Do not edit. Edit the source file instead!
 */

module IPMROUTE-STD-MIB {

  namespace "urn:ietf:params:xml:ns:yang:smiv2:IPMROUTE-STD-MIB";
  prefix IPMROUTE-STD-MIB;

  import IANA-RTPROTO-MIB {
    prefix "iana-rtproto";
  }

  import IF-MIB {
    prefix "if-mib";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "IETF IDMR Working Group";

  contact
   " Dave Thaler
    Microsoft Corporation
    One Microsoft Way
    Redmond, WA  98052-6399
    US
    
    Phone: +1 425 703 8835
    EMail: dthaler@microsoft.com";

  description
   "The MIB module for management of IP Multicast routing, but
    independent of the specific multicast routing protocol in
    use.";

  revision 2000-09-22 {
    description
     "Initial version, published as RFC 2932.";
  }

  typedef LanguageTag {
    type string;
    description
     "An RFC 1766-style language tag, with all alphabetic
      characters converted to lowercase.  This restriction is
      intended to make the lexical ordering imposed by SNMP useful
      
      
      
      
      
      when applied to language tags.  Note that it is
      theoretically possible for a valid language tag to exceed
      the allowed length of this syntax, and thus be impossible to
      represent with this syntax.  Sampling of language tags in
      current use on the Internet suggests that this limit does
      not pose a serious problem in practice.";
    smiv2:display-hint "100a";
  }


  container IPMROUTE-STD-MIB {
    config false;

    container ipMRoute {
      smiv2:oid "1.3.6.1.2.1.83.1.1";

      leaf ipMRouteEnable {
        type enumeration {
          enum "enabled" {
            value "1";
          }
          enum "disabled" {
            value "2";
          }
        }
        description
         "The enabled status of IP Multicast routing on this router.";
        smiv2:max-access "read-write";
        smiv2:oid "1.3.6.1.2.1.83.1.1.1";
      }

      leaf ipMRouteEntryCount {
        type yang:gauge32;
        description
         "The number of rows in the ipMRouteTable.  This can be used
          to monitor the multicast routing table size.";
        smiv2:max-access "read-only";
        smiv2:oid "1.3.6.1.2.1.83.1.1.7";
      }
    }

    container ipMRouteTable {
      description
       "The (conceptual) table containing multicast routing
        information for IP datagrams sent by particular sources to
        the IP multicast groups known to this router.";
      smiv2:oid "1.3.6.1.2.1.83.1.1.2";

      list ipMRouteEntry {
        key "ipMRouteGroup ipMRouteSource ipMRouteSourceMask";
        description
         "An entry (conceptual row) containing the multicast routing
          information for IP datagrams from a particular source and
          addressed to a particular IP multicast group address.
          Discontinuities in counters in this entry can be detected by
          observing the value of ipMRouteUpTime.";
        smiv2:oid "1.3.6.1.2.1.83.1.1.2.1";

        leaf ipMRouteGroup {
          type inet:ipv4-address;
          description
           "The IP multicast group address for which this entry
            contains multicast routing information.";
          smiv2:max-access "not-accessible";
          smiv2:oid "1.3.6.1.2.1.83.1.1.2.1.1";
        }

        leaf ipMRouteSource {
          type inet:ipv4-address;
          description
           "The network address which when combined with the
            corresponding value of ipMRouteSourceMask identifies the
            sources for which this entry contains multicast routing
            information.";
          smiv2:max-access "not-accessible";
          smiv2:oid "1.3.6.1.2.1.83.1.1.2.1.2";
        }

        leaf ipMRouteSourceMask {
          type inet:ipv4-address;
          description
           "The network mask which when combined with the corresponding
            value of ipMRouteSource identifies the sources for which
            this entry contains multicast routing information.";
          smiv2:max-access "not-accessible";
          smiv2:oid "1.3.6.1.2.1.83.1.1.2.1.3";
        }

        leaf ipMRouteUpstreamNeighbor {
          type inet:ipv4-address;
          description
           "The address of the upstream neighbor (e.g., RPF neighbor)
            from which IP datagrams from these sources to this multicast
            address are received, or 0.0.0.0 if the upstream neighbor is
            unknown (e.g., in CBT).";
          smiv2:max-access "read-only";
          smiv2:oid "1.3.6.1.2.1.83.1.1.2.1.4";
        }

        leaf ipMRouteInIfIndex {
          type if-mib:InterfaceIndexOrZero;
          description
           "The value of ifIndex for the interface on which IP
            datagrams sent by these sources to this multicast address
            are received.  A value of 0 indicates that datagrams are not
            subject to an incoming interface check, but may be accepted
            on multiple interfaces (e.g., in CBT).";
          smiv2:max-access "read-only";
          smiv2:oid "1.3.6.1.2.1.83.1.1.2.1.5";
        }

        leaf ipMRouteUpTime {
          type yang:timeticks;
          description
           "The time since the multicast routing information
            represented by this entry was learned by the router.";
          smiv2:max-access "read-only";
          smiv2:oid "1.3.6.1.2.1.83.1.1.2.1.6";
        }

        leaf ipMRouteExpiryTime {
          type yang:timeticks;
          description
           "The minimum amount of time remaining before this entry will
            be aged out.  The value 0 indicates that the entry is not
            subject to aging.";
          smiv2:max-access "read-only";
          smiv2:oid "1.3.6.1.2.1.83.1.1.2.1.7";
        }

        leaf ipMRoutePkts {
          type yang:counter32;
          description
           "The number of packets which this router has received from
            these sources and addressed to this multicast group
            address.";
          smiv2:max-access "read-only";
          smiv2:oid "1.3.6.1.2.1.83.1.1.2.1.8";
        }

        leaf ipMRouteDifferentInIfPackets {
          type yang:counter32;
          description
           "The number of packets which this router has received from
            these sources and addressed to this multicast group address,
            which were dropped because they were not received on the
            interface indicated by ipMRouteInIfIndex.  Packets which are
            not subject to an incoming interface check (e.g., using CBT)
            are not counted.";
          smiv2:max-access "read-only";
          smiv2:oid "1.3.6.1.2.1.83.1.1.2.1.9";
        }

        leaf ipMRouteOctets {
          type yang:counter32;
          description
           "The number of octets contained in IP datagrams which were
            received from these sources and addressed to this multicast
            group address, and which were forwarded by this router.";
          smiv2:max-access "read-only";
          smiv2:oid "1.3.6.1.2.1.83.1.1.2.1.10";
        }

        leaf ipMRouteProtocol {
          type iana-rtproto:IANAipMRouteProtocol;
          description
           "The multicast routing protocol via which this multicast
            forwarding entry was learned.";
          smiv2:max-access "read-only";
          smiv2:oid "1.3.6.1.2.1.83.1.1.2.1.11";
        }

        leaf ipMRouteRtProto {
          type iana-rtproto:IANAipRouteProtocol;
          description
           "The routing mechanism via which the route used to find the
            upstream or parent interface for this multicast forwarding
            entry was learned.  Inclusion of values for routing
            protocols is not intended to imply that those protocols need
            be supported.";
          smiv2:max-access "read-only";
          smiv2:oid "1.3.6.1.2.1.83.1.1.2.1.12";
        }

        leaf ipMRouteRtAddress {
          type inet:ipv4-address;
          description
           "The address portion of the route used to find the upstream
            or parent interface for this multicast forwarding entry.";
          smiv2:max-access "read-only";
          smiv2:oid "1.3.6.1.2.1.83.1.1.2.1.13";
        }

        leaf ipMRouteRtMask {
          type inet:ipv4-address;
          description
           "The mask associated with the route used to find the upstream
            or parent interface for this multicast forwarding entry.";
          smiv2:max-access "read-only";
          smiv2:oid "1.3.6.1.2.1.83.1.1.2.1.14";
        }

        leaf ipMRouteRtType {
          type enumeration {
            enum "unicast" {
              value "1";
            }
            enum "multicast" {
              value "2";
            }
          }
          description
           "The reason the given route was placed in the (logical)
            multicast Routing Information Base (RIB).  A value of
            unicast means that the route would normally be placed only
            in the unicast RIB, but was placed in the multicast RIB
            (instead or in addition) due to local configuration, such as
            when running PIM over RIP.  A value of multicast means that
            
            
            
            
            
            the route was explicitly added to the multicast RIB by the
            routing protocol, such as DVMRP or Multiprotocol BGP.";
          smiv2:max-access "read-only";
          smiv2:oid "1.3.6.1.2.1.83.1.1.2.1.15";
        }

        leaf ipMRouteHCOctets {
          type yang:counter64;
          description
           "The number of octets contained in IP datagrams which were
            received from these sources and addressed to this multicast
            group address, and which were forwarded by this router.
            This object is a 64-bit version of ipMRouteOctets.";
          smiv2:max-access "read-only";
          smiv2:oid "1.3.6.1.2.1.83.1.1.2.1.16";
        }
      }
    }

    container ipMRouteNextHopTable {
      description
       "The (conceptual) table containing information on the next-
        hops on outgoing interfaces for routing IP multicast
        datagrams.  Each entry is one of a list of next-hops on
        outgoing interfaces for particular sources sending to a
        particular multicast group address.";
      smiv2:oid "1.3.6.1.2.1.83.1.1.3";

      list ipMRouteNextHopEntry {
        key "ipMRouteNextHopGroup ipMRouteNextHopSource ipMRouteNextHopSourceMask ipMRouteNextHopIfIndex ipMRouteNextHopAddress";
        description
         "An entry (conceptual row) in the list of next-hops on
          outgoing interfaces to which IP multicast datagrams from
          particular sources to a IP multicast group address are
          routed.  Discontinuities in counters in this entry can be
          detected by observing the value of ipMRouteUpTime.";
        smiv2:oid "1.3.6.1.2.1.83.1.1.3.1";

        leaf ipMRouteNextHopGroup {
          type inet:ipv4-address;
          description
           "The IP multicast group for which this entry specifies a
            next-hop on an outgoing interface.";
          smiv2:max-access "not-accessible";
          smiv2:oid "1.3.6.1.2.1.83.1.1.3.1.1";
        }

        leaf ipMRouteNextHopSource {
          type inet:ipv4-address;
          description
           "The network address which when combined with the
            corresponding value of ipMRouteNextHopSourceMask identifies
            the sources for which this entry specifies a next-hop on an
            outgoing interface.";
          smiv2:max-access "not-accessible";
          smiv2:oid "1.3.6.1.2.1.83.1.1.3.1.2";
        }

        leaf ipMRouteNextHopSourceMask {
          type inet:ipv4-address;
          description
           "The network mask which when combined with the corresponding
            value of ipMRouteNextHopSource identifies the sources for
            which this entry specifies a next-hop on an outgoing
            interface.";
          smiv2:max-access "not-accessible";
          smiv2:oid "1.3.6.1.2.1.83.1.1.3.1.3";
        }

        leaf ipMRouteNextHopIfIndex {
          type if-mib:InterfaceIndex;
          description
           "The ifIndex value of the interface for the outgoing
            interface for this next-hop.";
          smiv2:max-access "not-accessible";
          smiv2:oid "1.3.6.1.2.1.83.1.1.3.1.4";
        }

        leaf ipMRouteNextHopAddress {
          type inet:ipv4-address;
          description
           "The address of the next-hop specific to this entry.  For
            most interfaces, this is identical to ipMRouteNextHopGroup.
            NBMA interfaces, however, may have multiple next-hop
            addresses out a single outgoing interface.";
          smiv2:max-access "not-accessible";
          smiv2:oid "1.3.6.1.2.1.83.1.1.3.1.5";
        }

        leaf ipMRouteNextHopState {
          type enumeration {
            enum "pruned" {
              value "1";
            }
            enum "forwarding" {
              value "2";
            }
          }
          description
           "An indication of whether the outgoing interface and next-
            hop represented by this entry is currently being used to
            forward IP datagrams.  The value 'forwarding' indicates it
            is currently being used; the value 'pruned' indicates it is
            not.";
          smiv2:max-access "read-only";
          smiv2:oid "1.3.6.1.2.1.83.1.1.3.1.6";
        }

        leaf ipMRouteNextHopUpTime {
          type yang:timeticks;
          description
           "The time since the multicast routing information
            represented by this entry was learned by the router.";
          smiv2:max-access "read-only";
          smiv2:oid "1.3.6.1.2.1.83.1.1.3.1.7";
        }

        leaf ipMRouteNextHopExpiryTime {
          type yang:timeticks;
          description
           "The minimum amount of time remaining before this entry will
            be aged out.  If ipMRouteNextHopState is pruned(1), the
            remaining time until the prune expires and the state reverts
            to forwarding(2).  Otherwise, the remaining time until this
            entry is removed from the table.  The time remaining may be
            copied from ipMRouteExpiryTime if the protocol in use for
            this entry does not specify next-hop timers.  The value 0
            
            
            
            
            
            indicates that the entry is not subject to aging.";
          smiv2:max-access "read-only";
          smiv2:oid "1.3.6.1.2.1.83.1.1.3.1.8";
        }

        leaf ipMRouteNextHopClosestMemberHops {
          type int32;
          description
           "The minimum number of hops between this router and any
            member of this IP multicast group reached via this next-hop
            on this outgoing interface.  Any IP multicast datagrams for
            the group which have a TTL less than this number of hops
            will not be forwarded to this next-hop.";
          smiv2:max-access "read-only";
          smiv2:oid "1.3.6.1.2.1.83.1.1.3.1.9";
        }

        leaf ipMRouteNextHopProtocol {
          type iana-rtproto:IANAipMRouteProtocol;
          description
           "The routing mechanism via which this next-hop was learned.";
          smiv2:max-access "read-only";
          smiv2:oid "1.3.6.1.2.1.83.1.1.3.1.10";
        }

        leaf ipMRouteNextHopPkts {
          type yang:counter32;
          description
           "The number of packets which have been forwarded using this
            route.";
          smiv2:max-access "read-only";
          smiv2:oid "1.3.6.1.2.1.83.1.1.3.1.11";
        }
      }
    }

    container ipMRouteInterfaceTable {
      description
       "The (conceptual) table containing multicast routing
        information specific to interfaces.";
      smiv2:oid "1.3.6.1.2.1.83.1.1.4";

      list ipMRouteInterfaceEntry {
        key "ipMRouteInterfaceIfIndex";
        description
         "An entry (conceptual row) containing the multicast routing
          information for a particular interface.";
        smiv2:oid "1.3.6.1.2.1.83.1.1.4.1";

        leaf ipMRouteInterfaceIfIndex {
          type if-mib:InterfaceIndex;
          description
           "The ifIndex value of the interface for which this entry
            contains information.";
          smiv2:max-access "not-accessible";
          smiv2:oid "1.3.6.1.2.1.83.1.1.4.1.1";
        }

        leaf ipMRouteInterfaceTtl {
          type int32 {
            range "0..255";
          }
          description
           "The datagram TTL threshold for the interface. Any IP
            multicast datagrams with a TTL less than this threshold will
            not be forwarded out the interface. The default value of 0
            means all multicast packets are forwarded out the
            interface.";
          smiv2:max-access "read-write";
          smiv2:oid "1.3.6.1.2.1.83.1.1.4.1.2";
        }

        leaf ipMRouteInterfaceProtocol {
          type iana-rtproto:IANAipMRouteProtocol;
          description
           "The routing protocol running on this interface.";
          smiv2:max-access "read-only";
          smiv2:oid "1.3.6.1.2.1.83.1.1.4.1.3";
        }

        leaf ipMRouteInterfaceRateLimit {
          type int32;
          description
           "The rate-limit, in kilobits per second, of forwarded
            multicast traffic on the interface.  A rate-limit of 0
            indicates that no rate limiting is done.";
          smiv2:defval "0";
          smiv2:max-access "read-write";
          smiv2:oid "1.3.6.1.2.1.83.1.1.4.1.4";
        }

        leaf ipMRouteInterfaceInMcastOctets {
          type yang:counter32;
          description
           "The number of octets of multicast packets that have arrived
            on the interface, including framing characters.  This object
            is similar to ifInOctets in the Interfaces MIB, except that
            only multicast packets are counted.";
          smiv2:max-access "read-only";
          smiv2:oid "1.3.6.1.2.1.83.1.1.4.1.5";
        }

        leaf ipMRouteInterfaceOutMcastOctets {
          type yang:counter32;
          description
           "The number of octets of multicast packets that have been
            sent on the interface.";
          smiv2:max-access "read-only";
          smiv2:oid "1.3.6.1.2.1.83.1.1.4.1.6";
        }

        leaf ipMRouteInterfaceHCInMcastOctets {
          type yang:counter64;
          description
           "The number of octets of multicast packets that have arrived
            on the interface, including framing characters.  This object
            is a 64-bit version of ipMRouteInterfaceInMcastOctets.  It
            is similar to ifHCInOctets in the Interfaces MIB, except
            that only multicast packets are counted.";
          smiv2:max-access "read-only";
          smiv2:oid "1.3.6.1.2.1.83.1.1.4.1.7";
        }

        leaf ipMRouteInterfaceHCOutMcastOctets {
          type yang:counter64;
          description
           "The number of octets of multicast packets that have been
            
            
            
            
            
            sent on the interface.  This object is a 64-bit version of
            ipMRouteInterfaceOutMcastOctets.";
          smiv2:max-access "read-only";
          smiv2:oid "1.3.6.1.2.1.83.1.1.4.1.8";
        }
      }
    }

    container ipMRouteBoundaryTable {
      description
       "The (conceptual) table listing the router's scoped
        multicast address boundaries.";
      smiv2:oid "1.3.6.1.2.1.83.1.1.5";

      list ipMRouteBoundaryEntry {
        key "ipMRouteBoundaryIfIndex ipMRouteBoundaryAddress ipMRouteBoundaryAddressMask";
        description
         "An entry (conceptual row) in the ipMRouteBoundaryTable
          representing a scoped boundary.";
        smiv2:oid "1.3.6.1.2.1.83.1.1.5.1";

        leaf ipMRouteBoundaryIfIndex {
          type if-mib:InterfaceIndex;
          description
           "The IfIndex value for the interface to which this boundary
            applies.  Packets with a destination address in the
            associated address/mask range will not be forwarded out this
            interface.";
          smiv2:max-access "not-accessible";
          smiv2:oid "1.3.6.1.2.1.83.1.1.5.1.1";
        }

        leaf ipMRouteBoundaryAddress {
          type inet:ipv4-address;
          description
           "The group address which when combined with the
            corresponding value of ipMRouteBoundaryAddressMask
            identifies the group range for which the scoped boundary
            exists.  Scoped addresses must come from the range 239.x.x.x
            as specified in RFC 2365.";
          smiv2:max-access "not-accessible";
          smiv2:oid "1.3.6.1.2.1.83.1.1.5.1.2";
        }

        leaf ipMRouteBoundaryAddressMask {
          type inet:ipv4-address;
          description
           "The group address mask which when combined with the
            corresponding value of ipMRouteBoundaryAddress identifies
            the group range for which the scoped boundary exists.";
          smiv2:max-access "not-accessible";
          smiv2:oid "1.3.6.1.2.1.83.1.1.5.1.3";
        }

        leaf ipMRouteBoundaryStatus {
          type snmpv2-tc:RowStatus;
          description
           "The status of this row, by which new entries may be
            created, or old entries deleted from this table.";
          smiv2:max-access "read-write";
          smiv2:oid "1.3.6.1.2.1.83.1.1.5.1.4";
        }
      }
    }

    container ipMRouteScopeNameTable {
      description
       "The (conceptual) table listing the multicast scope names.";
      smiv2:oid "1.3.6.1.2.1.83.1.1.6";

      list ipMRouteScopeNameEntry {
        key "ipMRouteScopeNameAddress ipMRouteScopeNameAddressMask ipMRouteScopeNameLanguage";
        smiv2:implied "ipMRouteScopeNameLanguage";
        description
         "An entry (conceptual row) in the ipMRouteScopeNameTable
          representing a multicast scope name.";
        smiv2:oid "1.3.6.1.2.1.83.1.1.6.1";

        leaf ipMRouteScopeNameAddress {
          type inet:ipv4-address;
          description
           "The group address which when combined with the
            corresponding value of ipMRouteScopeNameAddressMask
            identifies the group range associated with the multicast
            scope.  Scoped addresses must come from the range
            239.x.x.x.";
          smiv2:max-access "not-accessible";
          smiv2:oid "1.3.6.1.2.1.83.1.1.6.1.1";
        }

        leaf ipMRouteScopeNameAddressMask {
          type inet:ipv4-address;
          description
           "The group address mask which when combined with the
            corresponding value of ipMRouteScopeNameAddress identifies
            the group range associated with the multicast scope.";
          smiv2:max-access "not-accessible";
          smiv2:oid "1.3.6.1.2.1.83.1.1.6.1.2";
        }

        leaf ipMRouteScopeNameLanguage {
          type IPMROUTE-STD-MIB:LanguageTag;
          description
           "The RFC 1766-style language tag associated with the scope
            name.";
          smiv2:max-access "not-accessible";
          smiv2:oid "1.3.6.1.2.1.83.1.1.6.1.3";
        }

        leaf ipMRouteScopeNameString {
          type snmp-framework:SnmpAdminString;
          description
           "The textual name associated with the multicast scope.  The
            value of this object should be suitable for displaying to
            end-users, such as when allocating a multicast address in
            this scope.  When no name is specified, the default value of
            this object should be the string 239.x.x.x/y with x and y
            replaced appropriately to describe the address and mask
            length associated with the scope.";
          smiv2:max-access "read-write";
          smiv2:oid "1.3.6.1.2.1.83.1.1.6.1.4";
        }

        leaf ipMRouteScopeNameDefault {
          type boolean;
          description
           "If true, indicates a preference that the name in the
            following language should be used by applications if no name
            is available in a desired language.";
          smiv2:defval "false";
          smiv2:max-access "read-write";
          smiv2:oid "1.3.6.1.2.1.83.1.1.6.1.5";
        }

        leaf ipMRouteScopeNameStatus {
          type snmpv2-tc:RowStatus;
          description
           "The status of this row, by which new entries may be
            created, or old entries deleted from this table.";
          smiv2:max-access "read-write";
          smiv2:oid "1.3.6.1.2.1.83.1.1.6.1.6";
        }
      }
    }
  }

  smiv2:alias "ipMRouteStdMIB" {
    smiv2:oid "1.3.6.1.2.1.83";
  }

  smiv2:alias "ipMRouteMIBObjects" {
    smiv2:oid "1.3.6.1.2.1.83.1";
  }

  smiv2:alias "ipMRoute" {
    smiv2:oid "1.3.6.1.2.1.83.1.1";
  }

  smiv2:alias "ipMRouteMIBConformance" {
    smiv2:oid "1.3.6.1.2.1.83.2";
  }

  smiv2:alias "ipMRouteMIBCompliances" {
    smiv2:oid "1.3.6.1.2.1.83.2.1";
  }

  smiv2:alias "ipMRouteMIBGroups" {
    smiv2:oid "1.3.6.1.2.1.83.2.2";
  }

}
