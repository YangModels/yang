submodule Cisco-IOS-XE-ipv6 {
  belongs-to Cisco-IOS-XE-native {
    prefix ios;
  }

  import ietf-inet-types {
    prefix inet;
  }


  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native IPv6 Yang Model.
     Copyright (c) 2016-2017 by Cisco Systems, Inc.
     All rights reserved.";

  // =========================================================================
  // REVISION
  // =========================================================================
  revision 2017-07-05 {
    description
      "Adding model for ipv6 router ospf *";
  }
  revision 2017-02-23 {
    description    
      "Changes to support openconfig-network-instance mapping";
  }

  revision 2017-02-07 {
    description
      "Initial revision";
  }


  grouping ipv6-route-options-grouping {
    leaf next-hop {
      description
        "IPv6 address of next-hop";
      type inet:ipv6-address;
    }
    leaf distance {
      type uint8;
    }
    leaf name {
      description
        "Specify name of the next hop";
      type string;
    }
    choice type-choice {
      leaf multicast {
        description
          "Route only usable by multicast";
        type empty;
      }
      leaf unicast {
        description
          "Route only usable by unicast";
        type empty;
      }
    }
    leaf tag {
      description
        "Tag value";
      type uint32;
    }
    leaf track {
      description
        "Tracked";
      type uint32;
    }
  }

  grouping ipv6-route-grouping {
    list ipv6-route-list {
      key "prefix";
      leaf prefix {
        type ios-types:ipv6-prefix;
      }
      list ipv6-fwd-list {
        key fwd;
        leaf fwd {
          type union {
             type enumeration {
                 enum "Null0" {
                 }
             }
             type inet:ipv6-address;
             type string;
           }
        }
        uses ipv6-route-options-grouping;
      }
    }
  }

  /////////////////////////////////////////////////////////
  // native / ipv6
  /////////////////////////////////////////////////////////
  grouping config-ipv6-grouping {
    container ipv6 { 
      description
        "Global IPv6 configuration commands";

      container source-guard { 
        description "Configure IPv6 sourceguard";
        list policy {
          description "Configure a policy for feature sourceguard";
          key "source-guard-policy-name";
          leaf source-guard-policy-name{
            type string;
          }
          container validate {
            description "Validate the src of the received data traffic";
            leaf address {
              description "Validate against addresses learned in NDP/DHCP traffic (default)";
              type empty;
            }
            leaf prefix {
              description "Validate against prefixes learned in RA or DHCP-PD traffic";
              type empty;
            }
          }
        }
      }

      container destination-guard { 
        description "Configure Destination guard";
        list policy {
          description "Configure a policy for feature destguard";
          key "destination-guard-policy-name" ;
          leaf destination-guard-policy-name{
            type string;
          }
          container enforcement {
            description "Sets the enforcement level";
            leaf always {
              description "Enforced under all conditions (default)";
              type empty;
            }
            leaf stressed {
              description "Enforced when system is under stress";
              type empty;
            }
          }
        }
      }

      container dhcp { 
        description 
          "IPv6 DHCP";
        // @mount Cisco-IOS-XE-dhcp
      }

      container access-list { 
        description
          "Configure access lists";
        // @mount Cisco-IOS-XE-acl
      }

      // ipv6 flowset
      leaf flowset {
        description
          "Set flow label random for originated packets";
        type empty;
      }

      // ipv6 unicast-routing
      leaf unicast-routing {
        description
          "Enable unicast routing";
        type empty;
      }

      container multicast {
        description
          "Configure multicast related commands";
        // @mount Cisco-IOS-XE-multicast
      }

      // ipv6 multicast-routing
      // @mount Cisco-IOS-XE-multicast

      // ipv6 cef
      container cef { 
        description
          "Cisco Express Forwarding";
        presence "true";
        // @mount Cisco-IOS-XE-cef
      }

      //ipv6 nd
      container nd {
        description
          "Configure IPv6 ND";
        // @mount Cisco-IOS-XE-nd
      }

      container pim { 
        description
          "Configure Protocol Independent Multicast";
        // @mount Cisco-IOS-XE-mcast
      }

      //ipv6 rip
      //@mount Cisco-IOS-XE-rip

      /////////////////////////////////////////////////////////
      // native / ipv6 / route
      /////////////////////////////////////////////////////////
      container route {
        description
          "Configure static routes";
        // ipv6 route prefix
        uses ipv6-route-grouping;
        // ipv6 route vrf *
        list vrf {
          description
            "Configure static route for a VPN Routing/Forwarding instance";
          key "name";
          leaf name {
            type string;
          }
          uses ipv6-route-grouping;
        }
      }

      /////////////////////////////////////////////////////////
      // native / ipv6 / router
      /////////////////////////////////////////////////////////
      container router {
        description
          "Enable an IPV6 routing process";
        list eigrp {
          description
            "Enhanced Interior Gateway Routing Protocol (EIGRP)";
          // @mount Cisco-IOS-XE-eigrp
          key "id";
          leaf id {
            description
              "Autonomous System ID";
            type uint16 {
              range "1..65535";
            }
          }
        }
        list ospf {
          description
            "Open Shortest Path First (OSPFv3)";
          key "id";
          leaf id {
            description
              "Process ID";
            type uint16 {
              range "1..65535";
            }
          }
        }
        // ipv6 router rip
        // @mount Cisco-IOS-XE-rip
      }

      // source-route Process packets with source routing header options
      // ipv6 source-route
      leaf source-route {
        description
          "Process packets with source routing header options";
        type boolean;
      }

      //ipv6 spd
      container spd {
        description
          "spd";
        leaf mode {
          type enumeration {
            enum "aggressive";
          }
        }
        container queue {
          description
            "queue";
          leaf max-threshold {
            description "Max threshold";
            type uint16 {
              range "0..65535";
            }
          }
          leaf min-threshold {
            description "Min threshold";
            must ". < ../max-threshold" {
              error-message "min-threshold must be less than max-threshold";
            }
            type uint16 {
              range "0..65535";
            }
          }
        }
      }

      // ipv6 prefix-list
      container prefix-list { 
        description
          "Build a prefix list";
        list prefixes {
          key "name";
          leaf name {
            type string {
              pattern "([^s].*)|(s[^e].*)|(se[^q].*)(seq[^u].*)|(sequ[^e].*)|(seque[^n].*)|(sequen[^c].*)|(sequenc[^e].*)|(sequence[^\\-].*)|(sequence\\-[^n].*)|(sequence\\-n[^u].*)|(sequence\\-nu[^m].*)|(sequence\\-num[^b].*)|(sequence\\-numb[^e].*)|(sequence\\-numbe[^r].*)|(sequence\\-number..*)";
            }
          }
          leaf description {
            description
              "Prefix-list specific description";
            type string {
              length "1..80";
            }
          }
          container permit {
            description
              "Specify packets to forward";
            leaf address {
              type ios-types:ipv6-prefix;
            }
            leaf ge {
              description
                "Minimum prefix length to be matched";
              type uint8 {
                range "0..128";
              }
            }
            leaf le {
              description
                "Maximum prefix length to be matched";
              type uint8 {
                range "0..128";
              }
            }
          }
          container deny {
            description
              "Specify packets to reject";
            leaf address {
              type ios-types:ipv6-prefix;
            }
            leaf ge {
              description
                "Minimum prefix length to be matched";
              type uint8 {
                range "0..128";
              }
            }
            leaf le {
              description
                "Maximum prefix length to be matched";
              type uint8 {
                range "0..128";
              }
            }
          }
          list seq {
            // NOTE: the seq element is not actually mandatory
            // in the Cisco CLI. If it isn't give
            description
              "sequence number of an entry";
            key "no";
            leaf no {
              type uint32 {
                range "1..4294967294";
              }
            }
            container deny {
              description
                "Specify packets to reject";
              leaf ip {
                type ios-types:ipv6-prefix;
              }
              leaf ge {
                description
                  "Minimum prefix length to be matched";
                type uint16 {
                  range "1..128";
                }
              }
              leaf le {
                description
                  "Maximum prefix length to be matched";
                type uint16 {
                  range "1..128";
                }
              }
            }
            container permit {
              description
                "Specify packets to forward";
              leaf ip {
                type ios-types:ipv6-prefix;
              }
              leaf ge {
                description
                  "Minimum prefix length to be matched";
                type uint16 {
                  range "1..128";
                }
              }
              leaf le {
                description
                  "Maximum prefix length to be matched";
                type uint16 {
                  range "1..128";
                }
              }
            }
          }
        }
        leaf sequence-number {
          description
            "Include/exclude sequence numbers in NVGEN";
          type empty;
        }
      }
      
      //ipv6 neighbor
      list neighbor {
        description "Neighbor";
	key "address interface";
	leaf address {
	  description "X:X:X:X::X  IPv6 address";
	  type inet:ipv6-address;
	}
	leaf interface {
	  type string;
	}
	leaf hardware-address {
	  description "H.H.H  48-bit hardware address";
	  type string;
	}
      }
    }
  }
}
