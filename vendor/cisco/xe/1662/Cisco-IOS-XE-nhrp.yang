module Cisco-IOS-XE-nhrp {
  namespace "http://cisco.com/ns/yang/Cisco-IOS-XE-nhrp";
  prefix ios-nhrp;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Next Hop Resolution Protocol (NHRP) Yang model.
     Copyright (c) 2016 by Cisco Systems, Inc.
     All rights reserved.";

  // =========================================================================
  // REVISION
  // =========================================================================
  revision 2017-02-07 {
    description
      "Initial revision";
  }

  grouping config-interface-nhrp-grouping {
    container nhrp {
      description
        "NHRP interface subcommands";
      container attribute {
        description
          "NHRP attribute set";
        container set {
          description
            "attribute set";
          list attr-type {
            key "attr-type";
            leaf attr-type {
              description
                "attribute type";
              type string;
            }
            leaf attr-val {
              description
                "attribute value";
              type string;
            }
          }
        }
      }
      leaf authentication {
        description
          "authentication string";
        type string;
      }
      container cache {
        description
          "NHRP Cache related commands.";
        leaf non-authoritative {
          description
            "Mark cache entries non-authoritative";
          type empty;
        }
      }
      leaf connect {
        description
          "NHRP event request id";
        type uint16 {
          range "1..65535";
        }
      }
      leaf group {
        type string;
      }
      leaf holdtime {
        description
          "Number of seconds";
        type uint16 {
          range "1..65535";
        }
      }
      container interest {
        description
          "Specify an access list";
        leaf acl-range {
          description
            "IP access list";
          type uint8 {
            range "1..199";
          }
        }
        leaf none {
          description
            "No traffic is interesting.";
          type empty;
        }
      }
      container map {
        description
          "Map dest IP addresses to NBMA addresses";
        list dest-ipv4 {
          key "dest-ipv4";
          leaf dest-ipv4 {
            description
              "IP address of destination";
            type inet:ipv4-address;
          }
          list nbma-ipv4 {
            key "nbma-ipv4";
            leaf nbma-ipv4 {
              description
                "IP NBMA address";
              type inet:ipv4-address;
            }
            leaf ipv4 {
              type inet:ipv4-address;
            }
            leaf ipv6 {
              type inet:ipv6-address;
            }
          }
          list dest-mask {
            key "dest-mask";
            leaf dest-mask {
              description
                "IP mask of destination";
              type inet:ipv4-address;
            }
            leaf ipv4 {
              type inet:ipv4-address;
            }
            leaf ipv6 {
              type inet:ipv6-address;
            }
          }
          leaf nbma-ipv6 {
            type inet:ipv6-address;
          }
        }
        container multicast {
          description
            "Use this NBMA mapping for broadcasts/multicasts";
          leaf-list nbma_ipv4 {
              type inet:ipv4-address;
          }
          leaf-list nbma_ipv6 {
            type inet:ipv6-address;
          }
          leaf dynamic {
            description
              "Dynamically learn destinations from client registrations on hub";
            type empty;
          }
        }
        list group {
          key "name";
          leaf name {
            type string;
          }
          container service-policy {
            leaf output {
              description
                "Policy";
              type string;
            }
          }
        }
      }
      container max-send {
        description
          "Rate limit NHRP traffic";
        list pkt-count {
          key "pkt-count";
          leaf pkt-count {
            description
              "Packet count";
            type uint16 {
              range "1..65535";
            }
          }
          leaf every {
            description
              "Interval in seconds";
            type uint16 {
              range "10..65535";
            }
          }
        }
      }
      leaf network-id {
        description
          "Network identifier";
        type uint32 {
          range "1..4294967295";
        }
      }
      container nhs {
        description
          "Specify a next hop server";
        list ipv4 {
          key "ipv4";
          leaf ipv4 {
            description
              "Protocol IP address of NHS";
            type inet:ipv4-address;
          }
          leaf cluster {
            description
              "NHS cluster number";
            type uint8 {
              range "0..10";
            }
          }
          container nbma {
            description
              "NBMA of NHS";
            list ipv4 {
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list prior {
                    key "prior";
                    leaf prior {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list pri {
                  key "pri";
                  leaf pri {
                    description
                      "NHS priority, range = 0 to 255, 0 is the highest";
                    type uint8 {
                      range "0..255";
                    }
                  }
                  leaf cluster {
                    description
                      "NHS cluster number";
                    type uint8 {
                      range "0..10";
                    }
                  }
                }
              }
            }
            list nhs-fqdn {
              key "nhs-fqdn";
              leaf nhs-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list nhs-pri {
                  key "nhs-pri";
                  leaf nhs-pri {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list mc-pri {
                    key "mc-pri";
                    leaf mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list mc-prior {
                  key "mc-prior";
                  leaf mc-prior {
                    description
                      "NHS priority, range = 0 to 255, 0 is the highest";
                    type uint8 {
                      range "0..255";
                    }
                  }
                  leaf cluster {
                    description
                      "NHS cluster number";
                    type uint8 {
                      range "0..10";
                    }
                  }
                }
              }
            }
          }
          container priority {
            description
              "NHS priority, don't specify for default priority";
            list pri-range {
              key "pri-range";
              leaf pri-range {
                description
                  "NHS priority, range = 0 to 255, 0 is the highest";
                type uint8 {
                  range "0..255";
                }
              }
              leaf cluster {
                description
                  "NHS cluster number";
                type uint8 {
                  range "0..10";
                }
              }
            }
          }
        }
        container cluster {
          description
            "NHS Redundancy cluster configurations";
          list clus-num {
            key "clus-num";
            leaf clus-num {
              description
                "NHS cluster number";
              type uint8 {
                range "0..10";
              }
            }
            leaf max-connections {
              description
                "Max-connections value";
              type uint8 {
                range "0..255";
              }
            }
          }
        }
        container dynamic {
          description
            "NHS protocol address dynamically learnt";
          container nbma {
            description
              "NBMA of NHS";
            list ipv4 {
              description
                "NBMA of NHS";
              key "ipv4";
              leaf ipv4 {
                description
                  "IPv4 address";
                type inet:ipv4-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-pri {
                    key "dyn-pri";
                    leaf dyn-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list n-prior {
                  key "n-prior";
                  leaf n-prior {
                    description
                      "NHS priority, range = 0 to 255, 0 is the highest";
                    type uint8 {
                      range "0..255";
                    }
                  }
                  leaf cluster {
                    description
                      "NHS cluster number";
                    type uint8 {
                      range "0..10";
                    }
                  }
                }
              }
            }
            list dyn-fqdn {
              key "dyn-fqdn";
              leaf dyn-fqdn {
                description
                  "NHS FQDN string";
                type string;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list dyn-mc-pri {
                    key "dyn-mc-pri";
                    leaf dyn-mc-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list dp {
                  key "dp";
                  leaf dp {
                    description
                      "NHS priority, range = 0 to 255, 0 is the highest";
                    type uint8 {
                      range "0..255";
                    }
                  }
                  leaf cluster {
                    description
                      "NHS cluster number";
                    type uint8 {
                      range "0..10";
                    }
                  }
                }
              }
            }
            list ipv6 {
              key "ipv6";
              leaf ipv6 {
                description
                  "IPv6 address";
                type inet:ipv6-address;
              }
              leaf cluster {
                description
                  "NHS cluster number";
                type uint8 {
                  range "0..10";
                }
              }
              container multicast {
                description
                  "Use this NBMA mapping for broadcasts/multicasts";
                presence "true";
                leaf cluster {
                  description
                    "NHS cluster number";
                  type uint8 {
                    range "0..10";
                  }
                }
                container priority {
                  description
                    "NHS priority, don't specify for default priority";
                  list v6-pri {
                    key "v6-pri";
                    leaf v6-pri {
                      description
                        "NHS priority, range = 0 to 255, 0 is the highest";
                      type uint8 {
                        range "0..255";
                      }
                    }
                    leaf cluster {
                      description
                        "NHS cluster number";
                      type uint8 {
                        range "0..10";
                      }
                    }
                  }
                }
              }
              container priority {
                description
                  "NHS priority, don't specify for default priority";
                list v6-pri2 {
                  key "v6-pri2";
                  leaf v6-pri2 {
                    description
                      "NHS priority, range = 0 to 255, 0 is the highest";
                    type uint8 {
                      range "0..255";
                    }
                  }
                  leaf cluster {
                    description
                      "NHS cluster number";
                    type uint8 {
                      range "0..10";
                    }
                  }
                }
              }
            }
          }
        }
        leaf fallback {
          description
            "NHS Redundancy Fallback time, 0 -60 seconds";
          type uint8 {
            range "0..60";
          }
        }
      }
      leaf record {
        description
          "Allow NHRP record option";
        type empty;
      }
      container redirect {
        description
          "Enable NHRP redirect traffic indication";
        presence "true";
        leaf timeout {
          description
            "Interval in seconds";
          type uint8 {
            range "2..30";
          }
        }
      }
      container registration {
        description
          "Settings for registration packets.";
        leaf no-unique {
          description
            "Do not set the 'Unique' flag in registration requests.";
          type empty;
        }
        leaf timeout {
          description
            "Number of seconds";
          type uint16 {
            range "1..65535";
          }
        }
      }
      container reject {
        description
          "NHRP resolution reject request";
        list reqid {
          key "reqid";
          leaf reqid {
            description
              "reqid value";
            type uint16 {
              range "1..65535";
            }
          }
          leaf rej-secs {
            description
              "Number of seconds";
            type uint16 {
              range "0..65535";
            }
          }
        }
      }
      container responder {
        description
          "Responder interface";
        leaf res-int {
          description
            "Virtual ACR interface";
          type string;
        }
        leaf Analysis-Module {
          description
            "Analysis-Module interface number";
          type uint8;
        }
        leaf Fcpa {
          description
            "Fcpa interface number";
          type uint8;
        }
        leaf SBC {
          description
            "SBC interface number";
          type uint32 {
            range "0..2147483647";
          }
        }
        leaf SONET_ACR {
          description
            "SONET_ACR interface number";
          type uint8;
        }
        leaf TB-controller {
          description
            "Telecom-Bus Clock Controller";
          type string;
        }
        leaf Service-Engine {
          description
            "Service-Engine interface number";
          type uint8;
        }
        leaf Tunnel {
          description
            "Tunnel interface number";
          type uint32 {
            range "0..2147483647";
          }
        }
        leaf Tunnel-tp {
          description
            "Tunnel-tp interface number";
          type uint16 {
            range "0..65535";
          }
        }
        leaf VPN {
          description
            "VPN interface number";
          type uint32 {
            range "0..2147483647";
          }
        }
        leaf Virtual-TokenRing {
          description
            "Virtual-TokenRing interface number";
          type uint32 {
            range "0..2147483647";
          }
        }
        leaf VirtualPortGroup {
          description
            "VirtualPortGroup interface number";
          type uint8 {
            range "0..31";
          }
        }
        leaf Vlan {
          description
            "Vlan interface number";
          type uint16 {
            range "1..4095";
          }
        }
        leaf ucse {
          description
            "ucse interface number";
          type uint8;
        }
        leaf vasileft {
          description
            "vasileft interface number";
          type uint16 {
            range "1..2000";
          }
        }
        leaf vasiright {
          description
            "vasiright interface number";
          type uint16 {
            range "1..2000";
          }
        }
      }
      container server-only {
        description
          "Disable NHRP requests";
        presence "true";
        leaf non-caching {
          description
            "Do not create NHRP cache entries";
          type empty;
        }
      }
      container shortcut {
        description
          "Enable shortcut switching";
        presence "true";
        leaf virtual-template {
          description
            "Virtual template number";
          type uint16 {
            range "1..4095";
          }
        }
      }
      container trigger-svc {
        description
          "Create NHRP cut-through based on traffic load";
        list kbps {
          key "kbps";
          leaf kbps {
            description
              "Trigger rate in kbps";
            type uint32 {
              range "1..4294967295";
            }
          }
          leaf tear-kbps {
            description
              "Teardown rate in kbps";
            type uint32 {
              range "0..4294967295";
            }
          }
        }
      }
      leaf use {
        description
          "Number of packets to cause NHRP request";
        type uint16 {
          range "1..65535";
        }
      }
    }
  }

  /////////////////////////////////////////////////////////
  // native / interface / Tunnel / ip
  /////////////////////////////////////////////////////////
  augment "/ios:native/ios:interface/ios:Tunnel/ios:ip" {
    uses config-interface-nhrp-grouping;
  }
}
