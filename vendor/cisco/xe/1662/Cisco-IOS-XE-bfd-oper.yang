module Cisco-IOS-XE-bfd-oper {

    yang-version 1;

    namespace "http://cisco.com/ns/yang/Cisco-IOS-XE-bfd-oper";
    prefix bfd-ios-xe-oper;

    import ietf-inet-types {
        prefix inet;
    }

    organization
       "Cisco Systems, Inc.";

    contact
       "Cisco Systems, Inc. Customer Service Postal: 170 W Tasman Drive
     San Jose, CA 95134 Tel: +1 1800 553-NETS E-mail: cs-yang@cisco.com";
    
    description
       "This module contains a collection of YANG definitions for
        monitoring BFD neighbours."+
       "Copyright (c) 2016-2017 by Cisco Systems, Inc."+
       "All rights reserved.";

  // =========================================================================
  // REVISION
  // =========================================================================
  revision 2017-02-07 {
    description
      "Initial revision";
  }

    grouping bfd-neighbor-params {
        description "BFD neighbour parameters";
        leaf ld {
            type uint32;
            description "local-discriminator";
        }

        leaf rd {
            type uint32;
            description "remote-discriminator";
        }

        leaf remote-state {
            type bfd-ios-xe-oper:bfd-remote-state-type;
            description " Remote Heard. RH state of BFD version '0' 
                          is also mapped to up/down. ";
        }

        leaf state {
            type bfd-ios-xe-oper:bfd-state-type;
            description
                "BFD state";
        }
    }

    grouping bfd-tunnel-path-key {
        description "BFD tunnel Path Key";

        leaf interface {
            type  string;
        }

        leaf lsp-type {
            type bfd-ios-xe-oper:bfd-lsp-type;
        }
    }

    grouping bfd-circuit-key {
        description "BFD circuit key";
        leaf interface {
            type string;
        }

        leaf vcid {
            type uint32;
        }
    }

    grouping bfd-nbr-key {
        description "BFD Neighbor key";
        leaf ip {
            type inet:ip-address;
        }

        leaf interface {
            type string;
        }
    }

    grouping mhop-nbr-key {
        description "BHD MHOP Neighbor key";
        leaf ip {
            type inet:ip-address;
        }
    }

    grouping mhop-vrf-nbr-key {
        description "BHD MHOP VRF Neighbor key";
        leaf ip {
            type inet:ip-address;
        }

        leaf vrf {
            type string;
        }
 
    }

    grouping bfd-session {
        description "BHD session data";
        leaf type {
            description "Session type";
            type bfd-ios-xe-oper:bfd-oper-session-type;
        }

        container bfd-tunnel-paths {
            list bfd-tunnel-path {
                when "../../type='mpls-tp'"; 
                key "interface lsp-type";

                description "Tunnel Path";
                uses bfd-ios-xe-oper:bfd-tunnel-path-key;
                uses bfd-ios-xe-oper:bfd-neighbor-params;
            }
        }

        container bfd-circuits {
            list bfd-circuit {
                when "../../type='vccv'";
                key "interface vcid";

                description "BFD circuit";
                uses bfd-ios-xe-oper:bfd-circuit-key;
                uses bfd-ios-xe-oper:bfd-neighbor-params;
            }
        }

        container bfd-nbrs {
            list bfd-nbr {
                when "../../type!='mpls-tp' and ../../type!='vccv'";
                key "ip interface";
                description
                    "This is for directly connected neighbor case";
 
                uses bfd-ios-xe-oper:bfd-nbr-key;
                uses bfd-ios-xe-oper:bfd-neighbor-params;
            }
        }

        container bfd-mhop-nbrs {
            list bfd-mhop-nbr {
                when "../../type='ipv4-multihop' or ../../type='ipv6-multihop'";
                key "ip";
                description
                    "This is for multi hop neighbor scenario 
                    for global VRF (no VRF).";

                uses bfd-ios-xe-oper:mhop-nbr-key;
                uses bfd-ios-xe-oper:bfd-neighbor-params;
            }
        }

        container bfd-mhop-vrf-nbrs {
            list bfd-mhop-vrf-nbr {
                when "../../type='ipv4-multihop' or ../../type='ipv6-multihop'";
                key "ip vrf";
                description
                    "This is for multi hop neighbor scenario 
                    for non-global VRF.";
 
                uses bfd-ios-xe-oper:mhop-vrf-nbr-key;
                uses bfd-ios-xe-oper:bfd-neighbor-params;
            }
        }
    }

    typedef bfd-oper-session-type {
        description "BFD session type";
        type enumeration {
            enum ipv4;
            enum ipv6;
            enum vccv;
            enum mpls-tp;
            enum ipv4-multihop;
            enum ipv6-multihop;
        }
    }

    typedef bfd-remote-state-type {
        description "BFD remote state type";
        type enumeration {
            enum up;
            enum down;
            enum init;
            enum admindown;
            enum invalid;
        }
    }

    typedef bfd-state-type {
        description "BFD state type";
        type enumeration {
            enum admindown;
            enum down;
            enum fail;
            enum init;
            enum up;
            enum invalid;
        }
    }

    typedef bfd-lsp-type {
        description "BFD lsp type";
        type enumeration {
            enum working;
            enum protect;
            enum unknown;
        }
    }



    container bfd-state {
        config false;

        description
          "Data nodes for BFD neighbors.";

        container sessions {
            list session {
                key "type";
                uses bfd-ios-xe-oper:bfd-session;
            }
        }
    }
}
