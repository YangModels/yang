module Cisco-IOS-XE-ezpm {
  namespace "http://cisco.com/ns/yang/Cisco-IOS-XE-ezpm";
  prefix ios-ezpm;


  import ietf-inet-types {
    prefix inet;
  }

  import Cisco-IOS-XE-native {
    prefix ios;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Easy Performance Monitor (ezPM) Yang model.
     Copyright (c) 2016 by Cisco Systems, Inc.
     All rights reserved.";

  // =========================================================================
  // REVISION
  // =========================================================================
  revision 2017-02-07 {
    description
      "Initial revision";
  }


  grouping pm-context-traffic-monitor-app-traffic-stats-grouping {
    leaf cache-size {
      description
        "Maximum flow entries in the Flow Cache";
      type uint32 {
        range "64..2000000";
      }
    }
    leaf class-replace {
      description
        "Replace traffic classification";
      type string;
    }
    leaf interval-timeout {
      description
        "The exporting interval timeout";
      type uint32 {
        range "1..604800";
      }
    }
  }

  grouping pm-context-traffic-monitor-ip-grouping {
    leaf ipv4 {
      description
        "Activate monitor for ipv4 traffic";
      type empty;
    }
    leaf ipv6 {
      description
        "Activate monitor for ipv6 traffic";
      type empty;
    }
  }

  grouping performance-monitor-context-grouping {
    container exporter {
      description
        "Create exporter";
      leaf destination {
        description
          "Export destination configuration";
        type inet:ip-address;
      }
      leaf source {
        description
          "Originating interface";
        type string;
      }
      leaf port {
        description
          "port";
        type uint16;
      }
      leaf transport {
        description
          "transport";
        type enumeration {
          enum "udp";
        }
      }
      leaf vrf {
        description
          "vrf";
        type string;
      }
    }
    container traffic-monitor {
      description
        "Select traffic monitor";
      container all {
        description
          "All traffic monitors in this profile";
        when "../../profile = 'application-experience' or ../../profile = 'application-performance'";
        presence "true";
        leaf ipv4 {
          description
            "Activate monitor for ipv4 traffic";
          type empty;
        }
        leaf ipv6 {
          description
            "Activate monitor for ipv6 traffic";
          type empty;
        }
      }
      container application-response-time {
        description
          "Application response time (ART) metrics and counters for TCP traffic";
        when "../../profile = 'application-experience' or ../../profile = 'application-performance'";
        presence "true";
        uses pm-context-traffic-monitor-app-traffic-stats-grouping;
        leaf cache-type {
          description
            "The type of the Flow Cache";
          type enumeration {
            enum "normal";
            enum "synchronized";
          }
        }
        leaf class-and {
          description
            "Narrow down default traffic classification";
          type string;
        }
        uses pm-context-traffic-monitor-ip-grouping;
      }
      container application-traffic-stats {
        description
          "Application level counters for dns and dht protocol";
        when "../../profile = 'application-experience'";
        presence "true";
        uses pm-context-traffic-monitor-app-traffic-stats-grouping;
      }
      container conversation-traffic-stats {
        description
          "Conversation level counters for IP traffic";
        when "../../profile = 'application-experience'";
        presence "true";
        uses pm-context-traffic-monitor-app-traffic-stats-grouping;
        leaf cache-type {
          description
            "The type of the Flow Cache";
          type enumeration {
            enum "normal";
            enum "synchronized";
          }
        }
        uses pm-context-traffic-monitor-ip-grouping;
      }
      container media {
        description
          "Media metrics and counters for rtp and telepresence-media traffic";
        when "../../profile = 'application-experience' or ../../profile = 'application-performance'";
        presence "true";
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        uses pm-context-traffic-monitor-ip-grouping;
      }
      container url {
        description
          "URL information, application response time (ART) metrics and counters";
        when "../../profile = 'application-experience' or ../../profile = 'application-performance'";
        presence "true";
        leaf cache-size {
          description
            "Maximum flow entries in the Flow Cache";
          type uint32 {
            range "64..2000000";
          }
        }
        leaf class-and {
          description
            "Narrow down default traffic classification";
          type string;
        }
        leaf class-replace {
          description
            "Replace traffic classification";
          type string;
        }
        uses pm-context-traffic-monitor-ip-grouping;
        leaf sampling-rate {
          description
            "Sampling rate of flow sampler";
          type uint32 {
            range "1..32768";
          }
        }
      }
      container application-client-server-stats {
        description
          "Per interface, client, server and application statistics";
        presence "true";
        when "../../profile = 'application-performance' or ../../profile = 'application-statistics'";
        uses pm-context-traffic-monitor-app-traffic-stats-grouping;
        leaf cache-type {
          description
            "The type of the Flow Cache";
          type enumeration {
            enum "normal";
            enum "synchronized";
          }
        }
        uses pm-context-traffic-monitor-ip-grouping;
      }
      container application-stats {
        description
          "Per application and interface statistics";
        presence "true";
        when "../../profile = 'application-performance' or ../../profile = 'application-statistics'";
        uses pm-context-traffic-monitor-app-traffic-stats-grouping;
      }
    }
  }

  grouping performance-monitor-context-default-grouping {
    container exporter {
      description
        "Create exporter";
      leaf destination {
        description
          "Export destination configuration";
        type inet:ip-address;
      }
      leaf source {
        description
          "Originating interface";
        type string;
      }
      leaf port {
        description
          "port";
        type uint16;
      }
      leaf transport {
        description
          "transport";
        type enumeration {
          enum "udp";
        }
      }
      leaf vrf {
        description
          "vrf";
        type string;
      }
    }
    container traffic-monitor {
      description
        "Select traffic monitor";
      container all {
        description
          "All traffic monitors in this profile";
        when "../../../profile = 'application-experience' or ../../../profile = 'application-performance'";
        presence "true";
        leaf ipv4 {
          description
            "Activate monitor for ipv4 traffic";
          type empty;
        }
        leaf ipv6 {
          description
            "Activate monitor for ipv6 traffic";
          type empty;
        }
      }
      container application-response-time {
        description
          "Application response time (ART) metrics and counters for TCP traffic";
        when "../../../profile = 'application-experience' or ../../../profile = 'application-performance'";
        presence "true";
        uses pm-context-traffic-monitor-app-traffic-stats-grouping;
        leaf cache-type {
          description
            "The type of the Flow Cache";
          type enumeration {
            enum "normal";
            enum "synchronized";
          }
        }
        leaf class-and {
          description
            "Narrow down default traffic classification";
          type string;
        }
        uses pm-context-traffic-monitor-ip-grouping;
      }
      container application-traffic-stats {
        description
          "Application level counters for dns and dht protocol";
        when "../../../profile = 'application-experience'";
        presence "true";
        uses pm-context-traffic-monitor-app-traffic-stats-grouping;
      }
      container conversation-traffic-stats {
        description
          "Conversation level counters for IP traffic";
        when "../../../profile = 'application-experience'";
        presence "true";
        uses pm-context-traffic-monitor-app-traffic-stats-grouping;
        leaf cache-type {
          description
            "The type of the Flow Cache";
          type enumeration {
            enum "normal";
            enum "synchronized";
          }
        }
        uses pm-context-traffic-monitor-ip-grouping;
      }
      container media {
        description
          "Media metrics and counters for rtp and telepresence-media traffic";
        when "../../../profile = 'application-experience' or ../../../profile = 'application-performance'";
        presence "true";
        uses pm-context-traffic-monitor-app-traffic-stats-grouping;
        leaf class-and {
          description
            "Narrow down default traffic classification";
          type string;
        }
        leaf egress {
          description
            "Activate monitor on egress direction";
          type empty;
        }
        leaf ingress {
          description
            "Activate monitor on ingress direction";
          type empty;
        }
        uses pm-context-traffic-monitor-ip-grouping;
      }
      container url {
        description
          "URL information, application response time (ART) metrics and counters";
        when "../../../profile = 'application-experience' or ../../../profile = 'application-performance'";
        presence "true";
        leaf cache-size {
          description
            "Maximum flow entries in the Flow Cache";
          type uint32 {
            range "64..2000000";
          }
        }
        leaf class-and {
          description
            "Narrow down default traffic classification";
          type string;
        }
        leaf class-replace {
          description
            "Replace traffic classification";
          type string;
        }
        uses pm-context-traffic-monitor-ip-grouping;
        leaf sampling-rate {
          description
            "Sampling rate of flow sampler";
          type uint32 {
            range "1..32768";
          }
        }
      }
      container application-client-server-stats {
        description
          "Per interface, client, server and application statistics";
        presence "true";
        when "../../../profile = 'application-performance' or ../../../profile = 'application-statistics'";
        uses pm-context-traffic-monitor-app-traffic-stats-grouping;
        leaf cache-type {
          description
            "The type of the Flow Cache";
          type enumeration {
            enum "normal";
            enum "synchronized";
          }
        }
        uses pm-context-traffic-monitor-ip-grouping;
      }
      container application-stats {
        description
          "Per application and interface statistics";
        presence "true";
        when "../../../profile = 'application-performance' or ../../../profile = 'application-statistics'";
        uses pm-context-traffic-monitor-app-traffic-stats-grouping;
      }
    }
  }

  grouping config-ezpm-grouping {
    container monitor {
      description
        "monitor";
      list context {
        description
          "Define ezPM context";
        key "name";
        leaf name {
          type string;
        }
        leaf profile {
          description
            "Select ezPM profile";
          type enumeration {
            enum "application-experience";
            enum "application-performance";
            enum "application-statistics";
          }
        }
        container default {
          description
            "Set a command to its defaults";
          leaf description {
            description
              "Provide a description for ezPM context";
            type empty;
          }
          uses performance-monitor-context-default-grouping;
        }
        leaf description {
          description
            "Provide a description for ezPM context";
          type string;
        }
        uses performance-monitor-context-grouping;
      }
      container observation-point {
        description
          "Select observation point";
        leaf encrypted-text {
          description
            "Select clear text for observation";
          type empty;
        }
      }
    }
  }

  grouping config-interface-ezpm-grouping {
    container performance {
      description
        "Global performance monitor configuration";
      container monitor {
        description
          "monitor";
        leaf-list context {
          description
            "Select ezPM context";
          type string;
        }
      }
    }
  }

  /////////////////////////////////////////////////////////
  // native / performance
  /////////////////////////////////////////////////////////
  augment "/ios:native/ios:performance" {
    uses config-ezpm-grouping;
  }

  /////////////////////////////////////////////////////////
  // native / interface * / performance monitor
  /////////////////////////////////////////////////////////
  augment "/ios:native/ios:interface/ios:FastEthernet" {
    uses config-interface-ezpm-grouping {
      if-feature ios-features:ezpm;
    }
  }

  augment "/ios:native/ios:interface/ios:GigabitEthernet" {
    uses config-interface-ezpm-grouping {
      if-feature ios-features:ezpm;
    }
  }

  augment "/ios:native/ios:interface/ios:TenGigabitEthernet" {
    uses config-interface-ezpm-grouping {
      if-feature ios-features:ezpm;
    }
  }

  augment "/ios:native/ios:interface/ios:Tunnel" {
    uses config-interface-ezpm-grouping {
      if-feature ios-features:ezpm;
    }
  }

  augment "/ios:native/ios:interface/ios:Loopback" {
    uses config-interface-ezpm-grouping {
      if-feature ios-features:ezpm;
    }
  }

} //module
