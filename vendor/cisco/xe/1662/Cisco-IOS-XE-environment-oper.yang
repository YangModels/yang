module Cisco-IOS-XE-environment-oper {
  yang-version 1;
  namespace "http://cisco.com/ns/yang/Cisco-IOS-XE-environment-oper";
  prefix environment-ios-xe-oper;

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for monitoring Environment of a Network Element.
     Copyright (c) 2016-2017 by Cisco Systems, Inc.
     All rights reserved.";

  revision 2017-02-07 {
    description
      "Initial revision";
    reference "1.0.0";
  }

  typedef sensor-units-type {
    type enumeration {
      enum "Watts" {
        value 0;
      }
      enum "Celsius" {
        value 1;
      }
      enum "milliVolts" {
        value 2;
      }
      enum "Amperes" {
        value 3;
      }
      enum "Volts-DC" {
        value 4;
      }
      enum "Volts-AC" {
        value 5;
      }
      enum "milliAmperes" {
        value 6;
      }
    }
    description
      "Units used by various sensors";
  }

  grouping sensor-name-loc-key {
    description
      "Each sensor representing a data node is 
       uniquely identified by a name and a location based key";
    leaf name {
      type string;
      description
        "Name of the sensor component.
         This includes all physical components of the chasis -
         both fixed and pluggable";
    }
    leaf location {
      type string;
      description
        "Sensor location";
    }
  }

  grouping sensor-params {
    description
      "Sensor parameters";
    leaf state {
      type string;
      description
        "A description of the current state of the sensor";
    }
    leaf current-reading {
      type uint32;
      description
        "Numerical value of the current sensor reading in sensor-units";
    }
    leaf sensor-units {
      type environment-ios-xe-oper:sensor-units-type;
      description
        "Units corresponding to the current-reading value";
    }
  }

  container environment-sensors {
    config false;
    description
      "Data nodes for Environmental Monitoring";
    list environment-sensor {
      key "name location";
      description
        "The list of components on the device chasis";
      uses environment-ios-xe-oper:sensor-params;
      uses environment-ios-xe-oper:sensor-name-loc-key;
    }
  }
}
