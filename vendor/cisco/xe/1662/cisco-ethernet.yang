module cisco-ethernet {

     yang-version 1;

     namespace "urn:cisco:params:xml:ns:yang:cisco-ethernet";
     prefix eth;

     import ietf-interfaces {
       prefix if;
     }

     import iana-if-type {
        prefix ianaift;
     }

     organization
    "Cisco Systems, Inc.";

   contact
    " Cisco Systems, Inc.
    Customer Service

    Postal: 170 W Tasman Drive
    San Jose, CA 95134

    Tel: +1 1800 553-NETS

    E-mail: cs-yang@cisco.com";
    
    description
       "This module contains a collection of YANG definitions for
        configuring Ethernet Interfaces.
        Copyright (c) 2016 by Cisco Systems, Inc.
        All rights reserved.";
    
    reference "TODO";

    revision 2016-05-10 {
      description
        "Added iana-if-type import";
    }

    revision 2016-03-30 {
      description
        "Update description with copyright notice.";
    }

    revision 2014-05-12 {
        description "Proposed";  
    }

     identity eth-if-speed {
       description "Representing the speed of the ethernet interface";
     }
     identity eth-if-speed-10mb {
       base eth-if-speed;
     }
     identity eth-if-speed-100mb {
       base eth-if-speed;
     }
      identity eth-if-speed-1gb {
       base eth-if-speed;
     }
     identity eth-if-speed-10gb {
       base eth-if-speed;
     }
     identity eth-if-speed-40gb {
       base eth-if-speed;
     }
     identity eth-if-speed-100gb {
       base eth-if-speed;
     }

     // configuration parameters for ethernet interfaces
     augment "/if:interfaces/if:interface" {
       when "if:type = 'ianaift:ethernetCsmacd'";

       container ethernet {
       
         container transmission-params {
          choice transmission-mode {
           case auto1 {
             leaf auto-negotiate {
               type empty;
             }
           }
           case manual {
             leaf duplex {
               type enumeration {
                 enum "half";
                 enum "full";
               }
             }
             leaf speed {
               type identityref {
                   base eth-if-speed;
                }
             }
           }

         }
       }
       
         leaf mtu-size {
           type uint16;
         }
         // must "mtu-size >=/if:interfaces-state/if:interface/eth:ethernet/eth:supported-mtu-range/eth:min-mtu-size and mtu-size <= /if:interfaces-state/if:interface/eth:ethernet/eth:supported-mtu-range/eth:max-mtu-size";
       }
     }

     // operational state parameters for ethernet interfaces
     augment "/if:interfaces-state/if:interface" {
       when "if:type = 'ianaift:ethernetCsmacd'";

       container ethernet {

         leaf duplex {
           type enumeration {
             enum "half";
             enum "full";
             enum "disagree";
           }
         }
          
          container supported-mtu-range {
           leaf min-mtu-size {
               type uint16;
           }
           leaf max-mtu-size {
               type uint16;
           }
           // must "min-mtu-size <= max-mtu-size";
          }
       }
     }
   }
