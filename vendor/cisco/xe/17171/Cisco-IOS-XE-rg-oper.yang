module Cisco-IOS-XE-rg-oper {
  yang-version 1.1;
  namespace "http://cisco.com/ns/yang/Cisco-IOS-XE-rg-oper";
  prefix rg-ios-xe-oper;

  import Cisco-IOS-XE-red-app-common-types {
    prefix red-app-comm-ios-xe-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for redundancy application operational data.
     Copyright (c) 2024 by Cisco Systems, Inc.
     All rights reserved.";

  revision 2024-07-01 {
    description
      "Initial revision";
    reference
      "1.0.0";
    cisco-semver:module-version "1.0.0";
  }

  grouping red-app-group {
    description
      "Redundancy group information";
    leaf rg-id {
      type uint32;
      description
        "Key for application group";
    }
    leaf sys-time {
      type yang:date-and-time;
      description
        "Time when the last role change occurred";
    }
    leaf site-id {
      type uint32;
      description
        "Site identifier";
    }
    leaf sys-ip-addr {
      type inet:ip-address;
      description
        "Local system address";
    }
    leaf role {
      type red-app-comm-ios-xe-types:rg-app-role;
      description
        "Redundancy application role";
    }
    leaf group-name {
      type string;
      description
        "Redundancy application group name";
    }
    leaf-list vpn-id {
      type uint32;
      max-elements 65536;
      ordered-by user;
      description
        "List of Redundancy application group VPN IDs";
    }
  }

  container rg-oper-data {
    config false;
    description
      "This is top level container for redundancy application operational data";
    list red-app-group {
      key "rg-id";
      description
        "Redundancy application group information";
      uses rg-ios-xe-oper:red-app-group;
    }
  }
}
