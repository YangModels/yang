module Cisco-IOS-XE-types {
  yang-version 1.1;
  namespace "http://cisco.com/ns/yang/Cisco-IOS-XE-types";
  prefix ios-types;

  import cisco-semver {
    prefix cisco-semver;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Common Type Definitions
     Copyright (c) 2016-2023 by Cisco Systems, Inc.
     All rights reserved.";

  revision 2025-03-01 {
    description
      "- Add fnf punt cause";
    cisco-semver:module-version "1.10.0";
  }
  revision 2024-03-01 {
    description
      "- Add voice port number type
       - Add punt-cause-type";
    cisco-semver:module-version "1.9.0";
  }
  revision 2023-07-01 {
    description
      "- Add Bundle interface type";
    cisco-semver:module-version "1.8.0";
  }
  revision 2023-03-01 {
    description
      "- added new data type for community name string
       - Updated the regular expression for community name";
    cisco-semver:module-version "1.7.0";
  }
  revision 2022-11-01 {
    description
      "- Update yang-version to 1.1";
    cisco-semver:module-version "1.6.0";
  }
  revision 2021-11-01 {
    description
      "- Added ip-address-both type";
    cisco-semver:module-version "1.5.0";
  }
  revision 2021-07-01 {
    description
      "- Added cos-type";
    cisco-semver:module-version "1.4.0";
  }
  revision 2021-03-01 {
    description
      "- Initial revision for 17.5.1";
    cisco-semver:module-version "1.3.0";
  }
  revision 2020-11-01 {
    description
      "- Added large-community-number-type";
    cisco-semver:module-version "1.2.0";
  }
  revision 2019-11-01 {
    description
      "
       - Added new typedef for link local address";
    cisco-semver:module-version "1.1.0";
  }
  revision 2019-07-01 {
    description
      "- Establish semantic version baseline
       - Added slot-bay-type for voice-card
       - Added mcast-std-acl-type for multicast
       - Add BD-VIF in interface type enum";
    cisco-semver:module-version "1.0.0";
  }
  revision 2019-01-22 {
    description
      "Added leaf for App-hosting Gigabit Ethernet interface";
  }
  revision 2018-06-24 {
    description
      "Added TCP-UDP port type";
  }
  revision 2018-05-22 {
    description
      "Change range-string pattern to single quotes";
  }
  revision 2017-11-27 {
    description
      "Added Change 25GE name";
  }
  revision 2017-10-15 {
    description
      "This revision has changes for new 2gig interface addition";
  }
  revision 2017-10-05 {
    description
      "Add a new type range-string";
  }
  revision 2017-08-16 {
    description
      "This revision has changes for new 5gig and 25gig interfaces addition";
  }
  revision 2017-06-09 {
    description
      "Add a new type ipv4-address-slash-prefix-len";
  }
  revision 2017-06-05 {
    description
      "Update the ipv4 cisco-route-distinguisher type 1 pattern to
       conform to YANG 1.1";
    reference
      "RFC 7950: The YANG 1.1 Data Modeling Language";
  }
  revision 2017-04-05 {
    description
      "Add value statements to udp and tcp ace port number enumerations";
  }
  revision 2017-02-07 {
    description
      "Initial revision";
  }

  typedef access-list-type {
    type union {
      type uint16 {
        range "1..199";
      }
      type uint16 {
        range "1300..2699";
      }
    }
  }

  typedef access-list-standard-id-type-non-default {
    type union {
      type access-list-type;
      type string;
    }
  }

  typedef access-list-standard-id-type {
    type union {
      type default-access-list-standard-id-type;
      type string;
    }
  }

  typedef access-list-in-out-type {
    type enumeration {
      enum in;
      enum out;
    }
  }

  typedef acl-udp-port-type {
    type union {
      type uint16;
      type enumeration {
        enum biff {
          value 512;
        }
        enum bootpc {
          value 68;
        }
        enum bootps {
          value 67;
        }
        enum discard {
          value 9;
        }
        enum dnsix {
          value 195;
        }
        enum domain {
          value 53;
        }
        enum echo {
          value 7;
        }
        enum isakmp {
          value 500;
        }
        enum mobile-ip {
          value 434;
        }
        enum nameserver {
          value 42;
        }
        enum netbios-dgm {
          value 138;
        }
        enum netbios-ns {
          value 137;
        }
        enum netbios-ss {
          value 139;
        }
        enum non500-isakmp {
          value 4500;
        }
        enum ntp {
          value 123;
        }
        enum pim-auto-rp {
          value 496;
        }
        enum rip {
          value 520;
        }
        enum ripv6 {
          value 521;
        }
        enum snmp {
          value 161;
        }
        enum snmptrap {
          value 162;
        }
        enum sunrpc {
          value 111;
        }
        enum syslog {
          value 514;
        }
        enum tacacs {
          value 49;
        }
        enum talk {
          value 517;
        }
        enum tftp {
          value 69;
        }
        enum time {
          value 37;
        }
        enum who {
          value 513;
        }
        enum xdmcp {
          value 177;
        }
      }
    }
  }

  typedef acl-tcp-port-type {
    type union {
      type uint16;
      type enumeration {
        enum bgp {
          value 179;
        }
        enum chargen {
          value 19;
        }
        enum cmd {
          value 514;
        }
        enum daytime {
          value 13;
        }
        enum discard {
          value 9;
        }
        enum domain {
          value 53;
        }
        enum echo {
          value 7;
        }
        enum exec {
          value 512;
        }
        enum finger {
          value 79;
        }
        enum ftp {
          value 21;
        }
        enum ftp-data {
          value 20;
        }
        enum gopher {
          value 70;
        }
        enum hostname {
          value 101;
        }
        enum ident {
          value 113;
        }
        enum irc {
          value 194;
        }
        enum klogin {
          value 543;
        }
        enum kshell {
          value 544;
        }
        enum login {
          value 513;
        }
        enum lpd {
          value 515;
        }
        enum msrpc {
          value 135;
        }
        enum nntp {
          value 119;
        }
        enum onep-plain {
          value 15001;
        }
        enum onep-tls {
          value 15002;
        }
        enum pim-auto-rp {
          value 496;
        }
        enum pop2 {
          value 109;
        }
        enum pop3 {
          value 110;
        }
        enum smtp {
          value 25;
        }
        enum sunrpc {
          value 111;
        }
        enum tacacs {
          value 49;
        }
        enum talk {
          value 517;
        }
        enum telnet {
          value 23;
        }
        enum time {
          value 37;
        }
        enum uucp {
          value 540;
        }
        enum whois {
          value 43;
        }
        enum www {
          value 80;
        }
      }
    }
  }

  typedef acl-tcp-udp-port-type {
    type union {
      type uint16;
      type enumeration {
        enum discard {
          value 9;
        }
        enum domain {
          value 53;
        }
        enum echo {
          value 7;
        }
        enum pim-auto-rp {
          value 496;
        }
        enum sunrpc {
          value 111;
        }
        enum syslog {
          value 514;
        }
        enum tacacs {
          value 49;
        }
        enum talk {
          value 517;
        }
      }
    }
  }

  typedef udp-port-type {
    type union {
      type uint16 {
        range "0..6|8|10..36|38..41|43..48|50..52|54..66|70..110|112..122|124..136|140..160|163..176|178..194|196..433|435..495|497..499|501..511|515|516|518|519|522..4499|4501..65535";
      }
      type enumeration {
        enum biff {
          value 512;
        }
        enum bootpc {
          value 68;
        }
        enum bootps {
          value 67;
        }
        enum discard {
          value 9;
        }
        enum dnsix {
          value 195;
        }
        enum domain {
          value 53;
        }
        enum echo {
          value 7;
        }
        enum isakmp {
          value 500;
        }
        enum mobile-ip {
          value 434;
        }
        enum nameserver {
          value 42;
        }
        enum netbios-dgm {
          value 138;
        }
        enum netbios-ns {
          value 137;
        }
        enum netbios-ss {
          value 139;
        }
        enum non500-isakmp {
          value 4500;
        }
        enum ntp {
          value 123;
        }
        enum pim-auto-rp {
          value 496;
        }
        enum rip {
          value 520;
        }
        enum ripv6 {
          value 521;
        }
        enum snmp {
          value 161;
        }
        enum snmptrap {
          value 162;
        }
        enum sunrpc {
          value 111;
        }
        enum syslog {
          value 514;
        }
        enum tacacs {
          value 49;
        }
        enum talk {
          value 517;
        }
        enum tftp {
          value 69;
        }
        enum time {
          value 37;
        }
        enum who {
          value 513;
        }
        enum xdmcp {
          value 177;
        }
      }
    }
  }

  typedef tcp-port-type {
    type union {
      type uint16 {
        range "0..6|8|10..12|14..18|22|24|26..36|38..42|44..48|50..52|54..69|71..78|81..100|102..108|112|114..118|120..134|136..178|180..193|195..495|497..511|516|518..539|540..542|545..15000|15003..65535";
      }
      type enumeration {
        enum bgp {
          value 179;
        }
        enum chargen {
          value 19;
        }
        enum cmd {
          value 514;
        }
        enum daytime {
          value 13;
        }
        enum discard {
          value 9;
        }
        enum domain {
          value 53;
        }
        enum echo {
          value 7;
        }
        enum exec {
          value 512;
        }
        enum finger {
          value 79;
        }
        enum ftp {
          value 21;
        }
        enum ftp-data {
          value 20;
        }
        enum gopher {
          value 70;
        }
        enum hostname {
          value 101;
        }
        enum ident {
          value 113;
        }
        enum irc {
          value 194;
        }
        enum klogin {
          value 543;
        }
        enum kshell {
          value 544;
        }
        enum login {
          value 513;
        }
        enum lpd {
          value 515;
        }
        enum msrpc {
          value 135;
        }
        enum nntp {
          value 119;
        }
        enum onep-plain {
          value 15001;
        }
        enum onep-tls {
          value 15002;
        }
        enum pim-auto-rp {
          value 496;
        }
        enum pop2 {
          value 109;
        }
        enum pop3 {
          value 110;
        }
        enum smtp {
          value 25;
        }
        enum sunrpc {
          value 111;
        }
        enum tacacs {
          value 49;
        }
        enum talk {
          value 517;
        }
        enum telnet {
          value 23;
        }
        enum time {
          value 37;
        }
        enum uucp {
          value 540;
        }
        enum whois {
          value 43;
        }
        enum www {
          value 80;
        }
      }
    }
  }

  typedef default-access-list-standard-id-type {
    type union {
      type uint8 {
        range "1..99";
      }
      type uint16 {
        range "1300..1999";
      }
    }
  }

  typedef redist-ospf-external-type {
    type enumeration {
      enum 1;
      enum 2;
    }
  }

  typedef bgp-as-number-type {
    type union {
      type uint32 {
        range "1..4294967295";
      }
      type string;
    }
  }

  typedef cos_value-type {
    type union {
      type uint8 {
        range "0..7";
      }
      type enumeration {
        enum cos;
        enum dscp;
        enum exp;
        enum precedence;
      }
    }
  }

  typedef cos-type {
    type uint8 {
      range "0..7";
    }
  }

  typedef exp-type {
    type uint8 {
      range "0..7";
    }
  }

  typedef dscp-type {
    type union {
      type uint8 {
        range "0..63";
      }
      type enumeration {
        enum af11 {
          value 10;
        }
        enum af12 {
          value 12;
        }
        enum af13 {
          value 14;
        }
        enum af21 {
          value 18;
        }
        enum af22 {
          value 20;
        }
        enum af23 {
          value 22;
        }
        enum af31 {
          value 26;
        }
        enum af32 {
          value 28;
        }
        enum af33 {
          value 30;
        }
        enum af41 {
          value 34;
        }
        enum af42 {
          value 36;
        }
        enum af43 {
          value 38;
        }
        enum cs1 {
          value 8;
        }
        enum cs2 {
          value 16;
        }
        enum cs3 {
          value 24;
        }
        enum cs4 {
          value 32;
        }
        enum cs5 {
          value 40;
        }
        enum cs6 {
          value 48;
        }
        enum cs7 {
          value 56;
        }
        enum default {
          value 0;
        }
        enum dscp;
        enum ef {
          value 46;
        }
        enum precedence;
      }
    }
  }

  typedef dscp-type-new {
    type union {
      type uint8 {
        range "1..7|9|11|13|15|17|19|21|23|25|27|29|31|33|35|37|39|41..45|47|49..55|57..63";
      }
      type enumeration {
        enum af11 {
          value 10;
        }
        enum af12 {
          value 12;
        }
        enum af13 {
          value 14;
        }
        enum af21 {
          value 18;
        }
        enum af22 {
          value 20;
        }
        enum af23 {
          value 22;
        }
        enum af31 {
          value 26;
        }
        enum af32 {
          value 28;
        }
        enum af33 {
          value 30;
        }
        enum af41 {
          value 34;
        }
        enum af42 {
          value 36;
        }
        enum af43 {
          value 38;
        }
        enum cs1 {
          value 8;
        }
        enum cs2 {
          value 16;
        }
        enum cs3 {
          value 24;
        }
        enum cs4 {
          value 32;
        }
        enum cs5 {
          value 40;
        }
        enum cs6 {
          value 48;
        }
        enum cs7 {
          value 56;
        }
        enum default {
          value 0;
        }
        enum ef {
          value 46;
        }
      }
    }
  }

  typedef exp-acl-type {
    type union {
      type uint16 {
        range "1..199 | 1300..2699";
      }
      type string {
        pattern '[a-zA-Z].*';
      }
    }
  }

  typedef exp_value-type {
    type union {
      type uint8 {
        range "0..7";
      }
      type enumeration {
        enum cos;
        enum dscp;
        enum exp;
        enum precedence;
      }
    }
  }

  typedef ext-acl-type {
    type union {
      type uint16 {
        range "100..199";
      }
      type uint16 {
        range "2000..2699";
      }
      type string {
        pattern '[a-zA-Z].*';
      }
    }
  }

  typedef hhmm-type {
    type string {
      pattern '([0-1]?[0-9]|2[0-4]):([0-5][0-9])(:[0-5][0-9])?';
    }
  }

  typedef hhmmss-type {
    type string {
      pattern '([0-1]?[0-9]|2[0-4]):([0-5][0-9]):([0-5][0-9])';
    }
  }

  typedef asn-ip-type {
    type string {
      pattern '(([0-9]+\.[0-9]+)|([0-9]+)|((([0-9]|[1-9][0-9]|1[0-9][0-9]|2[0-4][0-9]|25[0-5])\.){3}([0-9]|[1-9][0-9]|1[0-9][0-9]|2[0-4][0-9]|25[0-5]))):[0-9]+';
    }
  }

  typedef host-type {
    type union {
      type inet:ip-address;
      type inet:domain-name;
    }
  }

  typedef interface-type {
    type enumeration {
      enum BDI;
      enum FastEthernet;
      enum GigabitEthernet;
      enum Loopback;
      enum Port-channel;
      enum Serial;
      enum TenGigabitEthernet;
      enum Vlan;
      enum FiveGigabitEthernet;
      enum TwentyFiveGigE;
      enum TwoGigabitEthernet;
      enum AppGigabitEthernet;
      enum BD-VIF;
      enum Bundle;
    }
  }

  typedef interface-name {
    type union {
      type uint16;
      type uint32;
      type string;
    }
  }

  typedef ip-host {
    type union {
      type inet:ip-address;
      type inet:domain-name;
    }
  }

  typedef ipv4-host {
    type union {
      type inet:ipv4-address;
      type inet:domain-name;
    }
    description
      "The host type represents either an IPv4 address or a DNS
       domain name.";
  }

  typedef ipv6-host {
    type union {
      type inet:ipv6-address;
      type inet:domain-name;
    }
    description
      "The host type represents either an IPv6 address or a DNS
       domain name.";
  }

  typedef mobility-type {
    type union {
      type uint8;
      type enumeration {
        enum bind-acknowledgement;
        enum bind-error;
        enum bind-refresh;
        enum bind-update;
        enum cot;
        enum coti;
        enum hot;
        enum hoti;
      }
    }
  }

  typedef prec_value-type {
    type union {
      type uint8 {
        range "0..7";
      }
      type enumeration {
        enum cos;
        enum dscp;
        enum exp;
        enum precedence;
      }
    }
  }

  typedef precedence-type {
    type union {
      type uint8 {
        range "0..7";
      }
      type enumeration {
        enum critical;
        enum flash;
        enum flash-override;
        enum immediate;
        enum internet;
        enum network;
        enum priority;
        enum routine;
      }
    }
  }

  typedef std-acl-type {
    type union {
      type uint16 {
        range "1..99";
      }
      type uint16 {
        range "1300..1999";
      }
      type string {
        pattern '[a-zA-Z].*';
      }
    }
  }

  typedef percentage {
    type uint8 {
      range "0..100";
    }
  }

  typedef limit-dc-non-dc-type {
    type union {
      type uint32 {
        range "1 .. 255";
      }
      type enumeration {
        enum disable;
      }
    }
  }

  typedef ospf-area-type {
    type union {
      type uint32 {
        range "0 .. 4294967295";
      }
      type inet:ipv4-address;
    }
  }

  typedef ospf-metric-type {
    type uint32 {
      range "1 .. 2";
    }
  }

  typedef qos_value-type {
    type union {
      type uint8 {
        range "0..99";
      }
      type enumeration {
        enum cos;
        enum dscp;
        enum exp;
        enum precedence;
      }
    }
  }

  typedef weekday-type {
    type enumeration {
      enum Mon;
      enum Tue;
      enum Wed;
      enum Thu;
      enum Fri;
      enum Sat;
      enum Sun;
    }
  }

  typedef isis-distribute-list-type {
    type uint16 {
      range "100..199";
    }
  }

  typedef bgp-distribute-list-type {
    type union {
      type uint16 {
        range "100..199";
      }
      type uint16 {
        range "2000..2699";
      }
      type string {
        pattern '[a-zA-Z].*';
      }
    }
  }

  typedef bgp-distribute-list-type2 {
    type union {
      type uint16 {
        range "1..199";
      }
      type uint16 {
        range "1300..2699";
      }
      type string {
        pattern '[a-zA-Z].*';
      }
    }
  }

  typedef bgp_ipv4_af_type {
    type enumeration {
      enum unicast;
      enum multicast;
      enum mdt;
      enum tunnel;
      enum labeled-unicast;
      enum flowspec;
      enum mvpn;
      enum sr-policy;
    }
  }

  typedef bgp_ipv6_af_type {
    type enumeration {
      enum unicast;
      enum multicast;
      enum mdt;
      enum flowspec;
      enum mvpn;
    }
  }

  typedef storm-control-threshold-type {
    type string {
      pattern '[0-9]+.?[0-9]*[k|m|g]?';
    }
  }

  typedef community-number-type {
    type union {
      type uint32 {
        range "1..4294967295";
      }
      type string {
        pattern '(\d+:\d+)';
      }
    }
  }

  typedef community-name-string {
    type string {
      pattern '(([a-zA-Z0-9]*)(([^0-9]+)([a-zA-Z0-9]*))+)';
    }
  }

  typedef community-well-known-type {
    type enumeration {
      enum gshut;
      enum internet;
      enum local-AS;
      enum no-advertise;
      enum no-export;
    }
  }

  typedef large-community-number-type {
    type string {
      pattern '(\d+:\d+:\d+)';
    }
  }

  typedef community-well-known-add-type {
    type enumeration {
      enum gshut;
      enum internet;
      enum local-AS;
      enum no-advertise;
      enum no-export;
      enum additive;
    }
  }

  typedef cisco-mac-address-type {
    type string {
      pattern '[0-9a-fA-F]+\.[0-9a-fA-F]+\.[0-9a-fA-F]+';
    }
  }

  typedef month-type {
    type enumeration {
      enum Jan;
      enum Feb;
      enum Mar;
      enum Apr;
      enum May;
      enum Jun;
      enum Jul;
      enum Aug;
      enum Sep;
      enum Oct;
      enum Nov;
      enum Dec;
    }
  }

  typedef ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
      pattern '(([^:]+:){6}(([^:]+:[^:]+)|(.*\..*)))|((([^:]+:)*[^:]+)?::(([^:]+:)*[^:]+)?)(/.+)';
    }
  }

  typedef cisco-route-distinguisher {
    type union {
      type string {
        pattern '(65[0-5][0-3][0-5]|[1-5][1-5][0-9][0-9][0-9]|[1-9]?[1-9]?[0-9][0-9]|[0-9]):(4[0-2][0-9][0-4][0-9][0-6][0-7][0-2][0-9][0-5]|[0-3][0-9]{9}|[1-9][0-9]{1,8}|[0-9])';
      }
      type string {
        pattern '(([0-9]|[1-9][0-9]|1[0-9][0-9]|2[0-4][0-9]|25[0-5])\.){3}([0-9]|[1-9][0-9]|1[0-9][0-9]|2[0-4][0-9]|25[0-5]):(65[0-5][0-3][0-5]|[1-5][1-5][0-9][0-9][0-9]|[1-9]?[1-9]?[0-9][0-9]|[0-9])';
      }
      type string {
        pattern '(4[0-2][0-9][0-4][0-9][0-6][0-7][0-2][0-9][0-5]|[0-3][0-9]{9}|[1-9][0-9]{1,8}|[1-9]):(65[0-5][0-3][0-5]|[1-5]{2}[0-9]{3}|[1-9]{0,2}[0-9][0-9]|[0-9])';
      }
    }
  }

  typedef range-string {
    type string {
      pattern '((\d+(-\d+)?)(,(\d+(-\d+)?))*)';
    }
  }

  typedef ipv4-address-slash-prefix-len {
    type string {
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
  }

  typedef mcast-std-acl-type {
    type union {
      type uint8 {
        range "1..99";
      }
      type string {
        pattern '[a-zA-Z].*';
      }
    }
  }

  typedef slot-bay-type {
    type string {
      pattern '[0-9]+/[0-9]+';
    }
  }

  typedef ipv6-link-local-interface-address {
    type string {
      pattern '(([^:]+:){6}(([^:]+:[^:]+)|(.*\..*)))|((([^:]+:)*[^:]+)?::(([^:]+:)*[^:]+)?)(%.+)?';
    }
  }

  typedef ip-address-both {
    type union {
      type inet:ipv4-address;
      type inet:ipv6-address;
    }
    description
      "An IPv4 or IPv6 address with no prefix specified.";
  }

  typedef voice-port-num-type {
    description
      "Voice port number";
    type string {
      pattern '[0-9]+/[0-9]+/[0-9]+';
    }
  }

  typedef punt-cause-type {
    type enumeration {
      enum mpls-frag-req {
        value 1;
      }
      enum ipv4-options {
        value 2;
      }
      enum unknown-encap {
        value 3;
      }
      enum ppp-control {
        value 4;
      }
      enum clns-control {
        value 5;
      }
      enum hdlc-keepalive {
        value 6;
      }
      enum arp {
        value 7;
      }
      enum reserve-arp {
        value 8;
      }
      enum lmi-control {
        value 9;
      }
      enum incomplete-adj {
        value 10;
      }
      enum for-us-data {
        value 11;
      }
      enum mcast-dcs {
        value 12;
      }
      enum mcast-ipv4-options {
        value 13;
      }
      enum skip-path {
        value 14;
      }
      enum mpls-ttl {
        value 15;
      }
      enum mpls-res-label {
        value 16;
      }
      enum ipv6-badhop {
        value 17;
      }
      enum ipv6-hopopts {
        value 18;
      }
      enum mcast-send-internal-copy {
        value 19;
      }
      enum ipwrite {
        value 20;
      }
      enum diag {
        value 21;
      }
      enum fw-ipwrite {
        value 22;
      }
      enum mcast-igmp-nonroutable {
        value 23;
      }
      enum glean-adj {
        value 24;
      }
      enum mcast-pim-signaling {
        value 25;
      }
      enum generate-icmp {
        value 26;
      }
      enum ess-control {
        value 27;
      }
      enum ess-switch-back {
        value 28;
      }
      enum icmp-cfg-punt {
        value 29;
      }
      enum for-us-internal-data {
        value 30;
      }
      enum punt-adj {
        value 31;
      }
      enum sbc-rtp {
        value 32;
      }
      enum pw-vccv {
        value 33;
      }
      enum ipwrite-keep-gpm {
        value 34;
      }
      enum slow-protocol {
        value 35;
      }
      enum oam-loopback {
        value 36;
      }
      enum unused {
        value 37;
      }
      enum spa-ipc {
        value 38;
      }
      enum punt-replicate {
        value 39;
      }
      enum pppoe-control {
        value 40;
      }
      enum pppoe-session {
        value 41;
      }
      enum l2tp-control {
        value 42;
      }
      enum ipsub-control {
        value 43;
      }
      enum l2tp-session {
        value 44;
      }
      enum bfd-control {
        value 45;
      }
      enum mcast-rpf-signaling {
        value 46;
      }
      enum mvpn-pim-signalling {
        value 47;
      }
      enum loopback-to-rp {
        value 48;
      }
      enum sbc-reply {
        value 49;
      }
      enum ipv6-pkts {
        value 50;
      }
      enum dmvpn-redir-pkt {
        value 51;
      }
      enum pfr-mp-cache {
        value 52;
      }
      enum pfr-tt-cache {
        value 53;
      }
      enum pfr-tt-appl-cache {
        value 54;
      }
      enum for-us-ctrl {
        value 55;
      }
      enum for-us-internal-ctrl {
        value 56;
      }
      enum vtcp-ipwrite {
        value 57;
      }
      enum layer2-bd-data {
        value 58;
      }
      enum stile-ipwrite {
        value 59;
      }
      enum subnet-bcast {
        value 60;
      }
      enum ecfm-pkt {
        value 61;
      }
      enum ecfm-notify {
        value 62;
      }
      enum lisp-lsb-notify {
        value 63;
      }
      enum service-engine {
        value 64;
      }
      enum layer2-bd-ctrl {
        value 65;
      }
      enum layer2-bd-msg {
        value 66;
      }
      enum mfr-lip-control {
        value 67;
      }
      enum mmon-record {
        value 68;
      }
      enum otv-cntrl-pkt {
        value 69;
      }
      enum otv-arp-pkt {
        value 70;
      }
      enum rep-control {
        value 71;
      }
      enum ip-mtu {
        value 72;
      }
      enum l2-bpdu {
        value 73;
      }
      enum acl-log {
        value 74;
      }
      enum epc {
        value 75;
      }
      enum lisp-dynamic-eid {
        value 76;
      }
      enum l2cp {
        value 77;
      }
      enum waas {
        value 78;
      }
      enum dhcp-snoop {
        value 79;
      }
      enum mma-record {
        value 80;
      }
      enum dmvpnv6-redir-req {
        value 81;
      }
      enum ecfm-from-core {
        value 82;
      }
      enum ecfm-punt-fwd {
        value 83;
      }
      enum ptp {
        value 84;
      }
      enum isdn-channel {
        value 85;
      }
      enum svc-ctlr-scg {
        value 86;
      }
      enum fhs-source-guard {
        value 87;
      }
      enum fhs-data-glean {
        value 88;
      }
      enum sbc-dsp {
        value 89;
      }
      enum serial-traffic {
        value 90;
      }
      enum sslvpn {
        value 91;
      }
      enum deny-acl {
        value 92;
      }
      enum cent-smp {
        value 93;
      }
      enum appnav-vpath {
        value 94;
      }
      enum automatic-hw {
        value 95;
      }
      enum layer2-ctrl {
        value 96;
      }
      enum lfts-transport {
        value 97;
      }
      enum vlan-autosense {
        value 98;
      }
      enum ztp {
        value 99;
      }
      enum cable-arp-filter {
        value 100;
      }
      enum cable-l3-mobility {
        value 101;
      }
      enum sv-match-unknown {
        value 102;
      }
      enum cable-pre-reg {
        value 103;
      }
      enum mpls-receive-adj {
        value 104;
      }
      enum mka {
        value 105;
      }
      enum icmp-unreachable {
        value 106;
      }
      enum cable-dhcp {
        value 107;
      }
      enum snooping {
        value 108;
      }
      enum proto-snoop {
        value 109;
      }
      enum ppp-intf-ip-addr {
        value 110;
      }
      enum embedded-cause {
        value 111;
      }
      enum qos-cac {
        value 112;
      }
      enum active-identity {
        value 113;
      }
      enum bgp-tun-pkt {
        value 114;
      }
      enum lisp-gsmr-ena {
        value 115;
      }
      enum async-term-serv {
        value 116;
      }
      enum mma-packet {
        value 117;
      }
      enum cbl-dhcpv6-solicit {
        value 118;
      }
      enum cbl-dhcpv6-req {
        value 119;
      }
      enum sbc-rtp-fwd {
        value 120;
      }
      enum path-manager {
        value 121;
      }
      enum l2-lisp-vxlan {
        value 122;
      }
      enum dialer-list {
        value 123;
      }
      enum dialer-update-time {
        value 124;
      }
      enum cable-rphy-ctrl {
        value 125;
      }
      enum openflow-sdn {
        value 126;
      }
      enum path-manager-ttl {
        value 127;
      }
      enum l3-ptp-message {
        value 128;
      }
      enum wls_dot11_pkt {
        value 129;
      }
      enum wls_capwap_pkt {
        value 130;
      }
      enum wls_mobility_pkt {
        value 131;
      }
      enum wls_sisf_pkt {
        value 132;
      }
      enum cbl-dhcpv6-sub {
        value 133;
      }
      enum cbl-dhcpv4-sub {
        value 134;
      }
      enum cbl-dhcpv4-disc-req {
        value 135;
      }
      enum x25-control-pkt {
        value 136;
      }
      enum x25-data-pkt {
        value 137;
      }
      enum NAT {
        value 138;
      }
      enum dns-snoop {
        value 139;
      }
      enum efp-dot1x {
        value 140;
      }
      enum dmvpn-gal-check {
        value 141;
      }
      enum cbl-ipsec-for-us {
        value 142;
      }
      enum epbr {
        value 143;
      }
      enum pmip-ctrl {
        value 144;
      }
      enum cbl-ipsec-lifetime {
        value 145;
      }
      enum cbl-ipsec-prng {
        value 146;
      }
      enum mcast-udlr {
        value 147;
      }
      enum l2bd-sisf-ctrl {
        value 148;
      }
      enum Metanoia-L2-MGMT {
        value 149;
      }
      enum sr-twamp-probe {
        value 150;
      }
      enum wpan-linkinfo {
        value 151;
      }
      enum wpan-punt-dot1x {
        value 152;
      }
      enum wpan-mpl-enabled {
        value 153;
      }
      enum wpan-l2 {
        value 154;
      }
      enum wpan-ns {
        value 155;
      }
      enum bfd-l2-control {
        value 156;
      }
      enum cable-snmp {
        value 157;
      }
      enum ext-icmp {
        value 158;
      }
      enum profinet {
        value 159;
      }
      enum wls_sisf_arp_v6nd_pkt {
        value 160;
      }
      enum nbar {
        value 161;
      }
      enum aaa {
        value 162;
      }
      enum wls_ap_https {
        value 163;
      }
      enum lfts-perfmon {
        value 164;
      }
      enum ie_mrp {
        value 165;
      }
      enum cable-pma-mer-pkt {
        value 166;
      }
      enum cable-pnm-mer-pkt {
        value 167;
      }
      enum lfts-fnf {
        value 173;
      }
    }
  }
}
