module Cisco-IOS-XE-wireless-events-oper {
  yang-version 1.1;
  namespace "http://cisco.com/ns/yang/Cisco-IOS-XE-wireless-events-oper";
  prefix wireless-event-oper;

  import Cisco-IOS-XE-wireless-mobility-types {
    prefix wireless-mobility-types;
  }
  import Cisco-IOS-XE-wsa-types {
    prefix wsa-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless operations events generated from the Cisco Wireless
     controller. These models may produce high volume of data.
     Copyright (c) 2018-2022 by Cisco Systems, Inc.
     All rights reserved";

  revision 2022-11-01 {
    description
      "Update yang-version to 1.1";
    reference
      "2.3.0";
    cisco-semver:module-version "2.3.0";
  }
  revision 2022-07-01 {
    description
      "- Added new ap upgrade asynchronous notification event.";
    reference
      "2.2.0";
    cisco-semver:module-version "2.2.0";
  }
  revision 2021-07-01 {
    description
      "- Added Band ID for 6GHz channels to Rogue WSA.
       - Added new threshold warning manager event.";
    reference
      "2.1.0";
    cisco-semver:module-version "2.1.0";
  }
  revision 2020-07-01 {
    description
      "- Added dot1x flag in rogue potential honeypot event.
       - Remove unused empty container wireless-events";
    reference
      "2.0.0";
    cisco-semver:module-version "2.0.0";
  }
  revision 2020-03-01 {
    description
      "- Added beacon DS information in impersonation event.
       - Added new rogue WSA event.
       - Added client mac in rogue WSA event.";
    reference
      "1.4.0";
    cisco-semver:module-version "1.4.0";
  }
  revision 2019-05-01 {
    description
      "- Added rogue WSA events.
       - Added semantic version";
    reference
      "1.3.0";
    cisco-semver:module-version "1.3.0";
  }
  revision 2018-10-29 {
    description
      "Cleaned up spelling errors in descriptions.";
    reference
      "1.2.0";
    cisco-semver:module-version "1.2.0";
  }
  revision 2018-10-05 {
    description
      "Addition of fabric parameters to wsa client event.";
    reference
      "1.1.0";
    cisco-semver:module-version "1.1.0";
  }
  revision 2018-06-11 {
    description
      "Initial revision";
    reference
      "1.0.0";
    cisco-semver:module-version "1.0.0";
  }

  typedef rogue-event-type {
    type enumeration {
      enum rogue-potential-honeypot-detected {
        value 0;
        description
          "Potential honeypot detected event";
      }
      enum rogue-potential-honeypot-cleared {
        value 1;
        description
          "Potential honeypot cleared event";
      }
      enum rogue-ap-impersonation-detected {
        value 2;
        description
          "AP impersonation detected event";
      }
      enum rogue-mfp-containment-detected {
        value 3;
        description
          "PMF containment attempt detected event";
      }
    }
    description
      "Rogue event type";
  }

  typedef threshold-warning-event-type {
    type enumeration {
      enum wireless-clients-threshold-reached {
        value 0;
        description
          "Wireless clients reached the threshold.";
      }
    }
    description
      "Threshold warning event type.";
  }

  typedef ap-upgrade-state {
    type enumeration {
      enum ap-ev-pred-start {
        value 0;
        description
          "AP image predownload started";
      }
      enum ap-ev-pred-in-progress {
        value 1;
        description
          "AP image predownload in progress";
      }
      enum ap-ev-pred-failed {
        value 2;
        description
          "AP image predownload failed";
      }
      enum ap-ev-pred-abort {
        value 3;
        description
          "AP image predownload aborted";
      }
      enum ap-ev-pred-complete {
        value 4;
        description
          "AP image predownload complete";
      }
      enum ap-ev-up-start {
        value 5;
        description
          "Staggered AP upgrade process started";
      }
      enum ap-ev-up-in-progress {
        value 6;
        description
          "Staggered AP upgrade process is in progress";
      }
      enum ap-ev-up-failed {
        value 7;
        description
          "Staggered AP upgrade process failed";
      }
      enum ap-ev-up-abort {
        value 8;
        description
          "Staggered AP upgrade process was aborted";
      }
      enum ap-ev-up-interrupted {
        value 9;
        description
          "Staggered AP upgrade process was interrupted due to an SSO. The process should continue in some time.";
      }
      enum ap-ev-up-continued {
        value 10;
        description
          "Staggered AP upgrade process restarted after the SSO.";
      }
      enum ap-ev-up-paused {
        value 11;
        description
          "Staggered AP upgrade process is paused because the destination controller is no longer reachable.";
      }
      enum ap-ev-up-resumed {
        value 12;
        description
          "Staggered AP upgrade is resumed after the destination controller is back up.";
      }
      enum ap-ev-up-stopped {
        value 13;
        description
          "Staggered AP upgrade process was stopped as per configuration.";
      }
      enum ap-ev-up-complete {
        value 14;
        description
          "Staggered AP upgrade process is complete";
      }
    }
    description
      "AP upgrade event type";
  }

  grouping rogue-potential-honeypot {
    description
      "Potential honeypot event";
    leaf ssid {
      type string;
      description
        "SSID name";
    }
    leaf channel {
      type uint32;
      description
        "Channel number";
    }
    leaf is-dot1x {
      type boolean;
      description
        "Indicates whether honeypot AP uses 802.1x authentication.";
    }
    leaf band-id {
      type uint8;
      description
        "Radio Band ID";
    }
  }

  grouping rogue-ap-impersonation {
    description
      "AP impersonation event";
    leaf impersonating-src-mac {
      type yang:mac-address;
      description
        "Impersonating source MAC address";
    }
    leaf is-beacon-ds {
      type boolean;
      description
        "Impersonation attack is also a beacon DS attack";
    }
    leaf channel {
      type uint8;
      description
        "Channel where beacon DS attack is performed";
    }
    leaf band-id {
      type uint8;
      description
        "Radio Band ID";
    }
  }

  grouping rogue-pmf-info {
    description
      "Info about rogue with PMF enabled";
    leaf is-client {
      type boolean;
      description
        "Indicates whether rogue is client or AP.";
    }
    leaf pmf-client-mac {
      when "(../is-client = 'true')";
      type yang:mac-address;
      description
        "MAC address of PMF client";
    }
  }

  grouping ap-lrad {
    description
      "AP LRAD information";
    leaf name {
      type string;
      description
        "AP name";
    }
    leaf mac-address {
      type yang:mac-address;
      description
        "AP MAC address";
    }
    leaf slot-id {
      type uint32;
      description
        "Slot ID";
    }
  }

  grouping rogue-event {
    description
      "Rogue WSA event";
    container reporting-ap {
      description
        "AP reporting the event";
      uses wireless-event-oper:ap-lrad;
    }
    leaf rogue-mac-address {
      type yang:mac-address;
      description
        "MAC of the rogue AP";
    }
    choice event-type-choice {
      description
        "Type of event";
      case rogue-potential-honeypot-detected {
        container potential-honeypot-detected {
          description
            "Potential honeypot detected event";
          uses wireless-event-oper:rogue-potential-honeypot;
        }
      }
      case rogue-potential-honeypot-cleared {
        container potential-honeypot-cleared {
          description
            "Potential honeypot cleared event";
          uses wireless-event-oper:rogue-potential-honeypot;
        }
      }
      case rogue-ap-impersonation-detected {
        container ap-impersonation-detected {
          description
            "AP impersonation detected event";
          uses wireless-event-oper:rogue-ap-impersonation;
        }
      }
      case rogue-mfp-containment-detected {
        container pmf-info-detected {
          description
            "PMF containment info (MAC address of Rogue client with PMF enabled)";
          uses wireless-event-oper:rogue-pmf-info;
        }
      }
    }
  }

  grouping st-threshold-warning-event {
    description
      "Threshold warning event.";
    leaf event-type {
      type wireless-event-oper:threshold-warning-event-type;
      description
        "Type of threshold warning event.";
    }
    leaf entry-count {
      type uint32;
      description
        "Entry count at the moment the threshold has been reached.";
    }
    leaf configured-threshold {
      type uint8;
      units "percentage";
      description
        "Value of the configured threshold.";
    }
    leaf threshold-reached-clear {
      type boolean;
      description
        "Flag indicating whether threshold edge is positive or negative";
    }
    leaf timestamp {
      type yang:date-and-time;
      description
        "Timestamp when the event occurred.";
    }
  }

  grouping st-dhcp-ip-addr {
    description
      "List of DHCP server IP addresses";
    leaf server-ip {
      type inet:ip-address;
      description
        "Server IP address";
    }
  }

  grouping wsa-client-eventq-db-elem {
    description
      "Wireless client lifecycle events data model";
    leaf client-mac {
      type yang:mac-address;
      description
        "Wireless Client's MAC Address";
    }
    leaf wtp-mac {
      type yang:mac-address;
      description
        "AP mac client is associated to";
    }
    leaf state-transition-timestamp {
      type yang:date-and-time;
      description
        "Timestamp indicating when a client transitioned into the present lifecycle event. Time elapsed since 00:00:00 UTC, Thursday, 1 January 1970";
    }
    leaf audit-session-id {
      type string;
      description
        "Audit session id of the session";
    }
    leaf ssid {
      type string;
      description
        "SSID client is associated to";
    }
    leaf client-event {
      type wsa-types:wsa-client-events;
      description
        "Wireless client event type, indicating the phase a client is in its lifecycle";
    }
    leaf client-event-result {
      type wsa-types:wsa-client-event-result;
      description
        "Wireless client event status, indicating a failure or success in client lifecycle";
    }
    leaf vlan-id {
      type uint32;
      description
        "Wireless Client layer 2 vlan id";
    }
    leaf client-vnid {
      type uint32;
      description
        "Fabric client's Virtual Network ID. This information is valid only if client is a fabric client";
    }
    leaf client-sgt {
      type uint16;
      description
        "Fabric client's group tag. This information is valid only if client is a fabric client";
    }
    leaf rssi {
      type int8;
      description
        "Last updated Radio Signal Strength indicator, of a Wireless Client";
    }
    leaf snr {
      type uint8;
      description
        "Last updated Signal strength to noise ratio, of a Wireless Client";
    }
    leaf ms-ap-slot-id {
      type uint8;
      description
        "AP slot client is associated to";
    }
    leaf mm-client-role {
      type wireless-mobility-types:mm-client-role;
      description
        "Wireless Client's mobility role";
    }
    leaf ipv4-address {
      type inet:ipv4-address;
      description
        "Wireless Client's IPv4 address";
    }
    leaf-list ipv6 {
      type inet:ipv6-address;
      max-elements 8;
      ordered-by user;
      description
        "Wireless Client's IPv6 list of addresses";
    }
    list dhcp-server-ip-addr {
      description
        "DHCP server IP the Wireless client has communicated with";
      uses wireless-event-oper:st-dhcp-ip-addr;
    }
    leaf aaa-server {
      type inet:ip-address;
      description
        "AAA server IP the Wireless client has communicated with";
    }
    leaf is-fabric-client {
      type boolean;
      description
        "Indicates whether the client is a fabric client or not";
    }
  }

  grouping wsa-client-eventq-db-elem-3p {
    description
      "Wireless client lifecycle third-party events data model enumeration";
    leaf client-event-reason {
      type wsa-types:wsa-client-event-reason-3p;
      description
        "Wireless client event reason third-party, indicating what is happening with a client in its current lifecycle event";
    }
    leaf client-event-reason-addon {
      type wsa-types:wsa-client-event-reason-addon-3p;
      description
        "Wireless client event reason addon third-party, provides more information about the client_event_reason";
    }
  }

  grouping ap-predownload-elem {
    description
      "Elements of AP predownload event asynchronous notifications";
    leaf upgrade-state {
      type wireless-event-oper:ap-upgrade-state;
      description
        "State of the predownload event";
    }
    leaf total-num-of-aps {
      type uint32;
      description
        "Total number of APs selected for predownload";
    }
    leaf num-of-aps-predownloaded {
      type uint32;
      description
        "Number of APs which have completed predownload";
    }
    leaf percentage-predownloaded {
      type uint8;
      units "percentage";
      description
        "Percentage completion of predownload procedure";
    }
  }

  grouping ap-upgrade-elem {
    description
      "Elements of Detailed AP upgrade event asynchronous notifications";
    leaf upgrade-state {
      type wireless-event-oper:ap-upgrade-state;
      description
        "AP upgrade State";
    }
    leaf uuid {
      type string;
      description
        "Netconf UUID of the request";
    }
    leaf percentage-completed {
      type uint8;
      units "percentage";
      description
        "Staggered AP upgrade progress percentage";
    }
    leaf num-of-aps-upgraded {
      type uint32;
      description
        "Number of APs upgraded so far";
    }
    leaf aps-selected-for-upgd {
      type uint32;
      description
        "Number of APs selected for upgrade process";
    }
    leaf num-of-iterations {
      type uint8;
      description
        "Predicted total number of iterations required";
    }
    leaf current-iteration {
      type int8;
      description
        "Current iteration number of the upgrade";
    }
    leaf from-version {
      type string;
      description
        "AP image version before upgrade process";
    }
    leaf to-version {
      type string;
      description
        "AP image version after upgrade process";
    }
    leaf start-time {
      type yang:date-and-time;
      description
        "Staggered AP upgrade process start time";
    }
    leaf expected-end-time {
      type yang:date-and-time;
      description
        "Expected time of completion of upgrade";
    }
  }

  notification wsa-client-event {
    description
      "Wireless client operational events. Provides an event for each significant activity in the Wireless clients life cycle. It may generate high volume of data, depending on scale";
    uses wireless-event-oper:wsa-client-eventq-db-elem;
    uses wireless-event-oper:wsa-client-eventq-db-elem-3p;
  }

  notification rogue-events {
    description
      "Rogue WSA events. Provides an event for each significant activity of
       rogue. It may generate high volume of data, depending on scale";
    uses wireless-event-oper:rogue-event;
  }

  notification threshold-warning-event {
    description
      "Threshold warning manager events. Provides an event when the configured
       threshold is crossed.";
    uses wireless-event-oper:st-threshold-warning-event;
  }

  notification ap-predownload-event {
    description
      "AP predownload Events. Provides summary of AP predownload events whenever
       predownload task is being performed.";
    uses wireless-event-oper:ap-predownload-elem;
  }

  notification ap-upgrade-event {
    description
      "Staggered AP upgrade events. Provides details of AP events whenever
       upgrade task is being performed.";
    uses wireless-event-oper:ap-upgrade-elem;
  }
}
