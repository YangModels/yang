module cisco-xe-openconfig-spanning-tree-ext {
    namespace "http://cisco.com/ns/yang/cisco-xe-openconfig-spanning-tree-ext";
    
    prefix oc-stp-ext;

    import openconfig-spanning-tree {
       prefix oc-stp;
    }

    import openconfig-spanning-tree-types {
       prefix oc-stp-types;
    }

    organization "Cisco Systems";

    description
       "Augment file for oc-spanning-tree";

////////////////////////////////////////////////////////////////////////////
// REVISION
///////////////////////////////////////////////////////////////////////////
 revision 2017-10-24 {
   description "Extended enum instances of STP port state and role";
 }

 revision 2017-07-17 {
   description "Initial Draft to change from leaf-list to leaf enabled-protocol";
 }

////////////////////////////////////////////////////////////////////////////
// AUGMENT
///////////////////////////////////////////////////////////////////////////

  deviation "/oc-stp:stp/oc-stp:global/oc-stp:config/oc-stp:enabled-protocol" {
    deviate  not-supported;
  }

  deviation "/oc-stp:stp/oc-stp:global/oc-stp:state/oc-stp:enabled-protocol" {
    deviate  not-supported;
  }

  augment "/oc-stp:stp/oc-stp:global/oc-stp:config" {
    leaf enabled-protocol {
      type identityref {
        base oc-stp-types:STP_PROTOCOL;
      }
      description
        "List of the spanning tree protocols enabled on the
       device";
    }
  }

  augment "/oc-stp:stp/oc-stp:global/oc-stp:state" {
    leaf enabled-protocol {
      type identityref {
        base oc-stp-types:STP_PROTOCOL;
      }
      description
        "List of the spanning tree protocols enabled on the
       device";
    }
  }

//////////////////////////////////////////////////////////////////////////////
// Extend Enum instances
//////////////////////////////////////////////////////////////////////////////

  identity BROKEN {
    base oc-stp-types:STP_PORT_STATE;
    description
      "Cisco added port state enum instance BROKEN";
  }

  identity INVALID {
    base oc-stp-types:STP_PORT_STATE;
    description
      "Cisco added port state enum instance INVALID";
  }

  identity MASTER {
    base oc-stp-types:STP_PORT_ROLE;
    description
      "Cisco added port role enum instance MASTER";
  }
}
