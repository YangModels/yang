module Cisco-IOS-XE-cwmp {
  yang-version 1.1;
  namespace "http://cisco.com/ns/yang/Cisco-IOS-XE-cwmp";
  prefix ios-cwmp;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Customer Premise Equipment
     Wide Area Network Management Protocol Yang model.
     Copyright (c) 2024 by Cisco Systems, Inc.
     All rights reserved.";

  revision 2024-07-01 {
    description
      "- Initial revision";
    cisco-semver:module-version "1.0.0";
  }

  grouping config-cwmp-grouping {
    container agent {
      description
        "Agent configuration for
         Customer  Wide Area Network Management Protocol";
      container enable {
        leaf download {
          description
            "Download option";
          type empty;
        }
      }
      container request {
        description
          "Limit of number of outstanding requests";
        leaf outstanding {
          description
            "Number of outstanding requests";
          type uint8 {
            range "1..10";
          }
          default "5";
        }
      }
      container parameter {
        description
          "Notification parameter properties";
        container change {
          description
            "Notification parameter interval";
          container notify {
            description
              "Parameter change notification";
            leaf interval {
              description
                "Notification interval in seconds";
              type uint16 {
                range "15..300";
              }
              default "60";
            }
          }
        }
      }
      container session {
        description
          "Session retry queue size";
        container retry {
          description
            "Number of session retries";
          leaf limit {
            description
              "Number of session retries";
            type uint8 {
              range "10..15";
            }
            default "11";
          }
        }
      }
      container provision {
        description
          "Provision code";
        leaf code {
          description
            "Provision code string";
          type string;
        }
      }
      container connection {
        description
          "Connection request username/password to authenticate
           ACS server";
        container request {
          description
            "Connection request parameters";
          leaf username {
            description
              "Connection request username to authenticate ACS server";
            type string;
          }
          container password {
            description
              "Connection request password to authenticate ACS server";
            leaf encryption {
              description
                "Password encryption type";
              type enumeration {
                enum 0;
                enum 7;
              }
            }
            leaf password-string {
              description
                "Connection request password string";
              type string;
            }
          }
        }
      }
      container management {
        description
          "Parameters  for username/password/url";
        container server {
          description
            "Server information";
          leaf username {
            description
              "Server username to authenticate ACS server";
            type string;
          }
          container password {
            description
              "Server password to authenticate ACS server";
            leaf encryption {
              description
                "Choose encryption type";
              type enumeration {
                enum 0;
                enum 7;
              }
            }
            leaf password-string {
              description
                "ACS server password string";
              type string;
            }
          }
          leaf url {
            description
              "ACS server through URL string";
            type string;
          }
        }
      }
    }
  }

  augment "/ios:native/ios:cwmp" {
    uses config-cwmp-grouping;
  }
}
