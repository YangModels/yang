module Cisco-IOS-XE-yang-interfaces-cfg {
  yang-version 1.1;
  namespace "http://cisco.com/ns/yang/Cisco-IOS-XE-yang-interfaces-cfg";
  prefix yang-interfaces-cfg;

  import Cisco-IOS-XE-dmi-common-types {
    prefix dmi-common-types;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Configuration for YANG model-based interfaces.
     Copyright (c) 2018-2024 by Cisco Systems, Inc.
     All rights reserved.";

  revision 2025-03-01 {
    description
      "- Add length and pattern constraints on strings.";
    reference
      "2.0.0";
    cisco-semver:module-version "2.0.0";
  }
  revision 2024-11-01 {
    description
      "- Added configuration of a trustpoint to be used for NETCONF SSH transport";
    reference
      "1.7.0";
    cisco-semver:module-version "1.7.0";
  }
  revision 2024-07-01 {
    description
      "- Added features config including atomic config for YANG Interfaces
       - Added config knob to control handling of deprecated Yang model elements
       - Added accounting configuration for YANG interfaces";
    reference
      "1.6.0";
    cisco-semver:module-version "1.6.0";
  }
  revision 2023-03-01 {
    description
      "- Added NETCONF SSH server configuration for YANG Interfaces.";
    reference
      "1.5.0";
    cisco-semver:module-version "1.5.0";
  }
  revision 2022-11-01 {
    description
      "Update yang-version to 1.1";
    reference
      "1.4.0";
    cisco-semver:module-version "1.4.0";
  }
  revision 2022-03-01 {
    description
      "- Added AAA configuration for YANG Interfaces.";
    reference
      "1.3.0";
    cisco-semver:module-version "1.3.0";
  }
  revision 2021-07-01 {
    description
      "- Added netconf SSH local VRF configuration
       - Allow usage of special characters in netconf ACL name";
    reference
      "1.2.0";
    cisco-semver:module-version "1.2.0";
  }
  revision 2019-05-21 {
    description
      "- Add semantic version
       - Add SNMP to NETCONF/YANG configuration";
    reference
      "1.1.0";
    cisco-semver:module-version "1.1.0";
  }
  revision 2018-11-01 {
    description
      "Initial revision";
    reference
      "1.0.0";
    cisco-semver:module-version "1.0.0";
  }

  grouping dmi-ssh-hostkey-algorithms {
    description
      "Host key public key algorithms.";
    leaf rsa-sha2-256 {
      type boolean;
      default "true";
      description
        "RSA-SHA2-256 Public key based authentication.";
    }
    leaf rsa-sha2-512 {
      type boolean;
      default "true";
      description
        "RSA-SHA2-512 Public key based authentication.";
    }
    leaf ssh-rsa {
      type boolean;
      default "true";
      description
        "RSA-SHA1 Public key based authentication.";
    }
  }

  grouping dmi-ssh-cipher-algorithms {
    description
      "Encryption algorithms.";
    leaf aes128-ctr {
      type boolean;
      default "true";
      description
        "AES with 128-bit key in CTR mode.";
    }
    leaf aes192-ctr {
      type boolean;
      default "true";
      description
        "AES with 192-bit key in CTR mode.";
    }
    leaf aes256-ctr {
      type boolean;
      default "true";
      description
        "AES with 256-bit key in CTR mode.";
    }
    leaf aes128-cbc {
      type boolean;
      default "true";
      description
        "AES with 128-bit key in CBC mode.";
    }
    leaf aes256-cbc {
      type boolean;
      default "true";
      description
        "AES with 256-bit key in CBC mode.";
    }
  }

  grouping dmi-ssh-mac-algorithms {
    description
      "Message authentication code algorithms.";
    leaf hmac-sha2-256 {
      type boolean;
      default "true";
      description
        "HMAC-SHA2-256.";
    }
    leaf hmac-sha2-512 {
      type boolean;
      default "true";
      description
        "HMAC-SHA2-512.";
    }
    leaf hmac-sha1 {
      type boolean;
      default "true";
      description
        "HMAC-SHA1.";
    }
  }

  grouping dmi-ssh-kex-algorithms {
    description
      "Key exchange algorithms.";
    leaf dh-group14-sha1 {
      type boolean;
      default "true";
      description
        "DH-GROUP-14-SHA1 key exchange algorithm.";
    }
    leaf dh-group14-sha256 {
      type boolean;
      default "true";
      description
        "DH-GROUP-14-SHA256 key exchange algorithm.";
    }
    leaf ecdh-sha2-nistp256 {
      type boolean;
      default "true";
      description
        "Elliptic Curve DH-SHA2-P256 key exchange algorithm.";
    }
    leaf ecdh-sha2-nistp384 {
      type boolean;
      default "true";
      description
        "Elliptic Curve DH-SHA2-P384 key exchange algorithm.";
    }
    leaf ecdh-sha2-nistp521 {
      type boolean;
      default "true";
      description
        "Elliptic Curve DH-SHA2-P521 key exchange algorithm.";
    }
    leaf dh-group16-sha512 {
      type boolean;
      default "true";
      description
        "DH-GROUP-16-SHA512 key exchange algorithm.";
    }
  }

  grouping dmi-ssh-server {
    description
      "SSH server algorithm.";
    container kex-alg {
      description
        "Key exchange algorithms for NETCONF SSH server.";
      uses yang-interfaces-cfg:dmi-ssh-kex-algorithms;
    }
    container macs {
      description
        "Message authentication code algorithms for NETCONF SSH server.";
      uses yang-interfaces-cfg:dmi-ssh-mac-algorithms;
    }
    container ciphers {
      description
        "Encryption algorithms for NETCONF SSH server.";
      uses yang-interfaces-cfg:dmi-ssh-cipher-algorithms;
    }
    container hostkey-alg {
      description
        "Host key algorithms for NETCONF SSH server.";
      uses yang-interfaces-cfg:dmi-ssh-hostkey-algorithms;
    }
    leaf tp-name {
      type string {
        length "0..128" {
          error-message "Trustpoint name must be between 0 and 128 characters";
          error-app-tag "must-violation";
        }
        pattern '[!-~]([ -~]*[!-~])?|' {
          error-message "Trustpoint name must use ASCII 32-126 characters and must not contain leading or trailing spaces";
          error-app-tag "pattern-violation";
        }
      }
      default "";
      description
        "Trustpoint used for NETCONF SSH server.";
    }
  }

  grouping dmi-authentication {
    description
      "AAA authentication method list for YANG Interfaces.";
    leaf login-method-list {
      type string {
        length "1..128" {
          error-message "AAA authentication method list must be between 1 and 128 characters";
          error-app-tag "must-violation";
        }
        pattern '[!-~]([ -~]*[!-~])?' {
          error-message "AAA authentication method list must use ASCII 32-126 characters and must not contain leading or trailing spaces";
          error-app-tag "pattern-violation";
        }
      }
      default "default";
      description
        "Method list name.";
    }
  }

  grouping dmi-authorization {
    description
      "AAA authorization method list for YANG Interfaces.";
    leaf exec-method-list {
      type string {
        length "1..128" {
          error-message "AAA authorization method list must be between 1 and 128 characters";
          error-app-tag "must-violation";
        }
        pattern '[!-~]([ -~]*[!-~])?' {
          error-message "AAA authorization method list must use ASCII 32-126 characters and must not contain leading or trailing spaces";
          error-app-tag "pattern-violation";
        }
      }
      default "default";
      description
        "Method list name.";
    }
  }

  grouping dmi-accounting {
    description
      "AAA accounting for YANG interfaces";
    leaf enabled {
      type boolean;
      default "true";
      description
        "Flag indicating whether AAA accounting for model interfaces is enabled";
    }
  }

  grouping dmi-aaa {
    description
      "AAA service for YANG Interfaces.";
    container authn {
      description
        "AAA authentication service for YANG Interfaces.";
      uses yang-interfaces-cfg:dmi-authentication;
    }
    container authz {
      description
        "AAA authorization service for YANG Interfaces.";
      uses yang-interfaces-cfg:dmi-authorization;
    }
    container acct {
      description
        "AAA accounting service for YANG Interfaces.";
      uses yang-interfaces-cfg:dmi-accounting;
    }
  }

  grouping dmi-yang-feature {
    description
      "Configuration details for YANG related features";
    leaf atomic-config {
      type boolean;
      default "false";
      description
        "Enables or disables non-service interrupting configuration validation";
    }
  }

  grouping dmi-acl-nbi-type {
    description
      "Configure an access-list for the selected service";
    leaf ipv4-acl-name {
      type string {
        length "1..32";
      }
      description
        "Validate access using an IPv4 access-list";
    }
    leaf ipv6-acl-name {
      type string {
        length "1..32";
      }
      description
        "Validate access using an IPv6 access-list";
    }
  }

  grouping dmi-acl {
    description
      "Service ACLs for YANG Interfaces";
    container netconf-yang-ssh {
      description
        "NETCONF-YANG SSH service";
      uses yang-interfaces-cfg:dmi-acl-nbi-type;
    }
    container restconf {
      description
        "RESTCONF service";
      uses yang-interfaces-cfg:dmi-acl-nbi-type;
    }
  }

  grouping dmi-snmp-trap {
    description
      "SNMP trap to NETCONF translation";
    leaf trap-oid {
      type string {
        length "3..200" {
          error-message "SNMP trap OID must be between 3 and 200 characters";
          error-app-tag "must-violation";
        }
        pattern '(([0-1](\.[1-3]?[0-9]))|(2\.(0|([1-9]\d*))))(\.(0|([1-9]\d*)))*';
        pattern '\d*(\.\d*){1,127}';
      }
      description
        "The OID for this trap";
    }
    leaf description {
      type string {
        length "0..128" {
          error-message "SNMP trap description must be between 0 and 128 characters";
          error-app-tag "must-violation";
        }
        pattern '[!-~]([ -~]*[!-~])?|' {
          error-message "SNMP trap description must use ASCII 32-126 characters and must not contain leading or trailing spaces";
          error-app-tag "pattern-violation";
        }
      }
      default "";
      description
        "A description for this trap";
    }
    leaf forward {
      type boolean;
      default "true";
      description
        "Enables or disables forwarding for this trap";
    }
  }

  grouping dmi-general {
    description
      "Configuration applicable to all YANG model-based interfaces";
    leaf snmp-global-forwarding {
      type boolean;
      default "true";
      description
        "Enables or disables forwarding for all SNMP traps";
    }
    list snmp-trap {
      key "trap-oid";
      description
        "List of SNMP traps considered for automatic translation to NETCONF
         notifications";
      uses yang-interfaces-cfg:dmi-snmp-trap;
    }
    leaf snmp-community {
      type string {
        length "1..128" {
          error-message "SNMP community string must be between 1 and 128 characters";
          error-app-tag "must-violation";
        }
        pattern '[!-~]([ -~]*[!-~])?' {
          error-message "SNMP community string must use ASCII 32-126 characters and must not contain leading or trailing spaces";
          error-app-tag "pattern-violation";
        }
      }
      default "private";
      description
        "The community string for communication with the SNMP agent";
    }
    leaf disable-deprecated {
      type boolean;
      description
        "Flag controlling behavior of deprecated model elements.
         When the flag is turned off deprecated model elements are not functional";
    }
  }

  grouping dmi-ssh-local-vrf {
    description
      "Configuration details of NETCONF access on local host in a specific VRF";
    leaf vrf-name {
      type dmi-common-types:enm-local-vrf-name;
      description
        "The name of the given VRF";
    }
    leaf vrf-enable {
      type boolean;
      default "false";
      description
        "Determines whether NETCONF access for local host in a given VRF
         is enabled";
    }
    leaf vrf-port {
      type uint32 {
        range "1 .. 65535";
      }
      default "830";
      description
        "Determines the port number to be open in a given VRF on local host
         for NETCONF access";
    }
  }

  container yang-interfaces-cfg-data {
    description
      "Configuration for YANG model-based interfaces";
    container acl {
      description
        "Optionally configure an access-list to validate access
         to the device";
      uses yang-interfaces-cfg:dmi-acl;
    }
    container aaa {
      presence "aaa";
      description
        "Configuration of AAA service for YANG Interfaces.";
      uses yang-interfaces-cfg:dmi-aaa;
    }
    container ssh-server {
      must "not((../ssh-server/kex-alg/dh-group14-sha1 = 'false') and (../ssh-server/kex-alg/dh-group14-sha256 = 'false') and (../ssh-server/kex-alg/ecdh-sha2-nistp256 = 'false') and (../ssh-server/kex-alg/ecdh-sha2-nistp384 = 'false') and (../ssh-server/kex-alg/ecdh-sha2-nistp521 = 'false') and (../ssh-server/kex-alg/dh-group16-sha512 = 'false'))" {
        error-message "At least one key exchange algorithm must be enabled";
        error-app-tag "must-violation";
      }
      must "not((../ssh-server/macs/hmac-sha2-256 = 'false') and (../ssh-server/macs/hmac-sha2-512 = 'false') and (../ssh-server/macs/hmac-sha1 = 'false'))" {
        error-message "At least one MAC algorithm must be enabled";
        error-app-tag "must-violation";
      }
      must "not((../ssh-server/ciphers/aes128-ctr = 'false') and (../ssh-server/ciphers/aes192-ctr = 'false') and (../ssh-server/ciphers/aes256-ctr = 'false') and (../ssh-server/ciphers/aes128-cbc = 'false') and (../ssh-server/ciphers/aes256-cbc = 'false'))" {
        error-message "At least one cipher algorithm must be enabled";
        error-app-tag "must-violation";
      }
      must "not((../ssh-server/hostkey-alg/rsa-sha2-256 = 'false') and (../ssh-server/hostkey-alg/rsa-sha2-512 = 'false'))" {
        error-message "Either rsa-sha2-256 or rsa-sha2-512 host key algorithm must be enabled";
        error-app-tag "must-violation";
      }
      presence "ssh-server";
      description
        "Configuration of NETCONF SSH server.";
      uses yang-interfaces-cfg:dmi-ssh-server;
    }
    container general {
      description
        "Configuration applicable to all YANG model-based interfaces";
      uses yang-interfaces-cfg:dmi-general;
    }
    list local-vrf {
      key "vrf-name";
      description
        "Configuration of NETCONF access on local host in a specific VRF";
      uses yang-interfaces-cfg:dmi-ssh-local-vrf;
    }
    container dmi-yang-feature {
      presence "dmi-yang-feature";
      description
        "Configuration details for YANG related features";
      uses yang-interfaces-cfg:dmi-yang-feature;
    }
  }
}
