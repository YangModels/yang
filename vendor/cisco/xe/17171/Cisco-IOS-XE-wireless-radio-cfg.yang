module Cisco-IOS-XE-wireless-radio-cfg {
  yang-version 1.1;
  namespace "http://cisco.com/ns/yang/Cisco-IOS-XE-wireless-radio-cfg";
  prefix wireless-radio-cfg;

  import Cisco-IOS-XE-wireless-enum-types {
    prefix wireless-enum-types;
  }
  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing radio configuration
     Copyright (c) 2019-2022, 2024 by Cisco Systems, Inc.
     All rights reserved.";

  revision 2025-03-01 {
    description
      "Added a range validation for DTIM period";
    reference
      "4.0.0";
    cisco-semver:module-version "4.0.0";
  }
  revision 2024-11-01 {
    description
      "Added default for leaf num-ant-enabled";
    reference
      "3.5.0";
    cisco-semver:module-version "3.5.0";
  }
  revision 2022-11-01 {
    description
      "Update yang-version to 1.1";
    reference
      "3.4.0";
    cisco-semver:module-version "3.4.0";
  }
  revision 2022-07-01 {
    description
      "- Added DTIM period configuration for radio profile";
    reference
      "3.3.0";
    cisco-semver:module-version "3.3.0";
  }
  revision 2021-11-01 {
    description
      "- Added mesh backhaul and designated downlink config for radio profile";
    reference
      "3.2.0";
    cisco-semver:module-version "3.2.0";
  }
  revision 2021-07-01 {
    description
      "- Added radio profile and antenna beam steering mode
       - Added antenna count for radio profile";
    reference
      "3.1.0";
    cisco-semver:module-version "3.1.0";
  }
  revision 2020-11-01 {
    description
      "Added a new leaf transmit-power and obsolete the leaf transmit-power-level";
    reference
      "3.0.0";
    cisco-semver:module-version "3.0.0";
  }
  revision 2020-03-01 {
    description
      "Added length constraint for AP hostname in AP specific configuration";
    reference
      "2.0.0";
    cisco-semver:module-version "2.0.0";
  }
  revision 2019-11-01 {
    description
      "Added roaming domain into ap specific configuration";
    reference
      "1.1.0";
    cisco-semver:module-version "1.1.0";
  }
  revision 2019-01-16 {
    description
      "Initial revision";
    reference
      "1.0.0";
    cisco-semver:module-version "1.0.0";
  }

  grouping st-ap-spec-config {
    description
      "AP specific configuration";
    leaf ap-eth-mac-addr {
      type yang:mac-address;
      description
        "AP ethernet mac address";
    }
    leaf ap-host-name {
      type string {
        length "1..28";
      }
      mandatory true;
      description
        "AP host name";
    }
    leaf enable-bssid-stats {
      type boolean;
      default "false";
      description
        "Enable/Disable the receiving bssid stats from AP";
    }
    leaf primary-controller-name {
      type string;
      description
        "Primary controller name";
    }
    leaf primary-controller-ip-addr {
      type inet:ipv4-address;
      description
        "Primary controller IP address";
    }
    leaf primary-controller-v6-ip-addr {
      type inet:ipv6-address;
      description
        "Primary controller v6 IP address";
    }
    leaf secondary-controller-name {
      type string;
      description
        "Secondary controller name";
    }
    leaf secondary-controller-ip-addr {
      type inet:ipv4-address;
      description
        "Secondary controller IP address";
    }
    leaf secondary-controller-v6-ip-addr {
      type inet:ipv6-address;
      description
        "Secondary controller v6 IP address";
    }
    leaf tertiary-controller-name {
      type string;
      description
        "Tertiary controller name";
    }
    leaf tertiary-controller-ip-addr {
      type inet:ipv4-address;
      description
        "Tertiary controller IP address";
    }
    leaf tertiary-controller-v6-ip-addr {
      type inet:ipv6-address;
      description
        "Tertiary controller v6 IP address";
    }
    leaf roaming-domain {
      type string;
      description
        "Roaming domain for the AP";
    }
  }

  grouping st-ap-specific-config {
    description
      "Container for radio configuration pertaining to an access point";
    leaf ap-ethernet-mac-addr {
      type yang:mac-address;
      description
        "Radio MAC address of the AP";
    }
    container ap-specific-slot-configs {
      description
        "List of Access-point specific slot configurations";
      list ap-specific-slot-config {
        key "slot-id";
        description
          "Access-point specific slot configurations";
        uses wireless-radio-cfg:st-ap-specific-slot-config;
      }
    }
  }

  grouping st-radio-params-24ghz {
    description
      "Radio parameters specific to 24 ghz radio";
    leaf admin-state {
      type boolean;
      default "true";
      description
        "Enable/disable the radio";
    }
    leaf transmit-power-level {
      type uint8;
      units "dBm";
      default "1";
      status obsolete;
      description
        "This leaf is obsolete. Use transmit-power leaf to set transmit power of the radio";
    }
    leaf channel {
      type uint8;
      default "1";
      description
        "Operating channel";
    }
    leaf channel-width {
      type uint8;
      default "20";
      description
        "Operating channel-width";
    }
    leaf dca {
      type boolean;
      default "true";
      description
        "Enable/disable dynamic channel allocation";
    }
    leaf dtp {
      type boolean;
      default "true";
      description
        "Enable/disable dynamic transmit power";
    }
    leaf antenna-gain {
      type uint8;
      units "dBi";
      default "0";
      description
        "Antenna gain applied to this Radio";
    }
    leaf transmit-power {
      type int8;
      units "dBm";
      default "1";
      description
        "Transmit power of the radio";
    }
  }

  grouping st-radio-params-5ghz {
    description
      "Radio parameters specific to 5GHz radio";
    leaf admin-state {
      type boolean;
      default "true";
      description
        "Radio admin state";
    }
    leaf transmit-power-level {
      type uint8;
      units "dBm";
      default "1";
      status obsolete;
      description
        "This leaf is obsolete. Use transmit-power leaf to set transmit power of the radio";
    }
    leaf channel {
      type uint8;
      default "36";
      description
        "Operating channel";
    }
    leaf channel-width {
      type uint8;
      default "20";
      description
        "Operating channel-width";
    }
    leaf dca {
      type boolean;
      default "true";
      description
        "Enable/disable dynamic channel allocation";
    }
    leaf dtp {
      type boolean;
      default "true";
      description
        "Enable/disable dynamic transmit power";
    }
    leaf antenna-gain {
      type uint8;
      units "dBm";
      default "0";
      description
        "Antenna gain applied to this Radio";
    }
    leaf transmit-power {
      type int8;
      units "dBm";
      default "1";
      description
        "Transmit power of the radio";
    }
  }

  grouping st-ap-specific-slot-config {
    description
      "Container holding the access point specific radio parameters";
    leaf slot-id {
      type uint8;
      description
        "Slot identifier for the radio";
    }
    leaf radio-band {
      type wireless-types:enm-radio-frequency;
      description
        "Radio band at which the radio is operating";
    }
    container radio-params-24ghz {
      description
        "Radio parameter specific to 24 ghz radio";
      uses wireless-radio-cfg:st-radio-params-24ghz;
    }
    container radio-params-5ghz {
      description
        "Radio parameter specific to 5GHz radio";
      uses wireless-radio-cfg:st-radio-params-5ghz;
    }
  }

  grouping st-radio-profile {
    description
      "Container holding the radio profile parameters for the AP";
    leaf name {
      type string {
        length "1..32";
        pattern '[!-~]([ -~]*[!-~])?';
      }
      description
        "Name of the radio profile";
    }
    leaf desc {
      type string {
        length "0..64";
      }
      description
        "Description for the radio profile";
    }
    leaf beam-steer-mode {
      type wireless-enum-types:enm-beam-selection-mode;
      description
        "Beam steering mode for the AP slot";
    }
    leaf num-ant-enabled {
      type uint8 {
        range "0 .. 8";
      }
      default "0";
      description
        "Number of antennas to be enabled for the AP slot";
    }
    leaf mesh-backhaul {
      type boolean;
      default "true";
      description
        "Enable mesh backhaul on this radio. Uplink will be attempted and if successful, downlink will be activated unless designated downlink exist";
    }
    leaf mesh-designated-downlink {
      type boolean;
      default "false";
      description
        "Use this radio as a designated mesh downlink backhaul. Uplink radio will not be used as downlink in presence of designated downlink";
    }
    leaf dtim-period {
      type uint8 {
        range "1..255";
      }
      default "1";
      description
        "DTIM interval for 6GHz radio";
    }
  }

  container radio-cfg-data {
    description
      "Top level container for AP specific radio configuration";
    container ap-specific-configs {
      description
        "List of Access-point specific configurations";
      list ap-specific-config {
        key "ap-ethernet-mac-addr";
        description
          "Access-point specific configurations";
        uses wireless-radio-cfg:st-ap-specific-config;
      }
    }
    container ap-spec-configs {
      description
        "List of Access-point specific radio configurations";
      list ap-spec-config {
        key "ap-eth-mac-addr";
        description
          "Access-point specific radio configurations";
        uses wireless-radio-cfg:st-ap-spec-config;
      }
    }
    container radio-profiles {
      description
        "List of radio profiles for access point";
      list radio-profile {
        key "name";
        max-elements 6000;
        description
          "Radio profile for access point";
        uses wireless-radio-cfg:st-radio-profile;
      }
    }
  }
}
