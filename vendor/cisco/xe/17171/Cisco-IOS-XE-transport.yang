submodule Cisco-IOS-XE-transport {
  yang-version 1.1;
  belongs-to Cisco-IOS-XE-native {
    prefix ios;
  }

  organization
    "Cisco Systems, Inc.";
  contact
    "Cisco Systems, Inc.
     Customer Service

     Postal: 170 W Tasman Drive
     San Jose, CA 95134

     Tel: 1 1800 553-NETS

     E-mail: cs-yang@cisco.com";
  description
    "Cisco XE Native Transport, configure a terminal transport Yang Model.
     Copyright (c) 2020-2024 by Cisco Systems, Inc.
     All rights reserved.";

  revision 2024-11-01 {
    description
      "- Added support for transport type persistent telnet input
       - Added support for transport type persistent ssh input
       - Added support for transport type persistent webui input";
  }

  grouping transport-type-grouping {
    container transport {
      description
        "Configure transport";
      container type {
        description
          "Specify transport type";
        container persistent {
          description
            "Persistent transport types";
          container telnet {
            description
              "Persistent telnet transport type";
            leaf input {
              description
                "Configure transport input properties";
              must '/native/transport-map/type/persistent/persistent-type-name[tm-name=current()]' {
                error-message "Please create transport-map name";
              }
              type string;
            }
          }
          container ssh {
            description
              "Persistent ssh transport type";
            leaf input {
              description
                "Configure transport input properties";
              must '/native/transport-map/type/persistent/persistent-type-name[tm-name=current()]' {
                error-message "Please create transport-map name";
              }
              type string;
            }
          }
          container webui {
            description
              "Persistent webui transport type";
            leaf input {
              description
                "Configure transport input properties";
              must '/native/transport-map/type/persistent/persistent-type-name[tm-name=current()]' {
                error-message "Please create transport-map name";
              }
              type string;
            }
          }
        }
      }
    }
  }
}
