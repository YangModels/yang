module Cisco-IOS-XE-utd {
  yang-version 1.1;
  namespace "http://cisco.com/ns/yang/Cisco-IOS-XE-utd";
  prefix ios-utd;

  import cisco-semver {
    prefix cisco-semver;
  }
  import ietf-inet-types {
    prefix inet;
  }
  import Cisco-IOS-XE-native {
    prefix ios;
  }
  import Cisco-IOS-XE-policy {
    prefix ios-policy;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Unified Threat Defense (UTD) Yang model.
     Copyright (c) 2016-2024 by Cisco Systems, Inc.
     All rights reserved.";

  revision 2025-03-01 {
    description
      "- Add max-detect policy option";
    cisco-semver:module-version "1.9.0";
  }
  revision 2024-11-01 {
    description
      "- Add type 0 and 6 support for signature update server password
       - Add type 6 support for AMP apikey";
    cisco-semver:module-version "1.8.0";
  }
  revision 2023-07-01 {
    description
      "- Added new options for utd-category-type";
    cisco-semver:module-version "1.7.0";
  }
  revision 2022-11-01 {
    description
      "- Update yang-version to 1.1
       - Added custom-signature rules
       - Added source-interface for logging host";
    cisco-semver:module-version "1.6.0";
  }
  revision 2022-07-01 {
    description
      "- Added TCP normalizer disable feature";
    cisco-semver:module-version "1.5.0";
  }
  revision 2021-11-01 {
    description
      "- Added URL-Filtering option to decrypt TLS to inject the blocked page";
    cisco-semver:module-version "1.4.0";
  }
  revision 2021-07-01 {
    description
      "- Added UTD Unified policy support
       - Added parameter-map for unified policy
       - Added annotation to only accept full 'no utd enable' on interface
       - Added delete dependencies for unified policy mode and parameter-map";
    cisco-semver:module-version "1.3.0";
  }
  revision 2021-03-01 {
    description
      "- Replaced deprecated diff-dependency annotations";
    cisco-semver:module-version "1.2.1";
  }
  revision 2020-11-01 {
    description
      "- Added port-scan support
       - Flow logging configuration
       - Refactor UTD multi-tenancy for unified policy
       - Obsolete interface augment";
    cisco-semver:module-version "1.2.0";
  }
  revision 2020-03-01 {
    description
      "-Fixed AMP ordering dependencies";
    cisco-semver:module-version "1.1.0";
  }
  revision 2019-07-01 {
    description
      "- Establish semantic version baseline
       - Add log level SSL decryption support
       - Add alert level SSL decryption support
       - Add global SSL decryption support
       - Add encryption type to apikey
       - Add skip-decrypt-threshold reputation support";
    cisco-semver:module-version "1.0.0";
  }
  revision 2019-01-22 {
    description
      "Added leaf for App-hosting Gigabit Ethernet interface";
  }
  revision 2019-01-07 {
    description
      "Add support for BD-VIF interface";
  }
  revision 2018-12-18 {
    description
      "Refactored file-inspection options";
  }
  revision 2018-12-11 {
    description
      "Added apikey to utd global file-analysis cfg";
  }
  revision 2018-12-07 {
    description
      "Fix incorrect block page text string length";
  }
  revision 2018-12-06 {
    description
      "Change non-strict-leafref's to leafref's for threat-defense features";
  }
  revision 2018-11-21 {
    description
      "Cleanup spelling errors in description statements";
  }
  revision 2018-11-14 {
    description
      "Add file types for file analysis in UTD multi-tenancy";
  }
  revision 2018-11-06 {
    description
      "Removed instances of max string length of 128/256/512";
  }
  revision 2018-10-17 {
    description
      "Add logging statistics options under utd engine standard threat-inspection";
  }
  revision 2018-10-04 {
    description
      "Added AMP CLIs in the UTD multi-tenancy grouping";
  }
  revision 2018-09-10 {
    description
      "Support quotes in block page text entries";
  }
  revision 2018-08-01 {
    description
      "Fix unable to move VRF between policies in a single transaction";
  }
  revision 2018-07-12 {
    description
      "Set default logging levels for IPS and URLF";
  }
  revision 2018-07-11 {
    description
      "fixed must constraints for default vrf 'global'";
  }
  revision 2018-06-28 {
    description
      "Added must constraints for deleting vrf";
  }
  revision 2018-05-22 {
    description
      "Add support for cloud-lookup CLI";
  }
  revision 2018-05-14 {
    description
      "Limit string lengths for threat-defense features";
  }
  revision 2018-04-24 {
    description
      "Add 'all-interfaces' and 'fail close' to multi-tenancy policy";
  }
  revision 2018-04-23 {
    description
      "Add generator id key to multi-tenancy whitelist";
  }
  revision 2018-03-22 {
    description
      "Add generator id key to single-tenancy whitelist";
  }
  revision 2018-02-22 {
    description
      "Add threat-defense support for Ethernet interfaces";
  }
  revision 2018-02-06 {
    description
      "Refactor parameter-map";
  }
  revision 2017-11-27 {
    description
      "Added Change 25GE name";
  }
  revision 2017-11-14 {
    description
      "Add 2GE interface";
  }
  revision 2017-09-19 {
    description
      "Add UTD multi-tenancy support";
  }
  revision 2017-08-30 {
    description
      "Move utd interface support";
  }
  revision 2017-08-26 {
    description
      "Update model to match CLI's in 16.05.01";
  }
  revision 2017-02-07 {
    description
      "Initial revision";
  }

  typedef utd-category-type {
    type enumeration {
      enum abortion;
      enum abused-drugs;
      enum adult-and-pornography;
      enum alcohol-and-tobacco;
      enum auctions;
      enum bot-nets;
      enum business-and-economy;
      enum cdns;
      enum cheating;
      enum computer-and-internet-info;
      enum computer-and-internet-security;
      enum confirmed-spam-sources;
      enum cult-and-occult;
      enum dating;
      enum dead-sites;
      enum dynamic-content;
      enum educational-institutions;
      enum entertainment-and-arts;
      enum fashion-and-beauty;
      enum financial-services;
      enum gambling;
      enum games;
      enum government;
      enum gross;
      enum hacking;
      enum hate-and-racism;
      enum health-and-medicine;
      enum home;
      enum hunting-and-fishing;
      enum illegal;
      enum image-and-video-search;
      enum individual-stock-advice-and-tools;
      enum internet-communications;
      enum internet-portals;
      enum job-search;
      enum keyloggers-and-monitoring;
      enum kids;
      enum legal;
      enum local-information;
      enum malware-sites;
      enum marijuana;
      enum military;
      enum motor-vehicles;
      enum music;
      enum news-and-media;
      enum nudity;
      enum online-greeting-cards;
      enum online-personal-storage;
      enum open-http-proxies;
      enum p2p;
      enum parked-sites;
      enum pay-to-surf;
      enum personal-sites-and-blogs;
      enum philosophy-and-political-advocacy;
      enum phishing-and-other-frauds;
      enum private-ip-addresses;
      enum proxy-avoid-and-anonymizers;
      enum questionable;
      enum real-estate;
      enum recreation-and-hobbies;
      enum reference-and-research;
      enum religion;
      enum search-engines;
      enum sex-education;
      enum shareware-and-freeware;
      enum shopping;
      enum social-network;
      enum society;
      enum spam-urls;
      enum sports;
      enum spyware-and-adware;
      enum streaming-media;
      enum swimsuits-and-intimate-apparel;
      enum training-and-tools;
      enum translation;
      enum travel;
      enum uncategorized;
      enum unconfirmed-spam-sources;
      enum violence;
      enum weapons;
      enum web-advertisements;
      enum web-based-email;
      enum web-hosting;
      enum unused-food-and-dining;
      enum unused-reputation;
      enum self-harm;
      enum dns-over-https;
      enum low-thc-cannabis-products;
      enum generative-ai;
    }
  }

  typedef utd-log-level-type {
    type enumeration {
      enum detailed;
      enum error;
      enum info;
    }
  }

  grouping utd-parameter-map-regex-grouping {
    container parameter-map {
      description
        "Enter the parameter-map information for the regex";
      leaf regex {
        description
          "Provide the regex parameter-map name";
        type leafref {
          path "/ios:native/ios:parameter-map/ios:type/ios-policy:regex/ios-policy:name";
        }
      }
    }
  }

  typedef utd-reputation-type {
    type enumeration {
      enum high-risk;
      enum low-risk;
      enum moderate-risk;
      enum suspicious;
      enum trustworthy;
    }
  }

  typedef utd-alert-type {
    type enumeration {
      enum all;
      enum blacklist;
      enum categories-reputation;
      enum whitelist;
    }
  }

  typedef utd-ssl-alert-type {
    type enumeration {
      enum all;
      enum blacklist;
      enum graylist;
      enum whitelist;
      enum categories;
      enum reputation;
    }
  }

  typedef utd-flow-logging-type {
    type enumeration {
      enum threat-inspection;
      enum web-filter;
      enum file-inspection;
      enum tls-decryption;
    }
  }

  grouping utd-domain-filter-grouping {
    container domain {
      description
        "UTD Domain based web-filtering submode";
      list profile {
        description
          "Provide the profile ID";
        key "id";
        leaf id {
          type string {
            length "1..128";
          }
        }
        leaf alert {
          description
            "Provide the logging alert level";
          type enumeration {
            enum all;
            enum blacklist;
            enum whitelist;
          }
        }
        container blacklist {
          description
            "Choose the blacklist parameter-map";
          presence "true";
          uses utd-parameter-map-regex-grouping;
        }
        container redirect-server {
          description
            "Provide the IP address for the redirect server for blocked domains";
          choice id-choice {
            leaf external {
              description
                "Provide data about the external redirect server";
              type inet:ipv4-address;
            }
            leaf local-block-server {
              description
                "Use the local block server as the redirect server";
              type leafref {
                path "../../../../block/local-server/profile/id";
              }
            }
          }
        }
        container whitelist {
          description
            "Choose the whitelist parameter-map";
          presence "true";
          uses utd-parameter-map-regex-grouping;
        }
      }
    }
  }

  grouping utd-category-list-grouping {
    list category {
      key "name";
      leaf name {
        type utd-category-type;
      }
    }
  }

  grouping utd-web-filter-grouping {
    container web-filter {
      description
        "UTD web-filter profile configuration";
      container block {
        description
          "UTD block profile information";
        container local-server {
          description
            "UTD local block server configuration profile";
          list profile {
            description
              "Provide the profile ID";
            key "id";
            leaf id {
              type string {
                length "1..128";
              }
            }
            container block-page-interface {
              description
                "Provide the interface to be used for the block server";
              leaf Loopback {
                description
                  "Loopback interface";
                type leafref {
                  path "/ios:native/ios:interface/ios:Loopback/ios:name";
                }
              }
            }
            container content {
              description
                "Provide the content to be served from the server";
              choice content-choice {
                leaf text {
                  description
                    "Provide the text to be printed in the web page served";
                  type string {
                    length "1..240";
                  }
                }
                leaf file {
                  description
                    "Provide the HTML file to be served";
                  type string {
                    length "1..128";
                  }
                }
              }
            }
            leaf http-ports {
              description
                "Provide the HTTP ports to be used";
              type string {
                length "1..100";
              }
            }
          }
        }
        container page {
          description
            "UTD inline block page response profile";
          list profile {
            description
              "Provide the profile ID";
            key "id";
            leaf id {
              type string {
                length "1..128";
              }
            }
            choice page-choice {
              leaf file {
                description
                  "Specify the file name to be used for the block page";
                type string {
                  length "1..128";
                }
              }
              leaf redirect-url {
                description
                  "Specify the URL to be used for redirection";
                type string {
                  length "1..128";
                }
              }
              leaf text {
                description
                  "Specify the text to be used to be sent back";
                type string {
                  length "1..240";
                }
              }
            }
          }
        }
      }
      list sourcedb {
        description
          "UTD Web filtering source DB configuration submode";
        key "id";
        leaf id {
          type string {
            length "1..128";
          }
        }
        container logging {
          description
            "Provide source DB logging information";
          leaf level {
            description
              "Provide the logging level";
            type enumeration {
              enum debug;
              enum error;
              enum info;
              enum trace;
              enum warning;
            }
            default "error";
          }
        }
      }
      container url {
        description
          "UTD URL based web-filtering submode";
        list profile {
          description
            "Provide the profile ID";
          key "id";
          leaf id {
            type string {
              length "1..128";
            }
          }
          leaf-list alert {
            description
              "Provide the logging alert level";
            type utd-alert-type;
          }
          container blacklist {
            description
              "Choose the blacklist parameter-map";
            presence "true";
            uses utd-parameter-map-regex-grouping;
          }
          container categories {
            description
              "Choose from a list of categories";
            container allow {
              description
                "Choose the list of categories to be allowed";
              presence "true";
              uses utd-category-list-grouping;
            }
            container block {
              description
                "Choose the list of categories to be blocked";
              presence "true";
              uses utd-category-list-grouping;
            }
          }
          container block {
            description
              "Provide information on the block page/server to be used";
            leaf local-server {
              description
                "Provide the local block server profile ID";
              type leafref {
                path "../../../../block/local-server/profile/id";
              }
            }
            leaf page-profile {
              description
                "Provide the ID of the block page profile to be used";
              type leafref {
                path "../../../../block/page/profile/id";
              }
            }
          }
          container log {
            description
              "Choose the URL filtering preprocessor debug log options";
            leaf level {
              description
                "Choose the URL filtering preprocessor log level";
              type utd-log-level-type;
              default "error";
            }
          }
          container reputation {
            description
              "Choose the reputation range for the URLs to be blocked";
            presence "true";
            leaf block-threshold {
              description
                "Block the URLs with reputation at or above the specified level";
              type utd-reputation-type;
            }
          }
          container sourcedb {
            description
              "Choose source DB related configuration";
            container fail {
              description
                "Choose the fail option to apply when the source DB is down";
              leaf close {
                description
                  "Drop all URL filtering traffic on source DB failure";
                type empty;
              }
            }
          }
          container whitelist {
            description
              "Choose the whitelist parameter-map";
            presence "true";
            uses utd-parameter-map-regex-grouping;
          }
          leaf tls-decrypt-inject-block {
            description
              "Decrypt TLS (when able) for the purpose of injecting HTTP blocked content";
            type boolean;
            default "true";
          }
        }
      }
    }
  }

  grouping hour-minute-grouping {
    leaf hours {
      type uint8 {
        range "0..23";
      }
    }
    leaf minutes {
      type uint8 {
        range "0..59";
      }
    }
  }

  grouping username-password-grouping {
    leaf username {
      description
        "Provide the username for authentication";
      type string {
        length "1..64";
      }
    }
    container password-config {
      description
        "Provide the password for authentication";
      leaf type {
        type enumeration {
          enum 0 {
            description
              "Unencrypted password";
          }
          enum 6 {
            description
              "AES encrypted password";
          }
        }
        default "0";
      }
      leaf password {
        description
          "Provide the password for authentication";
        type string {
          length "1..64";
        }
      }
    }
    leaf password {
      description
        "***DEPRECATED*** Provide the password for authentication";
      status deprecated;
      type string {
        length "1..64";
      }
    }
  }

  grouping utd-engine-standard-grouping {
    container logging {
      description
        "Provide config options for logging the alerts";
      list host {
        description
          "Log the alerts to a host";
        key "name";
        leaf name {
          type string {
            length "1..45";
          }
        }
        leaf source-interface {
          description
            "Interface to source UTD syslogs from";
          must '/ios:native/ios:interface/*[concat(local-name(.), ios:name) = current()]';
          type string;
        }
      }
      leaf syslog {
        description
          "Log the alerts to IOS syslogs";
        type empty;
      }
    }
    container threat-inspection {
      description
        "IPS (or IDS) specific config commands";
      presence "true";
      container signature {
        description
          "Provide config options for the signatures";
        container update {
          description
            "Provide config options for the signature updates";
          container occur-at {
            description
              "Specify update occurence by calendar time";
            choice occur-at-choice {
              leaf daily {
                description
                  "Option for daily update";
                type empty;
              }
              leaf monthly {
                description
                  "Option for monthly update";
                type string {
                  length "1..128";
                }
              }
              leaf weekly {
                description
                  "Option for weekly update";
                type string {
                  length "1..128";
                }
              }
            }
            uses hour-minute-grouping;
          }
          container server {
            description
              "Provide config options for the signature update server";
            container cisco {
              description
                "Use Cisco site to provide updates";
              uses username-password-grouping;
            }
            container url {
              description
                "Enter the complete URL for the path to the update server";
              choice url-uname-passwd {
                case all-case {
                  container all {
                    leaf name {
                      type string {
                        length "1..128";
                      }
                    }
                    uses username-password-grouping;
                  }
                }
                case name-only {
                  leaf name {
                    type string {
                      length "1..128";
                    }
                  }
                }
              }
            }
          }
        }
      }
    }
    container web-filter {
      description
        "UTD engine standard web-filtering configuration";
      presence "true";
      leaf cloud-lookup {
        description
          "Cloud Lookup for web filtering";
        type boolean;
        default "true";
      }
      leaf sourcedb {
        description
          "Choose the source DB profile to use for web filtering";
        type leafref {
          path "../../../../web-filter/sourcedb/id";
        }
      }
    }
  }

  grouping utd-engine-threat-inspection-grouping {
    leaf threat {
      description
        "Provide the threat detection/protection option (default=detection)";
      type enumeration {
        enum detection;
        enum protection;
      }
    }
    leaf policy {
      description
        "Provide the policy option (default=balanced)";
      type enumeration {
        enum balanced;
        enum connectivity;
        enum security;
        enum max-detect;
      }
    }
    container logging {
      description
        "Provide logging level for the alerts for IPS/IDS";
      leaf level {
        description
          "Provide the log level";
        type enumeration {
          enum emerg;
          enum alert;
          enum crit;
          enum err;
          enum warning;
          enum notice;
          enum info;
          enum debug;
        }
        default "err";
      }
    }
    container port-scan {
      description
        "Provide the port-scan option";
      presence "true";
      container sense {
        description
          "Provide the sense level for port-scan";
        leaf level {
          description
            "Provide the sense level";
          type enumeration {
            enum low;
            enum medium;
            enum high;
          }
          default "low";
        }
      }
    }
  }

  grouping utd-threat-inspection-whitelist {
    list generator {
      description
        "Provide generator for the whitelist";
      key "id";
      leaf id {
        description
          "Provide the generator ID to be whitelisted";
        type uint32 {
          range "0..4294967295";
        }
      }
      list signature {
        description
          "Provide signature for the whitelist";
        key "id";
        leaf id {
          description
            "Provide the signature ID to be whitelisted";
          type uint32 {
            range "0..4294967295";
          }
        }
        leaf comment {
          description
            "Provide a comment for the whitelist";
          type string {
            length "1..128";
          }
        }
      }
    }
  }

  grouping utd-threat-inspection-custom-signature-grouping {
    leaf file {
      description
        "Provide file for the custom-signature";
      type string {
        length "8..128";
        pattern '(((bootflash:)|(flash:)|(harddisk:)).*)';
      }
    }
  }

  grouping utd-threat-inspection-grouping {
    container threat-inspection {
      description
        "UTD Threat Inspection (IPS/IDS) config modes";
      container whitelist {
        description
          "UTD whitelist config submode";
        list profile {
          description
            "UTD whitelist profile";
          key "name";
          leaf name {
            type string {
              length "1..128";
            }
          }
          uses utd-threat-inspection-whitelist;
        }
      }
      container custom-signature {
        description
          "UTD custom-signature config submode";
        list profile {
          description
            "UTD custom-signature profile";
          key "name";
          leaf name {
            type string {
              length "1..128";
            }
          }
          uses utd-threat-inspection-custom-signature-grouping;
        }
      }
      list profile {
        description
          "UTD Threat Inspection profile";
        key "name";
        leaf name {
          type string {
            length "1..128";
          }
        }
        uses utd-engine-threat-inspection-grouping;
        container whitelist {
          description
            "Associate a whitelist profile with this profile";
          leaf profile {
            description
              "UTD whitelist profile";
            type leafref {
              path "../../../whitelist/profile/name";
            }
          }
        }
        container custom-signature {
          description
            "Associate a custom-signature profile with this profile";
          leaf profile {
            description
              "UTD custom-signature profile";
            type leafref {
              path "../../../custom-signature/profile/name";
            }
          }
        }
      }
    }
  }

  grouping config-threat-inspection-normalizer-grouping {
    container normalizer {
      description
        "Provide config options for normalizer";
      presence "true";
      container tcp {
        description
          "Provide config options for TCP normalizer";
        presence "true";
        choice tcp-choice {
          default "tcp-all-case";
          case tcp-all-case {
            leaf all {
              description
                "Disable TCP normalizer all options";
              type boolean;
              default "true";
            }
          }
          case tcp-options-case {
            leaf block {
              description
                "Disable TCP normalizer block option";
              type boolean;
              default "true";
            }
          }
        }
      }
    }
  }

  grouping utd-global-config-grouping {
    container utd {
      description
        "UTD engine standard settings";
      container global {
        description
          "UTD engine standard global settings";
        presence "true";
        uses utd-engine-standard-grouping {
          augment "threat-inspection" {
            uses config-threat-inspection-normalizer-grouping;
          }
        }
        container file-reputation {
          description
            "UTD file reputation global configuration";
          presence "true";
          leaf cloud-server {
            description
              "Provide file reputation cloud server configuration";
            type string {
              length "1..128";
            }
          }
          leaf est-server {
            description
              "Provide file reputation est server configuration";
            type string {
              length "1..128";
            }
          }
          leaf query-interval {
            description
              "Set the query interval";
            type uint32 {
              range "1..86400";
            }
          }
        }
        container file-analysis {
          description
            "UTD file analysis configuration";
          presence "true";
          leaf cloud-server {
            description
              "Provide file analysis cloud server configuration";
            type string {
              length "1..128";
            }
          }
          container apikey {
            description
              "Provide file analysis apikey configuration";
            leaf type {
              type enumeration {
                enum 0 {
                  description
                    "Unencrypted APIkey";
                }
                enum 6 {
                  description
                    "AES Encrypted APIkey";
                }
              }
            }
            leaf key {
              type string {
                length "1..128";
              }
            }
          }
        }
        container flow-logging {
          description
            "Provide the UTD flow logging level";
          choice flow-logging-choice {
            case all-case {
              leaf all {
                type empty;
              }
            }
            case list-case {
              leaf-list list {
                type utd-flow-logging-type;
              }
            }
          }
        }
      }
    }
  }

  grouping utd-file-analysis-profile-grouping {
    container file-analysis {
      description
        "UTD file analysis configuration";
      list profile {
        description
          "UTD file analysis profile configuration";
        key "name";
        leaf name {
          type string {
            length "1..128";
          }
        }
        container file-types {
          description
            "Add the file types to be sent for analysis";
          presence "true";
          list file-type {
            key "name";
            leaf name {
              type enumeration {
                enum pdf;
                enum ms-exe;
                enum new-office;
                enum rtf;
                enum mdb;
                enum mscab;
                enum msole2;
                enum wri;
                enum xlw;
                enum flv;
                enum swf;
              }
            }
          }
        }
        container alert {
          description
            "File analysis alert level configuration";
          leaf level {
            description
              "Specify alert level configuration";
            type enumeration {
              enum critical;
              enum warning;
              enum info;
            }
          }
        }
      }
    }
  }

  grouping utd-file-reputation-profile-grouping {
    container file-reputation {
      description
        "UTD file reputation configuration";
      list profile {
        description
          "UTD file reputation profile configuration";
        key "name";
        leaf name {
          type string {
            length "1..128";
          }
        }
        container alert {
          description
            "File reputation alert level configuration";
          leaf level {
            description
              "Specify alert level configuration";
            type enumeration {
              enum critical;
              enum warning;
              enum info;
            }
          }
        }
      }
    }
  }

  grouping utd-file-inspection-profile-grouping {
    container file-inspection {
      description
        "UTD file inspection configuration";
      list profile {
        description
          "UTD file inspection profile configuration";
        key "name";
        leaf name {
          type string {
            length "1..128";
          }
        }
        container analysis {
          description
            "Enable and configure file analysis for this profile";
          presence "true";
          leaf profile {
            description
              "Select the profile to use for file analysis";
            type leafref {
              path "../../../../file-analysis/profile/name";
            }
          }
        }
        container reputation {
          description
            "Enable and configure file reputation for this profile";
          presence "true";
          leaf profile {
            description
              "Select the profile to use for file reputation";
            type leafref {
              path "../../../../file-reputation/profile/name";
            }
          }
        }
      }
    }
  }

  grouping utd-tls-decryption-profile-grouping {
    container tls-decryption {
      description
        "UTD tls-decryption profile configuration";
      list profile {
        description
          "UTD tls-decryption profile configuration";
        key "name";
        leaf name {
          type string {
            length "1..128";
          }
        }
        leaf-list alert {
          description
            "Provide the logging alert level";
          type utd-ssl-alert-type;
        }
        container blacklist {
          description
            "Choose the blacklist parameter-map";
          presence "true";
          uses utd-parameter-map-regex-grouping;
        }
        container categories {
          description
            "Choose from a list of categories";
          container decrypt {
            description
              "Choose the list of categories to be decrypted";
            presence "true";
            uses utd-category-list-grouping;
          }
          container never-decrypt {
            description
              "Choose the list of categories to never be decrypted";
            presence "true";
            uses utd-category-list-grouping;
          }
          container skip-decrypt {
            description
              "Choose the list of categories to skip being decrypted";
            presence "true";
            uses utd-category-list-grouping;
          }
        }
        container graylist {
          description
            "Choose the graylist parameter-map";
          presence "true";
          uses utd-parameter-map-regex-grouping;
        }
        container log {
          description
            "Choose the tls-decryption preprocessor debug log options";
          leaf level {
            description
              "Choose the tls-decryption preprocessor log level";
            type utd-log-level-type;
            default "error";
          }
        }
        container reputation {
          description
            "Choose the reputation range for the URLs to be decrypted";
          presence "true";
          leaf decrypt-threshold {
            description
              "Decrypt URLs with reputation at or below the specified level";
            type utd-reputation-type;
          }
          leaf skip-decrypt-threshold {
            description
              "Skip decrypting URLs with reputation at or above the specified level";
            type utd-reputation-type;
          }
        }
        container sourcedb {
          description
            "Choose source DB related configuration";
          container fail {
            description
              "Choose the fail option to apply when the source DB is down";
            leaf decrypt {
              description
                "Decrypt all tls-decryption traffic on source DB failure";
              type empty;
            }
          }
        }
        container whitelist {
          description
            "Choose the whitelist parameter-map";
          presence "true";
          uses utd-parameter-map-regex-grouping;
        }
      }
    }
  }

  grouping utd-policy-profile-common-grouping {
    container fail {
      description
        "Enter the UTD engine fail mode operation";
      leaf close {
        description
          "Drop all IPS/IDS traffic on UTD engine failure";
        type empty;
      }
    }
    container file-inspection {
      description
        "Associate file-inspection profile with this policy";
      leaf profile {
        description
          "Associate file-inspection profile with this policy";
        type leafref {
          path "../../../file-inspection/profile/name";
        }
      }
    }
    container tls-decryption {
      description
        "Associate tls-decryption profile with this policy";
      leaf profile {
        description
          "Associate tls-decryption profile with this policy";
        type leafref {
          path "../../../tls-decryption/profile/name";
        }
      }
      leaf action {
        description
          "TLS decryption action to be taken for the sessions";
        when '(/ios:native/ios-utd:utd-unified-policy/ios-utd:utd/ios-utd:engine/ios-utd:standard/ios-utd:unified-policy)';
        type enumeration {
          enum decrypt;
          enum never-decrypt;
          enum skip-decrypt;
        }
      }
    }
    container threat-inspection {
      description
        "Associate threat-inspection profile with this policy";
      leaf profile {
        description
          "Associate threat-inspection profile with this policy";
        type leafref {
          path "../../../threat-inspection/profile/name";
        }
      }
    }
    container web-filter {
      description
        "Associate web filter profile with this policy";
      container url {
        description
          "Associate web filter profile with this policy";
        leaf profile {
          description
            "Associate web filter profile with this policy";
          type leafref {
            path "../../../../web-filter/url/profile/id";
          }
        }
      }
    }
  }

  grouping utd-mt-policy-grouping {
    list policy {
      description
        "Multi-tenancy utd policy";
      key "name";
      leaf name {
        type string {
          length "1..128";
        }
      }
      leaf all-interfaces {
        description
          "Enable intrusion inspection on all supported interfaces for this set of VRFs";
        type empty;
      }
      list vrf {
        description
          "Associate a VRF with this policy";
        key "name";
        leaf name {
          must "/ios:native/ios:vrf/ios:definition[ios:name=current()] or /ios:native/ios:ip/ios:vrf[ios:name=current()] or .='global'" {
            error-message "VRF must be created 1st, deleted last";
          }
          type string {
            length "1..32";
          }
        }
      }
      uses utd-policy-profile-common-grouping;
    }
  }

  grouping config-utd-mt-grouping {
    container utd-mt {
      container utd {
        description
          "Global Unified Threat Defense";
        leaf multi-tenancy {
          description
            "Enable UTD multi-tenancy mode";
          type empty;
        }
        container engine {
          description
            "UTD engine";
          container standard {
            description
              "UTD engine standard";
            container multi-tenancy {
              description
                "Enable UTD multi-tenancy mode";
              presence "true";
              uses utd-web-filter-grouping;
              uses utd-threat-inspection-grouping;
              uses utd-global-config-grouping;
              uses utd-file-analysis-profile-grouping;
              uses utd-file-reputation-profile-grouping;
              uses utd-file-inspection-profile-grouping;
              uses utd-tls-decryption-profile-grouping;
              uses utd-mt-policy-grouping;
            }
          }
        }
      }
    }
  }

  grouping utd-unified-policy-profile-grouping {
    list policy {
      description
        "Unified policy utd policy";
      key "name";
      leaf name {
        type string {
          length "1..128";
        }
      }
      uses utd-policy-profile-common-grouping;
    }
  }

  grouping config-utd-unified-policy-grouping {
    container utd-unified-policy {
      container utd {
        description
          "Global Unified Threat Defense";
        container engine {
          description
            "UTD engine";
          container standard {
            description
              "UTD engine standard";
            container unified-policy {
              description
                "Enable UTD unified-policy mode";
              presence "true";
              uses utd-web-filter-grouping;
              uses utd-threat-inspection-grouping;
              uses utd-global-config-grouping;
              uses utd-file-analysis-profile-grouping;
              uses utd-file-reputation-profile-grouping;
              uses utd-file-inspection-profile-grouping;
              uses utd-tls-decryption-profile-grouping;
              uses utd-unified-policy-profile-grouping;
            }
          }
        }
      }
    }
  }

  grouping config-utd-st-grouping {
    container utd-st {
      container utd {
        description
          "Global Unified Threat Defense Engine";
        uses utd-web-filter-grouping {
          augment "web-filter" {
            uses utd-domain-filter-grouping;
          }
        }
        container engine {
          description
            "UTD engine";
          container advanced {
            description
              "UTD engine advanced";
            presence "true";
            container threat {
              description
                "Provide threat detection";
              leaf detection {
                description
                  "Provide threat detection";
                type empty;
              }
            }
          }
          container standard {
            description
              "UTD engine standard";
            presence "true";
            uses utd-engine-standard-grouping {
              augment "threat-inspection" {
                uses utd-engine-threat-inspection-grouping {
                  augment "logging" {
                    container statistics {
                      description
                        "Provide logging statistics options";
                      leaf enable {
                        description
                          "Enable logging statistics";
                        type empty;
                      }
                    }
                  }
                }
                leaf whitelist {
                  description
                    "Enable whitelisting under the utd engine";
                  type empty;
                }
              }
              augment "web-filter" {
                leaf domain-profile {
                  description
                    "Choose the domain profile to use for web filtering";
                  type leafref {
                    path "../../../../web-filter/domain/profile/id";
                  }
                }
                leaf url-profile {
                  description
                    "Choose the url profile to use for web filtering";
                  type leafref {
                    path "../../../../web-filter/url/profile/id";
                  }
                }
              }
            }
          }
        }
        container threat-inspection {
          description
            "UTD Threat Inspection (IPS/IDS) config modes";
          container whitelist {
            description
              "UTD whitelist config submode";
            presence "true";
            uses utd-threat-inspection-whitelist;
          }
        }
      }
    }
  }

  grouping config-utd-grouping {
    container utd {
      description
        "Global Unified Threat Defense";
      presence "true";
      leaf all-interfaces {
        description
          "Enable intrusion inspection on all supported interfaces";
        type empty;
      }
      container redirect {
        description
          "Specify the interface connected to the UTD";
        container interface {
          description
            "Specify the interface connected to UTD";
          choice redirect-choice {
            leaf BDI {
              description
                "Bridge-Domain interface";
              type leafref {
                path "/ios:native/ios:interface/ios:BDI/ios:name";
              }
            }
            leaf VirtualPortGroup {
              description
                "Virtual Port Group";
              type leafref {
                path "/ios:native/ios:interface/ios:VirtualPortGroup/ios:name";
              }
            }
            leaf BD-VIF {
              description
                "Bridge-Domain Virtual IP interface";
              type leafref {
                path "/ios:native/ios:interface/ios:BD-VIF/ios:name";
              }
            }
          }
        }
      }
      container engine {
        description
          "Select UTD engine mode to run";
        presence "true";
        leaf mode {
          type enumeration {
            enum standard;
            enum advanced;
          }
        }
        container fail {
          description
            "Enter the UTD engine fail mode operation";
          leaf close {
            description
              "Drop all IPS/IDS traffic on UTD engine failure";
            type empty;
          }
        }
      }
    }
  }

  grouping config-interface-utd-grouping {
    container utd {
      description
        "UTD support on this interface";
      leaf enable {
        description
          "Enable threat defense on this interface";
        type empty;
      }
    }
  }

  grouping config-utd-parameter-map-grouping {
    container utd-policy {
      description
        "Attach UTD Policy";
      leaf policy-name {
        description
          "UTD Policy name";
        type leafref {
          path "/ios:native/ios-utd:utd-unified-policy/ios-utd:utd/ios-utd:engine/ios-utd:standard/ios-utd:unified-policy/ios-utd:policy/ios-utd:name";
        }
      }
    }
  }

  augment "/ios:native" {
    uses config-utd-grouping;
    uses config-utd-st-grouping;
    uses config-utd-mt-grouping;
    uses config-utd-unified-policy-grouping;
  }

  augment "/ios:native/ios:interface/ios:Ethernet" {
    uses config-interface-utd-grouping;
  }

  augment "/ios:native/ios:interface/ios:FastEthernet" {
    uses config-interface-utd-grouping;
  }

  augment "/ios:native/ios:interface/ios:GigabitEthernet" {
    uses config-interface-utd-grouping;
  }

  augment "/ios:native/ios:interface/ios:TenGigabitEthernet" {
    uses config-interface-utd-grouping;
  }

  augment "/ios:native/ios:interface/ios:FiveGigabitEthernet" {
    uses config-interface-utd-grouping;
  }

  augment "/ios:native/ios:interface/ios:AppGigabitEthernet" {
    uses config-interface-utd-grouping;
  }

  augment "/ios:native/ios:interface/ios:TwentyFiveGigE" {
    uses config-interface-utd-grouping;
  }

  augment "/ios:native/ios:interface/ios:TwentyFiveGigabitEthernet" {
    status obsolete;
    uses config-interface-utd-grouping {
      status obsolete;
    }
  }

  augment "/ios:native/ios:interface/ios:FortyGigabitEthernet" {
    uses config-interface-utd-grouping;
  }

  augment "/ios:native/ios:interface/ios:HundredGigE" {
    uses config-interface-utd-grouping;
  }

  augment "/ios:native/ios:interface/ios:TwoGigabitEthernet" {
    uses config-interface-utd-grouping;
  }

  augment "/ios:native/ios:interface/ios:LISP" {
    uses config-interface-utd-grouping;
  }

  augment "/ios:native/ios:interface/ios:Loopback" {
    uses config-interface-utd-grouping;
  }

  augment "/ios:native/ios:interface/ios:Tunnel" {
    uses config-interface-utd-grouping;
  }

  augment "/ios:native/ios:interface/ios:Virtual-Template" {
    uses config-interface-utd-grouping;
  }

  augment "/ios:native/ios:interface/ios:Vlan" {
    uses config-interface-utd-grouping;
  }

  augment "/ios:native/ios:interface/ios:vasileft" {
    uses config-interface-utd-grouping;
  }

  augment "/ios:native/ios:interface/ios:vasiright" {
    uses config-interface-utd-grouping;
  }

  augment "/ios:native/ios:parameter-map/ios:type/ios-policy:inspect" {
    uses config-utd-parameter-map-grouping;
  }

  augment "/ios:native/ios:parameter-map/ios:type/ios-policy:inspect-global" {
    uses config-utd-parameter-map-grouping;
  }
}
