module Cisco-IOS-XE-meraki-connect-oper {
  yang-version 1.1;
  namespace "http://cisco.com/ns/yang/Cisco-IOS-XE-meraki-connect-oper";
  prefix meraki-connect-ios-xe-oper;

  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     monitoring all parameters of Cloud Monitoring with Meraki Dashboard in a Network Element.
     Copyright (c) 2023-2024 by Cisco Systems, Inc.
     All rights reserved.";

  revision 2025-03-01 {
    description
      "- Added new enum values for config updater event result.
       - Added save config operation progress and process status";
    reference
      "2.3.0";
    cisco-semver:module-version "2.3.0";
  }
  revision 2024-11-01 {
    description
      "- Added new product identifiers for Meraki monitoring support.
       - Added new enum values for config updater event result
       - Added new product identifiers for Meraki monitoring support";
    reference
      "2.2.0";
    cisco-semver:module-version "2.2.0";
  }
  revision 2024-07-01 {
    description
      "- Added network name to nextunnel config.
       - Added certificate expiration time to device registration.
       - Added XPath and resulting operations to config monitor notifications.
       - Added retry states to fetch data from Meraki dashboard.
       - Added new product identifiers for Meraki dashboard support.
       - Added device migration compatibility failure details.
       - Added new product identifiers for Meraki monitoring support.";
    reference
      "2.1.0";
    cisco-semver:module-version "2.1.0";
  }
  revision 2024-03-01 {
    description
      "- Added LED management and reset features.
       - Added details of active Nextunnel sessions.
       - Added device migration mode, state and status.
       - Added config monitor notification entries and process status.
       - Added config updater state machine progress and process status.
       - Added cloud ID to device registration, and obsolete meraki ID.";
    reference
      "2.0.0";
    cisco-semver:module-version "2.0.0";
  }
  revision 2023-11-01 {
    description
      "Initial revision";
    reference
      "1.0.0";
    cisco-semver:module-version "1.0.0";
  }

  typedef migration-mode-types {
    type enumeration {
      enum mig-managed-mode {
        value 0;
        description
          "Device migration mode managed";
      }
      enum mig-monitor-mode {
        value 1;
        description
          "Device migration mode monitor";
      }
      enum mig-factory-mode {
        value 2;
        description
          "Device migration mode managed-factory";
      }
      enum mig-catalyst-mode {
        value 3;
        description
          "Device migration mode catalyst";
      }
    }
    description
      "Migration mode types";
  }

  typedef meraki-fetch-state {
    type enumeration {
      enum meraki-config-fetch-init {
        value 0;
        description
          "Config fetch init";
      }
      enum meraki-config-fetch-retry {
        value 1;
        description
          "Config fetch init retry";
      }
      enum meraki-config-fetch-failed {
        value 2;
        description
          "Config fetch failed";
      }
      enum meraki-config-fetch-succeeded {
        value 3;
        description
          "Config fetch succeeded";
      }
    }
    description
      "Possible fetch states for Meraki Nextunnel";
  }

  typedef meraki-nextunnel-state {
    type enumeration {
      enum meraki-tunnel-down {
        value 0;
        description
          "Meraki Nextunnel is down";
      }
      enum meraki-tunnel-up {
        value 1;
        description
          "Meraki Nextunnel is up";
      }
    }
    description
      "Possible states of the Meraki Nextunnel";
  }

  typedef meraki-reg-state {
    type enumeration {
      enum reg-init {
        value 0;
        description
          "Device registering";
      }
      enum reg-succeeded {
        value 1;
        description
          "Device register succeeded";
      }
      enum reg-failed {
        value 2;
        description
          "Device register failed";
      }
      enum reg-empty {
        value 3;
        description
          "Device is not registered";
      }
      enum reg-claim-id-fetch {
        value 4;
        description
          "Fetch the claim id from Meraki dashboard";
      }
      enum reg-token-fetch {
        value 5;
        description
          "Fetch the token from the Meraki dashboard";
      }
      enum reg-cert-fetch {
        value 6;
        description
          "Fetch the certificate from the Meraki dashboard";
      }
      enum reg-cert-fetch-renew {
        value 7;
        description
          "Fetch the new certificate from the Meraki dashboard";
      }
      enum reg-claim-id-fetch-retry {
        value 8;
        description
          "Retry fetching the Cloud ID from Meraki dashboard";
      }
      enum reg-token-fetch-retry {
        value 9;
        description
          "Retry fetching the token from the Meraki dashboard";
      }
      enum reg-cert-fetch-retry {
        value 10;
        description
          "Retry fetching the certificate from the Meraki dashboard";
      }
      enum reg-cert-fetch-renew-retry {
        value 11;
        description
          "Retry renewing certificate from the Meraki dashboard";
      }
    }
    description
      "Possible device registration states with Meraki dashboard";
  }

  typedef meraki-device-pid {
    type enumeration {
      enum c9200l-48pl-4g {
        value 0;
        description
          "Catalyst 9200 48-port partial PoE+, 4 of 1 Gigabit fixed uplink";
      }
      enum c9200l-48pl-4x {
        value 1;
        description
          "Catalyst 9200 48-port partial PoE+, 4 of 1/10 Gigabit fixed uplink";
      }
      enum c9200l-48pxg-4x {
        value 2;
        description
          "Catalyst 9200 48 ports full POE+ (12 mGig ports up to 10 Gigabit, 36 ports up to 1 Gigabit), 4 of 1/10 Gigabit fixed uplink";
      }
      enum c9200l-24pxg-4x {
        value 3;
        description
          "Catalyst 9200 24 ports full PoE+ (8 mGig ports up to 10 Gigabit, 16 ports up to 1 Gigabit), 4 of 1/10 Gigabit fixed uplink";
      }
      enum c9200l-48p-4x {
        value 4;
        description
          "Catalyst 9200 48 ports full PoE+, 4 of 1/10 Gigabit fixed uplink";
      }
      enum c9200l-24p-4x {
        value 5;
        description
          "Catalyst 9200 24 ports full PoE+, 4 of 1/10 Gigabit fixed uplink";
      }
      enum c9200l-24t-4g {
        value 6;
        description
          "Catalyst 9200 24 ports data, 4 of 1 Gigabit fixed uplink";
      }
      enum c9200l-24p-4g {
        value 7;
        description
          "Catalyst 9200 24 ports full PoE+, 4 of 1 Gigabit fixed uplink";
      }
      enum c9200l-48t-4g {
        value 8;
        description
          "Catalyst 9200 48 ports data, 4 of 1 Gigabit fixed uplink";
      }
      enum c9200l-48p-4g {
        value 9;
        description
          "Catalyst 9200 48 ports full POE+, 4 of 1 Gigabit fixed uplink";
      }
      enum c9200l-24t-4x {
        value 10;
        description
          "Catalyst 9200 24 ports data, 4 of 1/10 Gigabit fixed uplink";
      }
      enum c9200l-48t-4x {
        value 11;
        description
          "Catalyst 9200 48 ports data, 4 of 1/10 Gigabit fixed uplink";
      }
      enum c9200l-24pxg-2y {
        value 12;
        description
          "Catalyst 9200 24 ports full PoE+ (8 mGig ports up to 10 Gigabit, 16 ports up to 1 Gigabit), 2 of 1/10/25 Gigabit fixed uplink";
      }
      enum c9200l-48pxg-2y {
        value 13;
        description
          "Catalyst 9200 48 ports full POE+ (8 mGig ports up to 10 Gigabit, 40 ports up to 1 Gigabit), 2 of 1/10/25 Gigabit fixed uplink";
      }
      enum c9200-24t {
        value 14;
        description
          "Catalyst 9200 24 ports data, Modular uplink options";
      }
      enum c9200-24p {
        value 15;
        description
          "Catalyst 9200 24 ports full PoE+, Modular uplink options";
      }
      enum c9200-24pb {
        value 16;
        description
          "Catalyst 9200 24 ports full PoE+, Modular uplink options";
      }
      enum c9200-24pxg {
        value 17;
        description
          "Catalyst 9200 24 ports full PoE+ (8 mGig ports up to 10 Gigabit, 16 ports up to 1 Gigabit), Modular uplink options";
      }
      enum c9200-48t {
        value 18;
        description
          "Catalyst 9200 48 ports data, Modular uplink options";
      }
      enum c9200-48p {
        value 19;
        description
          "Catalyst 9200 48 ports full PoE+, Modular uplink options";
      }
      enum c9200-48pb {
        value 20;
        description
          "Catalyst 9200 48 ports full PoE+, Modular uplink options";
      }
      enum c9200-48pl {
        value 21;
        description
          "Catalyst 9200 48 ports full PoE+, Modular uplink options";
      }
      enum c9200-48pxg {
        value 22;
        description
          "Catalyst 9200 48 ports full PoE+ (8 mGig ports up to 10 Gigabit, 40 ports up to 1 Gigabit), Modular uplink options";
      }
      enum c9200cx-12t-2x2g {
        value 23;
        description
          "Catalyst 9200 12 ports data, 2 of 1 Gigabit copper, 1 of 1 Gigabit Class 6, 2 of 10 Gigabit SFP+ fixed uplink";
      }
      enum c9200cx-8p-2x2g {
        value 24;
        description
          "Catalyst 9200 8 ports full PoE+, 2 of 1 Gigabit copper, 2 of 10 Gigabit SFP+ fixed uplink";
      }
      enum c9200cx-12p-2x2g {
        value 25;
        description
          "Catalyst 9200 12 ports PoE+, 2 of 1 Gigabit copper, 2 of 10 Gigabit SFP+ fixed uplink";
      }
      enum c9200cx-8uxg-2x {
        value 26;
        description
          "Catalyst 9200 8 ports UPOE (4 mGig ports up to 10 Gigabit, 4 ports up to 1 Gigabit), 2 of 10 Gigabit SFP+ fixed uplink";
      }
      enum c9200cx-8p-2xgh {
        value 27;
        description
          "Catalyst 9200 8 ports full PoE+, 2 of 1 Gigabit copper, 2 of 10 Gigabit SFP+ fixed uplink";
      }
      enum c9200cx-12p-2xgh {
        value 28;
        description
          "Catalyst 9200 12 ports PoE+, 2 of 1 Gigabit copper, 2 of 10 Gigabit SFP+ fixed uplink";
      }
      enum c9200cx-8uxg-2xh {
        value 29;
        description
          "Catalyst 9200 8 ports UPOE (4 mGig ports up to 10 Gigabit, 4 ports up to 1 Gigabit), 2 of 10 Gigabit SFP+ fixed uplink";
      }
      enum c9300l-48uxg-4x {
        value 30;
        description
          "Catalyst 9300 Series Switch with 36 of x1 Gigabit 12 of mGig UPOE downlink 4 of 10 Gigabit fixed uplink";
      }
      enum c9300l-24p-4g {
        value 31;
        description
          "Catalyst 9300 Series Switch with 24 of 1 Gigabit POE+ downlink 4 of 1 Gigabit fixed uplink";
      }
      enum c9300l-24p-4x {
        value 32;
        description
          "Catalyst 9300 Series Switch with 24 of 1 Gigabit POE+ downlink 4 of 10 Gigabit Fixed uplink";
      }
      enum c9300l-24t-4g {
        value 33;
        description
          "Catalyst 9300 Series Switch with 24 of 1 Gigabit non-POE downlink 4 of 1 Gigabit fixed uplink";
      }
      enum c9300l-24t-4x {
        value 34;
        description
          "Catalyst 9300 Series Switch with 24 of 1 Gigabit non-POE downlink 4 of 10 Gigabit fixed Uplink";
      }
      enum c9300l-24uxg-2q {
        value 35;
        description
          "Catalyst 9300 Series Switch with 16 of 1 Gigabit 8 of mGig UPOE downlink 2 of 40 Gigabit fixed uplink";
      }
      enum c9300l-24uxg-4x {
        value 36;
        description
          "Catalyst 9300 Series Switch with 16 of 1 Gigabit 8 of mGig UPOE downlink 4 of 10 Gigabit fixed uplink";
      }
      enum c9300l-48p-4g {
        value 37;
        description
          "Catalyst 9300 Series Switch with 48 of 1 Gigabit POE+ downlink 4 of 1 Gigabit fixed uplink";
      }
      enum c9300l-48p-4x {
        value 38;
        description
          "Catalyst 9300 Series Switch with 48 of 1 Gigabit POE+ downlink 4 of 10 Gigabit fixed uplink";
      }
      enum c9300l-48t-4g {
        value 39;
        description
          "Catalyst 9300 Series Switch with 48 of 1 Gigabit non-POE downlink 4 of 1 Gigabit fixed uplink";
      }
      enum c9300l-48t-4x {
        value 40;
        description
          "Catalyst 9300 Series Switch with 48 of 1 Gigabit non-POE downlink 4 of 10 Gigabit fixed uplink";
      }
      enum c9300l-48uxg-2q {
        value 41;
        description
          "Catalyst 9300 Series Switch with 36 of 1 Gigabit 12 of mGig UPOE downlink 2 of 40 Gigabit fixed uplink";
      }
      enum c9300l-48pf-4x {
        value 42;
        description
          "Catalyst 9300 Series Switch with 48 of 1 Gigabit POE+ downlink 4 of 10 Gigabit fixed uplink";
      }
      enum c9300l-48pf-4g {
        value 43;
        description
          "Catalyst 9300 Series Switch with 48 of 1 Gigabit POE+ downlink 4 of 1 Gigabit fixed uplink";
      }
      enum c9300lm-24u-4y-a-e {
        value 44;
        description
          "Catalyst 9300 Series Switch with 24 of 1 Gigabit UPOE downlink 4 of 25 Gigabit fixed uplink";
      }
      enum c9300lm-48t-4y-a-e {
        value 45;
        description
          "Catalyst 9300 Series Switch with 48 of 1 Gigabit downlink 4 of 25 Gigabit fixed uplink";
      }
      enum c9300lm-48u-4y-a-e {
        value 46;
        description
          "Catalyst 9300 Series Switch with 48 of 1 Gigabit UPOE downlink 4 of 25 Gigabit fixed uplink";
      }
      enum c9300lm-48ux-4y-a-e {
        value 47;
        description
          "Catalyst 9300 Series Switch with 40 of 1 Gigabit 8 of mGig UPOE downlink 4 of 25 Gigabit fixed uplink";
      }
      enum c9300-24t {
        value 48;
        description
          "Catalyst 9300 Series Switch with 24 of 1 Gigabit Interfaces";
      }
      enum c9300-24p {
        value 49;
        description
          "Catalyst 9300 Series Switch with 24 of 1 Gigabit POE Interfaces";
      }
      enum c9300-24u {
        value 50;
        description
          "Catalyst 9300 Series Switch";
      }
      enum c9300-24ub {
        value 51;
        description
          "Catalyst 9300 Series Switch with 24 of 1 Gigabit UPOE Interfaces";
      }
      enum c9300-24h {
        value 52;
        description
          "Catalyst 9300 Series Switch with 24 of 1 Gigabit UPOE+ Interfaces";
      }
      enum c9300-24ux {
        value 53;
        description
          "Catalyst 9300 Series Switch with 24 of 10 Gigabit UPOE Interfaces";
      }
      enum c9300-24uxb {
        value 54;
        description
          "Catalyst 9300 Series Switch with 24 of 10 Gigabit UPOE Interfaces";
      }
      enum c9300-48t {
        value 55;
        description
          "Catalyst 9300 Series Switch with 48 of 1 Gigabit Interfaces";
      }
      enum c9300-48p {
        value 56;
        description
          "Catalyst 9300 Series Switch with 48 of 1 Gigabit POE Interfaces";
      }
      enum c9300-48u {
        value 57;
        description
          "Catalyst 9300 Series Switch with 48 of 1 Gigabit UPOE Interfaces";
      }
      enum c9300-48ub {
        value 58;
        description
          "Catalyst 9300 Series Switch with 48 of 1 Gigabit UPOE Interfaces";
      }
      enum c9300-48h {
        value 59;
        description
          "Catalyst 9300 Series Switch with 48 of 1 Gigabit UPOE+ Interfaces";
      }
      enum c9300-48uxm {
        value 60;
        description
          "Catalyst 9300 Series Switch with 36 2.5G and 12 mGig UPOE Interfaces";
      }
      enum c9300-48un {
        value 61;
        description
          "Catalyst 9300 Series Switch with 48 of 5 Gigabit UPOE Interface";
      }
      enum c9300x-24hx {
        value 62;
        description
          "Catalyst 9300 Series Switch with 24 mGig UPOE Interfaces";
      }
      enum c9300x-48tx {
        value 63;
        description
          "Catalyst 9300 Series Switch with 48 mGig non-POE Interfaces";
      }
      enum c9300x-48hxn {
        value 64;
        description
          "Catalyst 9300 Series Switch with 40 of 5 Gigabit 8 of mGig UPOE Interfaces";
      }
      enum c9300x-48hx {
        value 65;
        description
          "Catalyst 9300 Series Switch with 48 mGig UPOE Interfaces";
      }
      enum c9300x-12y {
        value 66;
        description
          "Catalyst 9300 Series Switch with 12 of 25 Gigabit Interfaces";
      }
      enum c9300x-24y {
        value 67;
        description
          "Catalyst 9300 Series Switch with 24 of 25 Gigabit Interfaces";
      }
      enum c9500x-60l4d {
        value 68;
        description
          "Catalyst 9500 Series fixed switch with 60 of 50 Gigabit ports and 4 of 400 Gigabit ports";
      }
      enum c9500x-28c8d {
        value 69;
        description
          "Catalyst 9500 industry Gigabit switch";
      }
      enum c9500-32qc {
        value 70;
        description
          "Catalyst 9500 series with 32 Ports of 40 Gigabit/16 Ports of 100 Gigabit";
      }
      enum c9500-32c {
        value 71;
        description
          "Catalyst 9500 series with 32 Ports of 40 Gigabit/16 Ports of 100 Gigabit";
      }
      enum c9500-48y4c {
        value 72;
        description
          "Catalyst 9500 series with 48 Ports of 1 Gigabit/10 Gigabit/25 Gigabit + 4 Ports of 40 Gigabit/100 Gigabit";
      }
      enum c9500-24y4c {
        value 73;
        description
          "Catalyst 9500 is 1 RU fixed chassis with 24 Ports of 1 Gigabit/10 Gigabit/25 Gigabit + 4 Ports of 40 Gigabit/100 Gigabit";
      }
      enum c9500-24q {
        value 74;
        description
          "Catalyst 9500 24-port 40 Gigabit data only switch";
      }
      enum c9500-12q {
        value 75;
        description
          "Catalyst 9500 12-port 40 Gigabit data only switch";
      }
      enum c9500-40x {
        value 76;
        description
          "Catalyst 9500 40-port 10 Gigabit data only switch";
      }
      enum c9500-16x {
        value 77;
        description
          "Catalyst 9500 16-port 10 Gigabit data only switch";
      }
      enum c9800-40-k9 {
        value 78;
        description
          "Catalyst 9800-40 Wireless Controller";
      }
      enum c9800-80-k9 {
        value 79;
        description
          "Catalyst 9800-80 Wireless Controller";
      }
      enum c9800-l-c-k9 {
        value 80;
        description
          "Catalyst 9800-L-C Wireless Controller";
      }
      enum c9800-l-f-k9 {
        value 81;
        description
          "Catalyst 9800-L-F Wireless Controller";
      }
      enum c9800-cl-k9 {
        value 82;
        description
          "Catalyst 9800-CL virtual Wireless Controller";
      }
      enum cw9800m {
        value 83;
        description
          "Catalyst CW-9800-M Wireless Controller";
      }
      enum cw9800h1 {
        value 84;
        description
          "Catalyst CW-9800-H1 Wireless Controller";
      }
      enum cw9800h2 {
        value 85;
        description
          "Catalyst CW-9800-H2 Wireless Controller";
      }
      enum c9300-xxi2448s {
        value 86;
        description
          "Catalyst 9300 Series Switch with 24 of 1 Gigabit SFP uplink";
      }
      enum c9300-48s {
        value 87;
        description
          "Catalyst 9300 Series Switch with 48 of 1 Gigabit SFP uplink";
      }
      enum c9350-48u {
        value 88;
        description
          "Catalyst 9350 Series Switch with 48 Gigabit Ethernet UPOE Interfaces";
      }
      enum c9350-48p {
        value 89;
        description
          "Catalyst 9350 Series Switch with 48 Gigabit Ethernet POE+ Interfaces";
      }
      enum c9350-48t {
        value 90;
        description
          "Catalyst 9350 Series Switch with 48 Gigabit Ethernet Data Interfaces";
      }
      enum c9350-48hx {
        value 91;
        description
          "Catalyst 9350 Series Switch with 48 mGig UPOE+ Interfaces";
      }
      enum c9350-48tx {
        value 92;
        description
          "Catalyst 9350 Series Switch with 48 mGig Data Interfaces";
      }
      enum c9350-24u {
        value 93;
        description
          "Catalyst 9350 Series Switch with 24 Gigabit Ethernet UPOE Interfaces";
      }
      enum c9350-24p {
        value 94;
        description
          "Catalyst 9350 Series Switch with 24 Gigabit Ethernet POE+ Interfaces";
      }
      enum c9350-24t {
        value 95;
        description
          "Catalyst 9350 Series Switch with 24 Gigabit Ethernet Data Interfaces";
      }
      enum c9350-24hx {
        value 96;
        description
          "Catalyst 9350 Series Switch with 24 mGig UPOE+ Interfaces";
      }
      enum c9300lm-24u-4y {
        value 97;
        description
          "Catalyst 9300 Series Switch with 24 of 1 Gigabit UPOE downlink 4 of 25 Gigabit fixed uplink";
      }
      enum c9300lm-48t-4y {
        value 98;
        description
          "Catalyst 9300 Series Switch with 48 of 1 Gigabit downlink 4 of 25 Gigabit fixed uplink";
      }
      enum c9300lm-48u-4y {
        value 99;
        description
          "Catalyst 9300 Series Switch with 48 of 1 Gigabit UPOE downlink 4 of 25 Gigabit fixed uplink";
      }
      enum c9300lm-48ux-4y {
        value 100;
        description
          "Catalyst 9300 Series Switch with 40 of 1 Gigabit 8 of mGig UPOE downlink 4 of 25 Gigabit fixed uplink";
      }
    }
    description
      "Possible devices enabled with Meraki monitoring";
  }

  typedef meraki-progress-stage-id {
    type enumeration {
      enum meraki-no-conn {
        value 0;
        description
          "Switch is completely provisioned but unable to connect to meraki cloud";
      }
      enum meraki-proc-failure {
        value 1;
        description
          "System error: switch failed to complete local provisioning";
      }
      enum meraki-fan-ps-nm-fail {
        value 2;
        description
          "There is a fault with the power supply, fan, or network module (not traffic-related)";
      }
      enum meraki-upg {
        value 3;
        description
          "Firmware download / upgrade in progress";
      }
      enum meraki-conn-inprogress {
        value 4;
        description
          "Setting up local management and cloud-connectivity requirements";
      }
      enum meraki-conn-up {
        value 5;
        description
          "Switch is fully operational and connected to the meraki cloud";
      }
    }
    description
      "Possible stages which helps to identify ongoing meraki state/progress";
  }

  typedef meraki-reset-level-e {
    type enumeration {
      enum meraki-reset-level-none {
        value 0;
        description
          "Reset button is not triggered/pressed";
      }
      enum meraki-reset-level-1 {
        value 1;
        description
          "Reset level 1 triggered";
      }
      enum meraki-reset-level-2 {
        value 2;
        description
          "Reset level 2 triggered";
      }
      enum meraki-reset-level-3 {
        value 3;
        description
          "Reset level 3 triggered";
      }
    }
    description
      "Possible reset levels for software and hardware components to take corrective actions to recover the system";
  }

  typedef conf-monitor-proccess-state {
    type enumeration {
      enum cm-off {
        value 0;
        description
          "Config monitor is not running";
      }
      enum cm-start-fail {
        value 1;
        description
          "Config monitor failed to start";
      }
      enum cm-ipc-con {
        value 2;
        description
          "Config monitor is waiting connecting to socket";
      }
      enum cm-nc-con {
        value 3;
        description
          "Config monitor is waiting to connect to NETCONF";
      }
      enum cm-up {
        value 4;
        description
          "Config monitor is ready and subscribed";
      }
    }
    description
      "Config Monitor python process state";
  }

  typedef conf-updater-proccess-state {
    type enumeration {
      enum cu-off {
        value 0;
        description
          "Config updater is not running";
      }
      enum cu-start-fail {
        value 1;
        description
          "Config updater failed to start";
      }
      enum cu-ipc-con {
        value 2;
        description
          "Config updater is waiting connecting to socket";
      }
      enum cu-nc-con {
        value 3;
        description
          "Config updater is waiting to connect to NETCONF";
      }
      enum cu-up {
        value 4;
        description
          "Config updater is ready and waiting for Api call";
      }
      enum cu-get-op {
        value 5;
        description
          "Config updater is executing get config from NETCONF";
      }
      enum cu-set-op {
        value 6;
        description
          "Config updater is executing set config from NETCONF";
      }
      enum cu-save-op {
        value 7;
        description
          "Config updater is saving running config from NETCONF";
      }
      enum cu-rollback-op {
        value 8;
        description
          "Config updater is replacing running config with a rollback config";
      }
      enum cu-no-op {
        value 9;
        description
          "Config updater received unknown Api call";
      }
    }
    description
      "Config Monitor python process state";
  }

  typedef conf-updater-flow-entry {
    type enumeration {
      enum updater-no-event-entered {
        value 0;
        description
          "Config updater state machine is not entered";
      }
      enum cloud-cnfg-rdy {
        value 1;
        description
          "Config updater is applying config from dashboard";
      }
      enum sync-run-cnfg {
        value 2;
        description
          "Config updater upload running config to dashboard";
      }
      enum upld-run-cnfg {
        value 3;
        description
          "Config updater upload running config to dashboard";
      }
      enum save-upld-run-cnfg {
        value 4;
        description
          "Config updater upload running config to dashboard after save";
      }
    }
    description
      "List of entry points for config updater state machine";
  }

  typedef conf-updater-event-result {
    type enumeration {
      enum event-not-start {
        value 0;
        description
          "Config updater event is not started";
      }
      enum event-in-prog {
        value 1;
        description
          "Config updater event is currently executing";
      }
      enum event-pass {
        value 2;
        description
          "Config updater event exited with success";
      }
      enum event-fail {
        value 3;
        description
          "Config updater event exited with failure";
      }
      enum event-not-needed {
        value 4;
        description
          "Config updater event exited due to not being needed by dashboard";
      }
      enum event-aborted {
        value 5;
        description
          "Config updater event exited with abort";
      }
      enum event-done {
        value 6;
        description
          "Config updater event completed successfully";
      }
    }
    description
      "Config updater state machine event is in this current states";
  }

  typedef xpath-operation {
    type enumeration {
      enum xpath-create {
        value 0;
        description
          "A config was created using this XPath";
      }
      enum xpath-delete {
        value 1;
        description
          "A config was deleted using this XPath";
      }
      enum xpath-merge {
        value 2;
        description
          "A config was merged using this XPath";
      }
      enum xpath-replace {
        value 3;
        description
          "A config was replaced using this XPath";
      }
      enum xpath-remove {
        value 4;
        description
          "A config was removed using this XPath";
      }
    }
    description
      "All possible actions NETCONF notifications can return";
  }

  typedef device-mig-state {
    type enumeration {
      enum mig-state-nip {
        value 0;
        description
          "Migration is not in progress";
      }
      enum mig-state-detected {
        value 1;
        description
          "Device migration has been detected";
      }
      enum mig-state-prechk-ip {
        value 2;
        description
          "Migration pre-check in progress";
      }
      enum mig-state-config {
        value 3;
        description
          "Migration config in progress";
      }
      enum mig-state-reboot {
        value 4;
        description
          "Migration completed, reboot";
      }
      enum mig-state-failed {
        value 5;
        description
          "Migration has failed";
      }
      enum mig-state-pck-failed {
        value 6;
        description
          "Migration pre-check failed";
      }
      enum mig-state-consent-failed {
        value 7;
        description
          "Migration failed: Request secure shell-access";
      }
      enum mig-state-no-reg-failed {
        value 8;
        description
          "Migration failed: Switches not registered. Run \"show meraki\"";
      }
      enum mig-state-comp-failed {
        value 9;
        description
          "Migration failed compatibility check. Run \"show meraki compatibility\"";
      }
      enum mig-state-pkg-failed {
        value 10;
        description
          "Migration failed installed package verification";
      }
      enum mig-state-health-failed {
        value 11;
        description
          "Migration health check failed";
      }
      enum mig-state-conf-failed {
        value 12;
        description
          "Migration failed setting conversion/reversion config";
      }
    }
    description
      "Device migration state";
  }

  typedef mig-compat-err-type {
    type bits {
      bit comp-install-mode-err {
        position 0;
        description
          "Install mode incompatible";
      }
      bit comp-data-unavailable-err {
        position 1;
        description
          "Data not available for compatibility check";
      }
      bit comp-krport-ver--err {
        position 2;
        description
          "KR port version incompatible";
      }
      bit comp-mem-alloc-err {
        position 3;
        description
          "No memory for compatibility check";
      }
      bit comp-romm-ver-err {
        position 4;
        description
          "Rommon version incompatible";
      }
      bit comp-switch-incomp-err {
        position 5;
        description
          "Switch Incompatible error";
      }
      bit comp-fru-incomp-err {
        position 6;
        description
          "FRU Incompatible error";
      }
    }
    description
      "Migration compatibility errors";
  }

  grouping meraki-tunnel-config {
    description
      "Nextunnel configuration";
    leaf config-server {
      type string;
      description
        "Configuration server URL";
    }
    leaf primary {
      type string;
      description
        "Primary Nextunnel";
    }
    leaf secondary {
      type string;
      description
        "Secondary Nextunnel";
    }
    leaf client-ipv6-addr {
      type inet:ipv6-address;
      description
        "Client IPV6 address";
    }
    leaf server-ipv6-addr {
      type inet:ipv6-address;
      description
        "Server IPV6 address";
    }
    leaf backend-name {
      type string;
      description
        "Back end proxy URL";
    }
    leaf network-name {
      type string;
      description
        "The network name of the device";
    }
  }

  grouping meraki-tunnel-config-state {
    description
      "State of Nextunnel configuration";
    leaf last-fetch {
      type yang:date-and-time;
      description
        "Timestamp of the last Nextunnel configuration fetch";
    }
    leaf next-fetch {
      type yang:date-and-time;
      description
        "Timestamp of the next Nextunnel configuration fetch";
    }
    leaf fetch-state {
      type meraki-connect-ios-xe-oper:meraki-fetch-state;
      description
        "Nextunnel configuration fetches state";
    }
    leaf fetch-fail-detail {
      type string;
      description
        "Detail of Nextunnel configuration fetch fails reason";
    }
  }

  grouping meraki-connect {
    description
      "Details of the meraki connect";
    container config {
      description
        "Details of the tunnel configuration";
      uses meraki-connect-ios-xe-oper:meraki-tunnel-config;
    }
    container config-state {
      description
        "Details of the tunnel configuration state";
      uses meraki-connect-ios-xe-oper:meraki-tunnel-config-state;
    }
    leaf status {
      type boolean;
      description
        "The status of Meraki connect";
    }
  }

  grouping meraki-tunnel-sess {
    description
      "Detail of the active Nextunnel session";
    leaf src-ip {
      type inet:ip-address;
      description
        "Source IP address";
    }
    leaf src-port {
      type uint16;
      description
        "Source port";
    }
    leaf dst-ip {
      type inet:ip-address;
      description
        "Destination IP address";
    }
    leaf dst-port {
      type uint16;
      description
        "Destination port";
    }
  }

  grouping meraki-tunnel-state {
    description
      "The status of the Nextunnel connects to Meraki Dashboard";
    leaf primary {
      type meraki-connect-ios-xe-oper:meraki-nextunnel-state;
      description
        "Primary Nextunnel status";
    }
    leaf secondary {
      type meraki-connect-ios-xe-oper:meraki-nextunnel-state;
      description
        "Secondary Nextunnel status";
    }
    leaf primary-last-change {
      type yang:date-and-time;
      description
        "Timestamp of the last primary Nextunnel change";
    }
    leaf secondary-last-change {
      type yang:date-and-time;
      description
        "Timestamp of the last secondary Nextunnel change";
    }
    leaf client-last-restart {
      type yang:date-and-time;
      description
        "Timestamp of the last client restart";
    }
    list sess {
      description
        "List of active Nextunnel sessions";
      uses meraki-connect-ios-xe-oper:meraki-tunnel-sess;
    }
  }

  grouping meraki-tunnel-interface {
    description
      "The status of the Nextunnel interface";
    leaf status {
      type boolean;
      description
        "The Nextunnel interface status";
    }
    leaf rx-packets {
      type uint64;
      description
        "Number of packets received by the Nextunnel";
    }
    leaf tx-packets {
      type uint64;
      description
        "Number of packets transmitted by the Nextunnel";
    }
    leaf rx-errors {
      type uint64;
      description
        "Number of error packets received by the Nextunnel";
    }
    leaf tx-errors {
      type uint64;
      description
        "Number of error packets transmitted by the Nextunnel";
    }
    leaf rx-drop-packets {
      type uint64;
      description
        "Number of receiving packets dropped by the Nextunnel";
    }
    leaf tx-drop-packets {
      type uint64;
      description
        "Number of transmitting packets dropped by the Nextunnel";
    }
  }

  grouping device-reg-information {
    description
      "Details of the device registration information";
    leaf device-number {
      type uint8;
      description
        "Device number";
    }
    leaf pid {
      type meraki-connect-ios-xe-oper:meraki-device-pid;
      description
        "Product ID";
    }
    leaf serial-number {
      type string;
      description
        "Device serial number";
    }
    leaf mac-address {
      type yang:mac-address;
      description
        "Device MAC address ";
    }
    leaf meraki-id {
      type string;
      status obsolete;
      description
        "Meraki ID received from Meraki dashboard";
    }
    leaf status {
      type meraki-connect-ios-xe-oper:meraki-reg-state;
      description
        "The status of the device registration";
    }
    leaf err-detail {
      type string;
      description
        "Error message of the device registration";
    }
    leaf timestamp {
      type yang:date-and-time;
      description
        "Timestamp of updating device registration";
    }
    leaf cloud-id {
      type string;
      description
        "Cloud ID received from Meraki dashboard";
    }
    leaf cert-expiry {
      type yang:date-and-time;
      description
        "Expiration time of certificate";
    }
  }

  grouping meraki-registration {
    description
      "Details of the device registration information";
    leaf url {
      type string;
      description
        "Meraki Dashboard URL";
    }
    list device-reg {
      key "device-number";
      description
        "A list of device registration information";
      uses meraki-connect-ios-xe-oper:device-reg-information;
    }
  }

  grouping xpath-entry {
    description
      "Config monitor config change notification";
    leaf child-id {
      type uint32;
      description
        "XPath was assigned this unique ID";
    }
    leaf xpath {
      type string;
      description
        "Config was modified using this XPath";
    }
    leaf oper {
      type meraki-connect-ios-xe-oper:xpath-operation;
      description
        "Edit config action was performed.
         Reference:
         RFC 6241, edit config";
    }
  }

  grouping config-monitor-notif {
    description
      "Config monitor config change notification";
    leaf id {
      type uint32;
      description
        "Config change is assigned a unique ID";
    }
    leaf timestamp {
      type yang:date-and-time;
      description
        "Config change was caught at this timestamp";
    }
    leaf xpath-total {
      type uint32;
      description
        "Actual number of config modifications contained in the config notification";
    }
    list xpath-entry {
      key "child-id";
      description
        "List of XPath and operations for this notification.
         This list includes a subset of config modifications when xpath-total is
         greater than the size of this list";
      uses meraki-connect-ios-xe-oper:xpath-entry;
    }
  }

  grouping conf-monitor-status {
    description
      "Config monitor process state";
    leaf monitor-state {
      type meraki-connect-ios-xe-oper:conf-monitor-proccess-state;
      description
        "Config monitor is currently in this state";
    }
  }

  grouping conf-updater-status {
    description
      "Config updater process state";
    leaf process-state {
      type meraki-connect-ios-xe-oper:conf-updater-proccess-state;
      description
        "Config updater is currently in this state";
    }
  }

  grouping conf-updater-sm-op {
    description
      "Config updater state machine operation table";
    leaf operation {
      type meraki-connect-ios-xe-oper:conf-updater-flow-entry;
      description
        "Config updater is executing this operational flow";
    }
    leaf dwnld-config-path {
      type string;
      description
        "Config updater will download config from dashboard to this path";
    }
    leaf get-run-cfg-path {
      type string;
      description
        "Config updater will dump running config into this path";
    }
    leaf cloud-cfg-ready-started-ts {
      type yang:date-and-time;
      description
        "Cloud config ready event started at this timestamp";
    }
    leaf cloud-cfg-ready-result {
      type meraki-connect-ios-xe-oper:conf-updater-event-result;
      description
        "Cloud config ready event finished with this result, or has not started";
    }
    leaf cloud-cfg-ready-result-ts {
      type yang:date-and-time;
      description
        "Cloud config ready event finished at this timestamp";
    }
    leaf dwnld-run-cfg-started-ts {
      type yang:date-and-time;
      description
        "Download running config event started at this timestamp";
    }
    leaf dwnld-run-cfg-result {
      type meraki-connect-ios-xe-oper:conf-updater-event-result;
      description
        "Download running config event is in this current state";
    }
    leaf dwnld-run-cfg-result-ts {
      type yang:date-and-time;
      description
        "Download running config finished at this timestamp";
    }
    leaf apply-cfg-started-ts {
      type yang:date-and-time;
      description
        "Apply dashboard config event started at this timestamp";
    }
    leaf apply-cfg-result {
      type meraki-connect-ios-xe-oper:conf-updater-event-result;
      description
        "Apply dashboard config event is in this current state";
    }
    leaf apply-cfg-result-ts {
      type yang:date-and-time;
      description
        "Apply dashboard config finished at this timestamp";
    }
    leaf get-run-cfg-started-ts {
      type yang:date-and-time;
      description
        "Get running config event started at this timestamp";
    }
    leaf get-run-cfg-result {
      type meraki-connect-ios-xe-oper:conf-updater-event-result;
      description
        "Get running config event is in this current state";
    }
    leaf get-run-cfg-result-ts {
      type yang:date-and-time;
      description
        "Get running config finished at this timestamp";
    }
    leaf get-presign-url-start-ts {
      type yang:date-and-time;
      description
        "Get dashboard url event started at this timestamp";
    }
    leaf get-presign-url-result {
      type meraki-connect-ios-xe-oper:conf-updater-event-result;
      description
        "Get dashboard url event is in this current state";
    }
    leaf get-presign-url-result-ts {
      type yang:date-and-time;
      description
        "Get dashboard url finished at this timestamp";
    }
    leaf upload-config-started-ts {
      type yang:date-and-time;
      description
        "Upload config event started at this timestamp";
    }
    leaf upload-config-result {
      type meraki-connect-ios-xe-oper:conf-updater-event-result;
      description
        "Upload config event is in this current state";
    }
    leaf upload-config-result-ts {
      type yang:date-and-time;
      description
        "Upload config finished at this timestamp";
    }
    leaf dwnld-run-cfg-http-status {
      type uint16;
      description
        "Download running config http status code";
    }
    leaf get-presign-http-status {
      type uint16;
      description
        "Get dashboard url http status code";
    }
    leaf upload-cfg-http-status {
      type uint16;
      description
        "Upload config http status code";
    }
    leaf sc-start-ts {
      type yang:date-and-time;
      description
        "Save config event started at this timestamp";
    }
    leaf sc-end-ts {
      type yang:date-and-time;
      description
        "Save config finished at this timestamp";
    }
    leaf sc-result {
      type meraki-connect-ios-xe-oper:conf-updater-event-result;
      description
        "Final outcome of the save config operation";
    }
  }

  grouping meraki-progress-stage {
    description
      "Details of the meraki progress stages";
    leaf meraki-stage {
      type meraki-connect-ios-xe-oper:meraki-progress-stage-id;
      description
        "Meraki manager daemon stage";
    }
  }

  grouping meraki-reset-level {
    description
      "Details of the meraki reset levels";
    leaf switch-num {
      type uint8;
      description
        "Target switch for reset";
    }
    leaf reset-level {
      type meraki-connect-ios-xe-oper:meraki-reset-level-e;
      description
        "Current reset level";
    }
  }

  grouping meraki-migration-status {
    description
      "Meraki migration status details";
    leaf switch-num {
      type uint8;
      description
        "Switch number";
    }
    leaf curr-booted-mode {
      type meraki-connect-ios-xe-oper:migration-mode-types;
      description
        "Current booted mode";
    }
    leaf mig-mode {
      type meraki-connect-ios-xe-oper:migration-mode-types;
      description
        "Device migrating mode";
    }
    leaf mig-in-progress {
      type boolean;
      description
        "Migration in progress";
    }
    leaf mig-state {
      type meraki-connect-ios-xe-oper:device-mig-state;
      description
        "Device migration state";
    }
    leaf mig-start-time {
      type yang:date-and-time;
      description
        "Time device migration started";
    }
    leaf compat-err-detail {
      type meraki-connect-ios-xe-oper:mig-compat-err-type;
      description
        "Migration Compatibility error details";
    }
  }

  container meraki-connect-oper-data {
    config false;
    description
      "Operational data model for Meraki connect";
    container connect {
      presence "connect";
      description
        "Details of the Meraki connect";
      uses meraki-connect-ios-xe-oper:meraki-connect;
    }
    container tunnel-state {
      presence "tunnel-state";
      description
        "Details of the Nextunnel state";
      uses meraki-connect-ios-xe-oper:meraki-tunnel-state;
    }
    container tunnel-if {
      presence "tunnel-if";
      description
        "Details of the Nextunnel interface";
      uses meraki-connect-ios-xe-oper:meraki-tunnel-interface;
    }
    container reg {
      presence "reg";
      description
        "Details of the device registration with Meraki Dashboard";
      uses meraki-connect-ios-xe-oper:meraki-registration;
    }
    list config-monitor-notif {
      key "id";
      description
        "Details of config monitor notification changes";
      uses meraki-connect-ios-xe-oper:config-monitor-notif;
    }
    container meraki-progress-stage {
      presence "meraki-progress-stage";
      description
        "Details of the system progress stage";
      uses meraki-connect-ios-xe-oper:meraki-progress-stage;
    }
    container meraki-reset-level {
      presence "meraki-reset-level";
      description
        "Details of triggered reset level";
      uses meraki-connect-ios-xe-oper:meraki-reset-level;
    }
    container conf-monitor-status {
      presence "conf-monitor-status";
      description
        "Details of config monitor process status";
      uses meraki-connect-ios-xe-oper:conf-monitor-status;
    }
    container conf-updater-status {
      presence "conf-updater-status";
      description
        "Details of config updater notification changes";
      uses meraki-connect-ios-xe-oper:conf-updater-status;
    }
    container conf-updater-sm-op {
      presence "conf-updater-sm-op";
      description
        "Details of config updater state machine operations";
      uses meraki-connect-ios-xe-oper:conf-updater-sm-op;
    }
    list mig-status {
      key "switch-num";
      description
        "Details of device mode migration";
      uses meraki-connect-ios-xe-oper:meraki-migration-status;
    }
  }
}
