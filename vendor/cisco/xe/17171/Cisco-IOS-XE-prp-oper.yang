module Cisco-IOS-XE-prp-oper {
  yang-version 1.1;
  namespace "http://cisco.com/ns/yang/Cisco-IOS-XE-prp-oper";
  prefix prp-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for Parallel Redundancy Protocol (PRP) operational data.
     Copyright (c) 2021-2022 by Cisco Systems, Inc.
     All rights reserved.";

  revision 2022-11-01 {
    description
      "Update yang-version to 1.1";
    reference
      "1.1.0";
    cisco-semver:module-version "1.1.0";
  }
  revision 2022-07-01 {
    description
      "Initial revision";
    reference
      "1.0.0";
    cisco-semver:module-version "1.0.0";
  }

  typedef prp-port-state {
    type enumeration {
      enum port-inuse {
        value 0;
        description
          "Port is up";
      }
      enum port-not-inuse {
        value 1;
        description
          "Port is down";
      }
      enum port-not-inuse-admin-down {
        value 2;
        description
          "Port is down as it has been
           shut down administratively";
      }
      enum port-not-inuse-link-down {
        value 3;
        description
          "Port is down as the link is down";
      }
    }
    description
      "State of the port belonging to the PRP channel";
  }

  typedef prp-channel-state {
    type enumeration {
      enum channel-inuse {
        value 0;
        description
          "Channel is up";
      }
      enum channel-not-inuse {
        value 1;
        description
          "Channel is down";
      }
      enum channel-not-inuse-admin-down {
        value 2;
        description
          "Channel is down use as it has been
           shut down administratively";
      }
    }
    description
      "State of the PRP channel";
  }

  typedef prp-channel-layer-type {
    type enumeration {
      enum layer-2 {
        value 0;
        description
          "PRP channel is configured as Layer 2";
      }
      enum layer-3 {
        value 1;
        description
          "PRP channel is configured as Layer 3";
      }
    }
    description
      "Layer type of PRP channel interface";
  }

  typedef prp-channel-proto-status {
    type enumeration {
      enum disabled {
        value 0;
        description
          "Channel Protocol is down";
      }
      enum enabled {
        value 1;
        description
          "Channel Protocol is up";
      }
    }
    description
      "Protocol Status of the PRP channel";
  }

  typedef prp-ptp-profile {
    type enumeration {
      enum udp {
        value 0;
        description
          "PTP will use UDP as the transport protocol over IP";
      }
      enum l2-power {
        value 1;
        description
          "PTP power profile is set as Layer two";
      }
    }
    description
      "PTP power profile of the channel";
  }

  typedef prp-node-type {
    type enumeration {
      enum prp-node-none {
        value 0;
        description
          "Node attachment type is unknown";
      }
      enum prp-node-lan-a {
        value 1;
        description
          "Singly attached node on LAN-A";
      }
      enum prp-node-lan-b {
        value 2;
        description
          "Singly attached node on LAN-B";
      }
      enum prp-node-dan {
        value 3;
        description
          "Dual attached node";
      }
    }
    description
      "Attachment Type of the Node";
  }

  grouping prp-channel-identity {
    description
      "PRP channel identity, combination of id and name";
    leaf id {
      type uint8;
      description
        "PRP channel group number";
    }
    leaf name {
      type string;
      description
        "Name of the PRP channel";
    }
  }

  grouping prp-channel-port {
    description
      "Information of ports configured in the PRP Channel";
    leaf name {
      type string;
      description
        "Name of the port";
    }
    leaf slot {
      type uint8;
      description
        "Port Slot Number";
    }
    leaf subslot {
      type uint8;
      description
        "Port Subslot Number";
    }
    leaf state {
      type prp-ios-xe-oper:prp-port-state;
      description
        "State of the port belonging to the PRP channel";
    }
  }

  grouping prp-channel-info {
    description
      "Information about PRP Channel parameters";
    leaf layer {
      type prp-ios-xe-oper:prp-channel-layer-type;
      description
        "Layer type of PRP channel interface [L2/L3]";
    }
    leaf group {
      type uint8;
      description
        "PRP channel group number";
    }
    leaf state {
      type prp-ios-xe-oper:prp-channel-state;
      description
        "Current State of the PRP channel";
    }
    leaf proto-status {
      type prp-ios-xe-oper:prp-channel-proto-status;
      description
        "Information on channel protocol status";
    }
    leaf max-ports {
      type uint8;
      description
        "Maximum Number of ports that can be part of the channel";
    }
    list port-info {
      description
        "Information of all the ports of the channel";
      uses prp-ios-xe-oper:prp-channel-port;
    }
  }

  grouping prp-vdan-entry {
    description
      "PRP Virtual Doubly Attached Node entry";
    leaf index {
      type uint32;
      description
        "Unique ID of Virtual Doubly Attached Node (VDAN) entry";
    }
    leaf mac-addr {
      type yang:mac-address;
      description
        "MAC address of the node";
    }
    leaf dynamic {
      type boolean;
      description
        "PRP node was learned or configured";
    }
    leaf ttl {
      type uint8;
      units "seconds";
      description
        "Time after which node entry will be
         deleted in case of node being unresponsive";
    }
  }

  grouping prp-vdan-table {
    description
      "PRP Virtual Doubly Attached Node Table";
    list prp-vdan-entry {
      key "index";
      description
        "Entry of Virtual Doubly Attached Node";
      uses prp-ios-xe-oper:prp-vdan-entry;
    }
  }

  grouping prp-control-ptp {
    description
      "PTP Profile Info";
    leaf lan-val {
      type uint32;
      description
        "PTP LAN option value, informs if
         PTP is enabled on LAN-A or LAN-B";
    }
    leaf profile {
      type prp-ios-xe-oper:prp-ptp-profile;
      description
        "PTP clock power profile";
    }
  }

  grouping prp-control-super-frame {
    description
      "PRP Supervision Frame Info";
    leaf cos {
      type uint8;
      description
        "Class of Service (COS) value to be set
         in the VLAN tag of the Supervision frame";
    }
    leaf cfi {
      type uint32;
      description
        "Canonical Format Indicator (CFI)
         for the VLAN tagged frame";
    }
    leaf tag {
      type uint16;
      description
        "VLAN Tagging Option Value";
    }
    leaf mac-da {
      type uint8;
      description
        "The last byte of the destination
         MAC address of supervision frames";
    }
    leaf vlan-id {
      type uint16;
      description
        "VLAN identity value of the supervision frame";
    }
    leaf interval {
      type uint16;
      units "milliseconds";
      description
        "life check interval time value for supervision frames";
    }
    leaf red-box-mac-add {
      type yang:mac-address;
      description
        "Red-Box MAC address in the supervision frames";
    }
    leaf time {
      type uint16;
      units "milliseconds";
      description
        "Time interval between two supervision frames being sent";
    }
  }

  grouping prp-control {
    description
      "Information about PRP control parameters";
    container ptp-info {
      description
        "Information about PTP over PRP parameters";
      uses prp-ios-xe-oper:prp-control-ptp;
    }
    container supervision-frame {
      description
        "Information about PRP supervision frame parameters";
      uses prp-ios-xe-oper:prp-control-super-frame;
    }
  }

  grouping prp-node-entry {
    description
      "Entry of a Node attached with the channel";
    leaf index {
      type uint32;
      description
        "Unique ID of the node entry";
    }
    leaf mac-addr {
      type yang:mac-address;
      description
        "MAC address of the node";
    }
    leaf node-type {
      type prp-ios-xe-oper:prp-node-type;
      description
        "Attachment type of the node";
    }
    leaf dynamic {
      type boolean;
      description
        "PRP node was learned or configured";
    }
    leaf ttl {
      type uint8;
      units "seconds";
      description
        "Time after which node entry will be
         deleted in case of node being unresponsive";
    }
  }

  grouping prp-node-table {
    description
      "List of all the nodes attached to the channel";
    list prp-node-entry {
      key "index";
      description
        "Entry of a Node attached with the channel";
      uses prp-ios-xe-oper:prp-node-entry;
    }
  }

  grouping prp-node-table-stats {
    description
      "PRP Node Table Statistics";
    leaf proxynode-table-err {
      type uint32;
      description
        "Total number of proxy Node table errors";
    }
    leaf proxynode-table-num {
      type uint32;
      description
        "Total number of  proxy Node table active entries";
    }
    leaf node-table-err {
      type uint32;
      description
        "Total number of node table errors";
    }
    leaf node-table-num {
      type uint32;
      description
        "Total number of node table active entries";
    }
  }

  grouping prp-ingress-stats {
    description
      "Receive Statistics of the PRP channel";
    leaf pkt-lan-a {
      type uint64;
      description
        "Received packet count on LAN-A";
    }
    leaf pkt-lan-b {
      type uint64;
      description
        "Received packet count on LAN-B";
    }
    leaf crc-lan-a {
      type uint64;
      description
        "Received CRC count on LAN-A";
    }
    leaf crc-lan-b {
      type uint64;
      description
        "Received CRC count on LAN-B";
    }
    leaf danp-pkt-acpt {
      type uint64;
      description
        "Received packet count accepted from DAN";
    }
    leaf danp-pkt-dscrd {
      type uint64;
      description
        "Received packet count discarded from DAN";
    }
    leaf supfrm-rcv-a {
      type uint64;
      description
        "Received supervision frame count on lAN-A";
    }
    leaf supfrm-rcv-b {
      type uint64;
      description
        "Received supervision frame count on LAN-B";
    }
    leaf over-pkt-a {
      type uint64;
      description
        "Received over packet count on LAN-A";
    }
    leaf over-pkt-b {
      type uint64;
      description
        "Received over packet count on LAN-B";
    }
    leaf pri-over-pkt-a {
      type uint64;
      description
        "Received primary over packet count on LAN-A";
    }
    leaf pri-over-pkt-b {
      type uint64;
      description
        "Received primary over packet count on LAN-B";
    }
    leaf oversize-pkt-a {
      type uint64;
      description
        "Received over-sized packet count on LAN-A";
    }
    leaf oversize-pkt-b {
      type uint64;
      description
        "Received over-sized packet count on LAN-B";
    }
    leaf byte-lan-a {
      type uint64;
      description
        "Total ingress byte count on LAN A";
    }
    leaf byte-lan-b {
      type uint64;
      description
        "Total ingress byte count on LAN-B";
    }
    leaf wrong-lan-id-a {
      type uint64;
      description
        "Packet count with wrong vlan id on LAN-A";
    }
    leaf wrong-lan-id-b {
      type uint64;
      description
        "Packet count with wrong vlan id on LAN-B";
    }
    leaf warning-lan-a {
      type uint64;
      description
        "Total hardware attribute warnings on LAN-A";
    }
    leaf warning-lan-b {
      type uint64;
      description
        "Total hardware attribute warnings on LAN-B";
    }
    leaf warning-count-a {
      type uint64;
      description
        "Warning counts received on LAN-A";
    }
    leaf warning-count-b {
      type uint64;
      description
        "Warning counts received on LAN-B";
    }
    leaf unique-count-a {
      type uint64;
      description
        "Received unique packet count on LAN-A";
    }
    leaf unique-count-b {
      type uint64;
      description
        "Received unique packet count on LAN-B";
    }
    leaf duplicate-count-a {
      type uint64;
      description
        "Received duplicate packet count on LAN-A";
    }
    leaf duplicate-count-b {
      type uint64;
      description
        "Received duplicate packet count on LAN-B";
    }
    leaf multiple-count-a {
      type uint64;
      description
        "Received multiple packet count on LAN-A";
    }
    leaf multiple-count-b {
      type uint64;
      description
        "Received multiple packet count on LAN-B";
    }
  }

  grouping prp-egress-stats {
    description
      "PRP Transmit Statistics";
    leaf dup-pkt {
      type uint64;
      description
        "Total number of duplicate packets sent by the channel";
    }
    leaf supfrm-sent {
      type uint64;
      description
        "Total number of supervision frames sent by the channel";
    }
    leaf pkt-lan-a {
      type uint64;
      description
        "Total number of egress frames on LAN-A";
    }
    leaf pkt-lan-b {
      type uint64;
      description
        "Total number of egress frames on LAN-B";
    }
    leaf byte-lan-a {
      type uint64;
      description
        "Transmit byte count on LAN-A";
    }
    leaf byte-lan-b {
      type uint64;
      description
        "Transmit byte count on LAN-B";
    }
    leaf recv-switch {
      type uint64;
      description
        "Transmit receive switch";
    }
    leaf overrun {
      type uint64;
      description
        "Transmit Overrun packets";
    }
    leaf overrun-drop {
      type uint64;
      description
        "Transmit overrun dropped packets";
    }
  }

  grouping prp-pausefrm-stats {
    description
      "PRP Pause Frame Statistics";
    leaf pausefrm-sent {
      type uint32;
      description
        "Total number of pause frames sent from the channel";
    }
  }

  grouping prp-ptp-pkt-stats {
    description
      "PRP PTP Statistics";
    leaf ingress-lan-a {
      type uint32;
      description
        "PTP packet ingress count on LAN-A";
    }
    leaf ingress-drop-lan-a {
      type uint32;
      description
        "PTP packet drop count on LAN-A";
    }
    leaf ingress-lan-b {
      type uint32;
      description
        "PTP packet ingress count on LAN-B";
    }
    leaf ingress-drop-lan-b {
      type uint32;
      description
        "PTP packet drop count on LAN-B";
    }
    leaf egress-lan-a {
      type uint32;
      description
        "PTP packet egress count on LAN-A";
    }
    leaf egress-lan-b {
      type uint32;
      description
        "PTP packet egress count on LAN-B";
    }
  }

  grouping prp-stats {
    description
      "PRP all statistics";
    container ingress {
      description
        "Receive statistics of PRP channel";
      uses prp-ios-xe-oper:prp-ingress-stats;
    }
    container egress {
      description
        "Transmit statistics of PRP channel";
      uses prp-ios-xe-oper:prp-egress-stats;
    }
    container pause-frm {
      description
        "Pause Frame statistics of PRP channel";
      uses prp-ios-xe-oper:prp-pausefrm-stats;
    }
    container node-table {
      description
        "Node Table statistics of PRP channel";
      uses prp-ios-xe-oper:prp-node-table-stats;
    }
    container ptp {
      description
        "PTP statistics of PRP channel";
      uses prp-ios-xe-oper:prp-ptp-pkt-stats;
    }
  }

  container prp-oper-data {
    config false;
    description
      "PRP operational data";
    list prp-channel-info {
      key "id name";
      description
        "Information regarding the PRP channel";
      uses prp-ios-xe-oper:prp-channel-identity;
      uses prp-ios-xe-oper:prp-channel-info;
    }
    list prp-vdan-table {
      key "id name";
      description
        "List of PRP Virtual Doubly Attached Nodes (VDAN)";
      uses prp-ios-xe-oper:prp-channel-identity;
      uses prp-ios-xe-oper:prp-vdan-table;
    }
    list prp-control {
      key "id name";
      description
        "Information regarding control parameters of the channel";
      uses prp-ios-xe-oper:prp-channel-identity;
      uses prp-ios-xe-oper:prp-control;
    }
    list prp-node-table {
      key "id name";
      description
        "List of attached PRP nodes";
      uses prp-ios-xe-oper:prp-channel-identity;
      uses prp-ios-xe-oper:prp-node-table;
    }
    list prp-stats {
      key "id name";
      description
        "PRP channel statistics information";
      uses prp-ios-xe-oper:prp-channel-identity;
      uses prp-ios-xe-oper:prp-stats;
    }
  }
}
