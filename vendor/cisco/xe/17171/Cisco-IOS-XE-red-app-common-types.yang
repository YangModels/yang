module Cisco-IOS-XE-red-app-common-types {
  yang-version 1.1;
  namespace "http://cisco.com/ns/yang/Cisco-IOS-XE-red-app-common-types";
  prefix red-app-comm-ios-xe-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG
     definitions for redundancy application notification data.
     Copyright (c) 2024 by Cisco Systems, Inc.
     All rights reserved.";

  revision 2024-07-01 {
    description
      "Initial revision";
    reference
      "1.0.0";
    cisco-semver:module-version "1.0.0";
  }

  typedef rg-app-role {
    type enumeration {
      enum rg-role-unknown {
        value 0;
        description
          "Redundancy application group role unknown";
      }
      enum rg-role-init {
        value 1;
        description
          "Redundancy application group role init";
      }
      enum rg-role-standby {
        value 2;
        description
          "Redundancy application group role standby";
      }
      enum rg-role-active {
        value 3;
        description
          "Redundancy application group role active";
      }
    }
    description
      "Redundancy application group role";
  }
}
