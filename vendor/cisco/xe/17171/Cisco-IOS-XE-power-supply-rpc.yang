module Cisco-IOS-XE-power-supply-rpc {
  yang-version 1.1;
  namespace "http://cisco.com/ns/yang/Cisco-IOS-XE-power-supply-rpc";
  prefix power-supply-rpc-ios-xe;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for power-supply slot-A/B/C On/Off actions.
     Copyright (c) 2024 by Cisco Systems, Inc.
     All rights reserved.";

  revision 2024-11-01 {
    description
      "Initial revision";
    reference
      "1.0.0";
    cisco-semver:module-version "1.0.0";
  }

  typedef pwr-supply-state {
    type enumeration {
      enum power-off {
        value 0;
        description
          "Set the power supply off";
      }
      enum power-on {
        value 1;
        description
          "Set the power supply on";
      }
    }
    description
      "Power supply slot state";
  }

  typedef pwr-supply-slot {
    type enumeration {
      enum slot-a {
        value 0;
        description
          "Power supply Slot A";
      }
      enum slot-b {
        value 1;
        description
          "Power supply Slot B";
      }
      enum slot-c {
        value 2;
        description
          "Power supply Slot C";
      }
    }
    description
      "Power supply slot";
  }

  grouping pwr-supply-change {
    description
      "Set the power supply slot state";
    leaf switch-number {
      type uint8 {
        range "1..16";
      }
      mandatory true;
      description
        "Switch number";
    }
    leaf slot {
      type power-supply-rpc-ios-xe:pwr-supply-slot;
      mandatory true;
      description
        "Power supply slot name";
    }
    leaf state {
      type power-supply-rpc-ios-xe:pwr-supply-state;
      mandatory true;
      description
        "Power supply slot state";
    }
  }

  grouping pwr-supply {
    description
      "power supply";
    container supply {
      description
        "Set the power supply slot & state";
      uses power-supply-rpc-ios-xe:pwr-supply-change;
    }
  }

  rpc set-pwr-supply-slot-state {
    description
      "Set the stack slot status for a switch.";
    input {
      uses power-supply-rpc-ios-xe:pwr-supply;
    }
  }
}
