module Cisco-IOS-XE-livetools-oper {
  yang-version 1.1;
  namespace "http://cisco.com/ns/yang/Cisco-IOS-XE-livetools-oper";
  prefix livetools-ios-xe-oper;

  import Cisco-IOS-XE-common-types {
    prefix common-types-ios-xe;
  }
  import Cisco-IOS-XE-livetools-common-types {
    prefix livetools-common-types-ios-xe;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for live tools operational data.
     Copyright (c) 2024 by Cisco Systems, Inc.
     All rights reserved.";

  revision 2025-03-01 {
    description
      "- Added DNS lookup support
       - Added enums un-sent, timeout for echo status
       - Added enums ping-failed for ip ping error
       - Obsolete 'latency' leaf
       - Added 'latency-msec' leaf in milliseconds.
       - Adding MTR error codes for memory and address case";
    reference
      "2.0.0";
    cisco-semver:module-version "2.0.0";
  }
  revision 2024-07-01 {
    description
      "Initial revision";
    reference
      "1.0.0";
    cisco-semver:module-version "1.0.0";
  }

  typedef wol-errors {
    type enumeration {
      enum err-none {
        value 0;
        description
          "No failure is reported";
      }
      enum err-in-buff-alloc {
        value 1;
        description
          "Packet buffer allocation failed internally";
      }
      enum err-in-process-send {
        value 2;
        description
          "Process send routine failed internally";
      }
      enum err-in-pak-encap {
        value 3;
        description
          "Packet encapsulation failed internally";
      }
    }
    description
      "WAKE-ON-LAN Errors";
  }

  typedef thrpt-mode-result {
    type enumeration {
      enum thrpt-mode-avg {
        value 0;
        description
          "Measure throughput in average mode";
      }
      enum thrpt-mode-full {
        value 1;
        description
          "Measure throughput in full mode";
      }
      enum thrpt-mode-peak {
        value 2;
        description
          "Measure throughput in peak mode";
      }
    }
    description
      "Throughput mode options";
  }

  typedef thrpt-proto-result {
    type enumeration {
      enum thrpt-tcp-client {
        value 0;
        description
          "Operate as a TCP client";
      }
    }
    description
      "Protocol-Role combination;
       protocol: TCP/UDP, role: client/server";
  }

  typedef thrpt-err-msg {
    type enumeration {
      enum thrpt-err-no-error {
        value 0;
        description
          "No error";
      }
      enum thrpt-err-proc-send-msg-fail {
        value 1;
        description
          "Process send message failed";
      }
      enum thrpt-err-no-mem {
        value 2;
        description
          "No memory";
      }
      enum thrpt-err-read-fail {
        value 3;
        description
          "Socket data read failed";
      }
      enum thrpt-err-write-fail {
        value 4;
        description
          "Socket data write failed";
      }
      enum thrpt-err-data-overflow {
        value 5;
        description
          "Data overflow";
      }
      enum thrpt-err-sock-open-fail {
        value 6;
        description
          "Socket open failed";
      }
      enum thrpt-err-vrf-no-match {
        value 7;
        description
          "VRF does not exist";
      }
      enum thrpt-err-vrf-sock-opt-fail {
        value 8;
        description
          "Invalid VRF socket option";
      }
      enum thrpt-err-tos-sock-opt-fail {
        value 9;
        description
          "Invalid DSCP option";
      }
      enum thrpt-err-sock-conn-fail {
        value 10;
        description
          "Socket connection failed";
      }
    }
    description
      "Throughput error";
  }

  typedef ip-tracert-err {
    type enumeration {
      enum ip-tracert-no-err {
        value 0;
        description
          "IP trace route request successfully processed";
      }
      enum ip-tracert-host-nm-not-rsvld {
        value 1;
        description
          "Specified host name in IP trace route request could not be resolved";
      }
      enum ip-tracert-src-if-inv {
        value 2;
        description
          "Specified source interface in IP trace route request is not valid";
      }
      enum ip-tracert-src-if-dwn {
        value 3;
        description
          "Specified source interface in IP trace route request is down";
      }
      enum ip-tracert-inv-addr {
        value 4;
        description
          "Specified source IP address in IP trace route request is invalid";
      }
      enum ip-tracert-ip-disbl {
        value 5;
        description
          "Device handling the IP trace route request does not have
           IP enabled at source";
      }
      enum ip-tracert-vrf-not-ex {
        value 6;
        description
          "Device handling the IP trace route request does not have
           specified vrf configured";
      }
      enum ip-tracert-vrf-not-acc {
        value 7;
        description
          "Device handling the IP trace route request does not have
           access to the specified VRF instance";
      }
      enum ip-tracert-topo-not-ex {
        value 8;
        description
          "Device handling the IP trace route request does not have
           specified topology configured";
      }
      enum ip-tracert-minttl-grt-maxttl {
        value 9;
        description
          "Specified minimum TTL value in IP trace route request
           is greater than maximum TTL value";
      }
    }
    description
      "IP trace route processing error";
  }

  typedef ip-tracert-probe-rslt {
    type enumeration {
      enum ip-tracert-no-rch-port {
        value 0;
        description
          "Able to reach the destination host but was unable to establish
                  communication with the specified port";
      }
      enum ip-tracert-no-rch-adm {
        value 1;
        description
          "Packet was dropped as router and can not be forwarded due to
                  administrative filtering";
      }
      enum ip-tracert-no-rch-net {
        value 2;
        description
          "Packet was dropped due to unavailability of route to a specified network";
      }
      enum ip-tracert-no-rch-host {
        value 3;
        description
          "Host in a directly connected network is not reachable";
      }
      enum ip-tracert-no-rch-proto {
        value 4;
        description
          "Final destination does not support the transport protocol specified
                  in the packet";
      }
      enum ip-tracert-timeout {
        value 5;
        description
          "No response from an intermediate router or the destination host within a
                  specified period";
      }
      enum ip-tracert-ttl-exp {
        value 6;
        description
          "Packet has reached its maximum hop count and can not proceed further";
      }
      enum ip-tracert-src-qench {
        value 7;
        description
          "Packet can't be forwarded further due to network congestion";
      }
      enum ip-tracert-no-rch-rt {
        value 8;
        description
          "There is no route to the destination";
      }
      enum ip-tracert-no-rch-src-addr-pol {
        value 9;
        description
          "Host address is unreachable due to policy enforced by network";
      }
      enum ip-tracert-no-rch-rej-rt {
        value 10;
        description
          "Router along the traceroute path has rejected the packet";
      }
    }
    description
      "IP trace route probe result";
  }

  typedef echo-status {
    type enumeration {
      enum echo-failed {
        value 0;
        description
          "ICMP echo failed";
      }
      enum echo-success {
        value 1;
        description
          "ICMP echo success";
      }
      enum echo-unsent {
        value 2;
        description
          "ICMP echo not sent";
      }
      enum echo-timeout {
        value 3;
        description
          "ICMP echo timeout";
      }
    }
    description
      "Status of the ICMP echo";
  }

  typedef ip-ping-error {
    type enumeration {
      enum ip-ping-no-err {
        value 0;
        description
          "IP ping request successfully processed";
      }
      enum ip-ping-host-name-not-reslvd {
        value 1;
        description
          "Host name specified in IP ping request could not be resolved";
      }
      enum ip-ping-dest-addr-inv {
        value 2;
        description
          "Destination IP address specified in IP ping request is not valid";
      }
      enum ip-ping-src-addr-inv {
        value 3;
        description
          "Source IP address specified in IP ping request is not valid";
      }
      enum ip-ping-src-int-inv {
        value 4;
        description
          "Source interface specified in IP ping request is not valid";
      }
      enum ip-ping-vrf-inv {
        value 5;
        description
          "Device handling the IP ping request does not have
           access to the specified VRF instance";
      }
      enum ip-ping-err-unkwn {
        value 6;
        description
          "An unknown error occured when
           processing the IP ping request";
      }
      enum ip-ping-failed {
        value 7;
        description
          "IP ping request failed";
      }
    }
    description
      "IP Ping request processing error";
  }

  typedef mtr-err {
    type enumeration {
      enum mtr-no-err {
        value 0;
        description
          "MTR request successfully processed";
      }
      enum mtr-host-nm-not-rsvld {
        value 1;
        description
          "Specified host name in the MTR request could not be resolved";
      }
      enum mtr-src-if-inv {
        value 2;
        description
          "Specified source interface in the MTR request is not valid";
      }
      enum mtr-src-if-dwn {
        value 3;
        description
          "Specified source interface in the MTR request is down";
      }
      enum mtr-inv-addr {
        value 4;
        description
          "Specified source IP address in the MTR request is invalid";
      }
      enum mtr-ip-disbl {
        value 5;
        description
          "Device handling the MTR request does not have
           IP enabled at source";
      }
      enum mtr-vrf-not-ex {
        value 6;
        description
          "Device handling the MTR request does not have
           specified vrf configured";
      }
      enum mtr-vrf-not-acc {
        value 7;
        description
          "Device handling the MTR request does not have
           access to the specified VRF instance";
      }
      enum mtr-topo-not-ex {
        value 8;
        description
          "Device handling the MTR request does not have
           specified topology configured";
      }
      enum mtr-minttl-grt-maxttl {
        value 9;
        description
          "Specified minimum TTL value in the MTR request
           is greater than maximum TTL value";
      }
      enum mtr-unsptd-addr {
        value 10;
        description
          "Specified IP address is unsupported in the MTR request";
      }
      enum mtr-int-failure {
        value 11;
        description
          "MTR operation failed due to an internal failure";
      }
      enum mtr-inv-addr-zone {
        value 12;
        description
          "Specified IPv6 address is invalid in the
           IPv6 address zone calculation";
      }
      enum mtr-dest-failure {
        value 13;
        description
          "Trace operation did not reach final destination";
      }
    }
    description
      "MTR processing error";
  }

  typedef dns-error {
    type enumeration {
      enum dns-lookup-no-error {
        value 0;
        description
          "No error found";
      }
      enum dns-lookup-not-supported {
        value 1;
        description
          "DNS lookup functionality is not supported";
      }
      enum dns-lookup-internal-error {
        value 2;
        description
          "DNS lookup failed due to internal error";
      }
      enum dns-lookup-timeout {
        value 3;
        description
          "DNS lookup timed out";
      }
      enum dns-lookup-host-name-not-rsvld {
        value 4;
        description
          "Failed to resolve the hostname";
      }
    }
    description
      "DNS lookup request processing error";
  }

  typedef dns-class {
    type enumeration {
      enum dns-class-internet {
        value 0;
        description
          "Identifies DNS message class belongs to internet";
      }
    }
    description
      "DNS query class";
  }

  typedef dns-rec-type {
    type enumeration {
      enum dns-rec-none {
        value 0;
        description
          "Invalid record type";
      }
      enum dns-rec-a {
        value 1;
        description
          "DNS IPv4 resource record";
      }
      enum dns-rec-aaaa {
        value 2;
        description
          "DNS IPv6 resource record";
      }
      enum dns-rec-cname {
        value 3;
        description
          "DNS canonical name resource record";
      }
    }
    description
      "DNS resource record type";
  }

  typedef dns-flags {
    type bits {
      bit dns-flag-qr-query {
        position 0;
        description
          "Specifies message is a DNS query";
      }
      bit dns-flag-qr-response {
        position 1;
        description
          "Specifies message is a DNS response";
      }
      bit dns-flag-opcode-query {
        position 2;
        description
          "Standard DNS query";
      }
      bit dns-flag-opcode-iquery {
        position 3;
        description
          "DNS inverse query";
      }
      bit dns-flag-opcode-status {
        position 4;
        description
          "DNS server status";
      }
      bit dns-flag-opcode-notify {
        position 5;
        description
          "Informs a DNS server about changes to a zone";
      }
      bit dns-flag-opcode-update {
        position 6;
        description
          "Updates resource records in a DNS zone";
      }
      bit dns-flag-aa {
        position 7;
        description
          "Indicates answer section contains authoritative data";
      }
      bit dns-flag-tc {
        position 8;
        description
          "Indicates message was truncated and additional data is available";
      }
      bit dns-flag-rd {
        position 9;
        description
          "Requests that the DNS server pursue the query recursively";
      }
      bit dns-flag-ra {
        position 10;
        description
          "Denotes whether recursive query support is available in the name server";
      }
      bit dns-flag-z {
        position 11;
        description
          "Reserved for future use";
      }
      bit dns-rcode-noerror {
        position 12;
        description
          "Indicates a successful query";
      }
      bit dns-rcode-formerr {
        position 13;
        description
          "Indicates a format error in the query";
      }
      bit dns-rcode-servfail {
        position 14;
        description
          "Indicates a server failure";
      }
      bit dns-rcode-nxdomain {
        position 15;
        description
          "Indicates domain name does not exist";
      }
      bit dns-rcode-notimp {
        position 16;
        description
          "Indicates requested operation is not implemented";
      }
      bit dns-rcode-refused {
        position 17;
        description
          "Indicates server refuses to answer the query";
      }
      bit dns-rcode-yxdomain {
        position 18;
        description
          "Indicates domain name is not in the specified class";
      }
      bit dns-rcode-yxrrset {
        position 19;
        description
          "Resource record set exists when it should not";
      }
      bit dns-rcode-nxrrset {
        position 20;
        description
          "Resource record set that should exist";
      }
      bit dns-rcode-notauth {
        position 21;
        description
          "Indicates server is not an authoritative answer for the domain";
      }
      bit dns-rcode-notzone {
        position 22;
        description
          "Indicates domain is not in the server's zone";
      }
    }
    description
      "DNS header flags";
  }

  grouping wol-response {
    description
      "WAKE-ON-LAN response information";
    leaf vlan {
      type uint16;
      description
        "Destination VLAN identifier";
    }
    leaf mac-addr {
      type yang:mac-address;
      description
        "Destination MAC address";
    }
    leaf interval {
      type uint16;
      units "seconds";
      description
        "Interval between retries";
    }
    leaf count {
      type uint8;
      description
        "Total number of WAKE-ON-LAN packets to be sent";
    }
    leaf pak-sent {
      type uint8;
      description
        "Number of successful WAKE-ON-LAN packet sent";
    }
    leaf last-pak-sent {
      type yang:date-and-time;
      description
        "Time of the last successful WAKE-ON-LAN packet sent";
    }
    leaf error {
      type livetools-ios-xe-oper:wol-errors;
      description
        "Information about the error if the execution fails or is aborted due to internal failures.";
    }
  }

  grouping wol-results {
    description
      "WAKE-ON-LAN action RPC result";
    leaf job-id {
      type uint32;
      description
        "The ID is a unique identifier generated per WAKE-ON-LAN actions RPC request.
         It allows us to retrieve the operational data associated with a specific ID.
         This is useful for matching an action RPC response ID with the corresponding operational data";
    }
    container job-info {
      description
        "Job related data for the WAKE-ON-LAN action RPC execution";
      uses livetools-common-types-ios-xe:job-response;
    }
    container wol-info {
      description
        "WAKE-ON-LAN related data for the WAKE-ON-LAN action RPC execution";
      uses livetools-ios-xe-oper:wol-response;
    }
  }

  grouping thrpt-response {
    description
      "Throughput response data";
    leaf proto {
      type livetools-ios-xe-oper:thrpt-proto-result;
      description
        "Role of throughput tool: client/server";
    }
    leaf dest-addr {
      type inet:ip-address;
      description
        "Server IP address";
    }
    leaf ni-type {
      type common-types-ios-xe:net-inst-type;
      description
        "Network instance type. Differentiates between the
         default routing instance and VRFs";
    }
    leaf ni-name {
      type string;
      description
        "Network instance name. If the type is
         net-inst-default, the name is not meaningful";
    }
    leaf timeout {
      type uint64;
      units "seconds";
      description
        "Measurement time";
    }
    leaf wnd-span {
      type uint64;
      units "seconds";
      description
        "Duration of measurement window(s)";
    }
    leaf num-wnds {
      type uint32;
      description
        "Number of windows";
    }
    leaf port {
      type uint16;
      description
        "Server transport port";
    }
    leaf dscp {
      type uint8;
      description
        "Numeric value of DSCP used during traffic generation";
    }
    leaf client-rcv {
      type boolean;
      description
        "Flag to indicate that client should receive/read
         data from server instead of the default mode of writing data to
         server for throughput measurement";
    }
    leaf mode {
      type livetools-ios-xe-oper:thrpt-mode-result;
      description
        "Measurement mode";
    }
    leaf bytes {
      type uint64;
      units "bytes";
      description
        "Bytes transferred between client and server
         for the throughput measurement. Data transfer is supported in both
         directions on the client. The direction is 'transmit' by default.
         'Receive' is effective only when 'client-rcv' flag is set.";
    }
    leaf elapsed-time {
      type uint64;
      units "seconds";
      description
        "Time elapsed since the start of data sent/received";
    }
    leaf error-type {
      type livetools-ios-xe-oper:thrpt-err-msg;
      description
        "Contains an error type if encountered during throughput calculation";
    }
    leaf thrpt {
      type uint64;
      units "bps";
      description
        "Calculated throughput, in bits per second";
    }
  }

  grouping thrpt-result {
    description
      "Throughput result information";
    leaf job-id {
      type uint32;
      description
        "The ID is a unique identifier generated per successful
         throughput actions RPC request. It allows us to retrieve the operational
         data associated with a specific ID. This is useful for matching an action
         RPC response ID with the corresponding operational data";
    }
    container job-info {
      description
        "Job related data for the throughput action RPC execution";
      uses livetools-common-types-ios-xe:job-response;
    }
    container thrpt-info {
      description
        "Throughput related data for the throughput action RPC execution";
      uses livetools-ios-xe-oper:thrpt-response;
    }
  }

  grouping ip-tracert-probe {
    description
      "IP trace route per probe information ";
    leaf probe-num {
      type uint32;
      description
        "Sequence number assigned to each probe packet";
    }
    leaf result {
      type livetools-ios-xe-oper:ip-tracert-probe-rslt;
      description
        "Result of each probe packet sent";
    }
    leaf ip-addr {
      type inet:ip-address;
      description
        "IP address of the device on that particular hop";
    }
    leaf rtt {
      type uint32;
      units "milliseconds";
      description
        "Round-trip time of each probe packet sent";
    }
  }

  grouping ip-tracert-hop {
    description
      "IP trace route per hop information";
    leaf hop-num {
      type uint32;
      description
        "Sequential identifier of network hop
         encountered during trace route request";
    }
    list probe-info {
      description
        "Probe response information";
      uses livetools-ios-xe-oper:ip-tracert-probe;
    }
  }

  grouping ip-tracert-req {
    description
      "IP trace route request information";
    leaf ni-type {
      type common-types-ios-xe:net-inst-type;
      description
        "Network instance type. Differentiates between the
         default routing instance and VRFs";
    }
    leaf ni-name {
      type string;
      description
        "Network instance name. If the type is
         net-inst-default, the name is not meaningful";
    }
    choice src-choice {
      description
        "Source for IP trace route request as IP/IPv6 address or interface name";
      case src-if-name {
        leaf src-if {
          type string;
          description
            "Source interface name";
        }
      }
      case src-ip-addr {
        leaf src-ip {
          type inet:ip-address;
          description
            "Source IP/IPv6 address";
        }
      }
    }
    choice host-choice {
      description
        "Destination for IP trace route request as IP/IPv6 address or hostname";
      case host-name {
        leaf host-name {
          type string;
          description
            "Destination host name";
        }
      }
      case host-ip-addr {
        leaf host-ip {
          type inet:ip-address;
          description
            "Destination host IP address";
        }
      }
    }
  }

  grouping ip-tracert-resp {
    description
      "Information about IP trace route response";
    list hop-info {
      description
        "Hop response information";
      uses livetools-ios-xe-oper:ip-tracert-hop;
    }
  }

  grouping ip-tracert-result {
    description
      "Result of IP trace route request";
    leaf job-id {
      type uint32;
      description
        "The ID is a unique identifier generated per successful IP
         trace route actions RPC request. It allows us to retrieve the operational
         data associated with a specific ID. This is useful for matching an action
         RPC response ID with the corresponding operational data";
    }
    container req-info {
      description
        "Relevant information carried from IP trace route request";
      uses livetools-ios-xe-oper:ip-tracert-req;
    }
    container job-info {
      description
        "Status of the IP trace route request processing";
      uses livetools-common-types-ios-xe:job-response;
    }
    leaf error {
      type livetools-ios-xe-oper:ip-tracert-err;
      description
        "Contain the error reason of IP trace route request processing
         if there is any, otherwise specified as 'no-error'";
    }
    container resp-info {
      description
        "Response information of IP trace route request";
      uses livetools-ios-xe-oper:ip-tracert-resp;
    }
  }

  grouping ip-ping-echo {
    description
      "Information about the ICMP echo sent out as part of the ping request";
    leaf seq-num {
      type uint8;
      description
        "Sequence number assigned to the ICMP echo";
    }
    leaf status {
      type livetools-ios-xe-oper:echo-status;
      description
        "Status of the ICMP echo sent";
    }
    leaf latency {
      type uint8;
      status obsolete;
      description
        "Round-trip time for the ICMP echo";
    }
    leaf latency-msec {
      type uint32;
      units "milliseconds";
      description
        "Round-trip time in milliseconds for the ICMP echo";
    }
  }

  grouping ip-ping-response {
    description
      "Information about IP ping response";
    list echo-info {
      description
        "Response of the ICMP echoes sent out as part of the ping request";
      uses livetools-ios-xe-oper:ip-ping-echo;
    }
  }

  grouping ip-ping-request {
    description
      "IP ping request information";
    leaf ni-type {
      type common-types-ios-xe:net-inst-type;
      default "net-inst-default";
      description
        "Network instance type. Differentiates between the
         default routing instance and VRFs";
    }
    leaf ni-name {
      type string;
      description
        "Network instance name. If the type is
         net-inst-default, the name is not meaningful";
    }
    choice src-choice {
      description
        "Choice of source for ping - source address/interface";
      case src-if-name {
        leaf src-if {
          type string;
          description
            "Source interface name";
        }
      }
      case src-ip-addr {
        leaf src-ip {
          type inet:ip-address;
          description
            "Source IP address";
        }
      }
    }
    choice host-choice {
      description
        "Choice of destination host for ping - IP address/hostname";
      case host-name {
        leaf host-name {
          type string;
          description
            "Destination host name";
        }
      }
      case host-ip-addr {
        leaf host-ip {
          type inet:ip-address;
          description
            "Destination host IP address";
        }
      }
    }
  }

  grouping ip-ping-result {
    description
      "Result of the IP ping request";
    leaf job-id {
      type uint32;
      description
        "The ID is a unique identifier generated per successful
         ping action RPC request. It allows us to retrieve the operational
         data associated with a specific ID";
    }
    container req-info {
      description
        "Relevant information carried from the IP ping request";
      uses livetools-ios-xe-oper:ip-ping-request;
    }
    container job-info {
      description
        "Status of the IP ping request processing";
      uses livetools-common-types-ios-xe:job-response;
    }
    leaf error {
      type livetools-ios-xe-oper:ip-ping-error;
      description
        "Specifies the error that occured during the ping
         request processing, if any. If no error occured, 'ip-ping-no-err'
         is specified";
    }
    container resp-info {
      description
        "Response information of IP ping request";
      uses livetools-ios-xe-oper:ip-ping-response;
    }
  }

  grouping mtr-host {
    description
      "MTR response information";
    leaf host-num {
      type uint8;
      description
        "The number of hops on the route from the system to the target host";
    }
    leaf host-ip {
      type inet:ip-address;
      description
        "The IP address of the network node at each hop for MTR operation";
    }
    leaf loss-prcnt {
      type uint8;
      description
        "The percentage of packets lost at each hop";
    }
    leaf sent {
      type uint32;
      description
        "The total number of packets sent at each hop";
    }
    leaf last {
      type uint32;
      units "milliseconds";
      description
        "The latency of the last packet, in milliseconds";
    }
    leaf avg {
      type uint32;
      units "milliseconds";
      description
        "The average latency of all packets sent to this hop, in milliseconds";
    }
    leaf best {
      type uint32;
      units "milliseconds";
      description
        "The lowest (best) latency of all packets sent to the hop, in milliseconds";
    }
    leaf worst {
      type uint32;
      units "milliseconds";
      description
        "The highest (worst) latency of all packets sent to the hop, in milliseconds";
    }
    leaf stdev {
      type uint32;
      units "milliseconds";
      description
        "The standard deviation of the latency values for each hop, in milliseconds";
    }
  }

  grouping mtr-req {
    description
      "MTR request information";
    leaf ni-type {
      type common-types-ios-xe:net-inst-type;
      description
        "Network instance type. Differentiates between the
         default routing instance and VRFs";
    }
    leaf ni-name {
      type string;
      description
        "Network instance name. If the type is
         net-inst-default, the name is not meaningful";
    }
    leaf proto-hint {
      type livetools-common-types-ios-xe:dns-proto-hint;
      description
        "DNS resolution type";
    }
    leaf count {
      type uint8;
      description
        "The number of traceroute/ping probes or packets to be sent to each hop along the traceroute path";
    }
    leaf port {
      type uint16;
      description
        "Destination port to send UDP packets";
    }
    leaf timeout {
      type uint16;
      units "seconds";
      description
        "Probe timeout value";
    }
    leaf min-ttl {
      type uint8;
      description
        "Minimum value of time to live(TTL) for an IP packet";
    }
    leaf max-ttl {
      type uint8;
      description
        "Maximum value of time to live(TTL) for an IP packet";
    }
    choice dscp-choice {
      description
        "Choice for DSCP options to be set";
      case dscp-num {
        leaf dscp-num {
          type uint8;
          description
            "DSCP numeric value";
        }
      }
      case dscp-ascii {
        leaf dscp-ascii {
          type livetools-common-types-ios-xe:dscp-options;
          description
            "DSCP ASCII value selected from a set of known DSCP options";
        }
      }
    }
    choice src-choice {
      description
        "Source for the MTR request as IP/IPv6 address or interface name";
      case src-if-name {
        leaf src-if {
          type string;
          description
            "Source interface name";
        }
      }
      case src-ip-addr {
        leaf src-ip {
          type inet:ip-address;
          description
            "Source IP/IPv6 address";
        }
      }
    }
    choice host-choice {
      description
        "Destination for the MTR request as IP/IPv6 address or hostname";
      case host-name {
        leaf host-name {
          type string;
          description
            "Destination host name";
        }
      }
      case host-ip-addr {
        leaf host-ip {
          type inet:ip-address;
          description
            "Destination host IP address";
        }
      }
    }
  }

  grouping mtr-resp {
    description
      "Information about the MTR response";
    list host-info {
      description
        "Host response information";
      uses livetools-ios-xe-oper:mtr-host;
    }
  }

  grouping mtr-result {
    description
      "Result of the MTR request";
    leaf job-id {
      type uint32;
      description
        "The ID is a unique identifier generated per successful the MTR
         actions RPC request. It allows us to retrieve the operational
         data associated with a specific ID. This is useful for matching an action
         RPC response ID with the corresponding operational data";
    }
    container req-info {
      description
        "Relevant information carried from the MTR request";
      uses livetools-ios-xe-oper:mtr-req;
    }
    container job-info {
      description
        "Status of the MTR request processing";
      uses livetools-common-types-ios-xe:job-response;
    }
    leaf error {
      type livetools-ios-xe-oper:mtr-err;
      description
        "Contain the error reason of the MTR request processing
         if there is any, otherwise specified as 'mtr-err-none'";
    }
    container resp-info {
      description
        "Response information of the MTR request";
      uses livetools-ios-xe-oper:mtr-resp;
    }
  }

  grouping dns-header {
    description
      "DNS header information";
    leaf id {
      type uint16;
      description
        "Identification field information of DNS response header";
    }
    leaf flags {
      type livetools-ios-xe-oper:dns-flags;
      description
        "Flags information of DNS response header";
    }
    leaf qdcount {
      type uint16;
      description
        "Number of questions for which DNS response is received";
    }
    leaf ancount {
      type uint16;
      description
        "Number of answers resource records present in the DNS response";
    }
    leaf nscount {
      type uint16;
      description
        "Number of authority resource records present in the DNS response";
    }
    leaf arcount {
      type uint16;
      description
        "Number of additional resource records present in the DNS response";
    }
  }

  grouping dns-query {
    description
      "Query section from DNS response message";
    leaf query-name {
      type string;
      description
        "This field repeats the domain name from the original DNS query,
         confirming the response is for the correct domain";
    }
    leaf class {
      type livetools-ios-xe-oper:dns-class;
      description
        "DNS query class";
    }
    leaf type {
      type livetools-common-types-ios-xe:dns-qry-type;
      description
        "DNS query type";
    }
  }

  grouping dns-rr-a-aaaa {
    description
      "DNS resource record contains IPv4 and IPv6 address info";
    leaf ttl {
      type uint32;
      units "seconds";
      description
        "TTL of resource record";
    }
    leaf addr {
      type inet:ip-address;
      description
        "IP address in resource record";
    }
  }

  grouping dns-rr-cname {
    description
      "DNS resource record contains canonical name";
    leaf ttl {
      type uint32;
      units "seconds";
      description
        "TTL of resource record";
    }
    leaf alias-name {
      type string;
      description
        "Canonical name in the resource record";
    }
  }

  grouping dns-ans-sec {
    description
      "Answer resource record information of DNS response";
    choice rec-type-choice {
      description
        "Choice for DNS record type to be set";
      case dns-rec-a {
        container a-rec {
          description
            "Contains information of IPv4 resource record";
          uses livetools-ios-xe-oper:dns-rr-a-aaaa;
        }
      }
      case dns-rec-aaaa {
        container aaaa-rec {
          description
            "Contains information of IPv6 resource record";
          uses livetools-ios-xe-oper:dns-rr-a-aaaa;
        }
      }
      case dns-rec-cname {
        container cname-rec {
          description
            "Contains DNS canonical name resource record";
          uses livetools-ios-xe-oper:dns-rr-cname;
        }
      }
    }
  }

  grouping dns-query-response {
    description
      "DNS query response";
    container header {
      description
        "DNS response header information";
      uses livetools-ios-xe-oper:dns-header;
    }
    container query {
      description
        "Query section information from DNS response";
      uses livetools-ios-xe-oper:dns-query;
    }
    list ans-section {
      description
        "Answer section information from DNS response";
      uses livetools-ios-xe-oper:dns-ans-sec;
    }
    leaf query-time {
      type yang:date-and-time;
      description
        "Time when DNS query is sent out";
    }
    leaf payload-size {
      type uint32;
      description
        "DNS response payload size";
    }
    leaf rtt {
      type uint32;
      units "milliseconds";
      description
        "Round trip time";
    }
  }

  grouping dns-lookup-request {
    description
      "DNS lookup request information";
    leaf ni-type {
      type common-types-ios-xe:net-inst-type;
      description
        "Network instance type. Differentiates between the
         default routing instance and VRFs";
    }
    leaf ni-name {
      type string;
      description
        "Network instance name. If the type is
         net-inst-default, the name is not meaningful";
    }
    leaf dns-server {
      type inet:ip-address;
      description
        "DNS server address information";
    }
    choice qtype-choice {
      description
        "Choice of DNS query type";
      case dns-a-query {
        container a-qry {
          description
            "DNS query for IPv4 address lookup";
          uses livetools-common-types-ios-xe:dns-a-aaaa-qry;
        }
      }
      case dns-aaaa-query {
        container aaaa-qry {
          description
            "DNS query for IPv6 address lookup";
          uses livetools-common-types-ios-xe:dns-a-aaaa-qry;
        }
      }
    }
  }

  grouping dns-query-result {
    description
      "Result of the DNS query request";
    leaf job-id {
      type uint32;
      description
        "The ID is a unique identifier generated per successful
         DNS query action RPC request. It allows us to retrieve
         the operational data associated with a specific ID";
    }
    container job-info {
      description
        "Status of the DNS query request processing";
      uses livetools-common-types-ios-xe:job-response;
    }
    container request {
      description
        "Request information of the DNS query";
      uses livetools-ios-xe-oper:dns-lookup-request;
    }
    leaf error {
      type livetools-ios-xe-oper:dns-error;
      description
        "Contain the error reason of the DNS query request processing
         if there is any, otherwise specified as 'dns-lookup-success'";
    }
    list response {
      description
        "Response information of the DNS query request";
      uses livetools-ios-xe-oper:dns-query-response;
    }
  }

  container livetools-oper-data {
    config false;
    description
      "Live tools operational data";
    list tracert-result {
      key "job-id";
      description
        "IP trace route result";
      uses livetools-ios-xe-oper:ip-tracert-result;
    }
    list thrpt-result {
      key "job-id";
      description
        "Throughput result";
      uses livetools-ios-xe-oper:thrpt-result;
    }
    list ip-ping-result {
      key "job-id";
      description
        "Response of the IP ping operation";
      uses livetools-ios-xe-oper:ip-ping-result;
    }
    list dns-query-result {
      key "job-id";
      description
        "Response for DNS query";
      uses livetools-ios-xe-oper:dns-query-result;
    }
    list wol-result {
      key "job-id";
      description
        "WAKE-ON-LAN action RPC result";
      uses livetools-ios-xe-oper:wol-results;
    }
    list mtr-result {
      key "job-id";
      description
        "MTR action RPC result";
      uses livetools-ios-xe-oper:mtr-result;
    }
  }
}
