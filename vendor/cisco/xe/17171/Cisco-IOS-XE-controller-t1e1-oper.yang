module Cisco-IOS-XE-controller-t1e1-oper {
  yang-version 1.1;
  namespace "http://cisco.com/ns/yang/Cisco-IOS-XE-controller-t1e1-oper";
  prefix t1e1-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for monitoring controller T1/E1 operational information.
     Copyright (c) 2019, 2022 by Cisco Systems, Inc.
     All rights reserved.";

  revision 2022-11-01 {
    description
      "Update yang-version to 1.1";
    reference
      "1.1.0";
    cisco-semver:module-version "1.1.0";
  }
  revision 2019-11-01 {
    description
      "Initial revision";
    reference
      "1.0.0";
    cisco-semver:module-version "1.0.0";
  }

  typedef line-type {
    type enumeration {
      enum line-type-unknown {
        value 0;
        description
          "Line unknown";
      }
      enum line-type-t1 {
        value 1;
        description
          "T1 line";
      }
      enum line-type-e1-unbalanced {
        value 2;
        description
          "Unbalanced E1";
      }
      enum line-type-e1-balanced {
        value 3;
        description
          "Balanced E1";
      }
    }
    description
      "T1/E1 line types";
  }

  typedef frame-type {
    type enumeration {
      enum frame-type-unknown {
        value 0;
        description
          "Unknown frame";
      }
      enum frame-type-sf {
        value 1;
        description
          "T1 super-frame";
      }
      enum frame-type-esf {
        value 2;
        description
          "T1 extended super-frame";
      }
      enum frame-type-no-crc4 {
        value 3;
        description
          "E1 Frame no-crc-4";
      }
      enum frame-type-crc4 {
        value 4;
        description
          "E1 Frame crc-4";
      }
      enum frame-type-mf-no-crc4 {
        value 5;
        description
          "E1 Multi-Frame no-crc-4";
      }
      enum frame-type-mf-crc4 {
        value 6;
        description
          "E1 Multi-Frame crc-4";
      }
      enum frame-type-unframed {
        value 7;
        description
          "Unframed";
      }
      enum frame-type-j1-sf {
        value 8;
        description
          "Japan Super-frame";
      }
      enum frame-type-j1-esf {
        value 9;
        description
          "Japan Extended Super-frame";
      }
    }
    description
      "Frame type";
  }

  typedef cdb-state-type {
    type enumeration {
      enum cdb-state-type-down {
        value 0;
        description
          "Down state";
      }
      enum cdb-state-type-goingdown {
        value 1;
        description
          "Going down state";
      }
      enum cdb-state-type-init {
        value 2;
        description
          "Init state";
      }
      enum cdb-state-type-testing {
        value 3;
        description
          "Testing state";
      }
      enum cdb-state-type-up {
        value 4;
        description
          "Up state";
      }
      enum cdb-state-type-reset {
        value 5;
        description
          "Reset state";
      }
      enum cdb-state-type-admindown {
        value 6;
        description
          "Admindown state";
      }
      enum cdb-state-type-deleted {
        value 7;
        description
          "Deleted state";
      }
    }
    description
      "CDB state type";
  }

  typedef clock-type {
    type enumeration {
      enum clock-type-unknown {
        value 0;
        description
          "Clock unknown";
      }
      enum clock-type-line {
        value 1;
        description
          "Line clock";
      }
      enum clock-type-internal {
        value 2;
        description
          "Internal clock";
      }
      enum clock-type-primary {
        value 3;
        description
          "Line primary clock";
      }
      enum clock-type-secondary {
        value 4;
        description
          "Line secondary clock";
      }
      enum clock-type-network {
        value 5;
        description
          "Network clock for voice internal clocking";
      }
      enum clock-type-free {
        value 6;
        description
          "Free run";
      }
    }
    description
      "T1/E1 clock type";
  }

  typedef line-code-type {
    type enumeration {
      enum line-code-type-unknown {
        value 0;
        description
          "Unknown line code";
      }
      enum line-code-type-ami {
        value 1;
        description
          "Alternate mark inversion";
      }
      enum line-code-type-b8zs {
        value 2;
        description
          "Bipolar 8-zero substitution";
      }
      enum line-code-type-hdb3 {
        value 3;
        description
          "High-Density bipolar order 3";
      }
    }
    description
      "T1/E1 line code types";
  }

  typedef rx-alarm-type {
    type enumeration {
      enum rx-alarm-type-none {
        value 0;
        description
          "Received no alarm";
      }
      enum rx-alarm-type-ais {
        value 1;
        description
          "Receive alarm indication signal";
      }
      enum rx-alarm-type-los {
        value 2;
        description
          "Loss of signal";
      }
      enum rx-alarm-type-lof {
        value 3;
        description
          "Loss of frame";
      }
      enum rx-alarm-type-rem {
        value 4;
        description
          "Remote alarm";
      }
      enum rx-alarm-type-ais-ts16 {
        value 5;
        description
          "Received alarm indication signaling time-slot 16";
      }
      enum rx-alarm-type-lomf {
        value 6;
        description
          "Received remote time-slot 16 loss of multi-frame alignment";
      }
    }
    description
      "T1/E1 received alarm types";
  }

  typedef tx-alarm-type {
    type enumeration {
      enum tx-alarm-type-none {
        value 0;
        description
          "Transmitted no alarm";
      }
      enum tx-alarm-type-rem {
        value 1;
        description
          "Transmitted remote alarm";
      }
      enum tx-alarm-type-ais {
        value 2;
        description
          "Transmit alarm indication signal";
      }
      enum tx-alarm-type-lomf {
        value 3;
        description
          "Transmitted loss of multi-frame alignment alarm";
      }
    }
    description
      "T1/E1 transmitted alarm types";
  }

  typedef alarm-trigger-type {
    type enumeration {
      enum alarm-trigger-none {
        value 0;
        description
          "Triggered no alarm";
      }
      enum alarm-trigger-yellow {
        value 1;
        description
          "Yellow alarm";
      }
      enum alarm-trigger-blue {
        value 2;
        description
          "Blue alarm";
      }
    }
    description
      "T1/E1 transmit triggered alarm";
  }

  grouping port-info-key {
    description
      "Key information";
    leaf slot-num {
      type uint32;
      description
        "Slot number";
    }
    leaf subslot-num {
      type uint32;
      description
        "Sub Slot number";
    }
    leaf port-num {
      type uint32;
      description
        "Port number";
    }
  }

  grouping t1e1-line-stats-type {
    description
      "T1/E1 Line information";
    leaf lcvs {
      type uint32;
      description
        "Line code violations";
    }
    leaf pcvs {
      type uint32;
      description
        "Path code violations";
    }
    leaf csss {
      type uint32;
      units "seconds";
      description
        "Slip seconds";
    }
    leaf sefss {
      type uint32;
      units "seconds";
      description
        "Frame loss seconds";
    }
    leaf less {
      type uint32;
      units "seconds";
      description
        "Line error seconds";
    }
    leaf dms {
      type uint32;
      units "minutes";
      description
        "Degraded minutes";
    }
    leaf ess {
      type uint32;
      units "seconds";
      description
        "Error seconds";
    }
    leaf bess {
      type uint32;
      units "seconds";
      description
        "Burst error seconds";
    }
    leaf sess {
      type uint32;
      units "seconds";
      description
        "Severe error seconds";
    }
    leaf uass {
      type uint32;
      units "seconds";
      description
        "Unavailable seconds";
    }
  }

  grouping controller-t1e1-info {
    description
      "T1/E1 Controller information";
    leaf state {
      type t1e1-ios-xe-oper:cdb-state-type;
      description
        "T1/E1 Controller state";
    }
    leaf type {
      type t1e1-ios-xe-oper:line-type;
      description
        "Controller types";
    }
    leaf rx-alarm {
      type t1e1-ios-xe-oper:rx-alarm-type;
      description
        "Received alarm";
    }
    leaf tx-alarm {
      type t1e1-ios-xe-oper:tx-alarm-type;
      description
        "Transmitted alarm";
    }
    leaf alarm-triggered {
      type t1e1-ios-xe-oper:alarm-trigger-type;
      description
        "Triggered alarm";
    }
    leaf clocking {
      type t1e1-ios-xe-oper:clock-type;
      description
        "Clocking type";
    }
    leaf framing {
      type t1e1-ios-xe-oper:frame-type;
      description
        "Framing type";
    }
    leaf linecoding {
      type t1e1-ios-xe-oper:line-code-type;
      description
        "Line Code type";
    }
    container current-15min-stats {
      description
        "Current 15 minutes statistics";
      uses t1e1-ios-xe-oper:t1e1-line-stats-type;
    }
    container total-stats {
      description
        "Total accumulated statistics";
      uses t1e1-ios-xe-oper:t1e1-line-stats-type;
    }
  }

  container t1e1-oper-data {
    config false;
    description
      "T1/E1 controller information";
    list controller-t1e1-info {
      key "slot-num subslot-num port-num";
      description
        "T1/E1 controller information";
      uses t1e1-ios-xe-oper:controller-t1e1-info;
      uses t1e1-ios-xe-oper:port-info-key;
    }
  }
}
