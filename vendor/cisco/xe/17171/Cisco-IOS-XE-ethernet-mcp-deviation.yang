module Cisco-IOS-XE-ethernet-mcp-deviation {
  yang-version 1.1;
  namespace "http://cisco.com/ns/yang/Cisco-IOS-XE-ethernet-mcp-deviation";
  prefix ios-ethernet-mcp-d;

  import Cisco-IOS-XE-native {
    prefix ios;
  }
  import Cisco-IOS-XE-ethernet {
    prefix ios-ethernet;
  }
  import cisco-semver {
    prefix cisco-semver;
  }

  organization
    "Cisco Systems";
  description
    "Cisco XE Native Deviation YANG module for IOS
     Copyright (c) 2020 by Cisco Systems, Inc.
     All rights reserved.";

  revision 2024-11-10 {
    description
      "Initial Revision";
    cisco-semver:module-version "1.0.0";
  }

  deviation "/ios:native/ios:interface/ios:TenGigabitEthernet/ios-ethernet:negotiation/ios-ethernet:auto" {
    deviate add {
      default "false";
    }
  }
}
