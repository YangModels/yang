module Cisco-IOS-XE-irig {
  yang-version 1.1;
  namespace "http://cisco.com/ns/yang/Cisco-IOS-XE-irig";
  prefix ios-irig;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Inter-Range Instrumentation Group (IRIG) Yang Model.
     Copyright (c) 2024 by Cisco Systems, Inc.
     All rights reserved.";

  revision 2024-07-01 {
    description
      "- Initial version";
    cisco-semver:module-version "1.0.0";
  }

  grouping config-irig-grouping1 {
    container irig {
      container mode {
        choice analog-mode {
          case AM02-case {
            container AM02 {
              description
                "AM-B122 format";
              container dir {
                description
                  "Direction";
                choice direction-case {
                  case in-case {
                    leaf IN {
                      description
                        "Input direction";
                      must 'not (../../../TTL02/dir/IN or ../../../TTL03/dir/IN or ../../../TTL06/dir/IN or ../../../TTL07/dir/IN)' {
                        error-message "TTL mode has been setup as IRIG-B Input, action aborted";
                      }
                      type empty;
                    }
                  }
                  case out-case {
                    leaf OUT {
                      description
                        "Output direction";
                      type empty;
                    }
                  }
                }
              }
            }
          }
          case AM03-case {
            container AM03 {
              description
                "AM-B123 format";
              container dir {
                description
                  "Direction";
                choice direction-case {
                  case in-case {
                    leaf IN {
                      description
                        "Input direction";
                      must 'not (../../../TTL02/dir/IN or ../../../TTL03/dir/IN or ../../../TTL06/dir/IN or ../../../TTL07/dir/IN)' {
                        error-message "TTL mode has been setup as IRIG-B Input, action aborted";
                      }
                      type empty;
                    }
                  }
                  case out-case {
                    leaf OUT {
                      description
                        "Output direction";
                      type empty;
                    }
                  }
                }
              }
            }
          }
          case AM06-case {
            container AM06 {
              description
                "AM-B126 format";
              container dir {
                description
                  "Direction";
                choice direction-case {
                  case in-case {
                    leaf IN {
                      description
                        "Input direction";
                      must 'not (../../../TTL02/dir/IN or ../../../TTL03/dir/IN or ../../../TTL06/dir/IN or ../../../TTL07/dir/IN)' {
                        error-message "TTL mode has been setup as IRIG-B Input, action aborted";
                      }
                      type empty;
                    }
                  }
                  case out-case {
                    leaf OUT {
                      description
                        "Output direction";
                      type empty;
                    }
                  }
                }
              }
            }
          }
          case AM07-case {
            container AM07 {
              description
                "AM-B127 format";
              container dir {
                description
                  "Direction";
                choice direction-case {
                  case in-case {
                    leaf IN {
                      description
                        "Input direction";
                      must 'not (../../../TTL02/dir/IN or ../../../TTL03/dir/IN or ../../../TTL06/dir/IN or ../../../TTL07/dir/IN)' {
                        error-message "TTL mode has been setup as IRIG-B Input, action aborted";
                      }
                      type empty;
                    }
                  }
                  case out-case {
                    leaf OUT {
                      description
                        "Output direction";
                      type empty;
                    }
                  }
                }
              }
            }
          }
        }
        choice Digital-mode {
          case TTL02-case {
            container TTL02 {
              description
                "TTL-B002 format";
              container dir {
                description
                  "Direction";
                choice direction-case {
                  case in-case {
                    leaf IN {
                      description
                        "Input direction";
                      must 'not (../../../AM02/dir/IN or ../../../AM03/dir/IN or ../../../AM06/dir/IN or ../../../AM07/dir/IN)' {
                        error-message "Analog mode has been setup as IRIG-B Input, action aborted";
                      }
                      type empty;
                    }
                  }
                  case out-case {
                    leaf OUT {
                      description
                        "Output direction";
                      type empty;
                    }
                  }
                }
              }
            }
          }
          case TTL03-case {
            container TTL03 {
              description
                "TTL-B003 format";
              container dir {
                description
                  "Direction";
                choice direction-case {
                  case in-case {
                    leaf IN {
                      description
                        "Input direction";
                      must 'not (../../../AM02/dir/IN or ../../../AM03/dir/IN or ../../../AM06/dir/IN or ../../../AM07/dir/IN)' {
                        error-message "Analog mode has been setup as IRIG-B Input, action aborted";
                      }
                      type empty;
                    }
                  }
                  case out-case {
                    leaf OUT {
                      description
                        "Output direction";
                      type empty;
                    }
                  }
                }
              }
            }
          }
          case TTL06-case {
            container TTL06 {
              description
                "TTL-B006 format";
              container dir {
                description
                  "Direction";
                choice direction-case {
                  case in-case {
                    leaf IN {
                      description
                        "Input direction";
                      must 'not (../../../AM02/dir/IN or ../../../AM03/dir/IN or ../../../AM06/dir/IN or ../../../AM07/dir/IN)' {
                        error-message "Analog mode has been setup as IRIG-B Input, action aborted";
                      }
                      type empty;
                    }
                  }
                  case out-case {
                    leaf OUT {
                      description
                        "Output direction";
                      type empty;
                    }
                  }
                }
              }
            }
          }
          case TTL07-case {
            container TTL07 {
              description
                "TTL-B007 format";
              container dir {
                description
                  "Direction";
                choice direction-case {
                  case in-case {
                    leaf IN {
                      description
                        "Input direction";
                      must 'not (../../../AM02/dir/IN or ../../../AM03/dir/IN or ../../../AM06/dir/IN or ../../../AM07/dir/IN)' {
                        error-message "Analog mode has been setup as IRIG-B Input, action aborted";
                      }
                      type empty;
                    }
                  }
                  case out-case {
                    leaf OUT {
                      description
                        "Output direction";
                      type empty;
                    }
                  }
                }
              }
            }
          }
        }
      }
    }
  }

  augment "/ios:native" {
    uses config-irig-grouping1;
  }
}
