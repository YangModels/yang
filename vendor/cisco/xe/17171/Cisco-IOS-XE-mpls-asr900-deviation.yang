module Cisco-IOS-XE-mpls-asr900-deviation {
  yang-version 1.1;
  namespace "http://cisco.com/ns/yang/Cisco-IOS-XE-mpls-asr900-deviation";
  prefix ios-mpls-asr900-deviate;

  import Cisco-IOS-XE-native {
    prefix ios;
  }
  import Cisco-IOS-XE-mpls {
    prefix ios-mpls;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native MPLS Deviation Yang model for ASR900 platform.
     Copyright (c) 2023 by Cisco Systems, Inc.
     All rights reserved.";

  revision 2023-11-01 {
    description
      "- Initial Revision for 17.13
       - Added new mpls mtu range for asr900 variant";
  }

  deviation "/ios:native/ios:interface/ios:FastEthernet/ios:mpls/ios-mpls:mtu" {
    deviate replace {
      type uint16 {
        range "64..9670";
      }
    }
  }

  deviation "/ios:native/ios:interface/ios:GigabitEthernet/ios:mpls/ios-mpls:mtu" {
    deviate replace {
      type uint16 {
        range "64..9670";
      }
    }
  }

  deviation "/ios:native/ios:interface/ios:TenGigabitEthernet/ios:mpls/ios-mpls:mtu" {
    deviate replace {
      type uint16 {
        range "64..9670";
      }
    }
  }

  deviation "/ios:native/ios:interface/ios:FiveGigabitEthernet/ios:mpls/ios-mpls:mtu" {
    deviate replace {
      type uint16 {
        range "64..9670";
      }
    }
  }

  deviation "/ios:native/ios:interface/ios:AppGigabitEthernet/ios:mpls/ios-mpls:mtu" {
    deviate replace {
      type uint16 {
        range "64..9670";
      }
    }
  }

  deviation "/ios:native/ios:interface/ios:TwentyFiveGigE/ios:mpls/ios-mpls:mtu" {
    deviate replace {
      type uint16 {
        range "64..9670";
      }
    }
  }

  deviation "/ios:native/ios:interface/ios:TwoGigabitEthernet/ios:mpls/ios-mpls:mtu" {
    deviate replace {
      type uint16 {
        range "64..9670";
      }
    }
  }

  deviation "/ios:native/ios:interface/ios:FortyGigabitEthernet/ios:mpls/ios-mpls:mtu" {
    deviate replace {
      type uint16 {
        range "64..9670";
      }
    }
  }

  deviation "/ios:native/ios:interface/ios:HundredGigE/ios:mpls/ios-mpls:mtu" {
    deviate replace {
      type uint16 {
        range "64..9670";
      }
    }
  }

  deviation "/ios:native/ios:interface/ios:Vlan/ios:mpls/ios-mpls:mtu" {
    deviate replace {
      type uint16 {
        range "64..9670";
      }
    }
  }

  deviation "/ios:native/ios:interface/ios:Port-channel/ios:mpls/ios-mpls:mtu" {
    deviate replace {
      type uint16 {
        range "64..9670";
      }
    }
  }

  deviation "/ios:native/ios:interface/ios:Loopback/ios:mpls/ios-mpls:mtu" {
    deviate replace {
      type uint16 {
        range "64..9670";
      }
    }
  }

  deviation "/ios:native/ios:interface/ios:Tunnel/ios:mpls/ios-mpls:mtu" {
    deviate replace {
      type uint16 {
        range "64..9670";
      }
    }
  }

  deviation "/ios:native/ios:interface/ios:BDI/ios:mpls/ios-mpls:mtu" {
    deviate replace {
      type uint16 {
        range "64..9670";
      }
    }
  }

  deviation "/ios:native/ios:interface/ios:BD-VIF/ios:mpls/ios-mpls:mtu" {
    deviate replace {
      type uint16 {
        range "64..9670";
      }
    }
  }
}
