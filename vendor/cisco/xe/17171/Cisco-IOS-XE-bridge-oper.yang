module Cisco-IOS-XE-bridge-oper {
  yang-version 1.1;
  namespace "http://cisco.com/ns/yang/Cisco-IOS-XE-bridge-oper";
  prefix bridge-ios-xe-oper;

  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for bridge data.
     Copyright (c) 2018-2019, 2022 by Cisco Systems, Inc.
     All rights reserved.";

  revision 2022-11-01 {
    description
      "Update yang-version to 1.1";
    reference
      "1.3.0";
    cisco-semver:module-version "1.3.0";
  }
  revision 2019-05-01 {
    description
      "Added semantic version";
    reference
      "1.2.0";
    cisco-semver:module-version "1.2.0";
  }
  revision 2018-10-29 {
    description
      "Cleaned up spelling errors in descriptions.";
    reference
      "1.1.0";
    cisco-semver:module-version "1.1.0";
  }
  revision 2018-03-10 {
    description
      "Initial revision";
    reference
      "1.0.0";
    cisco-semver:module-version "1.0.0";
  }

  typedef intf-status-type {
    type enumeration {
      enum up {
        value 0;
      }
      enum down {
        value 1;
      }
    }
    description
      "Interface status type";
  }

  typedef bridge-mac-type {
    type enumeration {
      enum bridge-mac-type-static {
        value 0;
      }
      enum bridge-mac-type-dynamic {
        value 1;
      }
    }
    description
      "MAC address type";
  }

  grouping bridge-intf-entry {
    description
      "Bridge interface operational data";
    leaf if-name {
      type string;
      description
        "Switch port name belong to the bridge";
    }
    leaf vlan {
      type uint32;
      description
        "VLAN identifier";
    }
    leaf native-vlan {
      type boolean;
      description
        "If the VLAN is native VLAN";
    }
    leaf admin-status {
      type bridge-ios-xe-oper:intf-status-type;
      description
        "Bridge interface administration status";
    }
    leaf oper-status {
      type bridge-ios-xe-oper:intf-status-type;
      description
        "Bridge interface operational status";
    }
    leaf encap-type {
      type string;
      description
        "Bridge interface encapsulation type";
    }
    leaf ifindex {
      type uint32;
      description
        "Bridge interface index";
    }
    leaf mtu {
      type uint32;
      description
        "The Maximum Transmission Unit(byte) of Bridge interface";
    }
  }

  grouping bridge-matm-entry {
    description
      "Bridge MAC address operational data";
    leaf mac-address {
      type yang:mac-address;
      description
        "MAC address";
    }
    leaf-list interface {
      type string;
      ordered-by user;
      description
        "Interface name which MAC learnt from";
    }
    leaf vlan {
      type uint32;
      description
        "VLAN identifier";
    }
    leaf type {
      type bridge-ios-xe-oper:bridge-mac-type;
      description
        "MAC type";
    }
  }

  grouping bridge-entry {
    description
      "Bridge entry";
    leaf bridge-id {
      type uint32;
      description
        "Bridge id <1..4094>";
    }
    leaf name {
      type string;
      description
        "VLAN name";
    }
    leaf vlan {
      type uint32;
      description
        "VLAN identifier <1..4094>";
    }
    leaf routing-interface {
      type string;
      description
        "The name of VLAN routing interface";
    }
    leaf max-macs {
      type uint32;
      description
        "The maximum number of MAC learn limit for bridge";
    }
    leaf num-macs {
      type uint32;
      description
        "The number of MAC learned in bridge";
    }
    leaf age-time {
      type uint32;
      description
        "The aging time of MAC address,0 or <10..1000000> second";
    }
    leaf rx-packets {
      type uint64;
      description
        "The number of received packets in bridge";
    }
    leaf rx-octets {
      type uint64;
      description
        "The number of received bytes in bridge";
    }
    leaf tx-packets {
      type uint64;
      description
        "The number of transmitted packets out of bridge";
    }
    leaf tx-octets {
      type uint64;
      description
        "The number of transmitted bytes out of bridge";
    }
    leaf flood-packets {
      type uint64;
      description
        "The number of flood packets in bridge";
    }
    leaf flood-octets {
      type uint64;
      description
        "The number of flood bytes in bridge";
    }
    leaf rx-routed-packets {
      type uint64;
      description
        "L3 packets received from bridge";
    }
    leaf tx-routed-packets {
      type uint64;
      description
        "L3 packets transmit from bridge";
    }
    leaf learn {
      type uint64;
      description
        "MAC learned counter in bridge";
    }
    leaf age {
      type uint64;
      description
        "MAC aging counter in bridge";
    }
    leaf move {
      type uint64;
      description
        "MAC move counter in bridge";
    }
    container bridge-intf-entries {
      description
        "Bridge interface member information";
      list bridge-intf-entry {
        key "if-name";
        description
          "A list of bridge interface";
        uses bridge-ios-xe-oper:bridge-intf-entry;
      }
    }
    container bridge-matm-entries {
      description
        "Bridge matm member information";
      list bridge-matm-entry {
        key "mac-address";
        description
          "A list of mac table";
        uses bridge-ios-xe-oper:bridge-matm-entry;
      }
    }
  }

  container bridge-instances {
    config false;
    description
      "This is top level container for bridge table. It can have one
       or more bridge entry.";
    list bridge-entry {
      key "bridge-id";
      description
        "The bridge lists is an ordered list of bridge entries.
         Each bridge entries has a list of bridge interface members,
         and bridge attributes.";
      uses bridge-ios-xe-oper:bridge-entry;
    }
  }
}
