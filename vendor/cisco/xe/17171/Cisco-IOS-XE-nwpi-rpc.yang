module Cisco-IOS-XE-nwpi-rpc {
  yang-version 1.1;
  namespace "http://cisco.com/ns/yang/Cisco-IOS-XE-nwpi-rpc";
  prefix Cisco-IOS-XE-nwpi-rpc;

  import Cisco-IOS-XE-nwpi-types {
    prefix Cisco-IOS-XE-nwpi-types;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     network wide path insight RPC.
     Copyright (c) 2020-2024 by Cisco Systems, Inc.
     All rights reserved.";

  revision 2025-03-01 {
    description
      "- Added configurable QoS congestion duration.";
    reference
      "1.9.0";
    cisco-semver:module-version "1.9.0";
  }
  revision 2024-11-01 {
    description
      "- Added PCAP replay support.";
    reference
      "1.8.0";
    cisco-semver:module-version "1.8.0";
  }
  revision 2024-07-01 {
    description
      "- Added enable CMD header flag in trace start message.
       - Added transport interface name.
       - Added network instance identity";
    reference
      "1.7.0";
    cisco-semver:module-version "1.7.0";
  }
  revision 2024-03-01 {
    description
      "- Added ThousandEyes support.";
    reference
      "1.6.0";
    cisco-semver:module-version "1.6.0";
  }
  revision 2023-11-01 {
    description
      "- Added user identity support.";
    reference
      "1.5.0";
    cisco-semver:module-version "1.5.0";
  }
  revision 2023-07-01 {
    description
      "- Added trace model support.
       - Added multiple VPN support.
       - Added new capability support.
       - Added synthetic test support.";
    reference
      "1.4.0";
    cisco-semver:module-version "1.4.0";
  }
  revision 2022-11-01 {
    description
      "Update yang-version to 1.1";
    reference
      "1.3.0";
    cisco-semver:module-version "1.3.0";
  }
  revision 2022-07-01 {
    description
      "Added QoS monitor support.";
    reference
      "1.2.0";
    cisco-semver:module-version "1.2.0";
  }
  revision 2021-07-01 {
    description
      "1, Added new filters to match source/destination prefixes,
          application group, and domain list.
       2, Added new trace options to optionally have ART visibility,
          application visibility, direct internet access visibility,
          HUB WAN ingress traffic visibility, and flow sampling.
       3, Added domain monitor mode support.
       4, Change max vpn id from 65530 to 65531.";
    reference
      "1.1.0";
    cisco-semver:module-version "1.1.0";
  }
  revision 2020-11-01 {
    description
      "Initial revision";
    reference
      "1.0.0";
    cisco-semver:module-version "1.0.0";
  }

  typedef nwpi-control-type {
    type enumeration {
      enum nwpi-enable {
        value 0;
        description
          "Enable network wide path insight";
      }
      enum nwpi-disable {
        value 1;
        description
          "Disable network wide path insight";
      }
    }
    description
      "Network wide path insight control type";
  }

  grouping nwpi-trace {
    description
      "Trace identifier, action and filters";
    leaf trace-id {
      when "(../action[.='action-start-trace' or .='action-stop-trace' or .='action-clear-trace' or .='action-update-policy'])";
      type uint16 {
        range "1..65535";
      }
      mandatory true;
      description
        "Global unique trace identifier";
    }
    leaf action {
      type Cisco-IOS-XE-nwpi-types:nwpi-action-type;
      must ".!='action-enable-nwpi' and .!='action-disable-nwpi'" {
        error-message "Please use device-nwpi-global RPC instead";
        error-app-tag "must-violation";
      }
      mandatory true;
      description
        "Trace start/stop/clean actions";
    }
    leaf target {
      when "(../action = 'action-start-trace')";
      type Cisco-IOS-XE-nwpi-types:nwpi-target-type;
      mandatory true;
      description
        "Target types";
    }
    leaf vpn-id {
      when "(../action = 'action-start-trace') and (../target = 'target-vpn-id')";
      type uint32 {
        range "0..65531";
      }
      mandatory true;
      description
        "SD-WAN VPN identifier";
    }
    leaf vrf-name {
      when "(../action = 'action-start-trace') and (../target = 'target-vrf-name')";
      type string;
      mandatory true;
      description
        "VRF name";
    }
    leaf src-ip {
      type inet:ip-address;
      description
        "Source IP to filter";
    }
    leaf dst-ip {
      type inet:ip-address;
      description
        "Destination IP to filter";
    }
    leaf app {
      type string;
      description
        "Application to filter";
    }
    leaf src-if {
      type string;
      description
        "Source interface to filter";
    }
    leaf protocol {
      type uint8;
      description
        "IP protocol field in IP header to filter";
    }
    leaf src-port {
      type uint16;
      description
        "Source port to filter";
    }
    leaf dst-port {
      type uint16;
      description
        "Destination port to filter";
    }
    leaf dscp-is-valid {
      type boolean;
      description
        "Indicate DSCP filter was configured";
    }
    leaf dscp {
      when "(../dscp-is-valid = 'true')";
      type uint8 {
        range "0..63";
      }
      mandatory true;
      description
        "DSCP value to filter";
    }
    leaf duration {
      type uint16 {
        range "1..1440";
      }
      units "minutes";
      description
        "Option to change default trace duration of 60 minutes.
         The duration value is in minutes and in range between
         1 and 1440 minutes. A trace will auto stop if specified
         duration expired. If duration not specified and user didn't
         issue on-demand stop action, the trace will auto stop in
         60 minutes";
    }
    leaf src-pfx {
      type inet:ip-address;
      description
        "Source prefix to filter";
    }
    leaf src-pfx-len {
      type uint8;
      units "bits";
      description
        "Source prefix length to filter";
    }
    leaf dst-pfx {
      type inet:ip-address;
      description
        "Destination prefix to filter";
    }
    leaf dst-pfx-len {
      type uint8;
      units "bits";
      description
        "Destination prefix length to filter";
    }
    leaf app-grp {
      type string;
      description
        "Application grouped by vendors to filter";
    }
    leaf domain-mon {
      type boolean;
      description
        "Enable domain monitor";
    }
    leaf art-vis {
      type boolean;
      description
        "Enable ART visibility";
    }
    leaf app-vis {
      type boolean;
      description
        "Enable application visibility";
    }
    leaf dia-vis {
      type boolean;
      description
        "Enable direct internet access visibility";
    }
    leaf hub-wan-vis {
      type boolean;
      description
        "Enable HUB WAN ingress visibility";
    }
    leaf sampling {
      type boolean;
      description
        "Enable trace flow sampling";
    }
    leaf spl-intvl {
      type uint32 {
        range "1..86400000";
      }
      units "milliseconds";
      description
        "Option to change default trace flow sample interval of
         60000 milliseconds. The sample interval value is in milliseconds
         and in range between 1 and 86400000 milliseconds. Only one flow
         will be traced within a given interval";
    }
    list domain {
      description
        "Domain list to filter";
      uses Cisco-IOS-XE-nwpi-types:nwpi-domain-filter;
    }
    leaf qos-mon {
      type boolean;
      description
        "Enable QoS monitor";
    }
    list mon-domain {
      description
        "Domain list to monitor";
      uses Cisco-IOS-XE-nwpi-types:nwpi-domain-filter;
    }
    leaf model {
      type Cisco-IOS-XE-nwpi-types:nwpi-trace-mod;
      description
        "Trace model, different trace models have different behaviors
         and separate trace identifier space. Combination of trace model
         and trace identifier can uniquely identify a trace.";
    }
    leaf-list vpn-list {
      type uint16;
      ordered-by user;
      description
        "SD-WAN VPN list";
    }
    leaf agg-client-prefix {
      type boolean;
      description
        "Enable client prefix as a grouping factor in flexible aggregation";
    }
    leaf agg-svr-prefix {
      type boolean;
      description
        "Enable server prefix as a grouping factor in flexible aggregation";
    }
    leaf agg-src-sgt {
      type boolean;
      description
        "Enable source SGT as a grouping factor in flexible aggregation";
    }
    leaf agg-dst-sgt {
      type boolean;
      description
        "Enable destination SGT as a grouping factor in flexible aggregation";
    }
    leaf username {
      type string;
      description
        "Username classified by Cisco identity service engine to filter traffic";
    }
    leaf user-grp {
      type string;
      description
        "User group classified by Cisco identity service engine to filter traffic";
    }
    leaf src-sgt {
      type uint16;
      description
        "Source security group tag to filter traffic";
    }
    leaf dst-sgt {
      type uint16;
      description
        "Destination security group tag to filter";
    }
    leaf flow-mon {
      type boolean;
      description
        "Enable flow monitor to collect statistics of per application TCP and UDP flow count,
         flow setup rate, and average flow living time.";
    }
    leaf pol-mon {
      type boolean;
      description
        "Enable SD-WAN policy monitor to collect statistics of per application
         policy sequence match rate.";
    }
    leaf full-vis {
      type boolean;
      description
        "Enable full traffic visibility to process flexible aggregation on all traffic flows,
         flexible aggregation only process sampled flows when this option disabled.";
    }
    list test {
      description
        "List of synthetic tests to execute for this trace. Besides monitoring user traffic,
         each trace can specify multiple synthetic tests to targeted uniform resource locators,
         then first hop device will generate synthetic traffics toward the targets, and those
         traffics will be monitored by this trace as well.";
      uses Cisco-IOS-XE-nwpi-types:nwpi-test;
    }
    leaf agg-user-name {
      type boolean;
      description
        "Enable username as a grouping factor in flexible aggregation";
    }
    leaf te-mon {
      type boolean;
      description
        "Enable ThousandEyes agent monitor to collect statistics of ThousandEyes synthetic
         probes.";
    }
    container te-agent {
      when 'boolean(../te-mon)';
      description
        "ThousandEyes agent IP addresses to filter traffic";
      uses Cisco-IOS-XE-nwpi-types:nwpi-te-agent;
    }
    list net-id {
      description
        "List of network instance identity";
      uses Cisco-IOS-XE-nwpi-types:nwpi-net-identity;
    }
    leaf enable-cmd-header {
      type boolean;
      description
        "Enable CMD header in SD-Routing";
    }
    leaf-list trnspt-if-name {
      type string;
      ordered-by user;
      description
        "Transport intf list";
    }
    list pcap-replay {
      description
        "List of PCAP replay to execute for this trace. These
         traffic will be monitored by this trace.";
      uses Cisco-IOS-XE-nwpi-types:nwpi-pcap-replay;
    }
    leaf qos-congest-dur {
      type uint16 {
        range "1..65535";
      }
      units "seconds";
      description
        "Duration of QoS congestion to raise an alarm";
    }
  }

  grouping nwpi-global {
    description
      "Network wide path insight global control";
    leaf control {
      type Cisco-IOS-XE-nwpi-rpc:nwpi-control-type;
      mandatory true;
      description
        "Global enable/disable control";
    }
  }

  rpc device-nwpi {
    description
      "Device network wide path insight RPC";
    input {
      uses Cisco-IOS-XE-nwpi-rpc:nwpi-trace;
    }
  }

  rpc device-pcap-replay {
    description
      "Device PCAP replay RPC for starting/stopping PCAP replay";
    input {
      uses Cisco-IOS-XE-nwpi-types:nwpi-pcap-replay;
    }
  }

  rpc device-nwpi-global {
    description
      "Device network wide path insight global control RPC";
    input {
      uses Cisco-IOS-XE-nwpi-rpc:nwpi-global;
    }
  }
}
