module Cisco-IOS-XE-mvrp {
  yang-version 1.1;
  namespace "http://cisco.com/ns/yang/Cisco-IOS-XE-mvrp";
  prefix ios-mvrp;

  import cisco-semver {
    prefix cisco-semver;
  }
  import Cisco-IOS-XE-native {
    prefix ios;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Multiple VLAN Registration Protocol Yang Model.
     Copyright (c) 2016-2017 by Cisco Systems, Inc.
     All rights reserved.";

  revision 2022-11-01 {
    description
      "- Update yang-version to 1.1";
    cisco-semver:module-version "1.1.0";
  }
  revision 2019-07-01 {
    description
      "Establish semantic version baseline";
    cisco-semver:module-version "1.0.0";
  }
  revision 2019-02-26 {
    description
      "Added leaf for App-hosting Gigabit Ethernet interface";
  }
  revision 2017-11-27 {
    description
      "Added Change 25GE name";
  }
  revision 2017-11-14 {
    description
      "Added Fast, 2, 5, 25, 100GE interface support";
  }
  revision 2017-09-19 {
    description
      "Initial revision";
  }

  grouping config-mvrp-grouping {
    leaf global {
      type empty;
    }
    container mac-learning {
      leaf auto {
        type empty;
      }
    }
    container vlan {
      leaf create {
        type empty;
      }
    }
  }

  grouping config-interface-mvrp-grouping {
    container mvrp {
      presence "true";
      leaf mvrp {
        type empty;
      }
      container registration {
        leaf fixed {
          type empty;
        }
        leaf forbidden {
          type empty;
        }
        leaf normal {
          type empty;
        }
      }
      container timer {
        container join {
          presence "true";
          leaf _range {
            type uint32 {
              range "20..214748364";
            }
          }
        }
        container leave {
          presence "true";
          leaf _range {
            type uint32 {
              range "60..214748364";
            }
          }
        }
        container leave-all {
          presence "true";
          leaf _range {
            type uint32 {
              range "1000..214748364";
            }
          }
        }
        leaf periodic {
          type empty;
        }
      }
    }
  }

  augment "/ios:native/ios:mvrp" {
    uses config-mvrp-grouping;
  }

  augment "/ios:native/ios:interface/ios:GigabitEthernet" {
    uses config-interface-mvrp-grouping;
  }

  augment "/ios:native/ios:interface/ios:TenGigabitEthernet" {
    uses config-interface-mvrp-grouping;
  }

  augment "/ios:native/ios:interface/ios:FortyGigabitEthernet" {
    uses config-interface-mvrp-grouping;
  }

  augment "/ios:native/ios:interface/ios:FastEthernet" {
    uses config-interface-mvrp-grouping;
  }

  augment "/ios:native/ios:interface/ios:TwoGigabitEthernet" {
    uses config-interface-mvrp-grouping;
  }

  augment "/ios:native/ios:interface/ios:FiveGigabitEthernet" {
    uses config-interface-mvrp-grouping;
  }

  augment "/ios:native/ios:interface/ios:AppGigabitEthernet" {
    uses config-interface-mvrp-grouping;
  }

  augment "/ios:native/ios:interface/ios:TwentyFiveGigE" {
    uses config-interface-mvrp-grouping;
  }

  augment "/ios:native/ios:interface/ios:HundredGigE" {
    uses config-interface-mvrp-grouping;
  }

  augment "/ios:native/ios:interface/ios:Port-channel" {
    uses config-interface-mvrp-grouping;
  }
}
