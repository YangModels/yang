module Cisco-IOS-XE-wireless-rogue-authz-rpc {
  yang-version 1.1;
  namespace "http://cisco.com/ns/yang/Cisco-IOS-XE-wireless-rogue-authz-rpc";
  prefix wireless-rogue-authz-rpc;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for
     Wireless Rogue Authz Remote Control Procedures.
     Copyright (c) 2024 by Cisco Systems, Inc.
     All rights reserved.";

  revision 2025-03-01 {
    description
      "Initial revision";
    reference
      "1.0.0";
    cisco-semver:module-version "1.0.0";
  }

  grouping client-allow-list-export {
    description
      "Rogue Authz Client Allow list Export";
    leaf filename {
      type string {
        length "0..255";
      }
      mandatory true;
      description
        "Client Allow list export filename with csv extension";
    }
  }

  grouping ap-allow-list-export {
    description
      "Rogue Authz Access Point Allow list Export";
    leaf filename {
      type string {
        length "0..255";
      }
      mandatory true;
      description
        "Access Point Allow list export filename with csv extension";
    }
  }

  rpc clear-client-allow-list {
    description
      "Rogue Authz Clear Client Allow list entries Remote Control Procedure";
  }

  rpc clear-ap-allow-list {
    description
      "Rogue Authz Clear Access Point Allow list entries Remote Control Procedure";
  }

  rpc client-allow-list-export {
    description
      "Rogue Authz Export Client Allow list Remote Control Procedure";
    input {
      uses wireless-rogue-authz-rpc:client-allow-list-export;
    }
  }

  rpc ap-allow-list-export {
    description
      "Rogue Authz Export Access Point Allow list Remote Control Procedure";
    input {
      uses wireless-rogue-authz-rpc:ap-allow-list-export;
    }
  }
}
