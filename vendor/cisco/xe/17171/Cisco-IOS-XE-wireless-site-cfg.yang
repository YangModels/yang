module Cisco-IOS-XE-wireless-site-cfg {
  yang-version 1.1;
  namespace "http://cisco.com/ns/yang/Cisco-IOS-XE-wireless-site-cfg";
  prefix wireless-site-cfg;

  import Cisco-IOS-XE-wireless-ap-types {
    prefix wireless-ap-types;
  }
  import Cisco-IOS-XE-wireless-enum-types {
    prefix wireless-enum-types;
  }
  import Cisco-IOS-XE-wireless-general-cfg {
    prefix wireless-general-cfg;
  }
  import Cisco-IOS-XE-wireless-types {
    prefix wireless-types;
  }
  import Cisco-IOS-XE-wireless-wlan-cfg {
    prefix wireless-wlan-cfg;
  }
  import ietf-inet-types {
    prefix inet;
  }
  import ietf-yang-types {
    prefix yang;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "Model for managing site configurations
     Copyright (c) 2016-2023 by Cisco Systems, Inc.
     All rights reserved.";

  revision 2025-03-01 {
    description
      "- Added support for AP static PMTU
       - Added length constraint for AP packet capture profile
       - Added must constraints for priming profile controller names and IPs";
    reference
      "15.0.0";
    cisco-semver:module-version "15.0.0";
  }
  revision 2024-11-01 {
    description
      "- Added support for AP to Spaces connection config
       - Added AP profile RLAN fast switching related configuration
       - Added AP onboarding config";
    reference
      "14.1.0";
    cisco-semver:module-version "14.1.0";
  }
  revision 2024-07-01 {
    description
      "- Added support for height, height uncertainty and height type for priming profile";
    reference
      "14.0.0";
    cisco-semver:module-version "14.0.0";
  }
  revision 2024-03-01 {
    description
      "- Added support for CAPWAP message aggregation
       - Added support for Accelerometer sensor";
    reference
      "13.0.0";
    cisco-semver:module-version "13.0.0";
  }
  revision 2023-11-01 {
    description
      "- Added support for AP deployment mode config
       - Added support to configure network spectrum interface ports
       - Updated BSSID neighbor stats frequency default value and configuration range";
    reference
      "12.0.0";
    cisco-semver:module-version "12.0.0";
  }
  revision 2023-07-01 {
    description
      "- Added support for kernel coredump configuration
       - Added support for ap location configuration
       - Flex profile name in site is allowed when it's flex site";
    reference
      "11.1.0";
    cisco-semver:module-version "11.1.0";
  }
  revision 2022-11-01 {
    description
      "- Update yang-version to 1.1
       - Added support for telemetry exclusion configuration
       - Added AP priming profile configuration
       - Added support for AP pressure sensor configuration
       - Added site load configuration";
    reference
      "11.0.0";
    cisco-semver:module-version "11.0.0";
  }
  revision 2022-03-01 {
    description
      "- Added support for BLE configuration
       - Added AP sensor configuration
       - Added AP power profile and calendar profile configuration under AP profile
       - Added a limit for the maximum number of clients allowed on an AP";
    reference
      "10.0.0";
    cisco-semver:module-version "10.0.0";
  }
  revision 2021-11-01 {
    description
      "- Added radio statistics monitor configuration";
    reference
      "9.1.0";
    cisco-semver:module-version "9.1.0";
  }
  revision 2021-07-01 {
    description
      "- Added AP user management password constraints
       - Added support to enable AP DHCP broadcast in fabric configuration
       - Added option to configure IPv4 multicast group for AP in fabric configuration
       - Added option to configure country in AP profile";
    reference
      "9.0.0";
    cisco-semver:module-version "9.0.0";
  }
  revision 2021-03-01 {
    description
      "- Add ASCII 32-126 and leading/trailing spaces restriction for AP profile name and site tag name
       - Added support for AP stats
       - Added support for Office Extended AP configuration
       - Added support DTLS cipher suite server preference AP configuration";
    reference
      "8.0.0";
    cisco-semver:module-version "8.0.0";
  }
  revision 2020-11-01 {
    description
      "- Added AWIPS Forensic configuration
       - Added support for antenna monitoring configuration";
    reference
      "7.4.0";
    cisco-semver:module-version "7.4.0";
  }
  revision 2020-07-01 {
    description
      "- Added support for traffic distribution stats configuration
       - Added AP DHCP fallback option
       - Added obsolete status for LED flash configuration";
    reference
      "7.3.0";
    cisco-semver:module-version "7.3.0";
  }
  revision 2020-03-01 {
    description
      "- Deprecated old IOS BLE model
       - CAPWAP window size configuration
       - Added fabric config support for AP ARP caching
       - Added support for AP proxy";
    reference
      "7.2.0";
    cisco-semver:module-version "7.2.0";
  }
  revision 2019-11-01 {
    description
      "- Added configuration to enable AWIPS
       - Added Accounting information
       - Added support for IOX application hosting on APs
       - Added support for Auxiliary Client Interface on APs
       - Added support for BSSID stats configuration
       - Add public-ip-discovery and private-ip-discovery
         flag under AP config profile
       - Added AP LED flash mode and duration timer configuration
       - Added support for BSSID neighbor stats configuration";
    reference
      "7.1.0";
    cisco-semver:module-version "7.1.0";
  }
  revision 2019-09-20 {
    description
      "- Added obsolete status for Lawful Interception";
    reference
      "7.0.0";
    cisco-semver:module-version "7.0.0";
  }
  revision 2019-05-01 {
    description
      "- Removal of unused container related to Remote LAN port entry.
       - Add GAS rate limiting setting for Hotspot 2.0
       - Add NTP server information to be used by AP
       - Added client RSSI stats configuration
       - Add constraint check to image download profile name
       - Added semantic version
       - Added obsolete status for NTP server attribute";
    reference
      "6.0.0";
    cisco-semver:module-version "6.0.0";
  }
  revision 2019-03-13 {
    description
      "- Removed master AP list config under site tag config
       - Add DHCP server configuration
       - Removal of unused leaves
       - Cleaned up spelling errors in descriptions
       - Removal of unused leaves related to AP config profile
       - Removal of unused container related to Remote LAN port entry
       - Cleaned up descriptions
       - Making sure configured structure and structure send on protocol
         are aligned for AP profile
       - Restrict password type options available for local user
         under AP capture profile
       - Removed CAPWAP window size configuration from AP join profile.";
    reference
      "5.0.0";
    cisco-semver:module-version "5.0.0";
  }
  revision 2018-06-15 {
    description
      "AIRsense feature renamed to Intelligent Capture";
    reference
      "4.0.0";
    cisco-semver:module-version "4.0.0";
  }
  revision 2018-03-21 {
    description
      "Leaf removal and default changes";
    reference
      "3.0.0";
    cisco-semver:module-version "3.0.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  grouping site-tag-config {
    description
      "This structure stores the site tag configurations for an AP";
    leaf site-tag-name {
      type string {
        pattern '[!-~]([ -~]*[!-~])?';
      }
      description
        "Each entry represents a conceptual row in cLSiteTagConfigTable and corresponds to an Site Tag in a Elastic Wireless Controller.";
    }
    leaf description {
      type string;
      default "";
      description
        "Description of the Site Tag";
    }
    leaf flex-profile {
      when "../is-local-site = 'false'";
      type string;
      default "default-flex-profile";
      description
        "The flex profile which is part of the Site tag";
    }
    leaf ap-join-profile {
      type string;
      default "default-ap-profile";
      description
        "The Ap Join profile which is part of the Site tag";
    }
    leaf is-local-site {
      type boolean;
      default "true";
      description
        "This parameter is set to enable local site";
    }
    leaf fabric-control-plane-name {
      type string;
      description
        "Fabric Control Plane Name";
    }
    leaf image-download-profile-name {
      type string;
      must "(../image-download-profile-name = 'default')" {
        error-message "image download profile name should be default";
        error-app-tag "must-violation";
      }
      default "default";
      description
        "Image Download Profile Name";
    }
    leaf arp-caching {
      type boolean;
      default "true";
      description
        "Enable or disable AP ARP caching";
    }
    leaf dhcp-bcast {
      type boolean;
      default "false";
      description
        "Enable or disable fabric AP DHCP broadcast";
    }
    leaf fabric-mcast-ipv4-addr {
      type inet:ipv4-address;
      must "(../fabric-mcast-ipv4-addr = '0.0.0.0') or
            starts-with(../fabric-mcast-ipv4-addr, '224.') or starts-with(../fabric-mcast-ipv4-addr, '225.') or
            starts-with(../fabric-mcast-ipv4-addr, '226.') or starts-with(../fabric-mcast-ipv4-addr, '227.') or
            starts-with(../fabric-mcast-ipv4-addr, '228.') or starts-with(../fabric-mcast-ipv4-addr, '229.') or
            starts-with(../fabric-mcast-ipv4-addr, '230.') or starts-with(../fabric-mcast-ipv4-addr, '231.') or
            starts-with(../fabric-mcast-ipv4-addr, '232.') or starts-with(../fabric-mcast-ipv4-addr, '233.') or
            starts-with(../fabric-mcast-ipv4-addr, '234.') or starts-with(../fabric-mcast-ipv4-addr, '235.') or
            starts-with(../fabric-mcast-ipv4-addr, '236.') or starts-with(../fabric-mcast-ipv4-addr, '237.') or
            starts-with(../fabric-mcast-ipv4-addr, '238.') or starts-with(../fabric-mcast-ipv4-addr, '239.')" {
        error-message "Fabric multicast group IPv4 address must be in range 224.0.0.0-239.255.255.255 or 0.0.0.0";
        error-app-tag "must-violation";
      }
      default "232.255.255.1";
      description
        "Fabric multicast group IPv4 address";
    }
    leaf load {
      type uint16 {
        range "0 .. 1000";
      }
      default "0";
      description
        "Estimate of the relative load contributed by the site. AP count can be used as an approximation.";
    }
  }

  grouping halo-ble {
    description
      "BLE global configuration.It lists the ibeacon's identification number and attenuation value which is common to HALO enabled AP's that have joined the controller.";
    leaf beacon-id {
      type uint8 {
        range "0 .. 4";
      }
      description
        "BLE ibeacon ID for which global BLE configurations to be applied.";
    }
    leaf txpower {
      type uint8 {
        range "0 .. 52";
      }
      default "0";
      description
        "TX power of particular ibeacon for HALO enabled APs that have joined the controller.The TX power is based on size of proximity zone needed.";
    }
    leaf enabled {
      type boolean;
      default "false";
      description
        "The status of the BLE beacons. enable(1) - enable the BLE beacon disable(2) - disable the BLE beacon.";
    }
    leaf uuid {
      type string;
      default "00000000-0000-0000-0000-000000000000";
      description
        "The UUID (universally unique identifier) which is a 128-bit value";
    }
  }

  grouping st-icap-full-trace-client {
    description
      "Stores the client MAC address used in the ICap full packet trace subscription client filter";
    leaf addr {
      type yang:mac-address;
      description
        "MAC address";
    }
  }

  grouping st-icap-partial-trace-client {
    description
      "Stores the client MAC address used in the ICap partial packet trace subscription client filter";
    leaf addr {
      type yang:mac-address;
      description
        "MAC address";
    }
  }

  grouping st-icap-anomaly-det-client {
    description
      "Stores the client MAC address used in the ICap anomaly detection subscription client filter";
    leaf addr {
      type yang:mac-address;
      description
        "MAC address";
    }
  }

  grouping st-icap-client-stats-client {
    description
      "Stores the client MAC address used in the ICap client statistics subscription client filter";
    leaf addr {
      type yang:mac-address;
      description
        "MAC address";
    }
  }

  grouping st-icap-client-exclude-cfg {
    description
      "WLAN profile for which telemetry data to be filtered out";
    leaf wlan-profile {
      type string;
      description
        "WLAN profile";
    }
  }

  grouping st-qosmap-dscp-to-up {
    description
      "QoS Map DSCP to User Priority mapping";
    leaf dscp-low {
      type uint8 {
        range "0 .. 63";
      }
      default "0";
      description
        "DSCP range lower boundary";
    }
    leaf dscp-high {
      type uint8 {
        range "0 .. 63";
      }
      default "0";
      description
        "DSCP range upper boundary";
    }
    leaf up {
      type uint8 {
        range "0 .. 7";
      }
      description
        "User Priority";
    }
    leaf up-to-dscp {
      type uint8 {
        range "0 .. 63";
      }
      default "0";
      description
        "AP upstream traffic User Priority to DSCP mapping";
    }
  }

  grouping st-qosmap-dscp-to-up-exception {
    description
      "QoS Map DSCP to User Priority mapping exception";
    leaf dscp {
      type uint8 {
        range "0 .. 63";
      }
      description
        "DSCP to be mapped to User Priority";
    }
    leaf up {
      type uint8 {
        range "0 .. 7";
      }
      default "0";
      description
        "User Priority";
    }
  }

  grouping st-ap-profile-calendar-cfg {
    description
      "Calendar profile configuration for AP profile";
    leaf prof-name {
      type string {
        length "1..32" {
          error-message "Calendar profile name should not be greater than 32 characters";
          error-app-tag "must-violation";
        }
        pattern '[!-~]([ -~]*[!-~])?' {
          error-message "Calendar profile name must use ASCII 32-126 characters and must not contain leading or trailing spaces";
          error-app-tag "pattern-violation";
        }
      }
      must '(/wireless-wlan-cfg:wlan-cfg-data/wireless-wlan-cfg:calendar-profile-configs/wireless-wlan-cfg:calendar-profile-config[wireless-wlan-cfg:profile-name = current()])' {
        error-message "A calendar profile with the same name as configured under the AP profile must exist";
        error-app-tag "must-violation";
      }
      description
        "Calendar profile name";
    }
    container cal-ap-prof-pp-cfg {
      description
        "Power profile configuration";
      uses wireless-ap-types:ap-prof-power-profile-cfg;
    }
  }

  grouping ap-cfg-profile {
    description
      "The ap join profile configurations";
    leaf profile-name {
      type string {
        pattern '[!-~]([ -~]*[!-~])?';
      }
      description
        "The ap configuration profile name";
    }
    leaf description {
      type string;
      default "";
      description
        "Description for the ap configuration profile";
    }
    leaf ble-beacon-interval {
      type uint8 {
        range "1 .. 10";
      }
      default "1";
      description
        "The BLE beacon interval for the AP";
    }
    leaf ble-beacon-advpwr {
      type uint8 {
        range "40 .. 100";
      }
      default "59";
      description
        "The BLE beacon power";
    }
    leaf data-encryption-flag {
      type boolean;
      description
        "The data encryption status of AP";
    }
    leaf ap-packet-capture-profile {
      type string {
        length "0..32";
      }
      default "";
      description
        "Profile name for packet capture";
    }
    leaf ap-trace-profile {
      type string;
      default "";
      description
        "AP trace profile name applied on the AP";
    }
    container stats-timer {
      description
        "This object specifies the stats timer for the AP";
      uses wireless-ap-types:st-stats-timer;
    }
    container led-state {
      description
        "The LED state of all the access points should be enabled or disabled.";
      uses wireless-ap-types:st-led-state;
    }
    container link-latency {
      description
        "The link auditing options";
      uses wireless-ap-types:st-link-latency;
    }
    container jumbo-mtu {
      description
        "True if jumbo mtu is enabled for the AP";
      uses wireless-ap-types:st-jumbo-mtu;
    }
    container ap-mode {
      description
        "Mode of operation of the AP";
      uses wireless-ap-types:st-mode;
    }
    container poe {
      description
        "Power over ethernet configurations";
      uses wireless-ap-types:st-poe-cfg;
    }
    container device-mgmt {
      description
        "Device management related configurations";
      uses wireless-ap-types:st-device-mgmt-cfg;
    }
    container user-mgmt {
      description
        "User management related configuration";
      uses wireless-ap-types:st-user-mgmt-cfg;
    }
    container tcp-mss {
      description
        "IPV4 tcp mss related configurations";
      uses wireless-ap-types:st-tcp-mss-cfg;
    }
    container tunnel {
      description
        "The global capwap prefer-mode";
      uses wireless-ap-types:st-tunnel;
    }
    container capwap-timer {
      description
        "CAPWAP timer related configurations";
      uses wireless-ap-types:st-capwap-timer-cfg;
    }
    container retransmit-timer {
      description
        "The retransmit timer";
      uses wireless-ap-types:st-capwap-retransmit-timer-cfg;
    }
    container login-credentials {
      description
        "The Global AP 802.1x Supplicant Authentication login credentials";
      uses wireless-ap-types:st-login-credentials-cfg;
    }
    container dot1x-eap-type-info {
      description
        "Global AP 802.1x EAP type info";
      uses wireless-ap-types:st-dot1x-eap-auth-info;
    }
    container lsc-ap-auth-type-info {
      description
        "Global AP 802.1x LSC AP auth type info";
      uses wireless-ap-types:st-lsc-ap-auth-type-info;
    }
    container coredump {
      description
        "AP core dump related configurations";
      uses wireless-ap-types:st-coredump-cfg;
    }
    container syslog {
      description
        "AP sys log related configurations";
      uses wireless-ap-types:st-syslog-facility-cfg;
    }
    container backup-controllers {
      must "not((string-length(primary-controller-name) = 0) and (primary-controller-ip != '0.0.0.0')) " {
        error-message "Primary Controller IP can not be configured without Primary controller name";
        error-app-tag "must-violation";
      }
      must "not((string-length(secondary-controller-name) = 0) and (secondary-controller-ip != '0.0.0.0')) " {
        error-message "Secondary Controller IP can not be configured without Secondary controller name";
        error-app-tag "must-violation";
      }
      description
        "Backup controller configuration for the AP";
      uses wireless-ap-types:st-backup-controllers-cfg;
    }
    container hyperlocation {
      description
        "Hyperlocation configuration for the AP";
      uses wireless-ap-types:st-hyperlocation;
    }
    container rogue-detection {
      description
        "Rogue detection related parameters";
      uses wireless-ap-types:st-rogue-params;
    }
    container lag-info {
      description
        "The AP-lag status of all the access points in the profile whether enabled or disabled.";
      uses wireless-ap-types:st-capwap-lag-info;
    }
    container tftp-down-grade {
      description
        "Tftp downgrade related configurations";
      uses wireless-ap-types:st-tftp-downgrade;
    }
    container traffic-limit {
      description
        "The maximum dot1x session limit for the AP";
      uses wireless-ap-types:st-traffic-limit-cfg;
    }
    container cdp {
      description
        "True, if cdp is enabled for the AP";
      uses wireless-ap-types:st-cdp;
    }
    leaf ntp-server {
      type inet:ip-address;
      default "0.0.0.0";
      status obsolete;
      description
        "NTP server IP address";
    }
    container capwap-window {
      description
        "CAPWAP transport window size for the AP";
      uses wireless-ap-types:st-capwap-window;
    }
    container mesh {
      description
        "Mesh related config the AP";
      uses wireless-ap-types:st-mesh-cfg;
    }
    container reporting-interval {
      description
        "Interval at which AP should send client stats";
      uses wireless-ap-types:st-report-interval;
    }
    container ext-module {
      description
        "AP External Module related configurations";
      uses wireless-ap-types:st-ext-module-cfg;
    }
    container icap {
      description
        "Configuration of ICap subscriptions";
      uses wireless-ap-types:st-icap;
    }
    container lawful-interception {
      status obsolete;
      description
        "Lawful Interception related configurations";
      uses wireless-ap-types:st-lawful-interception-cfg;
    }
    container persistent-ssid-broadcast {
      description
        "True if persistent SSID broadcast is enabled on the AP";
      uses wireless-ap-types:st-persistent-ssid-broadcast-cfg;
    }
    container dhcp-server {
      description
        "DHCP server related configuration";
      uses wireless-ap-types:st-dhcp-server-cfg;
    }
    container usb-module-status {
      description
        "Status of USB configuration if disabled/enabled";
      uses wireless-ap-types:st-usb-module-cfg;
    }
    container halo-ble-entries {
      status deprecated;
      description
        "Encompasses the halo ble configurations";
      list halo-ble-entry {
        key "beacon-id";
        description
          "Encompasses the halo ble configurations";
        uses wireless-site-cfg:halo-ble;
      }
    }
    container icap-full-packet-trace-client-mac-address-entries {
      description
        "Selects the clients for which to collect traces, by client MAC address.";
      list icap-full-packet-trace-client-mac-address-entry {
        key "addr";
        description
          "Specifies the client MAC address.";
        uses wireless-site-cfg:st-icap-full-trace-client;
      }
    }
    container icap-partial-packet-trace-client-mac-address-entries {
      description
        "Selects the clients for which to collect traces, by client MAC address.";
      list icap-partial-packet-trace-client-mac-address-entry {
        key "addr";
        description
          "The client MAC address.";
        uses wireless-site-cfg:st-icap-partial-trace-client;
      }
    }
    container icap-anomaly-detection-client-mac-address-entries {
      description
        "Selects the clients for which to collect traces, by client MAC address.";
      list icap-anomaly-detection-client-mac-address-entry {
        key "addr";
        description
          "The client MAC address.";
        uses wireless-site-cfg:st-icap-anomaly-det-client;
      }
    }
    container icap-client-statistics-client-mac-address-entries {
      description
        "Selects the clients for which to collect statistics, by client MAC address.";
      list icap-client-statistics-client-mac-address-entry {
        key "addr";
        description
          "The client MAC address.";
        uses wireless-site-cfg:st-icap-client-stats-client;
      }
    }
    container gas-rate-limit {
      description
        "Contains GAS rate limiting related configurations";
      uses wireless-ap-types:st-gas-rate-limit-cfg;
    }
    container qosmap {
      description
        "QoS Map configuration";
      uses wireless-ap-types:st-qosmap-cfg;
    }
    container qosmap-dscp-to-ups {
      description
        "QoS Map - DSCP tp UP (User Priority) mapping ranges";
      list qosmap-dscp-to-up {
        key "up";
        description
          "QoS Map - DSCP tp UP (User Priority) mapping range";
        uses wireless-site-cfg:st-qosmap-dscp-to-up;
      }
    }
    container qosmap-dscp-to-up-exceptions {
      description
        "QoS Map - DSCP tp UP (User Priority) mapping exceptions";
      list qosmap-dscp-to-up-exception {
        key "dscp";
        description
          "QoS Map - DSCP tp UP (User Priority) mapping exception";
        uses wireless-site-cfg:st-qosmap-dscp-to-up-exception;
      }
    }
    container client-rssi {
      description
        "Configuration of Client RSSI statistics reporting";
      uses wireless-ap-types:st-client-rssi-cfg;
    }
    container ntp-server-info {
      must "(ntp-address != '255.255.255.0') and (ntp-address != '255.255.0.0') and (ntp-address != '255.0.0.0')" {
        error-message "Invalid IPv4 host address provided";
        error-app-tag "must-violation";
      }
      must "ntp-address != '255.255.255.255'" {
        error-message "Broadcast IPv4 address is invalid";
        error-app-tag "must-violation";
      }
      must "not(starts-with(ntp-address, '127.'))" {
        error-message "Loopback IPv4 address is invalid";
        error-app-tag "must-violation";
      }
      must "not(starts-with(ntp-address, '224.')) and not(starts-with(ntp-address, '225.')) and not(starts-with(ntp-address, '226.')) and not(starts-with(ntp-address, '227.')) and not(starts-with(ntp-address, '228.')) and not(starts-with(ntp-address, '229.')) and not(starts-with(ntp-address, '230.')) and not(starts-with(ntp-address, '231.')) and not(starts-with(ntp-address, '232.')) and not(starts-with(ntp-address, '233.')) and not(starts-with(ntp-address, '234.')) and not(starts-with(ntp-address, '235.')) and not(starts-with(ntp-address, '236.')) and not(starts-with(ntp-address, '237.')) and not(starts-with(ntp-address, '238.')) and not(starts-with(ntp-address, '239.'))" {
        error-message "Multicast IPv4 address is invalid";
        error-app-tag "must-violation";
      }
      must "not(contains(substring(ntp-address, 1, 4), 'fe80'))" {
        error-message "Link-local IPv6 address is invalid";
        error-app-tag "must-violation";
      }
      must "not(contains(substring(ntp-address, 1, 4), 'fec0'))" {
        error-message "Site-local IPv6 address is invalid";
        error-app-tag "must-violation";
      }
      description
        "NTP server information to be used by AP";
      uses wireless-ap-types:st-ntp-server-info-cfg;
    }
    leaf awips-enabled {
      type boolean;
      default "false";
      description
        "Flag to enable AWIPS";
    }
    container accounting {
      description
        "AP Accounting information";
      uses wireless-ap-types:st-accounting;
    }
    container apphost {
      description
        "Configuration of IOX application hosting";
      uses wireless-ap-types:st-apphost-cfg;
    }
    container aux-client-interface {
      description
        "Configuration of Auxiliary Client Interface";
      uses wireless-ap-types:st-aux-client-interface-cfg;
    }
    container proxy {
      description
        "Proxy configuration provisioned to AP";
      uses wireless-types:st-ap-proxy-cfg;
    }
    leaf grpc-enable {
      type boolean;
      default "false";
      description
        "Enable GRPC server on AP";
    }
    leaf bssid-enable-stats {
      type boolean;
      default "false";
      description
        "Flag to enable BSSID stats on AP";
    }
    leaf bssid-stats-frequency {
      type uint32 {
        range "1 .. 180";
      }
      units "seconds";
      default "30";
      description
        "Time frequency on AP to send BSSID stats";
    }
    leaf private-ip-discovery {
      type boolean;
      default "true";
      description
        "Discovery Response from private IP is enabled or disabled";
    }
    leaf public-ip-discovery {
      type boolean;
      default "true";
      description
        "Discovery Response from public IP is enabled or disabled";
    }
    container led-flash {
      status obsolete;
      description
        "LED flash mode and timer configuration of all the access points";
      uses wireless-ap-types:st-led-flash;
    }
    leaf bssid-neighbor-stats-enable {
      type boolean;
      default "false";
      description
        "Flag to enable BSSID neighbor statistics on AP";
    }
    leaf bssid-neighbor-stats-frequency {
      type uint32 {
        range "30 .. 600";
      }
      units "seconds";
      default "180";
      description
        "Time interval between consecutive BSSID neighbor stats update send by the AP.The permissible range is updated from 1..180 to 30..600 and default value is updated from 30 to 180 to prevent high CPU utilization due to processing of
         multiple BSSID neighbor reports per sec";
    }
    container traffic-distribution {
      description
        "Traffic Distribution Statistics Configuration";
      uses wireless-ap-types:st-traffic-distribution-stats;
    }
    container dhcp-fallback {
      description
        "Allow AP to fallback to DHCP if it can not join controller via Static IP";
      uses wireless-ap-types:st-dhcp-fallback;
    }
    container oeap {
      description
        "Office Extended AP configuration";
      uses wireless-ap-types:st-oeap;
    }
    leaf awips-forensic-enabled {
      type boolean;
      must "(../awips-forensic-enabled = 'false') or ((../awips-forensic-enabled = 'true') and (../awips-enabled = 'true'))" {
        error-message "Forensic capture cannot be enabled without AWIPS";
        error-app-tag "must-violation";
      }
      default "false";
      description
        "Flag to enable AWIPS forensic";
    }
    container antenna-monitor {
      description
        "Per AP profile antenna monitoring configuration";
      uses wireless-ap-types:st-antenna-mon-cfg;
    }
    container stats-monitor {
      description
        "Per AP profile ap stats configuration";
      uses wireless-ap-types:ap-stats-mon-cfg;
    }
    container ap-dtls-config {
      description
        "Per AP profile AP DTLS configuration";
      uses wireless-ap-types:st-ap-dtls-config;
    }
    container ap-country {
      description
        "Per AP profile AP country configuration";
      uses wireless-ap-types:st-ap-prof-country-cfg;
    }
    container ap-tz-config {
      description
        "AP timezone configuration";
      uses wireless-ap-types:st-ap-timezone-cfg-data;
    }
    container radio-stats-monitor {
      description
        "Per AP profile AP radio statistics monitoring configuration";
      uses wireless-ap-types:ap-radio-mon-cfg;
    }
    container ap-sensor-cfgs {
      description
        "Configure AP sensor attributes, by sensor type";
      list ap-sensor-cfg {
        key "sensor-type";
        description
          "Specifies AP sensor configuration";
        uses wireless-site-cfg:st-ap-sensor-cfg;
      }
    }
    container ble {
      must "(/wireless-general-cfg:general-cfg-data/wireless-general-cfg:mewlc-config/wireless-general-cfg:mewlc-platform = 'false') or
                   (../ble/scan-state = 'false')" {
        error-message "BLE feature is not supported on EWC platform";
        error-app-tag "must-violation";
      }
      description
        "Per AP profile BLE configuration";
      uses wireless-ap-types:st-ble-cfg;
    }
    container ap-prof-pp-cfg {
      description
        "Power profile configuration per AP profile";
      uses wireless-ap-types:ap-prof-power-profile-cfg;
    }
    container client-limit {
      description
        "Maximum client limit per AP configuration";
      uses wireless-ap-types:st-ap-max-clients-cfg;
    }
    container calendar-cfgs {
      description
        "Calendar profiles configuration for AP profile";
      list calendar-cfg {
        key "prof-name";
        max-elements 5;
        description
          "Calendar profile entry for AP profile";
        uses wireless-site-cfg:st-ap-profile-calendar-cfg;
      }
    }
    container press-sens-config {
      description
        "Configure AP pressure sensor";
      uses wireless-ap-types:st-ap-press-sens-cfg;
    }
    container icap-client-exclude-cfgs {
      description
        "Selects the WLAN profile for which telemetry data to be filtered out";
      list icap-client-exclude-cfg {
        key "wlan-profile";
        description
          "The WLAN profile";
        uses wireless-site-cfg:st-icap-client-exclude-cfg;
      }
    }
    container ap-location {
      description
        "location related configuration";
      uses wireless-ap-types:st-ap-cfg-profile-loc;
    }
    container kernel-coredump {
      description
        "AP kernel core dump related configurations";
      uses wireless-ap-types:st-kernel-coredump-cfg;
    }
    container deployment-mode {
      description
        "AP dual mode deployment mode";
      uses wireless-ap-types:st-ap-deployment-mode-cfg;
    }
    container nsi-ports-cfg {
      description
        "AP network spectrum interface ports related configurations";
      uses wireless-ap-types:st-ap-nsi-ports-cfg;
    }
    container aggregation {
      description
        "CAPWAP message aggregation configuration on controller";
      uses wireless-ap-types:st-ap-capwap-aggregation-cfg;
    }
    container accel-sensor {
      description
        "Accelerometer sensor configuration on controller";
      uses wireless-ap-types:st-ap-acc-sensor-cfg;
    }
    container spaces-conn-cfg {
      description
        "AP to Spaces connection configuration";
      uses wireless-ap-types:st-spaces-conn-cfg;
    }
    container rlan-cfg {
      description
        "AP profile RLAN fast switching configurations";
      uses wireless-ap-types:st-ap-prof-rlan-cfg;
    }
    container onboard-cfg {
      description
        "AP onboarding configuration";
      uses wireless-ap-types:st-ap-onboard-cfg;
    }
    container static-mtu {
      description
        "AP static PMTU configuration";
      uses wireless-ap-types:st-ap-pmtu;
    }
  }

  grouping ap-packet-capture-profile {
    description
      "The packet capture profile configurations of an AP";
    leaf profile-name {
      type string;
      description
        "The profile name of the packet capture profile";
    }
    leaf description {
      type string;
      description
        "Description of the packet capture profile";
    }
    leaf buffer-size {
      type uint16 {
        range "1024 .. 4096";
      }
      default "2048";
      description
        "The size of the buffer Access Point should use to copy the captured packets for client and dump it to the FTP server. Default value is 2048 kilobytes";
    }
    leaf duration {
      type uint16 {
        range "1 .. 60";
      }
      default "10";
      description
        "Duration for which the Access Point should capture packets for specified client. Default value is 10";
    }
    leaf truncate-len {
      type uint16 {
        range "0 .. 1500";
      }
      default "0";
      description
        "Length of the packet after truncation while capturing packets on the Access Point. Default value is 0 which indicates captured packet should contain the full payload length";
    }
    leaf ftp-server-ip {
      type inet:ip-address;
      default "0.0.0.0";
      description
        "The IP Address of the FTP server. Access Point will dump the captured packets to a file in this ftp server";
    }
    leaf ftp-path {
      type string;
      default "";
      description
        "The directory path in the ftp server for storing the file which contains the captured packets in the Access Point.";
    }
    leaf ftp-username {
      type string;
      default "";
      description
        "The username to login into the ftp server in order to transfer the captured packets from the Access Point.";
    }
    leaf ftp-password {
      type string;
      default "";
      description
        "The password to login into the ftp server in order to transfer the captured packets from the Access Point.";
    }
    leaf ftp-password-type {
      type wireless-enum-types:crypt-type;
      must "((current() = 'clear') or (current() = 'aes'))" {
        error-message "Password type should be either clear text or AES encryption";
        error-app-tag "must-violation";
      }
      default "clear";
      description
        "This object specifies the password type to login into the ftp server in order to transfer the captured packets from the Access Point.";
    }
    leaf classifier-control {
      type boolean;
      default "true";
      description
        "The filters for 802.11 control packets, while capturing packets on the Access Point. A value of 'true' indicates 802.11 control packets should be captured. A value of 'false' indicates 802.11 control packets should not be captured. Default value is true";
    }
    leaf classifier-management {
      type boolean;
      default "true";
      description
        "The filters for 802.11 Management packets, while capturing packets on the Access Point. A value of 'true' indicates 802.11 Management packets should be captured. A value of 'false' indicates 802.11 Management packets should not be captured. Default value is true";
    }
    leaf classifier-data {
      type boolean;
      default "false";
      description
        "The filters for 802.11 Data packets, while capturing packets on the Access Point. A value of 'true' indicates 802.11 Data packets should be captured. A value of 'false' indicates 802.11 Data packets should not be captured. Default value is false";
    }
    leaf classifier-dot1x {
      type boolean;
      default "false";
      description
        "The filters for 802.11 Dot1x packets, while capturing packets on the Access Point. A value of 'true' indicates 802.11 Dot1x packets should be captured. A value of 'false' indicates 802.11 Dot1x packets should not be captured. Default value is false";
    }
    leaf classifier-arp {
      type boolean;
      default "false";
      description
        "The filters for ARP packets while capturing packets on the Access Point. A value of 'true' indicates ARP packets should be captured. A value of 'false' indicates ARP packets should not be captured.Default value is false";
    }
    leaf classifier-iapp {
      type boolean;
      default "false";
      description
        "The filters for 802.11 IAPP packets, while capturing packets on the Access Point. A value of 'true' indicates IAPP packets should be captured. A value of 'false' indicates IAPP packets should not be captured. Default value is false";
    }
    leaf classifier-ip {
      type boolean;
      default "false";
      description
        "The filters for IP packets, while capturing packets on the Access Point. A value of ' true' indicates IP packets should be captured. A value of false' indicates IP packets should not be captured. Default value is false";
    }
    leaf classifier-tcp {
      type boolean;
      default "false";
      description
        "The filters for TCP packets while capturing packets on the Access Point. Value of 'true' indicates IP packets should be captured. Value of 'false' indicates IP packets should not be captured. Default value is false";
    }
    leaf classifier-tcp-port {
      type uint16 {
        range "0 .. 65535";
      }
      default "0";
      description
        "The filters for TCP packets, while capturing packets on the Access Point Value of 'true' indicates IP packets should be captured. Value of 'false' indicates IP packets should not be captured. Default value is false";
    }
    leaf classifier-udp {
      type boolean;
      default "false";
      description
        "The filters for TCP packets, while capturing packets on the Access Point. Value of 'true' indicates IP packets should be captured. Value of 'false' indicates IP packets should not be captured. Default value is fals";
    }
    leaf classifier-udp-port {
      type uint16 {
        range "0 .. 65535";
      }
      default "0";
      description
        "The filter value port number for UDP packets, while capturing packets on the Access Point. Default value is 0 which indicates all UDP packets should be captured";
    }
    leaf classifier-broadcast {
      type boolean;
      default "false";
      description
        "The filters for 802.11 Broadcast packets, while capturing packets on the Access Point. A value of 'true' indicates Broadcast packets should be captured.A value of 'false' indicates Broadcast packets should not be captured. Default value is false";
    }
    leaf classifier-multicast {
      type boolean;
      default "false";
      description
        "The filters for 802.11 Multicast packets, while capturing packets on the Access Point. A value of 'true' indicates Multicast packets should be captured. A value of 'false' indicates Multicast packets should not be captured. Default value is false";
    }
  }

  grouping ap-priming-profile {
    description
      "AP priming profile configuration";
    leaf profile-name {
      type string {
        length "1..32" {
          error-message "Priming profile name should not be greater than 32 characters";
          error-app-tag "must-violation";
        }
        pattern '[!-~]([ -~]*[!-~])?' {
          error-message "Priming profile name must use ASCII 32-126 characters and must not contain leading or trailing spaces";
          error-app-tag "pattern-violation";
        }
      }
      description
        "Priming profile name of the AP";
    }
    leaf description {
      type string;
      default "";
      description
        "Description of the AP priming profile";
    }
    leaf override-existing-priming {
      type boolean;
      default "false";
      description
        "Override current AP priming with priming profile";
    }
    leaf primary-wlc-name {
      type string;
      default "";
      description
        "Primary WLC name configuration of the AP";
    }
    leaf primary-wlc-ip {
      type inet:ip-address;
      must "(not((../primary-wlc-ip != '0.0.0.0') and (string-length(../primary-wlc-name) = 0)))" {
        error-message "Primary Controller IP can not be configured without Primary controller name";
        error-app-tag "must-violation";
      }
      default "0.0.0.0";
      description
        "Primary WLC IP configuration of the AP";
    }
    leaf secondary-wlc-name {
      type string;
      default "";
      description
        "Secondary WLC name configuration of the AP";
    }
    leaf secondary-wlc-ip {
      type inet:ip-address;
      must "(not((../secondary-wlc-ip != '0.0.0.0') and (string-length(../secondary-wlc-name) = 0)))" {
        error-message "Secondary Controller IP can not be configured without Secondary controller name";
        error-app-tag "must-violation";
      }
      default "0.0.0.0";
      description
        "Secondary WLC IP configuration of the AP";
    }
    leaf tertiary-wlc-name {
      type string;
      default "";
      description
        "Tertiary WLC name configuration of the AP";
    }
    leaf tertiary-wlc-ip {
      type inet:ip-address;
      must "(not((../tertiary-wlc-ip != '0.0.0.0') and (string-length(../tertiary-wlc-name) = 0)))" {
        error-message "Tertiary Controller IP can not be configured without Tertiary controller name";
        error-app-tag "must-violation";
      }
      default "0.0.0.0";
      description
        "Tertiary WLC IP configuration of the AP";
    }
    leaf height {
      type int16 {
        range "-100 .. 1000";
      }
      units "meters";
      default "0";
      description
        "AP AGL (Above Ground Level) height in meters in range -100..1000";
    }
    leaf height-uncertainty {
      type uint16 {
        range "1 .. 100";
      }
      units "meters";
      default "1";
      description
        "AP height uncertainty in meters in range 1..100";
    }
    leaf height-type {
      type wireless-enum-types:enm-geo-bulk-height-type;
      must "((../height-type = 'geo-afc-height-agl') or
            (../height-type = 'geo-afc-height-unknown' and ../height = 0 and ../height-uncertainty = 1))" {
        error-message
          "AP height type must be Above Ground Level (AGL) or
           when it is unknown, default height must be 0 and default height uncertainty must be 1";
        error-app-tag "must-violation";
      }
      default "geo-afc-height-unknown";
      description
        "AP geolocation height type";
    }
  }

  grouping ap-trace-profile {
    description
      "Trace profile configuration of the AP";
    leaf profile-name {
      type string;
      description
        "Trace profile name of the AP";
    }
    leaf description {
      type string;
      description
        "Description of the AP trace profile";
    }
    leaf ap-trace-client-console-log {
      type boolean;
      default "false";
      description
        "Flag to enable console logs at the AP";
    }
    leaf ap-trace-client-filter-arp {
      type boolean;
      default "false";
      description
        "Trace filter to enable client's ARP packets tracing at the AP";
    }
    leaf ap-trace-client-filter-assoc {
      type boolean;
      default "false";
      description
        "Trace filter to enable client's association packets tracing at the AP";
    }
    leaf ap-trace-client-filter-auth {
      type boolean;
      default "false";
      description
        "Trace filter to enable client's authentication packets at the AP";
    }
    leaf ap-trace-client-filter-dhcp {
      type boolean;
      default "false";
      description
        "Trace filter to enable client's DHCP packets tracing at the AP";
    }
    leaf ap-trace-client-filter-eap {
      type boolean;
      default "false";
      description
        "Trace filter to enable client's EAP packets tracing at the AP";
    }
    leaf ap-trace-client-filter-icmp {
      type boolean;
      default "false";
      description
        "Trace filter to enable client's ICMP packets tracing at the AP";
    }
    leaf ap-trace-client-filter-ndp {
      type boolean;
      default "false";
      description
        "Trace filter to enable client's NDP packets tracing at the AP";
    }
    leaf ap-trace-client-filter-probe {
      type boolean;
      default "false";
      description
        "Trace filter to enable client's probe packets tracing at the AP";
    }
  }

  grouping st-ap-sensor-cfg {
    description
      "AP sensor configuration";
    leaf sensor-type {
      type wireless-enum-types:enm-ap-sensor-type;
      description
        "Type of the sensor";
    }
    leaf config-state {
      type wireless-enum-types:enm-ap-sensor-state;
      default "sensor-disabled";
      description
        "Sensor config state";
    }
    leaf interval {
      type uint32 {
        range "5 .. 3600";
      }
      units "seconds";
      default "5";
      description
        "Sensor data collection sampling interval";
    }
  }

  container site-cfg-data {
    description
      "Yang model for site related config";
    container ap-cfg-profiles {
      description
        "Encompasses the ap config profile";
      list ap-cfg-profile {
        key "profile-name";
        description
          "List of AP config profiles";
        uses wireless-site-cfg:ap-cfg-profile;
      }
    }
    container ap-packet-capture-profiles {
      description
        "AP packet capture profile configuration";
      list ap-packet-capture-profile {
        key "profile-name";
        description
          "List of AP packet capture profiles";
        uses wireless-site-cfg:ap-packet-capture-profile;
      }
    }
    container ap-trace-profiles {
      description
        "AP trace profile configuration";
      list ap-trace-profile {
        key "profile-name";
        description
          "List of AP trace capture profiles";
        uses wireless-site-cfg:ap-trace-profile;
      }
    }
    container ap-priming-profiles {
      description
        "AP priming profile configuration";
      list ap-priming-profile {
        key "profile-name";
        description
          "List of AP priming profiles";
        uses wireless-site-cfg:ap-priming-profile;
      }
    }
    container site-tag-configs {
      description
        "Site tag configuration";
      list site-tag-config {
        key "site-tag-name";
        description
          "List of site tag configurations";
        uses wireless-site-cfg:site-tag-config;
      }
    }
  }
}
