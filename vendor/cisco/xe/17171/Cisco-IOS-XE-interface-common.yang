module Cisco-IOS-XE-interface-common {
  yang-version 1.1;
  namespace "http://cisco.com/ns/yang/Cisco-IOS-XE-interface-common";
  prefix ios-ifc;

  import cisco-semver {
    prefix cisco-semver;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Interfaces Common Yang model.
     Copyright (c) 2016-2020 by Cisco Systems, Inc.
     All rights reserved.";

  revision 2025-03-01 {
    description
      "- Added Bundle interface to obsolete list";
    cisco-semver:module-version "3.5.0";
  }
  revision 2024-11-01 {
    description
      "- Deprecate interface group and add new model of list";
    cisco-semver:module-version "3.4.0";
  }
  revision 2024-07-01 {
    description
      "- Add CEM interface range";
    cisco-semver:module-version "3.3.0";
  }
  revision 2023-07-01 {
    description
      "- Add Bundle interface type";
    cisco-semver:module-version "3.2.0";
  }
  revision 2022-11-01 {
    description
      "- Update yang-version to 1.1";
    cisco-semver:module-version "3.1.0";
  }
  revision 2022-03-01 {
    description
      "- Updated 'interface-deprecated-grouping' with missing interface nodes from 'interface-grouping'.
       - Updated 'interface-obsolete-grouping' with missing interface nodes from 'interface-grouping'.";
    cisco-semver:module-version "3.0.0";
  }
  revision 2021-07-01 {
    description
      "- Added L2LISP interface and subinterface";
    cisco-semver:module-version "2.1.0";
  }
  revision 2021-03-01 {
    description
      "- Added range for Loopback interface in interface-grouping";
    cisco-semver:module-version "2.0.0";
  }
  revision 2020-07-01 {
    description
      "- Added interface type MFR and serial-subinterface";
    cisco-semver:module-version "1.3.0";
  }
  revision 2020-03-01 {
    description
      "- Added Obsolete interface grouping for obsolete interfaces";
    cisco-semver:module-version "1.2.0";
  }
  revision 2019-11-01 {
    description
      "
       - Deprecating Async interface type";
    cisco-semver:module-version "1.1.0";
  }
  revision 2019-07-01 {
    description
      "- Establish semantic version baseline
       - Add BD-VIF interface";
    cisco-semver:module-version "1.0.0";
  }
  revision 2019-01-22 {
    description
      "Added leaf for App-hosting Gigabit Ethernet interface";
  }
  revision 2018-06-18 {
    description
      "Change passive-interface to 'leaf-list interface'";
  }
  revision 2018-02-08 {
    description
      "Add a type of Interface: Ethernet";
  }
  revision 2017-11-27 {
    description
      "Added Change 25GE name";
  }
  revision 2017-11-13 {
    description
      "Added leafs for FortyGigabitEthernet and HundredGigE interfaces";
  }
  revision 2017-09-15 {
    description
      "This revison has changes for the new 2gig interface addition";
  }
  revision 2017-08-16 {
    description
      "This revision has changes for new 5gig and 25gig interfaces addition";
  }
  revision 2017-03-04 {
    description
      "Changed LISP key type to string to support OC mapping";
  }
  revision 2017-02-07 {
    description
      "Initial revision";
  }

  grouping interface-grouping {
    choice interface-choice {
      leaf AppNav-Compress {
        description
          "Service-Context Virtual Interface Compress";
        type uint16;
      }
      leaf AppNav-UnCompress {
        description
          "Service-Context Virtual Interface UnCompress";
        type uint16;
      }
      leaf ATM {
        description
          "ATM interface";
        type string;
      }
      container ATM-subinterface {
        leaf ATM {
          type string;
        }
      }
      leaf ATM-ACR {
        description
          "ATM-ACR interface";
        type string {
          pattern '[0-9]';
        }
      }
      container ATM-ACRsubinterface {
        leaf ATM-ACR {
          type string {
            pattern '[0-9]\.([0-9]/){3}[0-9]';
          }
        }
      }
      leaf BDI {
        description
          "Bridge-Domain interface";
        type string;
      }
      leaf CEM {
        description
          "CEM interface";
        type string {
          pattern '([0-9]/){2}[0-9]{2}';
        }
      }
      leaf CEM-ACR {
        description
          "CEM-ACR interface";
        type uint8 {
          range "0..255";
        }
      }
      leaf Embedded-Service-Engine {
        description
          "cisco embedded service engine module";
        type string;
      }
      leaf Ethernet {
        description
          "IEEE 802.3";
        type string;
      }
      leaf FastEthernet {
        description
          "FastEthernet IEEE 802.3";
        type string;
      }
      leaf GigabitEthernet {
        description
          "GigabitEthernet IEEE 802.3z";
        type string;
      }
      leaf FiveGigabitEthernet {
        description
          "Five GigabitEthernet ";
        type string;
      }
      leaf AppGigabitEthernet {
        description
          "App-hosting Gigabit Ethernet IEEE 802.3z";
        type string;
      }
      leaf TwentyFiveGigabitEthernet {
        status obsolete;
        description
          "Twenty Five GigabitEthernet ";
        type string;
      }
      leaf TwentyFiveGigE {
        description
          "Twenty Five GigabitEthernet ";
        type string;
      }
      leaf TwoGigabitEthernet {
        description
          "Two GigabitEthernet ";
        type string;
      }
      leaf FortyGigabitEthernet {
        description
          "Forty GigabitEthernet ";
        type string;
      }
      leaf HundredGigE {
        description
          "Hundred GigabitEthernet";
        type string;
      }
      leaf L2LISP {
        description
          "L2 Locator/ID Separation Protocol Virtual Interface";
        type string;
      }
      container L2LISP-subinterface {
        description
          "L2 Locator/ID Separation Protocol Virtual Interface";
        leaf L2LISP {
          type string {
            pattern '[0-9]*(. ?[1-9][0-9]*)*';
          }
        }
      }
      leaf LISP {
        description
          "Locator/ID Separation Protocol Virtual Interface";
        type string;
      }
      container LISP-subinterface {
        description
          "Locator/ID Separation Protocol Virtual Interface";
        leaf LISP {
          type string {
            pattern '[0-9]*(. ?[1-9][0-9]*)*';
          }
        }
      }
      leaf Loopback {
        description
          "Loopback interface";
        type uint32 {
          range "0..2147483647";
        }
      }
      leaf Multilink {
        description
          "Multilink-group interface";
        type uint16;
      }
      leaf nve {
        description
          "Network virtualization endpoint interface";
        type uint16;
      }
      leaf overlay {
        description
          "Overlay interface";
        type uint16;
      }
      leaf Port-channel {
        description
          "Ethernet Channel of interfaces";
        type uint32;
      }
      container Port-channel-subinterface {
        leaf Port-channel {
          type string;
        }
      }
      leaf pseudowire {
        description
          "Pseudowire Interface";
        type uint32;
      }
      leaf SM {
        description
          "SM Interface";
        type string;
      }
      leaf Cellular {
        description
          "Cellular Interface";
        type string;
      }
      leaf Dialer {
        description
          "Dialer Interface";
        type string;
      }
      leaf Serial {
        description
          "Serial interface";
        type string;
      }
      leaf Async {
        description
          "Async serial interface";
        type string;
      }
      leaf TenGigabitEthernet {
        description
          "Ten Gigabit Ethernet";
        type string;
      }
      leaf Tunnel {
        description
          "Tunnel interface";
        type uint32;
      }
      leaf Virtual-Template {
        description
          "Virtual Template interface";
        type uint16;
      }
      leaf Vlan {
        description
          "Iosxr Vlans";
        type uint16;
      }
      leaf VirtualPortGroup {
        description
          "Virtual Port Group";
        type uint16;
      }
      leaf vasileft {
        description
          "vasileft";
        type uint16;
      }
      leaf vasiright {
        description
          "vasiright";
        type uint16;
      }
      leaf BD-VIF {
        description
          "Bridge-Domain Virtual IP interface";
        type string;
      }
      leaf MFR {
        description
          "MFR interface";
        type uint32 {
          range "0..2147483647";
        }
      }
      container Serial-subinterface {
        leaf Serial {
          type string;
        }
      }
      leaf Bundle {
        if-feature "ios-features:cable-config";
        description
          "Bundle interfaces";
        type uint32;
      }
    }
  }

  grouping interface-grouping-list {
    list AppNav-Compress {
      description
        "Service-Context Virtual Interface Compress";
      key "AppNav-Compress";
      leaf AppNav-Compress {
        type uint16;
      }
    }
    list AppNav-UnCompress {
      description
        "Service-Context Virtual Interface UnCompress";
      key "AppNav-UnCompress";
      leaf AppNav-UnCompress {
        type uint16;
      }
    }
    list ATM {
      description
        "ATM interface";
      key "ATM";
      leaf ATM {
        type string;
      }
    }
    container ATM-subinterface {
      list ATM {
        key "ATM";
        leaf ATM {
          type string;
        }
      }
    }
    list ATM-ACR {
      description
        "ATM-ACR interface";
      key "ATM-ACR";
      leaf ATM-ACR {
        type string {
          pattern '[0-9]';
        }
      }
    }
    container ATM-ACRsubinterface {
      list ATM-ACR {
        key "ATM-ACR";
        leaf ATM-ACR {
          type string {
            pattern '[0-9]\.([0-9]/){3}[0-9]';
          }
        }
      }
    }
    list BDI {
      description
        "Bridge-Domain interface";
      key "BDI";
      leaf BDI {
        type string;
      }
    }
    list CEM {
      description
        "CEM interface";
      key "CEM";
      leaf CEM {
        type string {
          pattern '([0-9]/){2}[0-9]{2}';
        }
      }
    }
    list CEM-ACR {
      description
        "CEM-ACR interface";
      key "CEM-ACR";
      leaf CEM-ACR {
        type uint8 {
          range "0..255";
        }
      }
    }
    list Embedded-Service-Engine {
      description
        "cisco embedded service engine module";
      key "Embedded-Service-Engine";
      leaf Embedded-Service-Engine {
        type string;
      }
    }
    list Ethernet {
      description
        "IEEE 802.3";
      key "Ethernet";
      leaf Ethernet {
        type string;
      }
    }
    list FastEthernet {
      description
        "FastEthernet IEEE 802.3";
      key "FastEthernet";
      leaf FastEthernet {
        type string;
      }
    }
    list GigabitEthernet {
      description
        "GigabitEthernet IEEE 802.3z";
      key "GigabitEthernet";
      leaf GigabitEthernet {
        type string;
      }
    }
    list FiveGigabitEthernet {
      description
        "Five GigabitEthernet ";
      key "FiveGigabitEthernet";
      leaf FiveGigabitEthernet {
        type string;
      }
    }
    list AppGigabitEthernet {
      description
        "App-hosting Gigabit Ethernet IEEE 802.3z";
      key "AppGigabitEthernet";
      leaf AppGigabitEthernet {
        type string;
      }
    }
    list TwentyFiveGigE {
      description
        "Twenty Five GigabitEthernet ";
      key "TwentyFiveGigE";
      leaf TwentyFiveGigE {
        type string;
      }
    }
    list TwoGigabitEthernet {
      description
        "Two GigabitEthernet ";
      key "TwoGigabitEthernet";
      leaf TwoGigabitEthernet {
        type string;
      }
    }
    list FortyGigabitEthernet {
      description
        "Forty GigabitEthernet ";
      key "FortyGigabitEthernet";
      leaf FortyGigabitEthernet {
        type string;
      }
    }
    list HundredGigE {
      description
        "Hundred GigabitEthernet";
      key "HundredGigE";
      leaf HundredGigE {
        type string;
      }
    }
    list L2LISP {
      description
        "L2 Locator/ID Separation Protocol Virtual Interface";
      key "L2LISP";
      leaf L2LISP {
        type string;
      }
    }
    container L2LISP-subinterface {
      description
        "L2 Locator/ID Separation Protocol Virtual Interface";
      list L2LISP {
        key "L2LISP";
        leaf L2LISP {
          type string {
            pattern '[0-9]*(. ?[1-9][0-9]*)*';
          }
        }
      }
    }
    list LISP {
      description
        "Locator/ID Separation Protocol Virtual Interface";
      key "LISP";
      leaf LISP {
        type string;
      }
    }
    container LISP-subinterface {
      description
        "Locator/ID Separation Protocol Virtual Interface";
      list LISP {
        key "LISP";
        leaf LISP {
          type string {
            pattern '[0-9]*(. ?[1-9][0-9]*)*';
          }
        }
      }
    }
    list Loopback {
      description
        "Loopback interface";
      key "Loopback";
      leaf Loopback {
        type uint32 {
          range "0..2147483647";
        }
      }
    }
    list Multilink {
      description
        "Multilink-group interface";
      key "Multilink";
      leaf Multilink {
        type uint16;
      }
    }
    list nve {
      description
        "Network virtualization endpoint interface";
      key "nve";
      leaf nve {
        type uint16;
      }
    }
    list overlay {
      description
        "Overlay interface";
      key "overlay";
      leaf overlay {
        type uint16;
      }
    }
    list Port-channel {
      description
        "Ethernet Channel of interfaces";
      key "Port-channel";
      leaf Port-channel {
        type uint32;
      }
    }
    container Port-channel-subinterface {
      list Port-channel {
        key "Port-channel";
        leaf Port-channel {
          type string;
        }
      }
    }
    list pseudowire {
      description
        "Pseudowire Interface";
      key "pseudowire";
      leaf pseudowire {
        type uint32;
      }
    }
    list SM {
      description
        "SM Interface";
      key "SM";
      leaf SM {
        type string;
      }
    }
    list Cellular {
      description
        "Cellular Interface";
      key "Cellular";
      leaf Cellular {
        type string;
      }
    }
    list Dialer {
      description
        "Dialer Interface";
      key "Dialer";
      leaf Dialer {
        type string;
      }
    }
    list Serial {
      description
        "Serial interface";
      key "Serial";
      leaf Serial {
        type string;
      }
    }
    list Async {
      description
        "Async serial interface";
      key "Async";
      leaf Async {
        type string;
      }
    }
    list TenGigabitEthernet {
      description
        "Ten Gigabit Ethernet";
      key "TenGigabitEthernet";
      leaf TenGigabitEthernet {
        type string;
      }
    }
    list Tunnel {
      description
        "Tunnel interface";
      key "Tunnel";
      leaf Tunnel {
        type uint32;
      }
    }
    list Virtual-Template {
      description
        "Virtual Template interface";
      key "Virtual-Template";
      leaf Virtual-Template {
        type uint16;
      }
    }
    list Vlan {
      description
        "Iosxr Vlans";
      key "Vlan";
      leaf Vlan {
        type uint16;
      }
    }
    list VirtualPortGroup {
      description
        "Virtual Port Group";
      key "VirtualPortGroup";
      leaf VirtualPortGroup {
        type uint16;
      }
    }
    list vasileft {
      description
        "vasileft";
      key "vasileft";
      leaf vasileft {
        type uint16;
      }
    }
    list vasiright {
      description
        "vasiright";
      key "vasiright";
      leaf vasiright {
        type uint16;
      }
    }
    list BD-VIF {
      description
        "Bridge-Domain Virtual IP interface";
      key "BD-VIF";
      leaf BD-VIF {
        type string;
      }
    }
    list MFR {
      description
        "MFR interface";
      key "MFR";
      leaf MFR {
        type uint32 {
          range "0..2147483647";
        }
      }
    }
    container Serial-subinterface {
      list Serial {
        key "Serial";
        leaf Serial {
          type string;
        }
      }
    }
    list Bundle {
      if-feature "ios-features:cable-config";
      description
        "Bundle interfaces";
      key "Bundle";
      leaf Bundle {
        type uint32;
      }
    }
  }

  grouping passive-interface-grouping {
    container passive-interface {
      description
        "Suppress routing updates on an interface";
      choice passive-interface-choice {
        leaf default {
          description
            "Suppress routing updates on all interfaces";
          type empty;
        }
        leaf-list interface {
          type string;
        }
      }
    }
    container disable {
      when '../passive-interface/default';
      list passive-interface {
        key "interface";
        leaf interface {
          type string;
        }
      }
    }
  }

  grouping interface-deprecated-grouping {
    choice interface-choice {
      leaf AppNav-Compress {
        status deprecated;
        description
          "Service-Context Virtual Interface Compress";
        type uint16;
      }
      leaf AppNav-UnCompress {
        status deprecated;
        description
          "Service-Context Virtual Interface UnCompress";
        type uint16;
      }
      leaf ATM {
        status deprecated;
        description
          "ATM interface";
        type string;
      }
      container ATM-subinterface {
        status deprecated;
        leaf ATM {
          status deprecated;
          type string;
        }
      }
      leaf ATM-ACR {
        status deprecated;
        description
          "ATM-ACR interface";
        type string {
          pattern '[0-9]';
        }
      }
      container ATM-ACRsubinterface {
        status deprecated;
        leaf ATM-ACR {
          status deprecated;
          type string {
            pattern '[0-9]\.([0-9]/){3}[0-9]';
          }
        }
      }
      leaf BDI {
        status deprecated;
        description
          "Bridge-Domain interface";
        type string;
      }
      leaf CEM {
        status deprecated;
        description
          "CEM interface";
        type string {
          pattern '([0-9]/){2}[0-9]';
        }
      }
      leaf CEM-ACR {
        status deprecated;
        description
          "CEM-ACR interface";
        type uint8 {
          range "0..255";
        }
      }
      leaf Embedded-Service-Engine {
        status deprecated;
        description
          "cisco embedded service engine module";
        type string;
      }
      leaf Ethernet {
        status deprecated;
        description
          "IEEE 802.3";
        type string;
      }
      leaf FastEthernet {
        status deprecated;
        description
          "FastEthernet IEEE 802.3";
        type string;
      }
      leaf GigabitEthernet {
        status deprecated;
        description
          "GigabitEthernet IEEE 802.3z";
        type string;
      }
      leaf FiveGigabitEthernet {
        status deprecated;
        description
          "Five GigabitEthernet ";
        type string;
      }
      leaf AppGigabitEthernet {
        status deprecated;
        description
          "App-hosting Gigabit Ethernet IEEE 802.3z";
        type string;
      }
      leaf TwentyFiveGigE {
        status deprecated;
        description
          "Twenty Five GigabitEthernet ";
        type string;
      }
      leaf TwoGigabitEthernet {
        status deprecated;
        description
          "Two GigabitEthernet ";
        type string;
      }
      leaf FortyGigabitEthernet {
        status deprecated;
        description
          "Forty GigabitEthernet ";
        type string;
      }
      leaf HundredGigE {
        status deprecated;
        description
          "Hundred GigabitEthernet";
        type string;
      }
      leaf L2LISP {
        description
          "L2 Locator/ID Separation Protocol Virtual Interface";
        status deprecated;
        type string;
      }
      container L2LISP-subinterface {
        description
          "L2 Locator/ID Separation Protocol Virtual Interface";
        leaf L2LISP {
          status deprecated;
          type string {
            pattern '[0-9]*(. ?[1-9][0-9]*)*';
          }
        }
      }
      leaf LISP {
        status deprecated;
        description
          "Locator/ID Separation Protocol Virtual Interface";
        type string;
      }
      container LISP-subinterface {
        status deprecated;
        description
          "Locator/ID Separation Protocol Virtual Interface";
        leaf LISP {
          status deprecated;
          type string {
            pattern '[0-9]*(. ?[1-9][0-9]*)*';
          }
        }
      }
      leaf Loopback {
        status deprecated;
        description
          "Loopback interface";
        type uint32;
      }
      leaf Multilink {
        status deprecated;
        description
          "Multilink-group interface";
        type uint16;
      }
      leaf nve {
        status deprecated;
        description
          "Network virtualization endpoint interface";
        type uint16;
      }
      leaf overlay {
        status deprecated;
        description
          "Overlay interface";
        type uint16;
      }
      leaf Port-channel {
        status deprecated;
        description
          "Ethernet Channel of interfaces";
        type uint32;
      }
      container Port-channel-subinterface {
        status deprecated;
        leaf Port-channel {
          status deprecated;
          type string;
        }
      }
      leaf pseudowire {
        status deprecated;
        description
          "Pseudowire Interface";
        type uint32;
      }
      leaf SM {
        status deprecated;
        description
          "SM Interface";
        type string;
      }
      leaf Cellular {
        status deprecated;
        description
          "Cellular Interface";
        type string;
      }
      leaf Dialer {
        status deprecated;
        description
          "Dialer Interface";
        type string;
      }
      leaf Serial {
        status deprecated;
        description
          "Serial interface";
        type string;
      }
      leaf Async {
        status deprecated;
        description
          "Async serial interface";
        type string;
      }
      leaf TenGigabitEthernet {
        status deprecated;
        description
          "Ten Gigabit Ethernet";
        type string;
      }
      leaf Tunnel {
        status deprecated;
        description
          "Tunnel interface";
        type uint32;
      }
      leaf Virtual-Template {
        status deprecated;
        description
          "Virtual Template interface";
        type uint16;
      }
      leaf Vlan {
        status deprecated;
        description
          "Iosxr Vlans";
        type uint16;
      }
      leaf VirtualPortGroup {
        status deprecated;
        description
          "Virtual Port Group";
        type uint16;
      }
      leaf vasileft {
        status deprecated;
        description
          "vasileft";
        type uint16;
      }
      leaf vasiright {
        status deprecated;
        description
          "vasiright";
        type uint16;
      }
      leaf BD-VIF {
        status deprecated;
        description
          "Bridge-Domain Virtual IP interface";
        type string;
      }
      leaf TwentyFiveGigabitEthernet {
        status obsolete;
        description
          "Twenty Five GigabitEthernet ";
        type string;
      }
      leaf MFR {
        description
          "MFR interface";
        status deprecated;
        type uint32 {
          range "0..2147483647";
        }
      }
      container Serial-subinterface {
        status deprecated;
        leaf Serial {
          status deprecated;
          type string;
        }
      }
      leaf Bundle {
        status deprecated;
        if-feature "ios-features:cable-config";
        description
          "Bundle interfaces";
        type uint32;
      }
    }
  }

  grouping interface-obsolete-grouping {
    choice interface-choice {
      status obsolete;
      leaf AppNav-Compress {
        status obsolete;
        description
          "Service-Context Virtual Interface Compress";
        type uint16;
      }
      leaf AppNav-UnCompress {
        description
          "Service-Context Virtual Interface UnCompress";
        status obsolete;
        type uint16;
      }
      leaf ATM {
        description
          "ATM interface";
        status obsolete;
        type string;
      }
      container ATM-subinterface {
        status obsolete;
        leaf ATM {
          status obsolete;
          type string;
        }
      }
      leaf ATM-ACR {
        description
          "ATM-ACR interface";
        status obsolete;
        type string {
          pattern '[0-9]';
        }
      }
      container ATM-ACRsubinterface {
        status obsolete;
        leaf ATM-ACR {
          status obsolete;
          type string {
            pattern '[0-9]\.([0-9]/){3}[0-9]';
          }
        }
      }
      leaf BDI {
        description
          "Bridge-Domain interface";
        status obsolete;
        type string;
      }
      leaf CEM {
        description
          "CEM interface";
        status obsolete;
        type string {
          pattern '([0-9]/){2}[0-9]';
        }
      }
      leaf CEM-ACR {
        description
          "CEM-ACR interface";
        status obsolete;
        type uint8 {
          range "0..255";
        }
      }
      leaf Embedded-Service-Engine {
        description
          "cisco embedded service engine module";
        status obsolete;
        type string;
      }
      leaf Ethernet {
        description
          "IEEE 802.3";
        status obsolete;
        type string;
      }
      leaf FastEthernet {
        description
          "FastEthernet IEEE 802.3";
        status obsolete;
        type string;
      }
      leaf GigabitEthernet {
        description
          "GigabitEthernet IEEE 802.3z";
        status obsolete;
        type string;
      }
      leaf FiveGigabitEthernet {
        description
          "Five GigabitEthernet ";
        status obsolete;
        type string;
      }
      leaf AppGigabitEthernet {
        description
          "App-hosting Gigabit Ethernet IEEE 802.3z";
        status obsolete;
        type string;
      }
      leaf TwentyFiveGigabitEthernet {
        status obsolete;
        description
          "Twenty Five GigabitEthernet ";
        type string;
      }
      leaf TwentyFiveGigE {
        description
          "Twenty Five GigabitEthernet ";
        status obsolete;
        type string;
      }
      leaf TwoGigabitEthernet {
        description
          "Two GigabitEthernet ";
        status obsolete;
        type string;
      }
      leaf FortyGigabitEthernet {
        description
          "Forty GigabitEthernet ";
        status obsolete;
        type string;
      }
      leaf HundredGigE {
        description
          "Hundred GigabitEthernet";
        status obsolete;
        type string;
      }
      leaf L2LISP {
        description
          "L2 Locator/ID Separation Protocol Virtual Interface";
        status obsolete;
        type string;
      }
      container L2LISP-subinterface {
        description
          "L2 Locator/ID Separation Protocol Virtual Interface";
        status obsolete;
        leaf L2LISP {
          status obsolete;
          type string {
            pattern '[0-9]*(. ?[1-9][0-9]*)*';
          }
        }
      }
      leaf LISP {
        description
          "Locator/ID Separation Protocol Virtual Interface";
        status obsolete;
        type string;
      }
      container LISP-subinterface {
        description
          "Locator/ID Separation Protocol Virtual Interface";
        status obsolete;
        leaf LISP {
          status obsolete;
          type string {
            pattern '[0-9]*(. ?[1-9][0-9]*)*';
          }
        }
      }
      leaf Loopback {
        description
          "Loopback interface";
        status obsolete;
        type uint32;
      }
      leaf Multilink {
        description
          "Multilink-group interface";
        status obsolete;
        type uint16;
      }
      leaf nve {
        description
          "Network virtualization endpoint interface";
        status obsolete;
        type uint16;
      }
      leaf overlay {
        description
          "Overlay interface";
        status obsolete;
        type uint16;
      }
      leaf Port-channel {
        description
          "Ethernet Channel of interfaces";
        status obsolete;
        type uint32;
      }
      container Port-channel-subinterface {
        status obsolete;
        leaf Port-channel {
          status obsolete;
          type string;
        }
      }
      leaf pseudowire {
        description
          "Pseudowire Interface";
        status obsolete;
        type uint32;
      }
      leaf SM {
        description
          "SM Interface";
        status obsolete;
        type string;
      }
      leaf Cellular {
        description
          "Cellular Interface";
        status obsolete;
        type string;
      }
      leaf Dialer {
        description
          "Dialer Interface";
        status obsolete;
        type string;
      }
      leaf Serial {
        description
          "Serial interface";
        status obsolete;
        type string;
      }
      leaf Async {
        description
          "Async serial interface";
        status obsolete;
        type string;
      }
      leaf TenGigabitEthernet {
        description
          "Ten Gigabit Ethernet";
        status obsolete;
        type string;
      }
      leaf Tunnel {
        description
          "Tunnel interface";
        status obsolete;
        type uint32;
      }
      leaf Virtual-Template {
        description
          "Virtual Template interface";
        status obsolete;
        type uint16;
      }
      leaf Vlan {
        description
          "Iosxr Vlans";
        status obsolete;
        type uint16;
      }
      leaf VirtualPortGroup {
        description
          "Virtual Port Group";
        status obsolete;
        type uint16;
      }
      leaf vasileft {
        description
          "vasileft";
        status obsolete;
        type uint16;
      }
      leaf vasiright {
        description
          "vasiright";
        status obsolete;
        type uint16;
      }
      leaf BD-VIF {
        description
          "Bridge-Domain Virtual IP interface";
        status obsolete;
        type string;
      }
      leaf MFR {
        description
          "MFR interface";
        status obsolete;
        type uint32 {
          range "0..2147483647";
        }
      }
      container Serial-subinterface {
        status obsolete;
        leaf Serial {
          status obsolete;
          type string;
        }
      }
      leaf Bundle {
        status obsolete;
        if-feature "ios-features:cable-config";
        description
          "Bundle interfaces";
        type uint32;
      }
    }
  }
}
