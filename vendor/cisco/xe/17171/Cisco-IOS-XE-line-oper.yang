module Cisco-IOS-XE-line-oper {
  yang-version 1.1;
  namespace "http://cisco.com/ns/yang/Cisco-IOS-XE-line-oper";
  prefix line-ios-xe-oper;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions for monitoring
     operational data of IOS terminal lines.
     Copyright (c) 2024 by Cisco Systems, Inc.
     All rights reserved.";

  revision 2024-11-01 {
    description
      "Initial revision";
    reference
      "1.0.0";
    cisco-semver:module-version "1.0.0";
  }

  typedef e-line-type {
    type enumeration {
      enum line-type-bad {
        value 0;
        description
          "Unknown (bad) line type";
      }
      enum line-type-cty {
        value 1;
        description
          "Console line";
      }
      enum line-type-tty {
        value 2;
        description
          "Normal async TTY line";
      }
      enum line-type-vty {
        value 3;
        description
          "Virtual terminal line";
      }
      enum line-type-str {
        value 4;
        description
          "String pointer line";
      }
      enum line-type-aux {
        value 5;
        description
          "AUX (auxiliary) line";
      }
    }
    description
      "Line type";
  }

  typedef e-line-state {
    type enumeration {
      enum line-state-in-use {
        value 0;
        description
          "Line is already in-use (busy)";
      }
      enum line-state-free {
        value 1;
        description
          "Line is free";
      }
    }
    description
      "Line state";
  }

  grouping line-data-entry {
    description
      "Line operational data";
    leaf number {
      type uint32;
      description
        "Line number";
    }
    leaf name {
      type string;
      description
        "Line name";
    }
    leaf type {
      type line-ios-xe-oper:e-line-type;
      description
        "Line type";
    }
    leaf tx-speed {
      type uint32;
      units "bps";
      description
        "Line TX speed";
    }
    leaf rx-speed {
      type uint32;
      units "bps";
      description
        "Line RX speed";
    }
    leaf state {
      type line-ios-xe-oper:e-line-state;
      description
        "Current line running state";
    }
    leaf desc {
      type string;
      description
        "Line description";
    }
  }

  container line-oper-data {
    config false;
    description
      "The top level container for line operational data";
    list line-data {
      key "number";
      description
        "Line operational data";
      uses line-ios-xe-oper:line-data-entry;
    }
  }
}
