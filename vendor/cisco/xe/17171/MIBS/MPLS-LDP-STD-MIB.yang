/*
 * Generated by confdc --mib2yang-std
 * Source: mgmt/dmi/model/mib/src/MPLS-LDP-STD-MIB.mib
 */
/*
 * This YANG module has been generated by smidump 0.5.0:
 *
 *      smidump -f yang MPLS-LDP-STD-MIB
 *
 * Do not edit. Edit the source file instead!
 */

module MPLS-LDP-STD-MIB {

  namespace "urn:ietf:params:xml:ns:yang:smiv2:MPLS-LDP-STD-MIB";
  prefix MPLS-LDP-STD-MIB;

  import DIFFSERV-MIB {
    prefix "diffserv-mib";
  }

  import INET-ADDRESS-MIB {
    prefix "inet-address";
  }

  import MPLS-LSR-STD-MIB {
    prefix "mpls-lsr";
  }

  import MPLS-TC-STD-MIB {
    prefix "mpls-tc";
  }

  import SNMPv2-TC {
    prefix "snmpv2-tc";
  }

  import ietf-inet-types {
    prefix "inet";
  }

  import ietf-yang-smiv2 {
    prefix "smiv2";
  }

  import ietf-yang-types {
    prefix "yang";
  }

  organization
   "Multiprotocol Label Switching (mpls)
    Working Group";

  contact
   "Joan Cucchiara (jcucchiara@mindspring.com)
    Marconi Communications, Inc.
    
    Hans Sjostrand (hans@ipunplugged.com)
    ipUnplugged
    
    James V. Luciani (james_luciani@mindspring.com)
    Marconi Communications, Inc.
    
    Working Group Chairs:
    George Swallow,   email: swallow@cisco.com
    Loa Andersson,    email: loa@pi.se
    
    MPLS Working Group, email: mpls@uu.net";

  description
   "Copyright (C) The Internet Society (2004). The
    initial version of this MIB module was published
    
    
    in RFC 3815. For full legal notices see the RFC
    itself or see:
    http://www.ietf.org/copyrights/ianamib.html
    
    This MIB contains managed object definitions for the
    'Multiprotocol Label Switching, Label Distribution
    Protocol, LDP' document.";

  revision 2004-06-03 {
    description
     "Initial version published as part of RFC 3815.";
  }


  container MPLS-LDP-STD-MIB {
    config false;

    container mplsLdpLsrObjects {
      smiv2:oid "1.3.6.1.2.1.10.166.4.1.1";

      leaf mplsLdpLsrId {
        type mpls-tc:MplsLsrIdentifier;
        description
         "The Label Switching Router's Identifier.";
        smiv2:max-access "read-only";
        smiv2:oid "1.3.6.1.2.1.10.166.4.1.1.1";
      }

      leaf mplsLdpLsrLoopDetectionCapable {
        type enumeration {
          enum "none" {
            value "1";
          }
          enum "other" {
            value "2";
          }
          enum "hopCount" {
            value "3";
          }
          enum "pathVector" {
            value "4";
          }
          enum "hopCountAndPathVector" {
            value "5";
          }
        }
        description
         "A indication of whether this
          Label Switching Router supports
          loop detection.
          
          none(1) -- Loop Detection is not supported
                     on this LSR.
          
          other(2) -- Loop Detection is supported but
                      by a method other than those
                      listed below.
          
          hopCount(3) -- Loop Detection is supported by
                         Hop Count only.
          
          pathVector(4) -- Loop Detection is supported by
                           Path Vector only.
          
          hopCountAndPathVector(5) -- Loop Detection is
                               supported by both Hop Count
                               And Path Vector.
          
          Since Loop Detection is determined during
          Session Initialization, an individual session
          may not be running with loop detection.  This
          object simply gives an indication of whether or not the
          LSR has the ability to support Loop Detection and
          which types.";
        smiv2:max-access "read-only";
        smiv2:oid "1.3.6.1.2.1.10.166.4.1.1.2";
      }
    }

    container mplsLdpEntityObjects {
      smiv2:oid "1.3.6.1.2.1.10.166.4.1.2";

      leaf mplsLdpEntityLastChange {
        type yang:timestamp;
        description
         "The value of sysUpTime at the time of the most
          recent addition or deletion of an entry
          to/from the mplsLdpEntityTable/mplsLdpEntityStatsTable, or
          the most recent change in value of any objects in the
          mplsLdpEntityTable.
          
          
          If no such changes have occurred since the last
          re-initialization of the local management subsystem,
          then this object contains a zero value.";
        smiv2:max-access "read-only";
        smiv2:oid "1.3.6.1.2.1.10.166.4.1.2.1";
      }

      leaf mplsLdpEntityIndexNext {
        type diffserv-mib:IndexIntegerNextFree;
        description
         "This object contains an appropriate value to
          be used for mplsLdpEntityIndex when creating
          entries in the mplsLdpEntityTable. The value
          0 indicates that no unassigned entries are
          available.";
        smiv2:max-access "read-only";
        smiv2:oid "1.3.6.1.2.1.10.166.4.1.2.2";
      }
    }

    container mplsLdpSessionObjects {
      smiv2:oid "1.3.6.1.2.1.10.166.4.1.3";

      leaf mplsLdpPeerLastChange {
        type yang:timestamp;
        description
         "The value of sysUpTime at the time of the most
          recent addition or deletion to/from the
          mplsLdpPeerTable/mplsLdpSessionTable.";
        smiv2:max-access "read-only";
        smiv2:oid "1.3.6.1.2.1.10.166.4.1.3.1";
      }

      leaf mplsLdpLspFecLastChange {
        type yang:timestamp;
        description
         "The value of sysUpTime at the time of the most
          recent addition/deletion of an entry
          to/from the mplsLdpLspFecTable or
          the most recent change in values to any objects in the
          mplsLdpLspFecTable.
          
          If no such changes have occurred since the last
          re-initialization of the local management subsystem,
          then this object contains a zero value.";
        smiv2:max-access "read-only";
        smiv2:oid "1.3.6.1.2.1.10.166.4.1.3.9";
      }
    }

    container mplsFecObjects {
      smiv2:oid "1.3.6.1.2.1.10.166.4.1.3.8";

      leaf mplsFecLastChange {
        type yang:timestamp;
        description
         "The value of sysUpTime at the time of the most
          recent addition/deletion of an entry
          to/from the mplsLdpFectTable or
          the most recent change in values to any objects
          in the mplsLdpFecTable.
          
          If no such changes have occurred since the last
          re-initialization of the local management subsystem,
          then this object contains a zero value.";
        smiv2:max-access "read-only";
        smiv2:oid "1.3.6.1.2.1.10.166.4.1.3.8.1";
      }

      leaf mplsFecIndexNext {
        type diffserv-mib:IndexIntegerNextFree;
        description
         "This object contains an appropriate value to
          be used for mplsFecIndex when creating
          entries in the mplsFecTable. The value
          0 indicates that no unassigned entries are
          available.";
        smiv2:max-access "read-only";
        smiv2:oid "1.3.6.1.2.1.10.166.4.1.3.8.2";
      }
    }

    container mplsLdpEntityTable {
      description
       "This table contains information about the
        MPLS Label Distribution Protocol Entities which
        exist on this Label Switching Router (LSR)
        or Label Edge Router (LER).";
      smiv2:oid "1.3.6.1.2.1.10.166.4.1.2.3";

      list mplsLdpEntityEntry {
        key "mplsLdpEntityLdpId mplsLdpEntityIndex";
        description
         "An entry in this table represents an LDP entity.
          An entry can be created by a network administrator
          or by an SNMP agent as instructed by LDP.";
        smiv2:oid "1.3.6.1.2.1.10.166.4.1.2.3.1";

        leaf mplsLdpEntityLdpId {
          type mpls-tc:MplsLdpIdentifier;
          description
           "The LDP identifier.";
          reference
           "RFC3036, LDP Specification, Section on LDP Identifiers.";
          smiv2:max-access "not-accessible";
          smiv2:oid "1.3.6.1.2.1.10.166.4.1.2.3.1.1";
        }

        leaf mplsLdpEntityIndex {
          type diffserv-mib:IndexInteger;
          description
           "This index is used as a secondary index to uniquely
            identify this row.  Before creating a row in this table,
            the 'mplsLdpEntityIndexNext' object should be retrieved.
            That value should be used for the value of this index
            when creating a row in this table.  NOTE:  if a value
            of zero (0) is retrieved, that indicates that no rows
            can be created in this table at this time.
            
            A secondary index (this object) is meaningful to some
            but not all, LDP implementations.  For example
            an LDP implementation which uses PPP would
            use this index to differentiate PPP sub-links.
            
            Another way to use this index is to give this the
            value of ifIndex.  However, this is dependant
            
            
            on the implementation.";
          smiv2:max-access "not-accessible";
          smiv2:oid "1.3.6.1.2.1.10.166.4.1.2.3.1.2";
        }

        leaf mplsLdpEntityProtocolVersion {
          type uint32 {
            range "1..65535";
          }
          description
           "The version number of the LDP protocol which will be
            used in the session initialization message.
            
            Section 3.5.3 in the LDP Specification specifies
            that the version of the LDP protocol is negotiated during
            session establishment. The value of this object
            represents the value that is sent in the initialization
            message.";
          reference
           "RFC3036, LDP Specification, Section 3.5.3 Initialization
            Message.";
          smiv2:defval "1";
          smiv2:max-access "read-write";
          smiv2:oid "1.3.6.1.2.1.10.166.4.1.2.3.1.3";
        }

        leaf mplsLdpEntityAdminStatus {
          type enumeration {
            enum "enable" {
              value "1";
            }
            enum "disable" {
              value "2";
            }
          }
          description
           "The administrative status of this LDP Entity.
            If this object is changed from 'enable' to 'disable'
            and this entity has already attempted to establish
            contact with a Peer, then all contact with that
            Peer is lost and all information from that Peer
            needs to be removed from the MIB. (This implies
            that the network management subsystem should clean
            up any related entry in the mplsLdpPeerTable.  This
            further implies that a 'tear-down' for that session
            is issued and the session and all information related
            to that session cease to exist).
            
            At this point the operator is able to change values
            which are related to this entity.
            
            When the admin status is set back to 'enable', then
            this Entity will attempt to establish a new session
            with the Peer.";
          smiv2:defval "enable";
          smiv2:max-access "read-write";
          smiv2:oid "1.3.6.1.2.1.10.166.4.1.2.3.1.4";
        }

        leaf mplsLdpEntityOperStatus {
          type enumeration {
            enum "unknown" {
              value "1";
            }
            enum "enabled" {
              value "2";
            }
            enum "disabled" {
              value "3";
            }
          }
          description
           "The operational status of this LDP Entity.
            
            The value of unknown(1) indicates that the
            operational status cannot be determined at
            this time.  The value of unknown should be
            a transient condition before changing
            to enabled(2) or disabled(3).";
          smiv2:max-access "read-only";
          smiv2:oid "1.3.6.1.2.1.10.166.4.1.2.3.1.5";
        }

        leaf mplsLdpEntityTcpPort {
          type inet:port-number;
          description
           "The TCP Port for
            LDP.  The default value is the well-known
            value of this port.";
          reference
           "RFC3036, LDP Specification, Section 3.10, Well-known
            Numbers, and Section 3.10.1.  UDP and TCP Ports.";
          smiv2:defval "646";
          smiv2:max-access "read-write";
          smiv2:oid "1.3.6.1.2.1.10.166.4.1.2.3.1.6";
        }

        leaf mplsLdpEntityUdpDscPort {
          type inet:port-number;
          description
           "The UDP Discovery Port for
            LDP.  The default value is the
            well-known value for this port.";
          reference
           "RFC3036, LDP Specification, Section 2.4.1,
            Basic Discovery Mechanism, Section 2.4.2,
            Extended Discovery Mechanism, Section
            3.10, Well-known Numbers, and Section 3.10.1.
            
            
            UDP and TCP Ports.";
          smiv2:defval "646";
          smiv2:max-access "read-write";
          smiv2:oid "1.3.6.1.2.1.10.166.4.1.2.3.1.7";
        }

        leaf mplsLdpEntityMaxPduLength {
          type uint32 {
            range "256..65535";
          }
          units "octets";
          description
           "The maximum PDU Length that is sent in
            the Common Session Parameters of an Initialization
            Message. According to the LDP Specification [RFC3036]
            a value of 255 or less specifies the
            default maximum length of 4096 octets, this is why
            the value of this object starts at 256.  The operator
            should explicitly choose the default value (i.e., 4096),
            or some other value.
            
            The receiving LSR MUST calculate the maximum PDU
            length for the session by using the smaller of its and
            its peer's proposals for Max PDU Length.";
          reference
           "RFC3036, LDP Specification, Section 3.5.3.
            Initialization Message.";
          smiv2:defval "4096";
          smiv2:max-access "read-write";
          smiv2:oid "1.3.6.1.2.1.10.166.4.1.2.3.1.8";
        }

        leaf mplsLdpEntityKeepAliveHoldTimer {
          type uint32 {
            range "1..65535";
          }
          units "seconds";
          description
           "The 16-bit integer value which is the proposed keep
            alive hold timer for this LDP Entity.";
          smiv2:defval "40";
          smiv2:max-access "read-write";
          smiv2:oid "1.3.6.1.2.1.10.166.4.1.2.3.1.9";
        }

        leaf mplsLdpEntityHelloHoldTimer {
          type uint32 {
            range "0..65535";
          }
          units "seconds";
          description
           "The 16-bit integer value which is the proposed Hello
            hold timer for this LDP Entity. The Hello Hold time
            in seconds.
            
            
            An LSR maintains a record of Hellos received
            from potential peers.  This object represents
            the Hold Time in the Common Hello Parameters TLV of
            the Hello Message.
            
            A value of 0 is a default value and should be
            interpretted in conjunction with the
            mplsLdpEntityTargetPeer object.
            
            If the value of this object is 0: if the value of the
            mplsLdpEntityTargetPeer object is false(2), then this
            specifies that the Hold Time's actual default value is
            15 seconds (i.e., the default Hold time for Link Hellos
            is 15 seconds).  Otherwise if the value of the
            mplsLdpEntityTargetPeer object is true(1), then this
            specifies that the Hold Time's actual default value is
            45 seconds (i.e., the default Hold time for Targeted
            Hellos is 45 seconds).
            
            A value of 65535 means infinite (i.e., wait forever).
            
            All other values represent the amount of time in
            seconds to wait for a Hello Message.  Setting the
            hold time to a value smaller than 15 is not
            recommended, although not forbidden according
            to RFC3036.";
          reference
           "RFC3036, LDP Specification, Section 3.5.2.,
            Hello Message.";
          smiv2:defval "0";
          smiv2:max-access "read-write";
          smiv2:oid "1.3.6.1.2.1.10.166.4.1.2.3.1.10";
        }

        leaf mplsLdpEntityInitSessionThreshold {
          type int32 {
            range "0..100";
          }
          description
           "When attempting to establish a session with
            a given Peer, the given LDP Entity should
            send out the SNMP notification,
            'mplsLdpInitSessionThresholdExceeded', when
            the number of Session Initialization messages
            sent exceeds this threshold.
            
            The notification is used to notify an
            operator when this Entity and its Peer are
            possibly engaged in an endless sequence
            of messages as each NAKs the other's
            
            
            Initialization messages with Error Notification
            messages.  Setting this threshold which triggers
            the notification is one way to notify the
            operator.  The notification should be generated
            each time this threshold is exceeded and
            for every subsequent Initialization message
            which is NAK'd with an Error Notification
            message after this threshold is exceeded.
            
            A value of 0 (zero) for this object
            indicates that the threshold is infinity, thus
            the SNMP notification will never be generated.";
          reference
           "RFC3036, LDP Specification,
            Section 2.5.3 Session Initialization.";
          smiv2:defval "8";
          smiv2:max-access "read-write";
          smiv2:oid "1.3.6.1.2.1.10.166.4.1.2.3.1.11";
        }

        leaf mplsLdpEntityLabelDistMethod {
          type mpls-tc:MplsLabelDistributionMethod;
          description
           "For any given LDP session, the method of
            label distribution must be specified.";
          smiv2:max-access "read-write";
          smiv2:oid "1.3.6.1.2.1.10.166.4.1.2.3.1.12";
        }

        leaf mplsLdpEntityLabelRetentionMode {
          type mpls-tc:MplsRetentionMode;
          description
           "The LDP Entity can be configured to use either
            conservative or liberal label retention mode.
            
            If the value of this object is conservative(1)
            then advertized label mappings are retained
            only if they will be used to forward packets,
            i.e., if label came from a valid next hop.
            
            If the value of this object is liberal(2)
            then all advertized label mappings are retained
            whether they are from a valid next hop or not.";
          smiv2:max-access "read-write";
          smiv2:oid "1.3.6.1.2.1.10.166.4.1.2.3.1.13";
        }

        leaf mplsLdpEntityPathVectorLimit {
          type int32 {
            range "0..255";
          }
          description
           "If the value of this object is 0 (zero) then
            Loop Detection for Path Vectors is disabled.
            
            Otherwise, if this object has a value greater than
            zero, then Loop Dection for Path Vectors is enabled,
            and the Path Vector Limit is this value.
            Also, the value of the object,
            'mplsLdpLsrLoopDetectionCapable', must be set to
            either 'pathVector(4)' or 'hopCountAndPathVector(5)',
            if this object has a value greater than 0 (zero),
            otherwise it is ignored.";
          reference
           "RFC3036, LDP Specification, Section 2.8 Loop Dection,
            Section 3.4.5 Path Vector TLV.";
          smiv2:max-access "read-write";
          smiv2:oid "1.3.6.1.2.1.10.166.4.1.2.3.1.14";
        }

        leaf mplsLdpEntityHopCountLimit {
          type int32 {
            range "0..255";
          }
          description
           "If the value of this object is 0 (zero),
            then Loop Detection using Hop Counters is
            disabled.
            
            If the value of this object is greater than
            0 (zero) then Loop Detection using Hop
            Counters is enabled, and this object
            specifies this Entity's maximum allowable
            value for the Hop Count.
            Also, the value of the object
            mplsLdpLsrLoopDetectionCapable must be set
            to either 'hopCount(3)' or
            'hopCountAndPathVector(5)' if this object
            has a value greater than 0 (zero), otherwise
            it is ignored.";
          smiv2:defval "0";
          smiv2:max-access "read-write";
          smiv2:oid "1.3.6.1.2.1.10.166.4.1.2.3.1.15";
        }

        leaf mplsLdpEntityTransportAddrKind {
          type enumeration {
            enum "interface" {
              value "1";
            }
            enum "loopback" {
              value "2";
            }
          }
          description
           "This specifies whether the loopback or interface
            address is to be used as the transport address
            in the transport address TLV of the
            hello message.
            
            If the value is interface(1), then the IP
            address of the interface from which hello
            messages are sent is used as the transport
            address in the hello message.
            
            Otherwise, if the value is loopback(2), then the IP
            address of the loopback interface is used as the
            transport address in the hello message.";
          smiv2:defval "loopback";
          smiv2:max-access "read-write";
          smiv2:oid "1.3.6.1.2.1.10.166.4.1.2.3.1.16";
        }

        leaf mplsLdpEntityTargetPeer {
          type boolean;
          description
           "If this LDP entity uses targeted peer then set
            this to true.";
          smiv2:defval "false";
          smiv2:max-access "read-write";
          smiv2:oid "1.3.6.1.2.1.10.166.4.1.2.3.1.17";
        }

        leaf mplsLdpEntityTargetPeerAddrType {
          type inet-address:InetAddressType;
          description
           "The type of the internetwork layer address used for
            the Extended Discovery.  This object indicates how
            the value of mplsLdpEntityTargetPeerAddr is to
            be interpreted.";
          smiv2:max-access "read-write";
          smiv2:oid "1.3.6.1.2.1.10.166.4.1.2.3.1.18";
        }

        leaf mplsLdpEntityTargetPeerAddr {
          type inet-address:InetAddress;
          description
           "The value of the internetwork layer address
            used for the Extended Discovery.  The value of
            mplsLdpEntityTargetPeerAddrType specifies how
            this address is to be interpreted.";
          smiv2:max-access "read-write";
          smiv2:oid "1.3.6.1.2.1.10.166.4.1.2.3.1.19";
        }

        leaf mplsLdpEntityLabelType {
          type mpls-tc:MplsLdpLabelType;
          description
           "Specifies the optional parameters for the LDP
            Initialization Message.
            
            If the value is generic(1) then no
            optional parameters will be sent in
            the LDP Initialization message associated
            with this Entity.
            
            If the value is atmParameters(2) then
            a row must be created in the
            mplsLdpEntityAtmTable, which
            corresponds to this entry.
            
            If the value is frameRelayParameters(3) then
            a row must be created in the
            mplsLdpEntityFrameRelayTable, which
            corresponds to this entry.";
          reference
           "RFC3036, LDP Specification, Section 3.5.3.,
            Initialization Message.";
          smiv2:max-access "read-write";
          smiv2:oid "1.3.6.1.2.1.10.166.4.1.2.3.1.20";
        }

        leaf mplsLdpEntityDiscontinuityTime {
          type yang:timestamp;
          description
           "The value of sysUpTime on the most recent occasion
            at which any one or more of this entity's counters
            suffered a discontinuity.  The relevant counters
            are the specific instances associated with this
            entity of any Counter32 object contained
            in the 'mplsLdpEntityStatsTable'.  If no such
            discontinuities have occurred since the last
            re-initialization of the local management
            subsystem, then this object contains a zero
            value.";
          smiv2:max-access "read-only";
          smiv2:oid "1.3.6.1.2.1.10.166.4.1.2.3.1.21";
        }

        leaf mplsLdpEntityStorageType {
          type snmpv2-tc:StorageType;
          description
           "The storage type for this conceptual row.
            Conceptual rows having the value 'permanent(4)'
            need not allow write-access to any columnar
            objects in the row.";
          smiv2:defval "nonVolatile";
          smiv2:max-access "read-write";
          smiv2:oid "1.3.6.1.2.1.10.166.4.1.2.3.1.22";
        }

        leaf mplsLdpEntityRowStatus {
          type snmpv2-tc:RowStatus;
          description
           "The status of this conceptual row.  All writable
            objects in this row may be modified at any
            time, however, as described in detail in
            the section entitled, 'Changing Values After
            Session Establishment', and again described
            in the DESCRIPTION clause of the
            mplsLdpEntityAdminStatus object, if a session
            has been initiated with a Peer, changing objects
            in this table will wreak havoc with the session
            and interrupt traffic.  To repeat again:
            the recommended procedure is to
            set the mplsLdpEntityAdminStatus to down, thereby
            explicitly causing a session to be torn down. Then,
            change objects in this entry, then set
            the mplsLdpEntityAdminStatus to enable,
            which enables a new session to be initiated.";
          smiv2:max-access "read-write";
          smiv2:oid "1.3.6.1.2.1.10.166.4.1.2.3.1.23";
        }
      }
    }

    container mplsLdpPeerTable {
      description
       "Information about LDP peers known by Entities in
        the mplsLdpEntityTable.  The information in this table
        is based on information from the Entity-Peer interaction
        during session initialization but is not appropriate
        for the mplsLdpSessionTable, because objects in this
        table may or may not be used in session establishment.";
      smiv2:oid "1.3.6.1.2.1.10.166.4.1.3.2";

      list mplsLdpPeerEntry {
        key "mplsLdpEntityLdpId mplsLdpEntityIndex mplsLdpPeerLdpId";
        description
         "Information about a single Peer which is related
          to a Session.  This table is augmented by
          the mplsLdpSessionTable.";
        smiv2:oid "1.3.6.1.2.1.10.166.4.1.3.2.1";

        leaf mplsLdpEntityLdpId {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityLdpId";
          }
        }

        leaf mplsLdpEntityIndex {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityIndex";
          }
        }

        leaf mplsLdpPeerLdpId {
          type mpls-tc:MplsLdpIdentifier;
          description
           "The LDP identifier of this LDP Peer.";
          smiv2:max-access "not-accessible";
          smiv2:oid "1.3.6.1.2.1.10.166.4.1.3.2.1.1";
        }

        leaf mplsLdpPeerLabelDistMethod {
          type mpls-tc:MplsLabelDistributionMethod;
          description
           "For any given LDP session, the method of
            label distribution must be specified.";
          smiv2:max-access "read-only";
          smiv2:oid "1.3.6.1.2.1.10.166.4.1.3.2.1.2";
        }

        leaf mplsLdpPeerPathVectorLimit {
          type int32 {
            range "0..255";
          }
          description
           "If the value of this object is 0 (zero) then
            Loop Dection for Path Vectors for this Peer
            is disabled.
            
            Otherwise, if this object has a value greater than
            zero, then Loop Dection for Path  Vectors for this
            Peer is enabled and the Path Vector Limit is this value.";
          reference
           "RFC3036, LDP Specification, Section 2.8 Loop Dection,
            Section 3.4.5 Path Vector TLV.";
          smiv2:max-access "read-only";
          smiv2:oid "1.3.6.1.2.1.10.166.4.1.3.2.1.3";
        }

        leaf mplsLdpPeerTransportAddrType {
          type inet-address:InetAddressType;
          description
           "The type of the Internet address for the
            mplsLdpPeerTransportAddr object.  The LDP
            specification describes this as being either
            an IPv4 Transport Address or IPv6 Transport
            
            
            Address which is used in opening the LDP session's
            TCP connection, or if the optional TLV is not
            present, then this is the IPv4/IPv6 source
            address for the UPD packet carrying the Hellos.
            
            This object specifies how the value of the
            mplsLdpPeerTransportAddr object should be
            interpreted.";
          reference
           "RFC3036, LDP Specification, Section 2.5.2
            Transport Connection Establishment and
            Section 3.5.2.1 Hello Message Procedures.";
          smiv2:max-access "read-only";
          smiv2:oid "1.3.6.1.2.1.10.166.4.1.3.2.1.4";
        }

        leaf mplsLdpPeerTransportAddr {
          type inet-address:InetAddress;
          description
           "The Internet address advertised by the peer
            in the Hello Message or the Hello source address.
            
            The type of this address is specified by the
            value of the mplsLdpPeerTransportAddrType
            object.";
          reference
           "RFC3036, LDP Specification, Section 2.5.2
            Transport Connection Establishment and
            Section 3.5.2.1 Hello Message Procedures.";
          smiv2:max-access "read-only";
          smiv2:oid "1.3.6.1.2.1.10.166.4.1.3.2.1.5";
        }
      }
    }

    container mplsLdpHelloAdjacencyTable {
      description
       "A table of Hello Adjacencies for Sessions.";
      smiv2:oid "1.3.6.1.2.1.10.166.4.1.3.5.1";

      list mplsLdpHelloAdjacencyEntry {
        key "mplsLdpEntityLdpId mplsLdpEntityIndex mplsLdpPeerLdpId mplsLdpHelloAdjacencyIndex";
        description
         "Each row represents a single LDP Hello Adjacency.
          An LDP Session can have one or more Hello
          Adjacencies.";
        smiv2:oid "1.3.6.1.2.1.10.166.4.1.3.5.1.1";

        leaf mplsLdpEntityLdpId {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityLdpId";
          }
        }

        leaf mplsLdpEntityIndex {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityIndex";
          }
        }

        leaf mplsLdpPeerLdpId {
          type leafref {
            path "/MPLS-LDP-STD-MIB:MPLS-LDP-STD-MIB/MPLS-LDP-STD-MIB:mplsLdpPeerTable/MPLS-LDP-STD-MIB:mplsLdpPeerEntry/MPLS-LDP-STD-MIB:mplsLdpPeerLdpId";
          }
        }

        leaf mplsLdpHelloAdjacencyIndex {
          type uint32 {
            range "1..4294967295";
          }
          description
           "An identifier for this specific adjacency.";
          smiv2:max-access "not-accessible";
          smiv2:oid "1.3.6.1.2.1.10.166.4.1.3.5.1.1.1";
        }

        leaf mplsLdpHelloAdjacencyHoldTimeRem {
          type snmpv2-tc:TimeInterval;
          units "seconds";
          description
           "If the value of this object is 65535,
            this means that the hold time is infinite
            (i.e., wait forever).
            
            Otherwise, the time remaining for
            this Hello Adjacency to receive its
            next Hello Message.
            
            This interval will change when the 'next'
            Hello Message which corresponds to this
            Hello Adjacency is received unless it
            is infinite.";
          smiv2:max-access "read-only";
          smiv2:oid "1.3.6.1.2.1.10.166.4.1.3.5.1.1.2";
        }

        leaf mplsLdpHelloAdjacencyHoldTime {
          type uint32 {
            range "0..65535";
          }
          description
           "The Hello hold time which is negotiated between
            the Entity and the Peer.  The entity associated
            with this Hello Adjacency issues a proposed
            Hello Hold Time value in the
            mplsLdpEntityHelloHoldTimer object.  The peer
            also proposes a value and this object represents
            the negotiated value.
            
            A value of 0 means the default,
            which is 15 seconds for Link Hellos
            and 45 seconds for Targeted Hellos.
            A value of 65535 indicates an
            infinite hold time.";
          reference
           "RFC3036, LDP Specification, Section 3.5.2 Hello Message";
          smiv2:max-access "read-only";
          smiv2:oid "1.3.6.1.2.1.10.166.4.1.3.5.1.1.3";
        }

        leaf mplsLdpHelloAdjacencyType {
          type enumeration {
            enum "link" {
              value "1";
            }
            enum "targeted" {
              value "2";
            }
          }
          description
           "This adjacency is the result of a 'link'
            hello if the value of this object is link(1).
            
            
            Otherwise, it is a result of a 'targeted'
            hello, targeted(2).";
          smiv2:max-access "read-only";
          smiv2:oid "1.3.6.1.2.1.10.166.4.1.3.5.1.1.4";
        }
      }
    }

    container mplsInSegmentLdpLspTable {
      description
       "A table of LDP LSP's which
        map to the mplsInSegmentTable in the
        MPLS-LSR-STD-MIB module.";
      smiv2:oid "1.3.6.1.2.1.10.166.4.1.3.6";

      list mplsInSegmentLdpLspEntry {
        key "mplsLdpEntityLdpId mplsLdpEntityIndex mplsLdpPeerLdpId mplsInSegmentLdpLspIndex";
        description
         "An entry in this table represents information
          on a single LDP LSP which is represented by
          a session's index triple (mplsLdpEntityLdpId,
          mplsLdpEntityIndex, mplsLdpPeerLdpId) AND the
          index for the mplsInSegmentTable
          (mplsInSegmentLdpLspLabelIndex) from the
          MPLS-LSR-STD-MIB.
          
          The information contained in a row is read-only.";
        smiv2:oid "1.3.6.1.2.1.10.166.4.1.3.6.1";

        leaf mplsLdpEntityLdpId {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityLdpId";
          }
        }

        leaf mplsLdpEntityIndex {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityIndex";
          }
        }

        leaf mplsLdpPeerLdpId {
          type leafref {
            path "/MPLS-LDP-STD-MIB:MPLS-LDP-STD-MIB/MPLS-LDP-STD-MIB:mplsLdpPeerTable/MPLS-LDP-STD-MIB:mplsLdpPeerEntry/MPLS-LDP-STD-MIB:mplsLdpPeerLdpId";
          }
        }

        leaf mplsInSegmentLdpLspIndex {
          type mpls-lsr:MplsIndexType;
          description
           "This contains the same value as the
            mplsInSegmentIndex in the
            MPLS-LSR-STD-MIB's mplsInSegmentTable.";
          smiv2:max-access "not-accessible";
          smiv2:oid "1.3.6.1.2.1.10.166.4.1.3.6.1.1";
        }

        leaf mplsInSegmentLdpLspLabelType {
          type mpls-tc:MplsLdpLabelType;
          description
           "The Layer 2 Label Type.";
          smiv2:max-access "read-only";
          smiv2:oid "1.3.6.1.2.1.10.166.4.1.3.6.1.2";
        }

        leaf mplsInSegmentLdpLspType {
          type mpls-tc:MplsLspType;
          description
           "The type of LSP connection.";
          smiv2:max-access "read-only";
          smiv2:oid "1.3.6.1.2.1.10.166.4.1.3.6.1.3";
        }
      }
    }

    container mplsOutSegmentLdpLspTable {
      description
       "A table of LDP LSP's which
        map to the mplsOutSegmentTable in the
        MPLS-LSR-STD-MIB.";
      smiv2:oid "1.3.6.1.2.1.10.166.4.1.3.7";

      list mplsOutSegmentLdpLspEntry {
        key "mplsLdpEntityLdpId mplsLdpEntityIndex mplsLdpPeerLdpId mplsOutSegmentLdpLspIndex";
        description
         "An entry in this table represents information
          on a single LDP LSP which is represented by
          a session's index triple (mplsLdpEntityLdpId,
          mplsLdpEntityIndex, mplsLdpPeerLdpId) AND the
          index (mplsOutSegmentLdpLspIndex)
          for the mplsOutSegmentTable.
          
          The information contained in a row is read-only.";
        smiv2:oid "1.3.6.1.2.1.10.166.4.1.3.7.1";

        leaf mplsLdpEntityLdpId {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityLdpId";
          }
        }

        leaf mplsLdpEntityIndex {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityIndex";
          }
        }

        leaf mplsLdpPeerLdpId {
          type leafref {
            path "/MPLS-LDP-STD-MIB:MPLS-LDP-STD-MIB/MPLS-LDP-STD-MIB:mplsLdpPeerTable/MPLS-LDP-STD-MIB:mplsLdpPeerEntry/MPLS-LDP-STD-MIB:mplsLdpPeerLdpId";
          }
        }

        leaf mplsOutSegmentLdpLspIndex {
          type mpls-lsr:MplsIndexType;
          description
           "This contains the same value as the
            mplsOutSegmentIndex in the
            MPLS-LSR-STD-MIB's mplsOutSegmentTable.";
          smiv2:max-access "not-accessible";
          smiv2:oid "1.3.6.1.2.1.10.166.4.1.3.7.1.1";
        }

        leaf mplsOutSegmentLdpLspLabelType {
          type mpls-tc:MplsLdpLabelType;
          description
           "The Layer 2 Label Type.";
          smiv2:max-access "read-only";
          smiv2:oid "1.3.6.1.2.1.10.166.4.1.3.7.1.2";
        }

        leaf mplsOutSegmentLdpLspType {
          type mpls-tc:MplsLspType;
          description
           "The type of LSP connection.";
          smiv2:max-access "read-only";
          smiv2:oid "1.3.6.1.2.1.10.166.4.1.3.7.1.3";
        }
      }
    }

    container mplsFecTable {
      description
       "This table represents the FEC
        (Forwarding Equivalence Class)
        Information associated with an LSP.";
      smiv2:oid "1.3.6.1.2.1.10.166.4.1.3.8.3";

      list mplsFecEntry {
        key "mplsFecIndex";
        description
         "Each row represents a single FEC Element.";
        smiv2:oid "1.3.6.1.2.1.10.166.4.1.3.8.3.1";

        leaf mplsFecIndex {
          type diffserv-mib:IndexInteger;
          description
           "The index which uniquely identifies this entry.";
          smiv2:max-access "not-accessible";
          smiv2:oid "1.3.6.1.2.1.10.166.4.1.3.8.3.1.1";
        }

        leaf mplsFecType {
          type enumeration {
            enum "prefix" {
              value "1";
            }
            enum "hostAddress" {
              value "2";
            }
          }
          description
           "The type of the FEC.  If the value of this object
            is 'prefix(1)' then the FEC type described by this
            row is an address prefix.
            
            If the value of this object is 'hostAddress(2)' then
            the FEC type described by this row is a host address.";
          reference
           "RFC3036, Section 3.4.1. FEC TLV.";
          smiv2:max-access "read-write";
          smiv2:oid "1.3.6.1.2.1.10.166.4.1.3.8.3.1.2";
        }

        leaf mplsFecAddrPrefixLength {
          type inet-address:InetAddressPrefixLength;
          description
           "If the value of the 'mplsFecType' is 'hostAddress(2)'
            then this object is undefined.
            
            If the value of 'mplsFecType' is 'prefix(1)'
            then the value of this object is the length in
            bits of the address prefix represented by
            'mplsFecAddr', or zero.  If the value of this
            object is zero, this indicates that the
            prefix matches all addresses.  In this case the
            address prefix MUST also be zero (i.e., 'mplsFecAddr'
            should have the value of zero.)";
          reference
           "RFC3036, Section 3.4.1. FEC TLV.";
          smiv2:defval "0";
          smiv2:max-access "read-write";
          smiv2:oid "1.3.6.1.2.1.10.166.4.1.3.8.3.1.3";
        }

        leaf mplsFecAddrType {
          type inet-address:InetAddressType;
          description
           "The value of this object is the type of the
            Internet address.  The value of this object,
            decides how the value of the mplsFecAddr object
            is interpreted.";
          reference
           "RFC3036, Section 3.4.1. FEC TLV.";
          smiv2:max-access "read-write";
          smiv2:oid "1.3.6.1.2.1.10.166.4.1.3.8.3.1.4";
        }

        leaf mplsFecAddr {
          type inet-address:InetAddress;
          description
           "The value of this object is interpreted based
            on the value of the 'mplsFecAddrType' object.
            
            This address is then further interpretted as
            an being used with the address prefix,
            or as the host address.  This further interpretation
            is indicated by the 'mplsFecType' object.
            In other words, the FEC element is populated
            according to the Prefix FEC Element value encoding, or
            the Host Address FEC Element encoding.";
          reference
           "RFC3036, Section 3.4.1 FEC TLV.";
          smiv2:max-access "read-write";
          smiv2:oid "1.3.6.1.2.1.10.166.4.1.3.8.3.1.5";
        }

        leaf mplsFecStorageType {
          type snmpv2-tc:StorageType;
          description
           "The storage type for this conceptual row.
            Conceptual rows having the value 'permanent(4)'
            need not allow write-access to any columnar
            objects in the row.";
          smiv2:defval "nonVolatile";
          smiv2:max-access "read-write";
          smiv2:oid "1.3.6.1.2.1.10.166.4.1.3.8.3.1.6";
        }

        leaf mplsFecRowStatus {
          type snmpv2-tc:RowStatus;
          description
           "The status of this conceptual row.  If the value of this
            object is 'active(1)', then none of the writable objects
            of this entry can be modified, except to set this object
            to 'destroy(6)'.
            
            NOTE: if this row is being referenced by any entry in
            the mplsLdpLspFecTable, then a request to destroy
            this row, will result in an inconsistentValue error.";
          smiv2:max-access "read-write";
          smiv2:oid "1.3.6.1.2.1.10.166.4.1.3.8.3.1.7";
        }
      }
    }

    container mplsLdpLspFecTable {
      description
       "A table which shows the relationship between
        LDP LSPs and FECs.  Each row represents
        a single LDP LSP to FEC association.";
      smiv2:oid "1.3.6.1.2.1.10.166.4.1.3.10";

      list mplsLdpLspFecEntry {
        key "mplsLdpEntityLdpId mplsLdpEntityIndex mplsLdpPeerLdpId mplsLdpLspFecSegment mplsLdpLspFecSegmentIndex mplsLdpLspFecIndex";
        description
         "An entry represents a LDP LSP
          to FEC association.";
        smiv2:oid "1.3.6.1.2.1.10.166.4.1.3.10.1";

        leaf mplsLdpEntityLdpId {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityLdpId";
          }
        }

        leaf mplsLdpEntityIndex {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityIndex";
          }
        }

        leaf mplsLdpPeerLdpId {
          type leafref {
            path "/MPLS-LDP-STD-MIB:MPLS-LDP-STD-MIB/MPLS-LDP-STD-MIB:mplsLdpPeerTable/MPLS-LDP-STD-MIB:mplsLdpPeerEntry/MPLS-LDP-STD-MIB:mplsLdpPeerLdpId";
          }
        }

        leaf mplsLdpLspFecSegment {
          type enumeration {
            enum "inSegment" {
              value "1";
            }
            enum "outSegment" {
              value "2";
            }
          }
          description
           "If the value is inSegment(1), then this
            indicates that the following index,
            mplsLdpLspFecSegmentIndex, contains the same
            value as the mplsInSegmentLdpLspIndex.
            
            Otherwise, if the value of this object is
            
            
            outSegment(2),  then this
            indicates that following index,
            mplsLdpLspFecSegmentIndex, contains the same
            value as the mplsOutSegmentLdpLspIndex.";
          smiv2:max-access "not-accessible";
          smiv2:oid "1.3.6.1.2.1.10.166.4.1.3.10.1.1";
        }

        leaf mplsLdpLspFecSegmentIndex {
          type mpls-lsr:MplsIndexType;
          description
           "This index is interpretted by using the value
            of the mplsLdpLspFecSegment.
            
            If the mplsLdpLspFecSegment is inSegment(1),
            then this index has the same value as
            mplsInSegmentLdpLspIndex.
            
            If the mplsLdpLspFecSegment is outSegment(2),
            then this index has the same value as
            mplsOutSegmentLdpLspIndex.";
          smiv2:max-access "not-accessible";
          smiv2:oid "1.3.6.1.2.1.10.166.4.1.3.10.1.2";
        }

        leaf mplsLdpLspFecIndex {
          type diffserv-mib:IndexInteger;
          description
           "This index identifies the FEC entry in the
            mplsFecTable associated with this session.
            In other words, the value of this index
            is the same as the value of the mplsFecIndex
            that denotes the FEC associated with this
            Session.";
          smiv2:max-access "not-accessible";
          smiv2:oid "1.3.6.1.2.1.10.166.4.1.3.10.1.3";
        }

        leaf mplsLdpLspFecStorageType {
          type snmpv2-tc:StorageType;
          description
           "The storage type for this conceptual row.
            Conceptual rows having the value 'permanent(4)'
            need not allow write-access to any columnar
            objects in the row.";
          smiv2:defval "nonVolatile";
          smiv2:max-access "read-write";
          smiv2:oid "1.3.6.1.2.1.10.166.4.1.3.10.1.4";
        }

        leaf mplsLdpLspFecRowStatus {
          type snmpv2-tc:RowStatus;
          description
           "The status of this conceptual row.  If the
            value of this object is 'active(1)', then
            none of the writable objects of this entry
            can be modified.
            
            The Agent should delete this row when
            the session ceases to exist.  If an
            operator wants to associate the session with
            a different FEC, the recommended
            procedure is (as described in detail in the section
            entitled, 'Changing Values After Session
            Establishment', and again described in the
            DESCRIPTION clause of the
            mplsLdpEntityAdminStatus object)
            is to set the mplsLdpEntityAdminStatus to
            down, thereby explicitly causing a session
            to be torn down. This will also
            cause this entry to be deleted.
            
            Then, set the mplsLdpEntityAdminStatus
            to enable which enables a new session to be initiated.
            Once the session is initiated, an entry may be
            added to this table to associate the new session
            with a FEC.";
          smiv2:max-access "read-write";
          smiv2:oid "1.3.6.1.2.1.10.166.4.1.3.10.1.5";
        }
      }
    }

    container mplsLdpSessionPeerAddrTable {
      description
       "This table 'extends' the mplsLdpSessionTable.
        This table is used to store Label Address Information
        from Label Address Messages received by this LSR from
        Peers.  This table is read-only and should be updated
        
        
        when Label Withdraw Address Messages are received, i.e.,
        Rows should be deleted as appropriate.
        
        NOTE:  since more than one address may be contained
        in a Label Address Message, this table 'sparse augments',
        the mplsLdpSessionTable's information.";
      smiv2:oid "1.3.6.1.2.1.10.166.4.1.3.11";

      list mplsLdpSessionPeerAddrEntry {
        key "mplsLdpEntityLdpId mplsLdpEntityIndex mplsLdpPeerLdpId mplsLdpSessionPeerAddrIndex";
        description
         "An entry in this table represents information on
          a session's single next hop address which was
          advertised in an Address Message from the LDP peer.
          The information contained in a row is read-only.";
        smiv2:oid "1.3.6.1.2.1.10.166.4.1.3.11.1";

        leaf mplsLdpEntityLdpId {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityLdpId";
          }
        }

        leaf mplsLdpEntityIndex {
          type leafref {
            path "/MPLS-LDP-STD-MIB:MPLS-LDP-STD-MIB/MPLS-LDP-STD-MIB:mplsLdpEntityTable/MPLS-LDP-STD-MIB:mplsLdpEntityEntry/MPLS-LDP-STD-MIB:mplsLdpEntityIndex";
          }
        }

        leaf mplsLdpPeerLdpId {
          type leafref {
            path "/MPLS-LDP-STD-MIB:MPLS-LDP-STD-MIB/MPLS-LDP-STD-MIB:mplsLdpPeerTable/MPLS-LDP-STD-MIB:mplsLdpPeerEntry/MPLS-LDP-STD-MIB:mplsLdpPeerLdpId";
          }
        }

        leaf mplsLdpSessionPeerAddrIndex {
          type uint32 {
            range "1..4294967295";
          }
          description
           "An index which uniquely identifies this entry within
            a given session.";
          smiv2:max-access "not-accessible";
          smiv2:oid "1.3.6.1.2.1.10.166.4.1.3.11.1.1";
        }

        leaf mplsLdpSessionPeerNextHopAddrType {
          type inet-address:InetAddressType;
          description
           "The internetwork layer address type of this Next Hop
            Address as specified in the Label Address Message
            associated with this Session. The value of this
            object indicates how to interpret the value of
            
            
            mplsLdpSessionPeerNextHopAddr.";
          smiv2:max-access "read-only";
          smiv2:oid "1.3.6.1.2.1.10.166.4.1.3.11.1.2";
        }

        leaf mplsLdpSessionPeerNextHopAddr {
          type inet-address:InetAddress;
          description
           "The next hop address.  The type of this address
            is specified by the value of the
            mplsLdpSessionPeerNextHopAddrType.";
          reference
           "RFC3036, Section 2.7. LDP Identifiers
            and Next Hop Addresses";
          smiv2:max-access "read-only";
          smiv2:oid "1.3.6.1.2.1.10.166.4.1.3.11.1.3";
        }
      }
    }
  }

  smiv2:alias "mplsLdpEntityStatsTable" {
    description
     "This table is a read-only table which augments
      the mplsLdpEntityTable.  The purpose of this
      table is to keep statistical information about
      the LDP Entities on the LSR.";
    smiv2:oid "1.3.6.1.2.1.10.166.4.1.2.4";
  }

  smiv2:alias "mplsLdpEntityStatsEntry" {
    description
     "A row in this table contains statistical information
      about an LDP Entity.  Some counters contained in a
      row are for fatal errors received during a former
      LDP Session associated with this entry.  For example,
      an LDP PDU received on a TCP connection during an
      LDP Session contains a fatal error.  That
      error is counted here, because the
      session is terminated.
      
      If the error is NOT fatal (i.e., the Session
      remains), then the error is counted in the
      mplsLdpSessionStatsEntry.";
    smiv2:oid "1.3.6.1.2.1.10.166.4.1.2.4.1";
  }

  augment "/MPLS-LDP-STD-MIB:MPLS-LDP-STD-MIB/MPLS-LDP-STD-MIB:mplsLdpEntityTable/MPLS-LDP-STD-MIB:mplsLdpEntityEntry" {
    description
     "A row in this table contains statistical information
      about an LDP Entity.  Some counters contained in a
      row are for fatal errors received during a former
      LDP Session associated with this entry.  For example,
      an LDP PDU received on a TCP connection during an
      LDP Session contains a fatal error.  That
      error is counted here, because the
      session is terminated.
      
      If the error is NOT fatal (i.e., the Session
      remains), then the error is counted in the
      mplsLdpSessionStatsEntry.";
    smiv2:oid "1.3.6.1.2.1.10.166.4.1.2.4.1";

    leaf mplsLdpEntityStatsSessionAttempts {
      type yang:counter32;
      description
       "A count of the Session Initialization messages
        which were sent or received by this LDP Entity and
        were NAK'd.   In other words, this counter counts
        the number of session initializations that failed.
        
        Discontinuities in the value of this counter can occur
        at re-initialization of the management system, and at
        other times as indicated by the value of
        mplsLdpEntityDiscontinuityTime.";
      smiv2:max-access "read-only";
      smiv2:oid "1.3.6.1.2.1.10.166.4.1.2.4.1.1";
    }

    leaf mplsLdpEntityStatsSessionRejectedNoHelloErrors {
      type yang:counter32;
      description
       "A count of the Session Rejected/No Hello Error
        Notification Messages sent or received by
        this LDP Entity.
        
        Discontinuities in the value of this counter can occur
        at re-initialization of the management system, and at
        other times as indicated by the value of
        mplsLdpEntityDiscontinuityTime.";
      smiv2:max-access "read-only";
      smiv2:oid "1.3.6.1.2.1.10.166.4.1.2.4.1.2";
    }

    leaf mplsLdpEntityStatsSessionRejectedAdErrors {
      type yang:counter32;
      description
       "A count of the Session Rejected/Parameters
        Advertisement Mode Error Notification Messages sent
        or received by this LDP Entity.
        
        Discontinuities in the value of this counter can occur
        at re-initialization of the management system, and at
        other times as indicated by the value of
        mplsLdpEntityDiscontinuityTime.";
      smiv2:max-access "read-only";
      smiv2:oid "1.3.6.1.2.1.10.166.4.1.2.4.1.3";
    }

    leaf mplsLdpEntityStatsSessionRejectedMaxPduErrors {
      type yang:counter32;
      description
       "A count of the Session Rejected/Parameters
        
        Max Pdu Length Error Notification Messages sent
        or received by this LDP Entity.
        
        Discontinuities in the value of this counter can occur
        at re-initialization of the management system, and at
        other times as indicated by the value of
        mplsLdpEntityDiscontinuityTime.";
      smiv2:max-access "read-only";
      smiv2:oid "1.3.6.1.2.1.10.166.4.1.2.4.1.4";
    }

    leaf mplsLdpEntityStatsSessionRejectedLRErrors {
      type yang:counter32;
      description
       "A count of the Session Rejected/Parameters
        Label Range Notification Messages sent
        or received by this LDP Entity.
        
        Discontinuities in the value of this counter can occur
        at re-initialization of the management system, and at
        other times as indicated by the value of
        mplsLdpEntityDiscontinuityTime.";
      smiv2:max-access "read-only";
      smiv2:oid "1.3.6.1.2.1.10.166.4.1.2.4.1.5";
    }

    leaf mplsLdpEntityStatsBadLdpIdentifierErrors {
      type yang:counter32;
      description
       "This object counts the number of Bad LDP Identifier
        Fatal Errors detected by the session(s)
        (past and present) associated with this LDP Entity.
        
        Discontinuities in the value of this counter can occur
        at re-initialization of the management system, and at
        other times as indicated by the value of
        mplsLdpEntityDiscontinuityTime.";
      reference
       "RFC3036, LDP Specification, Section 3.5.1.2.";
      smiv2:max-access "read-only";
      smiv2:oid "1.3.6.1.2.1.10.166.4.1.2.4.1.6";
    }

    leaf mplsLdpEntityStatsBadPduLengthErrors {
      type yang:counter32;
      description
       "This object counts the number of Bad PDU Length
        Fatal Errors detected by the session(s)
        (past and present) associated with this LDP Entity.
        
        Discontinuities in the value of this counter can occur
        at re-initialization of the management system, and at
        other times as indicated by the value of
        mplsLdpEntityDiscontinuityTime.";
      reference
       "RFC3036, LDP Specification, Section 3.5.1.2.";
      smiv2:max-access "read-only";
      smiv2:oid "1.3.6.1.2.1.10.166.4.1.2.4.1.7";
    }

    leaf mplsLdpEntityStatsBadMessageLengthErrors {
      type yang:counter32;
      description
       "This object counts the number of Bad Message
        Length Fatal Errors detected by the session(s)
        (past and present) associated with this LDP Entity.
        
        Discontinuities in the value of this counter can occur
        at re-initialization of the management system, and at
        other times as indicated by the value of
        mplsLdpEntityDiscontinuityTime.";
      reference
       "RFC3036, LDP Specification, Section 3.5.1.2.";
      smiv2:max-access "read-only";
      smiv2:oid "1.3.6.1.2.1.10.166.4.1.2.4.1.8";
    }

    leaf mplsLdpEntityStatsBadTlvLengthErrors {
      type yang:counter32;
      description
       "This object counts the number of Bad TLV
        Length Fatal Errors detected by the session(s)
        (past and present) associated with this LDP Entity.
        
        Discontinuities in the value of this counter can occur
        at re-initialization of the management system, and at
        other times as indicated by the value of
        mplsLdpEntityDiscontinuityTime.";
      reference
       "RFC3036, LDP Specification, Section 3.5.1.2.";
      smiv2:max-access "read-only";
      smiv2:oid "1.3.6.1.2.1.10.166.4.1.2.4.1.9";
    }

    leaf mplsLdpEntityStatsMalformedTlvValueErrors {
      type yang:counter32;
      description
       "This object counts the number of Malformed TLV
        Value Fatal Errors detected by the session(s)
        (past and present) associated with this
        LDP Entity.
        
        Discontinuities in the value of this counter can occur
        at re-initialization of the management system, and at
        other times as indicated by the value of
        mplsLdpEntityDiscontinuityTime.";
      reference
       "RFC3036, LDP Specification, Section 3.5.1.2.";
      smiv2:max-access "read-only";
      smiv2:oid "1.3.6.1.2.1.10.166.4.1.2.4.1.10";
    }

    leaf mplsLdpEntityStatsKeepAliveTimerExpErrors {
      type yang:counter32;
      description
       "This object counts the number of Session Keep Alive
        Timer Expired Errors detected by the session(s)
        (past and present) associated with this LDP Entity.
        
        Discontinuities in the value of this counter can occur
        at re-initialization of the management system, and at
        other times as indicated by the value of
        mplsLdpEntityDiscontinuityTime.";
      reference
       "RFC3036, LDP Specification, Section 3.5.1.2.";
      smiv2:max-access "read-only";
      smiv2:oid "1.3.6.1.2.1.10.166.4.1.2.4.1.11";
    }

    leaf mplsLdpEntityStatsShutdownReceivedNotifications {
      type yang:counter32;
      description
       "This object counts the number of Shutdown Notifications
        received related to session(s) (past and present)
        associated with this LDP Entity.
        
        Discontinuities in the value of this counter can occur
        at re-initialization of the management system, and at
        other times as indicated by the value of
        mplsLdpEntityDiscontinuityTime.";
      smiv2:max-access "read-only";
      smiv2:oid "1.3.6.1.2.1.10.166.4.1.2.4.1.12";
    }

    leaf mplsLdpEntityStatsShutdownSentNotifications {
      type yang:counter32;
      description
       "This object counts the number of Shutdown Notfications
        sent related to session(s) (past and present) associated
        with this LDP Entity.
        
        Discontinuities in the value of this counter can occur
        at re-initialization of the management system, and at
        other times as indicated by the value of
        
        
        mplsLdpEntityDiscontinuityTime.";
      smiv2:max-access "read-only";
      smiv2:oid "1.3.6.1.2.1.10.166.4.1.2.4.1.13";
    }
  }

  smiv2:alias "mplsLdpSessionTable" {
    description
     "A table of Sessions between the LDP Entities
      and LDP Peers.  This table AUGMENTS the
      mplsLdpPeerTable.  Each row in this table
      represents a single session.";
    smiv2:oid "1.3.6.1.2.1.10.166.4.1.3.3";
  }

  smiv2:alias "mplsLdpSessionEntry" {
    description
     "An entry in this table represents information on a
      single session between an LDP Entity and LDP Peer.
      The information contained in a row is read-only.
      
      Please note:  the Path Vector Limit for the
      Session is the value which is configured in
      the corresponding mplsLdpEntityEntry. The
      Peer's Path Vector Limit is in the
      mplsLdpPeerPathVectorLimit object in the
      mplsLdpPeerTable.
      
      Values which may differ from those configured are
      noted in the objects of this table, the
      mplsLdpAtmSessionTable and the
      mplsLdpFrameRelaySessionTable. A value will
      differ if it was negotiated between the
      Entity and the Peer.  Values may or may not
      be negotiated.  For example, if the values
      are the same then no negotiation takes place.
      If they are negotiated, then they may differ.";
    smiv2:oid "1.3.6.1.2.1.10.166.4.1.3.3.1";
  }

  augment "/MPLS-LDP-STD-MIB:MPLS-LDP-STD-MIB/MPLS-LDP-STD-MIB:mplsLdpPeerTable/MPLS-LDP-STD-MIB:mplsLdpPeerEntry" {
    description
     "An entry in this table represents information on a
      single session between an LDP Entity and LDP Peer.
      The information contained in a row is read-only.
      
      Please note:  the Path Vector Limit for the
      Session is the value which is configured in
      the corresponding mplsLdpEntityEntry. The
      Peer's Path Vector Limit is in the
      mplsLdpPeerPathVectorLimit object in the
      mplsLdpPeerTable.
      
      Values which may differ from those configured are
      noted in the objects of this table, the
      mplsLdpAtmSessionTable and the
      mplsLdpFrameRelaySessionTable. A value will
      differ if it was negotiated between the
      Entity and the Peer.  Values may or may not
      be negotiated.  For example, if the values
      are the same then no negotiation takes place.
      If they are negotiated, then they may differ.";
    smiv2:oid "1.3.6.1.2.1.10.166.4.1.3.3.1";

    leaf mplsLdpSessionStateLastChange {
      type yang:timestamp;
      description
       "The value of sysUpTime at the time this
        Session entered its current state as
        denoted by the mplsLdpSessionState
        object.";
      smiv2:max-access "read-only";
      smiv2:oid "1.3.6.1.2.1.10.166.4.1.3.3.1.1";
    }

    leaf mplsLdpSessionState {
      type enumeration {
        enum "nonexistent" {
          value "1";
        }
        enum "initialized" {
          value "2";
        }
        enum "openrec" {
          value "3";
        }
        enum "opensent" {
          value "4";
        }
        enum "operational" {
          value "5";
        }
      }
      description
       "The current state of the session, all of the
        states 1 to 5 are based on the state machine
        for session negotiation behavior.";
      reference
       "RFC3036, LDP Specification, Section 2.5.4,
        Initialization State Machine.";
      smiv2:max-access "read-only";
      smiv2:oid "1.3.6.1.2.1.10.166.4.1.3.3.1.2";
    }

    leaf mplsLdpSessionRole {
      type enumeration {
        enum "unknown" {
          value "1";
        }
        enum "active" {
          value "2";
        }
        enum "passive" {
          value "3";
        }
      }
      description
       "During session establishment the LSR/LER takes either
        the active role or the passive role based on address
        comparisons.  This object indicates whether this LSR/LER
        was behaving in an active role or passive role during
        this session's establishment.
        
        The value of unknown(1), indicates that the role is not
        able to be determined at the present time.";
      reference
       "RFC3036, LDP Specification, Section 2.5.3.,
        Session Initialization";
      smiv2:max-access "read-only";
      smiv2:oid "1.3.6.1.2.1.10.166.4.1.3.3.1.3";
    }

    leaf mplsLdpSessionProtocolVersion {
      type uint32 {
        range "1..65535";
      }
      description
       "The version of the LDP Protocol which
        this session is using.  This is the version of
        
        
        the LDP protocol which has been negotiated
        during session initialization.";
      reference
       "RFC3036, LDP Specification, Section 3.5.3,
        Initialization Message.";
      smiv2:max-access "read-only";
      smiv2:oid "1.3.6.1.2.1.10.166.4.1.3.3.1.4";
    }

    leaf mplsLdpSessionKeepAliveHoldTimeRem {
      type snmpv2-tc:TimeInterval;
      description
       "The keep alive hold time remaining for
        this session.";
      smiv2:max-access "read-only";
      smiv2:oid "1.3.6.1.2.1.10.166.4.1.3.3.1.5";
    }

    leaf mplsLdpSessionKeepAliveTime {
      type uint32 {
        range "1..65535";
      }
      units "seconds";
      description
       "The negotiated KeepAlive Time which
        represents the amount of seconds between
        keep alive messages.  The
        mplsLdpEntityKeepAliveHoldTimer
        related to this Session is the
        value that was proposed as the
        KeepAlive Time for this session.
        
        This value is negotiated during
        session initialization between
        the entity's proposed value
        (i.e., the value configured in
        mplsLdpEntityKeepAliveHoldTimer)
        and the peer's proposed
        KeepAlive Hold Timer value.
        This value is the smaller
        of the two proposed values.";
      reference
       "RFC3036, LDP Specification, Section 3.5.3,
        Initialization Message.";
      smiv2:max-access "read-only";
      smiv2:oid "1.3.6.1.2.1.10.166.4.1.3.3.1.6";
    }

    leaf mplsLdpSessionMaxPduLength {
      type uint32 {
        range "1..65535";
      }
      units "octets";
      description
       "The value of maximum allowable length for LDP PDUs for
        this session.  This value may have been negotiated
        during the Session Initialization.  This object is
        related to the mplsLdpEntityMaxPduLength object.  The
        mplsLdpEntityMaxPduLength object specifies the requested
        LDP PDU length, and this object reflects the negotiated
        LDP PDU length between the Entity and
        the Peer.";
      reference
       "RFC3036, LDP Specification, Section 3.5.3,
        Initialization Message.";
      smiv2:max-access "read-only";
      smiv2:oid "1.3.6.1.2.1.10.166.4.1.3.3.1.7";
    }

    leaf mplsLdpSessionDiscontinuityTime {
      type yang:timestamp;
      description
       "The value of sysUpTime on the most recent occasion
        at which any one or more of this session's counters
        suffered a discontinuity.  The relevant counters are
        the specific instances associated with this session
        of any Counter32 object contained in the
        mplsLdpSessionStatsTable.
        
        The initial value of this object is the value of
        sysUpTime when the entry was created in this table.
        
        Also, a command generator can distinguish when a session
        between a given Entity and Peer goes away and a new
        session is established.  This value would change and
        thus indicate to the command generator that this is a
        different session.";
      smiv2:max-access "read-only";
      smiv2:oid "1.3.6.1.2.1.10.166.4.1.3.3.1.8";
    }
  }

  smiv2:alias "mplsLdpSessionStatsTable" {
    description
     "A table of statistics for Sessions between
      LDP Entities and LDP Peers.  This table AUGMENTS
      
      
      the mplsLdpPeerTable.";
    smiv2:oid "1.3.6.1.2.1.10.166.4.1.3.4";
  }

  smiv2:alias "mplsLdpSessionStatsEntry" {
    description
     "An entry in this table represents statistical
      information on a single session between an LDP
      Entity and LDP Peer.";
    smiv2:oid "1.3.6.1.2.1.10.166.4.1.3.4.1";
  }

  augment "/MPLS-LDP-STD-MIB:MPLS-LDP-STD-MIB/MPLS-LDP-STD-MIB:mplsLdpPeerTable/MPLS-LDP-STD-MIB:mplsLdpPeerEntry" {
    description
     "An entry in this table represents statistical
      information on a single session between an LDP
      Entity and LDP Peer.";
    smiv2:oid "1.3.6.1.2.1.10.166.4.1.3.4.1";

    leaf mplsLdpSessionStatsUnknownMesTypeErrors {
      type yang:counter32;
      description
       "This object counts the number of Unknown Message Type
        Errors detected by this LSR/LER during this session.
        
        Discontinuities in the value of this counter can occur
        at re-initialization of the management system, and at
        other times as indicated by the value of
        mplsLdpSessionDiscontinuityTime.";
      smiv2:max-access "read-only";
      smiv2:oid "1.3.6.1.2.1.10.166.4.1.3.4.1.1";
    }

    leaf mplsLdpSessionStatsUnknownTlvErrors {
      type yang:counter32;
      description
       "This object counts the number of Unknown TLV Errors
        detected by this LSR/LER during this session.
        
        Discontinuities in the value of this counter can occur
        at re-initialization of the management system, and at
        other times as indicated by the value of
        mplsLdpSessionDiscontinuityTime.";
      smiv2:max-access "read-only";
      smiv2:oid "1.3.6.1.2.1.10.166.4.1.3.4.1.2";
    }
  }

  notification mplsLdpInitSessionThresholdExceeded {
    description
     "This notification is generated when the value of
      the 'mplsLdpEntityInitSessionThreshold' object
      is not zero, and the number of Session
      Initialization messages exceeds the value
      of the 'mplsLdpEntityInitSessionThreshold' object.";
    smiv2:oid "1.3.6.1.2.1.10.166.4.0.1";

    container object-1 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpEntityInitSessionThreshold {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityInitSessionThreshold";
        }
      }
    }
  }

  notification mplsLdpPathVectorLimitMismatch {
    description
     "This notification is sent when the
      'mplsLdpEntityPathVectorLimit' does NOT match
      the value of the 'mplsLdpPeerPathVectorLimit' for
      a specific Entity.";
    reference
     "RFC3036, LDP Specification, Section 3.5.3.";
    smiv2:oid "1.3.6.1.2.1.10.166.4.0.2";

    container object-1 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpEntityPathVectorLimit {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityPathVectorLimit";
        }
      }
    }

    container object-2 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpPeerPathVectorLimit {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerPathVectorLimit";
        }
      }
    }
  }

  notification mplsLdpSessionUp {
    description
     "If this notification is sent when the
      value of 'mplsLdpSessionState' enters
      the 'operational(5)' state.";
    smiv2:oid "1.3.6.1.2.1.10.166.4.0.3";

    container object-1 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionState {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionState";
        }
      }
    }

    container object-2 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionDiscontinuityTime {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionDiscontinuityTime";
        }
      }
    }

    container object-3 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionStatsUnknownMesTypeErrors {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionStatsUnknownMesTypeErrors";
        }
      }
    }

    container object-4 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionStatsUnknownTlvErrors {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionStatsUnknownTlvErrors";
        }
      }
    }
  }

  notification mplsLdpSessionDown {
    description
     "This notification is sent when the
      value of 'mplsLdpSessionState' leaves
      the 'operational(5)' state.";
    smiv2:oid "1.3.6.1.2.1.10.166.4.0.4";

    container object-1 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionState {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionState";
        }
      }
    }

    container object-2 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionDiscontinuityTime {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionDiscontinuityTime";
        }
      }
    }

    container object-3 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionStatsUnknownMesTypeErrors {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionStatsUnknownMesTypeErrors";
        }
      }
    }

    container object-4 {

      leaf mplsLdpEntityLdpId {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityLdpId";
        }
      }

      leaf mplsLdpEntityIndex {
        type leafref {
          path "/MPLS-LDP-STD-MIB:MPLS-LDP-STD-MIB/MPLS-LDP-STD-MIB:mplsLdpEntityTable/MPLS-LDP-STD-MIB:mplsLdpEntityEntry/MPLS-LDP-STD-MIB:mplsLdpEntityIndex";
        }
      }

      leaf mplsLdpPeerLdpId {
        type leafref {
          path "/MPLS-LDP-STD-MIB:MPLS-LDP-STD-MIB/MPLS-LDP-STD-MIB:mplsLdpPeerTable/MPLS-LDP-STD-MIB:mplsLdpPeerEntry/MPLS-LDP-STD-MIB:mplsLdpPeerLdpId";
        }
      }

      leaf mplsLdpSessionStatsUnknownTlvErrors {
        type leafref {
          path "/MPLS-LDP-STD-MIB:MPLS-LDP-STD-MIB/MPLS-LDP-STD-MIB:mplsLdpPeerTable/MPLS-LDP-STD-MIB:mplsLdpPeerEntry/MPLS-LDP-STD-MIB:mplsLdpSessionStatsUnknownTlvErrors";
        }
      }
    }
  }

  smiv2:alias "mplsLdpStdMIB" {
    smiv2:oid "1.3.6.1.2.1.10.166.4";
  }

  smiv2:alias "mplsLdpNotifications" {
    smiv2:oid "1.3.6.1.2.1.10.166.4.0";
  }

  smiv2:alias "mplsLdpObjects" {
    smiv2:oid "1.3.6.1.2.1.10.166.4.1";
  }

  smiv2:alias "mplsLdpLsrObjects" {
    smiv2:oid "1.3.6.1.2.1.10.166.4.1.1";
  }

  smiv2:alias "mplsLdpEntityObjects" {
    smiv2:oid "1.3.6.1.2.1.10.166.4.1.2";
  }

  smiv2:alias "mplsLdpSessionObjects" {
    smiv2:oid "1.3.6.1.2.1.10.166.4.1.3";
  }

  smiv2:alias "mplsLdpHelloAdjacencyObjects" {
    smiv2:oid "1.3.6.1.2.1.10.166.4.1.3.5";
  }

  smiv2:alias "mplsFecObjects" {
    smiv2:oid "1.3.6.1.2.1.10.166.4.1.3.8";
  }

  smiv2:alias "mplsLdpConformance" {
    smiv2:oid "1.3.6.1.2.1.10.166.4.2";
  }

  smiv2:alias "mplsLdpGroups" {
    smiv2:oid "1.3.6.1.2.1.10.166.4.2.1";
  }

  smiv2:alias "mplsLdpCompliances" {
    smiv2:oid "1.3.6.1.2.1.10.166.4.2.2";
  }

}
