module Cisco-IOS-XE-mka {
  yang-version 1.1;
  namespace "http://cisco.com/ns/yang/Cisco-IOS-XE-mka";
  prefix ios-mka;

  import cisco-semver {
    prefix cisco-semver;
  }
  import Cisco-IOS-XE-native {
    prefix ios;
  }
  import Cisco-IOS-XE-crypto {
    prefix ios-crypto;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE  Macsec Key Agreement protocol (MKA) Yang Model.
     Copyright (c) 2016-2017, 2019, 2022 by Cisco Systems, Inc.
     All rights reserved.";

  revision 2023-07-01 {
    description
      "- Added s-sci-based-on-sci and send-secure-announcements under policy
       - Added fallback-key-chain under key-chain";
    cisco-semver:module-version "2.0.0";
  }
  revision 2022-11-01 {
    description
      "- Update yang-version to 1.1";
    cisco-semver:module-version "1.1.0";
  }
  revision 2019-07-01 {
    description
      "- Establish semantic version baseline
       - Added delay-protection, include-icv-indicator
       - sak-rekey-interval and on-live-peer-loss
       - Added use-updated-eth-header under policy
       - Added mka default-policy under interface
       - Added mka suppress syslogs sak-rekey globally";
    cisco-semver:module-version "1.0.0";
  }
  revision 2019-01-22 {
    description
      "Added leaf for App-hosting Gigabit Ethernet interface";
  }
  revision 2017-11-27 {
    description
      "Added Change 25GE name";
  }
  revision 2017-11-14 {
    description
      "Add 100GE Support";
  }
  revision 2017-09-17 {
    description
      "add key-server priority for mka grouping";
  }
  revision 2017-08-16 {
    description
      "This revision has changes for new 5gig and 25gig interfaces addition";
  }
  revision 2017-07-26 {
    description
      "add confidentiality-offset for mka grouping";
  }
  revision 2017-02-07 {
    description
      "Initial revision";
  }

  grouping config-mka-grouping {
    list policy {
      description
        "Configure MKA policy";
      key "name";
      leaf name {
        description
          "MKA policy name";
        type string {
          length "1..16";
        }
      }
      container key-server {
        description
          "Configure MKA key-server options";
        leaf priority {
          description
            "Set MKA key-server priority";
          type uint8 {
            range "0..255";
          }
          default "0";
        }
      }
      leaf-list macsec-cipher-suite {
        description
          "Cipher Suite for SAK derivation";
        max-elements 4;
        ordered-by user;
        type enumeration {
          enum gcm-aes-128;
          enum gcm-aes-256;
          enum gcm-aes-xpn-128;
          enum gcm-aes-xpn-256;
        }
      }
      leaf confidentiality-offset {
        description
          "Set the confidentiality offset for MACsec operation";
        type enumeration {
          enum 0;
          enum 30;
          enum 50;
        }
        default "0";
      }
      leaf delay-protection {
        description
          "Configure MKA to use delay protection in sending MKPDU's";
        type boolean;
        default "false";
      }
      leaf include-icv-indicator {
        description
          "Include ICV indicator in MKPDU (default is to include)";
        type boolean;
        default "true";
      }
      container sak-rekey {
        description
          "Enable SAK-rekey during";
        container interval {
          description
            "SAK Rekey Interval";
          leaf time {
            description
              "SAK Rekey Interval in seconds (default is 0)";
            type uint32 {
              range "30..65535";
            }
          }
        }
        leaf on-live-peer-loss {
          description
            "peer loss from the live membership";
          type boolean;
          default "false";
        }
      }
      leaf use-updated-eth-header {
        description
          "Use updated ethernet header for ICV calculation (default is disabled)";
        type boolean;
        default "false";
      }
      leaf ssci-based-on-sci {
        description
          "Compute S-SCI based on SCI,higher the SCI lower the S-SCI value(default is disabled)";
        type boolean;
        default "false";
      }
      leaf send-secure-announcements {
        description
          "Configure MKA to send secure announcements in sending MKPDU's(default is disabled)";
        type boolean;
        default "false";
      }
    }
    container suppress {
      description
        "Suppress";
      container syslogs {
        description
          "System logs";
        leaf sak-rekey {
          description
            "SAK rekey messages";
          type boolean;
          default "false";
        }
      }
    }
  }

  grouping config-interface-mka-grouping {
    container mka {
      description
        "MACsec Key Agreement (MKA) interface configuration";
      container policy {
        description
          "Apply MKA Policy";
        leaf name {
          must '/ios:native/ios:mka/ios-mka:policy[ios-mka:name=current()]' {
            error-message "MKA policy must be configured first and should exist before applying on interface";
          }
          description
            "MKA Policy NAME";
          type string {
            length "1..16";
          }
        }
      }
      container pre-shared-key {
        description
          "Configure MKA Pre-Shared-Key";
        container key-chain {
          description
            "Configure the key-chain name";
          leaf name {
            description
              "Name of key-chain to be used to get keys";
            type leafref {
              path "/ios:native/ios:key/ios-crypto:chain/ios-crypto:name";
            }
          }
          leaf fallback-key-chain {
            description
              "Name of fallback key-chain to be used to get keys";
            type leafref {
              path "/ios:native/ios:key/ios-crypto:chain/ios-crypto:name";
            }
          }
        }
      }
      leaf default-policy {
        description
          "Apply MKA Default Policy";
        type boolean;
        default "false";
      }
    }
  }

  augment "/ios:native/ios:mka" {
    uses config-mka-grouping;
  }

  augment "/ios:native/ios:interface/ios:FastEthernet" {
    uses config-interface-mka-grouping;
  }

  augment "/ios:native/ios:interface/ios:GigabitEthernet" {
    uses config-interface-mka-grouping;
  }

  augment "/ios:native/ios:interface/ios:TenGigabitEthernet" {
    uses config-interface-mka-grouping;
  }

  augment "/ios:native/ios:interface/ios:FiveGigabitEthernet" {
    uses config-interface-mka-grouping;
  }

  augment "/ios:native/ios:interface/ios:AppGigabitEthernet" {
    uses config-interface-mka-grouping;
  }

  augment "/ios:native/ios:interface/ios:TwentyFiveGigE" {
    uses config-interface-mka-grouping;
  }

  augment "/ios:native/ios:interface/ios:TwoGigabitEthernet" {
    uses config-interface-mka-grouping;
  }

  augment "/ios:native/ios:interface/ios:FortyGigabitEthernet" {
    uses config-interface-mka-grouping;
  }

  augment "/ios:native/ios:interface/ios:HundredGigE" {
    uses config-interface-mka-grouping;
  }
}
