module Cisco-IOS-XE-cdp-deviation {
  yang-version 1.1;
  namespace "http://cisco.com/ns/yang/Cisco-IOS-XE-cdp-deviation";
  prefix ios-cdp-d;

  import Cisco-IOS-XE-native {
    prefix ios;
  }
  import Cisco-IOS-XE-cdp {
    prefix ios-cdp;
  }
  import cisco-semver {
    prefix cisco-semver;
  }

  organization
    "Cisco Systems";
  description
    "Cisco XE Native Deviation YANG module for IOS
     Copyright (c) 2016 by Cisco Systems, Inc.
     All rights reserved.";

  revision 2022-11-01 {
    description
      "- Update yang-version to 1.1";
    cisco-semver:module-version "1.2.0";
  }
  revision 2021-03-01 {
    description
      "Added cdp enable support under dialer interface";
    cisco-semver:module-version "1.0.0";
  }
  revision 2019-07-23 {
    description
      "Added cdp run and cdp enable deviation";
  }

  deviation "/ios:native/ios:cdp/ios-cdp:run-enable" {
    deviate replace {
      default "false";
    }
  }

  deviation "/ios:native/ios:interface/ios:BDI/ios-cdp:cdp/ios-cdp:enable" {
    deviate replace {
      default "false";
    }
  }

  deviation "/ios:native/ios:interface/ios:FastEthernet/ios-cdp:cdp/ios-cdp:enable" {
    deviate replace {
      default "false";
    }
  }

  deviation "/ios:native/ios:interface/ios:GigabitEthernet/ios-cdp:cdp/ios-cdp:enable" {
    deviate replace {
      default "false";
    }
  }

  deviation "/ios:native/ios:interface/ios:TwoGigabitEthernet/ios-cdp:cdp/ios-cdp:enable" {
    deviate replace {
      default "false";
    }
  }

  deviation "/ios:native/ios:interface/ios:FiveGigabitEthernet/ios-cdp:cdp/ios-cdp:enable" {
    deviate replace {
      default "false";
    }
  }

  deviation "/ios:native/ios:interface/ios:AppGigabitEthernet/ios-cdp:cdp/ios-cdp:enable" {
    deviate replace {
      default "false";
    }
  }

  deviation "/ios:native/ios:interface/ios:TenGigabitEthernet/ios-cdp:cdp/ios-cdp:enable" {
    deviate replace {
      default "false";
    }
  }

  deviation "/ios:native/ios:interface/ios:TwentyFiveGigE/ios-cdp:cdp/ios-cdp:enable" {
    deviate replace {
      default "false";
    }
  }

  deviation "/ios:native/ios:interface/ios:FortyGigabitEthernet/ios-cdp:cdp/ios-cdp:enable" {
    deviate replace {
      default "false";
    }
  }

  deviation "/ios:native/ios:interface/ios:HundredGigE/ios-cdp:cdp/ios-cdp:enable" {
    deviate replace {
      default "false";
    }
  }

  deviation "/ios:native/ios:interface/ios:Virtual-Template/ios-cdp:cdp/ios-cdp:enable" {
    deviate replace {
      default "false";
    }
  }

  deviation "/ios:native/ios:interface/ios:Dialer/ios-cdp:cdp/ios-cdp:enable" {
    deviate replace {
      default "false";
    }
  }
}
