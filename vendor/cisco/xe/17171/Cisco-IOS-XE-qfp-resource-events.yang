module Cisco-IOS-XE-qfp-resource-events {
  yang-version 1.1;
  namespace "http://cisco.com/ns/yang/Cisco-IOS-XE-qfp-resource-events";
  prefix qfp-resource-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG Definitions
     for qfp resource event notification.
     Copyright (c) 2024 by Cisco Systems, Inc.
     All rights reserved.";

  revision 2025-03-01 {
    description
      "Added support for QFP datapath alarm";
    reference
      "1.1.0";
    cisco-semver:module-version "1.1.0";
  }
  revision 2024-11-01 {
    description
      "Initial revision";
    reference
      "1.0.0";
    cisco-semver:module-version "1.0.0";
  }

  typedef notification-qfp-usage-status {
    type enumeration {
      enum usage-critical {
        value 0;
        description
          "QFP usage status usage-critical";
      }
      enum usage-warning {
        value 1;
        description
          "QFP usage status usage-warning";
      }
      enum usage-healthy {
        value 2;
        description
          "QFP usage status usage-healthy";
      }
    }
    description
      "QFP resource usage status";
  }

  grouping qfp-resource-usage {
    description
      "QFP utilization usage";
    leaf severity {
      type ios-common-ios-xe-oper:notification-severity;
      description
        "Event severity";
    }
    leaf host-name {
      type string;
      description
        "Host name";
    }
    leaf system-ip {
      type inet:ip-address;
      description
        "System IP address";
    }
    leaf warning-string {
      type string;
      description
        "QFP resource usage warning string";
    }
    leaf five-sec {
      type uint32;
      units "percentage";
      description
        "QFP resource average load (five sec)";
    }
    leaf one-min {
      type uint32;
      units "percentage";
      description
        "QFP resource average load (one min)";
    }
    leaf five-min {
      type uint32;
      units "percentage";
      description
        "QFP resource average load (five min)";
    }
    leaf sixty-min {
      type uint32;
      units "percentage";
      description
        "QFP resource average load (sixty min)";
    }
    leaf qfp-resource-status {
      type qfp-resource-ios-xe-events:notification-qfp-usage-status;
      description
        "QFP resource usage status";
    }
  }

  grouping qfp-exmem-usage {
    description
      "QFP exmem usage";
    leaf severity {
      type ios-common-ios-xe-oper:notification-severity;
      description
        "Event severity";
    }
    leaf host-name {
      type string;
      description
        "Host name";
    }
    leaf system-ip {
      type inet:ip-address;
      description
        "System IP address";
    }
    leaf warning-string {
      type string;
      description
        "QFP exmem usage warning string";
    }
    leaf total {
      type uint64;
      units "bytes";
      description
        "QFP exmem total DRAM memory";
    }
    leaf in-use {
      type uint64;
      units "bytes";
      description
        "QFP exmem total DRAM memory";
    }
    leaf qfp-exmem-status {
      type qfp-resource-ios-xe-events:notification-qfp-usage-status;
      description
        "QFP exmem usage status";
    }
  }

  notification qfp-resource-usage {
    description
      "QFP resource usage notification";
    uses qfp-resource-ios-xe-events:qfp-resource-usage;
  }

  notification qfp-exmem-usage {
    description
      "QFP DRAM memory usage notification";
    uses qfp-resource-ios-xe-events:qfp-exmem-usage;
  }
}
