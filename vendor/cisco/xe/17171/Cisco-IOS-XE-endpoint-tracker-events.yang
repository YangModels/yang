module Cisco-IOS-XE-endpoint-tracker-events {
  yang-version 1.1;
  namespace "http://cisco.com/ns/yang/Cisco-IOS-XE-endpoint-tracker-events";
  prefix endpoint-tracker-ios-xe-events;

  import Cisco-IOS-XE-ios-common-oper {
    prefix ios-common-ios-xe-oper;
  }
  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for endpoint tracker events.
     Copyright (c) 2021-2022 by Cisco Systems, Inc.
     All rights reserved.";

  revision 2024-07-01 {
    description
      "Add service chain notification";
    reference
      "1.3.0";
    cisco-semver:module-version "1.3.0";
  }
  revision 2023-03-01 {
    description
      "Add new address family enum";
    reference
      "1.2.0";
    cisco-semver:module-version "1.2.0";
  }
  revision 2022-11-01 {
    description
      "Update yang-version to 1.1";
    reference
      "1.1.0";
    cisco-semver:module-version "1.1.0";
  }
  revision 2021-11-01 {
    description
      "Initial revision";
    reference
      "1.0.0";
    cisco-semver:module-version "1.0.0";
  }

  typedef endpoint-tracker-af {
    type enumeration {
      enum tracker-af-ipv4 {
        value 0;
        description
          "Tracker Address Family IPv4";
      }
      enum tracker-af-ipv6 {
        value 1;
        description
          "Tracker Address Family IPv6";
      }
    }
    description
      "Endpoint tracker address family";
  }

  typedef endpoint-tracker-notif-state {
    type enumeration {
      enum tracker-notif-state-up {
        value 0;
        description
          "Tracker Notification State UP";
      }
      enum tracker-notif-state-down {
        value 1;
        description
          "Tracker Notification State DOWN";
      }
    }
    description
      "Endpoint tracker notification state";
  }

  typedef sc-status-change-notif-state {
    type enumeration {
      enum svc-chain-up {
        value 0;
        description
          "Service chain status notification state UP";
      }
      enum svc-chain-down {
        value 1;
        description
          "Service chain status notification state DOWN";
      }
    }
    description
      "Service chain status notification state";
  }

  typedef sc-status-change-reason {
    type enumeration {
      enum sc-reason-na {
        value 0;
        description
          "Service chain status reason unknown";
      }
      enum sc-reason-if-update {
        value 1;
        description
          "Service chain status reason interface";
      }
      enum sc-reason-tracker-update {
        value 2;
        description
          "Service chain status reason tracker";
      }
      enum sc-reason-config-update {
        value 3;
        description
          "Service chain status reason configuration update";
      }
      enum sc-reason-deleted {
        value 4;
        description
          "Service chain  status reason deleted";
      }
    }
    description
      "Service chain status reason";
  }

  grouping endpoint-tracker-state-change {
    description
      "Endpoint tracker state change notification";
    leaf severity-level {
      type ios-common-ios-xe-oper:notification-severity;
      description
        "Event severity";
    }
    leaf host-name {
      type string;
      description
        "Host name";
    }
    leaf system-ip {
      type inet:ip-address;
      description
        "System IP address";
    }
    leaf vrf-name {
      type string;
      description
        "VRF name";
    }
    leaf attach-point-name {
      type string;
      description
        "Attach point name";
    }
    leaf tracker-name {
      type string;
      description
        "Tracker name";
    }
    leaf new-state {
      type endpoint-tracker-ios-xe-events:endpoint-tracker-notif-state;
      description
        "New tracker state";
    }
    leaf address-family {
      type endpoint-tracker-ios-xe-events:endpoint-tracker-af;
      description
        "Address family";
    }
  }

  grouping sc-status-change-event {
    description
      "Service chain status change event";
    leaf severity {
      type ios-common-ios-xe-oper:notification-severity;
      description
        "Event severity";
    }
    leaf host-name {
      type string;
      description
        "Host name of the device";
    }
    leaf system-ip {
      type inet:ip-address;
      description
        "System IP of the device";
    }
    leaf name {
      type string;
      description
        "Service chain name";
    }
    leaf vpn {
      type string;
      description
        "Service chain VPN";
    }
    leaf status {
      type endpoint-tracker-ios-xe-events:sc-status-change-notif-state;
      description
        "Service chain status";
    }
    leaf reason {
      type endpoint-tracker-ios-xe-events:sc-status-change-reason;
      description
        "Service chain reason";
    }
    leaf if-name {
      type string;
      description
        "Interface name";
    }
    leaf tracker-name {
      type string;
      description
        "Tracker name";
    }
  }

  notification tracker-state-change {
    description
      "Endpoint tracker state change notification";
    uses endpoint-tracker-ios-xe-events:endpoint-tracker-state-change;
  }

  notification sc-status-change-event {
    description
      "Service chain status change notification";
    uses endpoint-tracker-ios-xe-events:sc-status-change-event;
  }
}
