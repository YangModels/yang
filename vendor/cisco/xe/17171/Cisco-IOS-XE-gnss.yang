module Cisco-IOS-XE-gnss {
  yang-version 1.1;
  namespace "http://cisco.com/ns/yang/Cisco-IOS-XE-gnss";
  prefix ios-gnss;

  import cisco-semver {
    prefix cisco-semver;
  }
  import Cisco-IOS-XE-native {
    prefix ios;
  }
  import Cisco-IOS-XE-features {
    prefix ios-features;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Global Navigation Satellite System (GNSS) Yang Model.
     Copyright (c) 2024 by Cisco Systems, Inc.
     All rights reserved.";

  revision 2024-11-01 {
    description
      "- Added feature for Sumatra platform";
    cisco-semver:module-version "2.0.0";
  }
  revision 2024-07-01 {
    description
      "Initial revision";
    cisco-semver:module-version "1.0.0";
  }

  grouping config-gnss-grouping {
    container gnss {
      description
        "GNSS Configurations";
      leaf cable-delay {
        description
          "Cable Delay in nanoseconds";
        type uint32 {
          range "0..1000";
        }
        default "50";
      }
      leaf cnr-threshold {
        if-feature "ios-features:sumatra-gnss";
        description
          "cnr-threshold in dBHz";
        type uint8 {
          range "0..99";
        }
        default "0";
      }
      container constellation {
        description
          "Satellite Constellation for GNSS";
        choice constellation-grouping-choice {
          leaf auto {
            description
              "Auto constellation";
            type empty;
          }
          leaf beidou {
            description
              "Beidou Constellation";
            type empty;
          }
          leaf galileo {
            description
              "Galileo Constellation";
            type empty;
          }
          leaf glonass {
            description
              "GLONASS Constellation";
            type empty;
          }
          leaf gps {
            description
              "GPS Constellation";
            type empty;
          }
        }
      }
      leaf elevation-threshold {
        if-feature "ios-features:sumatra-gnss";
        description
          "Elevation Threshold in degrees";
        type uint8 {
          range "0..15";
        }
        default "5";
      }
    }
  }

  augment "/ios:native" {
    uses config-gnss-grouping;
  }
}
