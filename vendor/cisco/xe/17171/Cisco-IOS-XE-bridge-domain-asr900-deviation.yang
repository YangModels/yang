module Cisco-IOS-XE-bridge-domain-asr900-deviation {
  yang-version 1.1;
  namespace "http://cisco.com/ns/yang/Cisco-IOS-XE-bridge-domain-asr900-deviation";
  prefix ios-bd-asr900-d;

  import Cisco-IOS-XE-native {
    prefix ios;
  }
  import Cisco-IOS-XE-bridge-domain {
    prefix ios-bd;
  }

  organization
    "Cisco Systems";
  description
    "Cisco XE Native Bridge Domain Deviation YANG module for IOS-XE ASR900 (RSP2 and RSP3)
     and ASR920 platforms
     Copyright (c) 2021 by Cisco Systems, Inc.
     All rights reserved.";

  revision 2024-03-01 {
    description
      "Changed deprecated models to obsolete, removed relevant entries";
  }
  revision 2022-11-01 {
    description
      "- Update yang-version to 1.1";
  }
  revision 2021-11-01 {
    description
      "Added mac learning deviation";
  }

  deviation "/ios:native/ios:bridge-domain/ios-bd:brd-id/ios-bd:mac/ios-bd:learning-boolean" {
    deviate not-supported;
  }
}
