submodule Cisco-IOS-XE-transceiver-monitor {
  yang-version 1.1;
  belongs-to Cisco-IOS-XE-native {
    prefix ios;
  }

  import cisco-semver {
    prefix cisco-semver;
  }
  import Cisco-IOS-XE-features {
    prefix ios-features;
  }

  organization
    "Cisco Systems, Inc.";
  description
    "Cisco XE Native Location Yang Model.
     Copyright (c) 2022 by Cisco Systems, Inc.
     All rights reserved.";

  revision 2022-11-01 {
    description
      "- Update yang-version to 1.1";
    cisco-semver:module-version "1.1.0";
  }
  revision 2022-07-01 {
    description
      "- Added transceiver deviation";
    cisco-semver:module-version "1.0.0";
  }

  grouping config-transceiver-grouping {
    container transceivers {
      if-feature "ios-features:transceiver";
      description
        "Select from transceiver configuration commands";
      container type {
        description
          "type keyword";
        container all {
          container monitoring-enable {
            leaf monitoring {
              description
                "Enable/disable monitoring";
              type empty;
            }
          }
          container monitoring-interval {
            container monitoring {
              description
                "Enable/disable monitoring";
              leaf interval {
                description
                  "Set interval for monitoring";
                type uint16 {
                  range "300..3600";
                }
              }
            }
          }
        }
      }
    }
  }
}
