module Cisco-IOS-XE-hsrp-oper {
  yang-version 1.1;
  namespace "http://cisco.com/ns/yang/Cisco-IOS-XE-hsrp-oper";
  prefix hsrp-ios-xe-oper;

  import ietf-inet-types {
    prefix inet;
  }
  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for HSRP operational data.
     Copyright (c) 2020, 2022 by Cisco Systems, Inc.
     All rights reserved.";

  revision 2022-11-01 {
    description
      "Update yang-version to 1.1";
    reference
      "1.1.0";
    cisco-semver:module-version "1.1.0";
  }
  revision 2020-11-01 {
    description
      "Initial revision";
    reference
      "1.0.0";
    cisco-semver:module-version "1.0.0";
  }

  typedef hsrp-oper-state-type {
    type enumeration {
      enum hsrp-state-invalid {
        value 0;
        description
          "HSRP state is Invalid";
      }
      enum hsrp-state-disabled {
        value 1;
        description
          "HSRP state is Disabled";
      }
      enum hsrp-state-init {
        value 2;
        description
          "HSRP state is Init";
      }
      enum hsrp-state-learn {
        value 3;
        description
          "HSRP state is Learn";
      }
      enum hsrp-state-listen {
        value 4;
        description
          "HSRP state is Listen";
      }
      enum hsrp-state-speak {
        value 5;
        description
          "HSRP state is Speak";
      }
      enum hsrp-state-standby {
        value 6;
        description
          "HSRP state is Standby";
      }
      enum hsrp-state-active {
        value 7;
        description
          "HSRP state is Active";
      }
    }
    description
      "HSRP State type";
  }

  grouping hsrp-neighbor-info {
    description
      "List of neighbors for a given interface";
    leaf address {
      type inet:ip-address;
      description
        "Neighbor IP address";
    }
    leaf-list active-list {
      type uint8;
      ordered-by user;
      description
        "List of groups for which this address is Active";
    }
    leaf-list standby-list {
      type uint8;
      ordered-by user;
      description
        "List of groups for which this address is Standby";
    }
    leaf passive {
      type boolean;
      description
        "Boolean indicating whether this neighbor is HSRP passive";
    }
    leaf passive-timer-remaining {
      type uint16;
      units "seconds";
      description
        "Timer remaining for the passive neighbor to expire";
    }
    leaf bfd-enabled {
      type boolean;
      description
        "BFD enabled";
    }
  }

  grouping hsrp-neighbor {
    description
      "HSRP Neighbor information";
    leaf if-name {
      type string;
      description
        "Interface name";
    }
    list neighbor {
      description
        "List of neighbors for a given interface";
      uses hsrp-ios-xe-oper:hsrp-neighbor-info;
    }
  }

  grouping hsrp-group-info-key {
    description
      "HSRP group information key";
    leaf group-id {
      type uint16;
      description
        "HSRP group identifier";
    }
    leaf if-name {
      type string;
      description
        "Interface name";
    }
  }

  grouping hsrp-group-info {
    description
      "HSRP group information";
    leaf priority {
      type uint32;
      description
        "Priority";
    }
    leaf preempt {
      type boolean;
      description
        "Preempt enabled";
    }
    leaf state {
      type hsrp-ios-xe-oper:hsrp-oper-state-type;
      description
        "HSRP group state";
    }
    leaf active-ip {
      type inet:ip-address;
      description
        "Active device IP";
    }
    leaf standby-ip {
      type inet:ip-address;
      description
        "Standby device IP";
    }
    leaf virtual-ip {
      type inet:ip-address;
      description
        "Virtual IP";
    }
  }

  container hsrp-oper-data {
    config false;
    description
      "HSRP operational data";
    list hsrp-group-info {
      key "group-id if-name";
      description
        "HSRP group information";
      uses hsrp-ios-xe-oper:hsrp-group-info;
      uses hsrp-ios-xe-oper:hsrp-group-info-key;
    }
    list hsrp-neighbor {
      key "if-name";
      description
        "HSRP Neighbor information";
      uses hsrp-ios-xe-oper:hsrp-neighbor;
    }
  }
}
