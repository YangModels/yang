module Cisco-IOS-XE-ptp {
  yang-version 1.1;
  namespace "http://cisco.com/ns/yang/Cisco-IOS-XE-ptp";
  prefix ios-ptp;

  import cisco-semver {
    prefix cisco-semver;
  }
  import ietf-inet-types {
    prefix inet;
  }
  import Cisco-IOS-XE-native {
    prefix ios;
  }
  import Cisco-IOS-XE-switch {
    prefix ios-sw;
  }
  import Cisco-IOS-XE-features {
    prefix ios-features;
  }
  import Cisco-IOS-XE-types {
    prefix ios-types;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Precision Time Protocol (PTP) Yang Model.
     Copyright (c) 2016-2017, 2019, 2023 by Cisco Systems, Inc.
     All rights reserved.";

  revision 2024-11-01 {
    description
      "- Added feature for platform based grouping
       - Added boundary clock mode and domain-num for tc
       - Added pd cli gaps in boundary clock";
    cisco-semver:module-version "4.0.0";
  }
  revision 2023-07-01 {
    description
      "- Added forward mode in transparent-clock-grouping";
    cisco-semver:module-version "3.2.0";
  }
  revision 2022-11-01 {
    description
      "- Update yang-version to 1.1
       - Added support for ptp clock transparent";
    cisco-semver:module-version "3.1.0";
  }
  revision 2020-07-01 {
    description
      "- Prepend switchport-config to switchport";
    cisco-semver:module-version "3.0.0";
  }
  revision 2019-12-01 {
    description
      "Adding Transport and Interface level CLIs";
    cisco-semver:module-version "2.0.0";
  }
  revision 2019-07-01 {
    description
      "Establish semantic version baseline";
    cisco-semver:module-version "1.0.0";
  }
  revision 2017-09-19 {
    description
      "Extension for edison";
  }
  revision 2017-02-07 {
    description
      "Initial revision";
  }

  grouping config-ptp-grouping {
    container ptp {
      description
        "Precision Time Protocol";
      container clock {
        description
          "Configure PTP clock";
        container ordinary {
          description
            "Configure PTP Ordinary clock";
          leaf domain {
            description
              "PTP domain";
            type int8 {
              range "0..127";
            }
          }
        }
        container clock-port {
          description
            "Configure clock port";
          leaf name {
            description
              "Port name";
            type string;
          }
          leaf slave {
            description
              "Configure as Slave";
            type empty;
          }
          leaf master {
            description
              "Configure as Master";
            type empty;
          }
          container transport {
            description
              "Set port transport parameters";
            leaf ipv4 {
              description
                "Use IPv4 encapsulation";
              type empty;
            }
            container unicast {
              description
                "Use unicast communication channel";
              leaf interface {
                type string;
              }
              leaf negotiation {
                description
                  "Enable unicast negotiation";
                type empty;
              }
            }
          }
          container clock {
            leaf source {
              type inet:ipv4-address;
            }
          }
        }
      }
    }
  }

  grouping config-ptp-bc-common-grouping1 {
    list clock-port {
      description
        "Configure clock port";
      key "name";
      leaf name {
        description
          "Port name";
        type string;
      }
      leaf slave {
        description
          "Configure as Slave";
        type empty;
      }
      leaf master {
        description
          "Configure as Master";
        if-feature "ios-features:ptp-bc";
        type empty;
      }
      container announce {
        description
          "announcement packet parameters";
        leaf interval {
          description
            "PTP announce interval";
          type int8 {
            range "0..4";
          }
          default "1";
        }
        leaf timeout {
          description
            "PTP announce timeout";
          type int8 {
            range "2..10";
          }
          default "3";
        }
      }
      container sync {
        leaf interval {
          description
            "PTP delay request interval";
          type int8 {
            range "-1..1";
          }
        }
        leaf limit {
          description
            "out of sync limit for sync fault";
          type uint32 {
            range "50..500000000";
          }
        }
      }
      container delay-req {
        leaf interval {
          description
            "PTP delay request interval";
          type int8 {
            range "0..5";
          }
        }
      }
      leaf delay-asymmetry {
        description
          "Delay asymmetry";
        type int64 {
          range "-500000000..500000000";
        }
        default "0";
      }
      container pdelay-req {
        description
          "Set parameters for peer-delay-req packets";
        leaf interval {
          description
            "Interval for PTP peer-delay-req packets";
          type uint8 {
            range "0..5";
          }
        }
      }
      leaf gmc-block {
        description
          "block rogue gmc";
        type empty;
      }
      container transport {
        description
          "Set port transport parameters";
        container ethernet {
          description
            "Use Ethernet encapsulation";
          container multicast {
            description
              "Use multicast communication channel";
            container interface {
              leaf GigabitEthernet {
                description
                  "GigabitEthernet IEEE 802.3z";
                type string;
              }
              leaf TenGigabitEthernet {
                description
                  "Ten Gigabit Ethernet";
                type string;
              }
            }
          }
          leaf unicast {
            if-feature "ios-features:ptp-bc";
            description
              "Use unicast communication channel";
            type empty;
          }
          leaf negotiation {
            if-feature "ios-features:ptp-bc";
            description
              "Enable unicast negotiation";
            type empty;
          }
        }
      }
      container unicast {
        if-feature "ios-features:ptp-bc";
        leaf grant-duration {
          type enumeration {
            enum 0;
          }
          default "0";
        }
      }
      leaf wait-to-restore {
        if-feature "ios-features:ptp-bc";
        type enumeration {
          enum 0;
        }
        default "0";
      }
      container clock {
        if-feature "ios-features:ptp-bc";
        container destination {
          description
            "Destination options";
          choice ipormac {
            case ip {
              leaf ip {
                type inet:ipv4-address;
              }
            }
            case mac {
              leaf mac {
                type ios-types:cisco-mac-address-type;
              }
            }
          }
        }
      }
    }
    container time-property {
      container persist {
        choice persist-case {
          case value-case {
            leaf value {
              type uint32 {
                range "0..100000";
              }
            }
          }
          case infinite-case {
            leaf infinite {
              type empty;
            }
          }
        }
      }
    }
    leaf allow-without-tlv {
      type empty;
    }
    leaf packet {
      type uint8 {
        range "0..7";
      }
    }
    leaf neighbor-propagation-delay-threshold {
      type uint32 {
        range "1..2147483646";
      }
    }
    container gmc-bc {
      if-feature "ios-features:ptp-bc";
      container source {
        leaf value {
          type uint8 {
            range "0..2";
          }
        }
        leaf ntp {
          type empty;
        }
      }
    }
    leaf priority1 {
      type uint8 {
        range "0..255";
      }
      default "128";
    }
    leaf priority2 {
      type uint8 {
        range "0..255";
      }
      default "128";
    }
    container utc-offset {
      leaf value {
        type uint32 {
          range "0..65535";
        }
      }
      leaf leap-second {
        type string;
      }
      leaf offset {
        type int8 {
          range "-1..1";
        }
      }
    }
  }

  grouping config-ptp-bc-grouping2 {
    container time-properties {
      if-feature "ios-features:ptp-bc";
      description
        "Time for which BC need to set UtcOffsetValid as true";
      leaf persist {
        description
          "Persist Time Interval for which BC need to set UtcOffsetValid as true";
        type uint16;
      }
    }
    leaf local-priority {
      if-feature "ios-features:ptp-bc";
      type uint8 {
        range "1..255";
      }
    }
    leaf min-clock-class {
      if-feature "ios-features:ptp-bc";
      type uint8 {
        range "0..255";
      }
    }
    list virtual-port {
      if-feature "ios-features:ptp-bc";
      key "name";
      leaf name {
        type string;
      }
      leaf profile {
        type enumeration {
          enum g8275.1;
        }
      }
      container sub_clis {
        leaf clock-class {
          type uint8 {
            range "0..255";
          }
        }
        leaf priority2 {
          type uint8 {
            range "0..255";
          }
        }
        container input {
          container input_port_1pps {
            leaf input_1pps {
              type empty;
            }
            leaf port_1pps {
              type enumeration {
                enum R0;
                enum R1;
              }
            }
            leaf offset {
              type uint64 {
                range "0..500000000";
              }
            }
            leaf negative {
              type empty;
            }
          }
          container tod {
            leaf tod_port {
              type enumeration {
                enum R0;
                enum R1;
              }
            }
            leaf tod_format {
              type enumeration {
                enum cisco;
                enum nmea;
                enum ntp;
                enum ubx;
                enum cmcc;
              }
            }
            leaf delay {
              type uint16 {
                range "1..999";
              }
            }
          }
        }
      }
      leaf local-priority {
        description
          "Set virtual port local priority";
        type uint8 {
          range "1..255";
        }
      }
    }
  }

  grouping config-ptp-grouping2 {
    leaf domain {
      description
        "Clock domain number";
      type uint8;
    }
    container profile {
      leaf dot1as {
        must 'not(../../transport/ipv4/udp)';
        type empty;
      }
    }
    leaf neighbor-propagation-delay-threshold {
      description
        "in nanoseconds";
      type uint32 {
        range "1..2147483646";
      }
    }
    leaf priority1 {
      description
        "clock priority1 number";
      type uint8;
    }
    leaf priority2 {
      description
        "clock priority2 number";
      type uint8;
    }
    container mode {
      container boundary {
        leaf delay-req {
          type empty;
        }
        leaf pdelay-req {
          type empty;
        }
      }
      leaf e2etransparent {
        type empty;
      }
      leaf p2ptransparent {
        type empty;
      }
    }
    container transport {
      description
        "Set transport mode";
      when 'not((/ios:native/ios:ptp/ios-ptp:mode/ios-ptp:boundary/ios-ptp:pdelay-req) or (/ios:native/ios:ptp/ios-ptp:mode/ios-ptp:boundary/ios-ptp:delay-req) or (/ios:native/ios:ptp/ios-ptp:mode/ios-ptp:e2etransparent) or (/ios:native/ios:ptp/ios-ptp:profile/ios-ptp:dot1as) or (/ios:native/ios:ptp/ios-ptp:mode/ios-ptp:p2ptransparent))';
      container ipv4 {
        description
          "Transport IPv4";
        leaf udp {
          description
            "Transport IPv4 UDP";
          type empty;
        }
      }
    }
    container clock {
      if-feature "ios-features:ptp";
      description
        "Configure PTP clock";
      leaf forward-mode {
        description
          "Configure PTP clock forward mode";
        type empty;
      }
      uses transparent-clock-grouping;
      uses boundary-clock-grouping;
    }
  }

  grouping config-interface-ptp-grouping {
    container ptp {
      description
        "PTP related interface configuration";
      leaf enable {
        description
          "Enable PTP";
        type empty;
      }
      container announce {
        when '(/ios:native/ios:ptp/ios-ptp:mode/ios-ptp:boundary/ios-ptp:delay-req) or (/ios:native/ios:ptp/ios-ptp:mode/ios-ptp:boundary/ios-ptp:pdelay-req)';
        leaf interval {
          description
            "log mean value of announce message transmit interval";
          type uint8 {
            range "0..4";
          }
          default "0";
        }
        leaf timeout {
          description
            "number of announce message transmit before timeout";
          type uint8 {
            range "2..10";
          }
          default "3";
        }
      }
      container sync {
        when '(/ios:native/ios:ptp/ios-ptp:mode/ios-ptp:boundary/ios-ptp:delay-req) or (/ios:native/ios:ptp/ios-ptp:mode/ios-ptp:boundary/ios-ptp:pdelay-req)';
        leaf interval {
          description
            "log mean value of sync message transmit interval";
          type int8 {
            range "-3..1";
          }
          default "0";
        }
      }
      container pdelay-req {
        when '(/ios:native/ios:ptp/ios-ptp:mode/ios-ptp:boundary/ios-ptp:pdelay-req)';
        leaf interval {
          description
            "log mean value of peer delay-req message transmit interval";
          type int8 {
            range "-1..5";
          }
          default "0";
        }
      }
      container delay-req {
        when '(/ios:native/ios:ptp/ios-ptp:mode/ios-ptp:boundary/ios-ptp:delay-req)';
        leaf interval {
          description
            "log mean value of delay request message transmit interval";
          type int8 {
            range "-1..5";
          }
          default "0";
        }
      }
      leaf vlan {
        description
          "PTP vlan id";
        when '(../../ios:switchport-config/ios:switchport/ios-sw:mode/ios-sw:trunk) and ((/ios:native/ios:ptp/ios-ptp:mode/ios-ptp:boundary/ios-ptp:delay-req) or (/ios:native/ios:ptp/ios-ptp:mode/ios-ptp:boundary/ios-ptp:pdelay-req))';
        type uint16 {
          range "1..4094";
        }
      }
    }
  }

  grouping boundary-clock-grouping {
    container boundary {
      list domain {
        description
          "PTP domain";
        key "domain-num";
        leaf domain-num {
          type uint16 {
            range "0..255";
          }
        }
        leaf hybrid {
          description
            "PTP hybrid mode";
          type empty;
        }
        container profile {
          description
            "Change PTP clock profile";
          choice profile-case {
            case g8275.1-case {
              leaf g8275.1 {
                if-feature "ios-features:ptp-bc";
                type empty;
              }
            }
            case power-case {
              leaf power {
                type empty;
              }
            }
            case default-case {
              leaf default {
                type empty;
              }
            }
            case dot1as-case {
              leaf dot1as {
                type empty;
              }
            }
          }
        }
        uses config-ptp-bc-common-grouping1;
        uses config-ptp-bc-grouping2;
      }
    }
  }

  grouping transparent-clock-grouping {
    container transparent {
      description
        "Configure PTP transparent clock";
      list domain {
        description
          "PTP domain";
        key "domain-num";
        leaf domain-num {
          description
            "Domain number";
          type uint8 {
            range "0..255";
          }
        }
        container profile {
          description
            "PTP profile";
          container default {
            must 'not(../power) and not(../power-2017)' {
              error-message "A clock with a different profile already exists for this domain";
            }
            presence "Default profile";
            list sync-limit {
              description
                "out of sync limit for sync fault";
              key "interface";
              leaf interface {
                must '/ios:native/ios:interface/*[concat(local-name(.), ios:name) = current()]';
                type string;
              }
              leaf sync-limit-value {
                description
                  "maximum offset from master before sync fault";
                type uint32 {
                  range "50..500000000";
                }
                default "500000";
              }
            }
            uses ptp-transparent-clock-common-profile-grouping;
          }
          container power {
            must 'not(../default) and not(../power-2017)' {
              error-message "A clock with a different profile already exists for domain this domain";
            }
            presence "Power profile";
            uses ptp-transparent-clock-common-profile-grouping;
            uses ptp-transparent-clock-power-profile-grouping;
          }
          container power-2017 {
            must 'not(../default) and not(../power)' {
              error-message "A clock with a different profile already exists for this domain";
            }
            presence "Power-2017 profile";
            uses ptp-transparent-clock-common-profile-grouping;
            uses ptp-transparent-clock-power-profile-grouping;
          }
        }
      }
    }
  }

  grouping ptp-transparent-clock-common-profile-grouping {
    list gmc-block {
      key "interface";
      leaf interface {
        must '/ios:native/ios:interface/*[concat(local-name(.), ios:name) = current()]';
        type string;
      }
    }
    leaf vlan {
      description
        "PTP vlan settings";
      type uint16 {
        range "1..4094";
      }
    }
  }

  grouping ptp-transparent-clock-power-profile-grouping {
    leaf allow-without-tlv {
      description
        "Allow PTP announce messages without TLVs";
      type boolean;
      default "false";
    }
    leaf packet {
      description
        "Set PTP Packet priority";
      type uint8 {
        range "0..7";
      }
      default "4";
    }
    list pdelay-interval {
      description
        "pdelay-message interval";
      key "interface";
      leaf interface {
        must '/ios:native/ios:interface/*[concat(local-name(.), ios:name) = current()]';
        type string;
      }
      leaf pdelay-interval-value {
        description
          "pdelay message transmit interval value";
        type uint8 {
          range "0..5";
        }
        default "0";
      }
    }
    list sync-limit {
      description
        "out of sync limit for sync fault";
      key "interface";
      leaf interface {
        must '/ios:native/ios:interface/*[concat(local-name(.), ios:name) = current()]';
        type string;
      }
      leaf sync-limit-value {
        description
          "maximum offset from master before sync fault";
        type uint32 {
          range "50..500000000";
        }
        default "10000";
      }
    }
  }

  augment "/ios:native/ios:ptp" {
    uses config-ptp-grouping2;
  }

  augment "/ios:native/ios:interface/ios:GigabitEthernet" {
    uses config-interface-ptp-grouping;
  }

  augment "/ios:native/ios:interface/ios:TenGigabitEthernet" {
    uses config-interface-ptp-grouping;
  }

  augment "/ios:native/ios:interface/ios:FiveGigabitEthernet" {
    uses config-interface-ptp-grouping;
  }

  augment "/ios:native/ios:interface/ios:TwentyFiveGigE" {
    uses config-interface-ptp-grouping;
  }

  augment "/ios:native/ios:interface/ios:TwoGigabitEthernet" {
    uses config-interface-ptp-grouping;
  }

  augment "/ios:native/ios:interface/ios:FortyGigabitEthernet" {
    uses config-interface-ptp-grouping;
  }

  augment "/ios:native/ios:interface/ios:HundredGigE" {
    uses config-interface-ptp-grouping;
  }
}
