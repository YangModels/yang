module Cisco-IOS-XE-dialer {
  yang-version 1.1;
  namespace "http://cisco.com/ns/yang/Cisco-IOS-XE-dialer";
  prefix ios-dial;

  import cisco-semver {
    prefix cisco-semver;
  }
  import Cisco-IOS-XE-native {
    prefix ios;
  }
  import ietf-inet-types {
    prefix inet;
  }

  organization
    "Cisco Systems, Inc.";
  contact
    "Cisco Systems, Inc.
     Customer Service

     Postal: 170 W Tasman Drive
     San Jose, CA 95134

     Tel: +1 1800 553-NETS

     E-mail: cs-yang@cisco.com";
  description
    "Cisco XE Native Dialer Interfaces.
     Copyright (c) 2020 by Cisco Systems, Inc.
     All rights reserved.";

  revision 2025-03-01 {
    description
      "- Moved deprecated nodes before 17.11 to obsolete";
    cisco-semver:module-version "2.0.0";
  }
  revision 2022-11-01 {
    description
      "- Update yang-version to 1.1";
    cisco-semver:module-version "1.3.0";
  }
  revision 2022-03-01 {
    description
      "- Deprecated leaf watch-group and added new leaf-list to store more than one entry like IOS ";
    cisco-semver:module-version "1.2.0";
  }
  revision 2020-11-01 {
    description
      "-down with vInterface ";
    cisco-semver:module-version "1.1.1";
  }
  revision 2019-07-01 {
    description
      "Establish semantic version baseline";
    cisco-semver:module-version "1.0.0";
  }
  revision 2018-08-30 {
    description
      "Added dependency for interface dialer in-band and pool";
  }
  revision 2018-05-01 {
    description
      "Move dialer related model to dialer yang file";
  }
  revision 2018-03-28 {
    description
      "Initial revision for Dialer Interface";
  }

  grouping config-dialer-grouping {
    container dialer {
      description
        "Dialer commands";
      list watch-list {
        description
          "Dialer watch list";
        key "number";
        leaf number {
          type uint8 {
            range "1..255";
          }
        }
        list delay {
          description
            "Dialer watch delay";
          key "interval";
          leaf interval {
            type enumeration {
              enum connect;
              enum disconnect;
              enum route-check;
            }
          }
          leaf initial {
            description
              "Delay for initial check of watched route after boot";
            when "../interval = 'route-check'";
            type empty;
          }
          leaf delay-time {
            description
              "Delay time in seconds";
            type uint32 {
              range "1..2147483";
            }
          }
        }
        list ip {
          description
            "IP";
          key "address";
          leaf address {
            description
              "IP address";
            type inet:ipv4-address;
          }
          leaf mask {
            description
              "IP subnet mask";
            type inet:ipv4-address;
          }
        }
      }
    }
  }

  grouping config-dialer-list-grouping {
    list dialer-list {
      description
        "Create a dialer list entry";
      key "group-number";
      leaf group-number {
        type uint8 {
          range "1..128";
        }
      }
      list protocol {
        key "protocol-type";
        leaf protocol-type {
          type enumeration {
            enum appletalk;
            enum bridge;
            enum clns;
            enum clns_es;
            enum clns_is;
            enum decnet;
            enum decnet_node;
            enum decnet_router-L1;
            enum decnet_router-L2;
            enum ip;
            enum ipv6;
            enum ipx;
            enum llc2;
            enum netbios;
            enum novell;
            enum vines;
            enum xns;
          }
        }
        leaf access {
          type enumeration {
            enum deny;
            enum list;
            enum permit;
          }
        }
        leaf list-name {
          when "../access = 'list'";
          type string;
        }
      }
    }
  }

  grouping config-interface-dialer-grouping {
    container dialer {
      leaf in-band {
        description
          "Dialing for interface";
        type empty;
      }
      leaf pool {
        description
          "Dialer pool to be used";
        type uint16 {
          range "1..255";
        }
      }
      leaf down-with-vInterface {
        description
          "Down with vInterface";
        must '../in-band or ../pool' {
          error-message "%Configure a \"dialer in-band\", or \"dialer pool\" first.";
        }
        type empty;
      }
      leaf idle-timeout {
        description
          "Idle timeout before disconnect";
        must '../in-band or ../pool' {
          error-message "%Configure a \"dialer in-band\", or \"dialer pool\" first.";
        }
        type uint32;
      }
      leaf string {
        description
          "number to be passed for calling";
        type string;
      }
      leaf-list watch-group-list {
        description
          "Assign interface to dialer-watch-list";
        ordered-by user;
        must '../in-band' {
          error-message "A dialer must first be specified";
        }
        type uint32 {
          range "1..255";
        }
      }
      leaf watch-group {
        description
          "(OBSOLETE)Assign interface to dialer-watch-list";
        status obsolete;
        type uint32;
      }
    }
    leaf dialer-group {
      description
        "Assign interface to dialer-list";
      type uint8 {
        range "1..128";
      }
    }
  }

  augment "/ios:native" {
    uses config-dialer-grouping;
  }

  augment "/ios:native" {
    uses config-dialer-list-grouping;
  }

  augment "/ios:native/ios:interface/ios:Dialer" {
    uses config-interface-dialer-grouping;
  }

  augment "/ios:native/ios:interface/ios:Cellular" {
    uses config-interface-dialer-grouping;
  }
}
