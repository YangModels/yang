module Cisco-IOS-XE-wireless-mobility-types {
  yang-version 1.1;
  namespace "http://cisco.com/ns/yang/Cisco-IOS-XE-wireless-mobility-types";
  prefix wireless-mobility-types;

  import cisco-semver {
    prefix cisco-semver;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains a collection of YANG definitions
     for wireless mobility data types.
     Copyright (c) 2016-2019, 2022 by Cisco Systems, Inc.
     All rights reserved.";

  revision 2024-07-01 {
    description
      "- Added Multilink Association Type enum";
    reference
      "2.7.0";
    cisco-semver:module-version "2.7.0";
  }
  revision 2022-11-01 {
    description
      "Update yang-version to 1.1";
    reference
      "2.6.0";
    cisco-semver:module-version "2.6.0";
  }
  revision 2022-03-01 {
    description
      "- Added mesh AP PMK delete";
    reference
      "2.5.0";
    cisco-semver:module-version "2.5.0";
  }
  revision 2019-11-01 {
    description
      "- Added handoff deny L3 VLAN override stats.
       - Added counter for handoffs received with an unknown peer address.
       - Added mobility domain information.";
    reference
      "2.4.0";
    cisco-semver:module-version "2.4.0";
  }
  revision 2019-05-01 {
    description
      "- Added message names in mobility message stats
       - Added dot11 roam type in mobility history
       - Added semantic version";
    reference
      "2.3.0";
    cisco-semver:module-version "2.3.0";
  }
  revision 2019-01-14 {
    description
      "- Cleaned up spelling errors in descriptions
       - Added mobility capability, DTLS events and message statistics
       - Added mobility management event stats
       - Added mobility interface event stats";
    reference
      "2.2.0";
    cisco-semver:module-version "2.2.0";
  }
  revision 2018-04-03 {
    description
      "Add DTLS and keepalive role negotiation";
    reference
      "2.1.0";
    cisco-semver:module-version "2.1.0";
  }
  revision 2018-01-24 {
    description
      "The first generally available version";
    reference
      "2.0.0";
    cisco-semver:module-version "2.0.0";
  }
  revision 2017-05-05 {
    description
      "Initial revision";
    reference
      "1.0.0";
    cisco-semver:module-version "1.0.0";
  }

  typedef dot11-client-roam-type {
    type enumeration {
      enum dot11-roam-type-none {
        value 0;
        description
          "Client dot11 roam type none";
      }
      enum dot11-roam-type-slow-11i {
        value 1;
        description
          "Client dot11 roam type 802.11i slow";
      }
      enum dot11-roam-type-fast-okc {
        value 2;
        description
          "Client dot11 roam type 802.11i opportunistic key caching";
      }
      enum dot11-roam-type-cckm {
        value 3;
        description
          "Client dot11 roam type CCKM";
      }
      enum dot11-roam-type-fast-11r {
        value 4;
        description
          "Client dot11 roam type 802.11r";
      }
    }
    description
      "Dot11 roam type";
  }

  typedef mm-msg-dgram-type {
    type enumeration {
      enum mm-msg-ctrl {
        value 0;
        description
          "Mobility control tunnel";
      }
      enum mm-msg-data {
        value 1;
        description
          "Mobility control tunnel";
      }
    }
    description
      "Mobility tunnel type";
  }

  typedef mm-mobility-msg-type {
    type enumeration {
      enum keepalive-data {
        value 0;
        description
          "Mobility data tunnel keepalive";
      }
      enum mobile-announce {
        value 1;
        description
          "Mobile announce";
      }
      enum mobile-announce-nak {
        value 2;
        description
          "Mobile announce nak";
      }
      enum static-ip-mobile-announce {
        value 3;
        description
          "Static IP mobile announce";
      }
      enum static-ip-mobile-response {
        value 4;
        description
          "Static IP mobile announce response";
      }
      enum handoff {
        value 5;
        description
          "Mobile handoff";
      }
      enum handoff-end {
        value 6;
        description
          "Handoff end";
      }
      enum handoff-end-ack {
        value 7;
        description
          "Handoff end ack";
      }
      enum anchor-req {
        value 8;
        description
          "Anchor request";
      }
      enum anchor-grant {
        value 9;
        description
          "Anchor grant";
      }
      enum anchor-xfer {
        value 10;
        description
          "Anchor transfer";
      }
      enum anchor-xfer-ack {
        value 11;
        description
          "Anchor transfer ack";
      }
      enum export-anchor-req {
        value 12;
        description
          "Export anchor request";
      }
      enum export-anchor-rsp {
        value 13;
        description
          "Export anchor response";
      }
      enum aaa-handoff {
        value 14;
        description
          "AAA handoff";
      }
      enum aaa-handoff-ack {
        value 15;
        description
          "AAA handoff ack";
      }
      enum ipv4-address-update {
        value 16;
        description
          "IPv4 address update";
      }
      enum ipv4-address-update-ack {
        value 17;
        description
          "IPv4 address update ack";
      }
      enum ipv6-nd-pkt {
        value 18;
        description
          "IPv6 neighbor discovery packet";
      }
      enum ipv6-address-update {
        value 19;
        description
          "IPv6 address update";
      }
      enum ipv6-address-update-ack {
        value 20;
        description
          "IPv6 address update ack";
      }
      enum client-add {
        value 21;
        description
          "Client add";
      }
      enum client-delete {
        value 22;
        description
          "Client delete";
      }
      enum keepalive-ctrl-req {
        value 23;
        description
          "Mobility control tunnel keepalive request";
      }
      enum keepalive-ctrl-rsp {
        value 24;
        description
          "Mobility control tunnel keepalive response";
      }
      enum mfp-key-request {
        value 25;
        description
          "Management frame protection key request";
      }
      enum mfp-key-update {
        value 26;
        description
          "Management frame protection key update";
      }
      enum mfp-key-ack {
        value 27;
        description
          "Management frame protection key ack";
      }
      enum mfp-key-delete {
        value 28;
        description
          "Management frame protection key delete";
      }
      enum aplist-update {
        value 29;
        description
          "AP list update";
      }
      enum client-device-profile-info {
        value 30;
        description
          "Client device profile info";
      }
      enum pmk-update {
        value 31;
        description
          "PMK update";
      }
      enum pmk-delete {
        value 32;
        description
          "PMK delete";
      }
      enum pmk-11r-nonce-update {
        value 33;
        description
          "PMK 802.11r pre-auth update";
      }
      enum device-cache-update {
        value 34;
        description
          "Device cache update";
      }
      enum ha-sso-announce {
        value 35;
        description
          "HA SSO announce";
      }
      enum ha-sso-announce-rsp {
        value 36;
        description
          "HA SSO announce response";
      }
      enum mesh-roam-req {
        value 37;
        description
          "Mesh roam request";
      }
      enum mesh-roam-rsp {
        value 38;
        description
          "Mesh roam response";
      }
      enum mesh-ap-pmk-key-time-update {
        value 39;
        description
          "Mesh AP PMK key time update";
      }
      enum mesh-ap-pmk-key-time-update-ack {
        value 40;
        description
          "Mesh AP PMK key time update ack";
      }
      enum mesh-ap-channel-list {
        value 41;
        description
          "Mesh AP channel list";
      }
      enum mesh-ap-channel-list-ack {
        value 42;
        description
          "Mesh AP channel list ack";
      }
      enum ap-upgrade {
        value 43;
        description
          "AP upgrade";
      }
      enum mesh-ap-pmk-delete {
        value 44;
        description
          "Mesh AP PMK delete";
      }
    }
    description
      "Mobility message types";
  }

  typedef mm-client-roam-type {
    type enumeration {
      enum mm-roam-type-none {
        value 0;
        description
          "Mobility roam type none (not L2, L3, L3 requested
           or L3 forced";
      }
      enum mm-roam-type-l2 {
        value 1;
        description
          "L2 roam because of VLAN match";
      }
      enum mm-roam-type-l3 {
        value 2;
        description
          "L3 roam because of VLAN difference";
      }
      enum mm-roam-type-l3-requested {
        value 3;
        description
          "L3 roam because of L2 anchoring";
      }
      enum mm-roam-type-l3-forced {
        value 4;
        description
          "L3 roam because of platform difference";
      }
    }
    description
      "Mobility client roaming type";
  }

  typedef mm-mobility-state {
    type enumeration {
      enum mm-mobility-incomplete {
        value 0;
        description
          "Incomplete mobility";
      }
      enum mm-mobility-complete {
        value 1;
        description
          "Mobility completed";
      }
    }
    description
      "Mobility state";
  }

  typedef mm-client-role {
    type enumeration {
      enum mm-client-role-unassoc {
        value 0;
        description
          "Unassociated mobile client";
      }
      enum mm-client-role-local {
        value 1;
        description
          "Local mobile client";
      }
      enum mm-client-role-anchor {
        value 2;
        description
          "Anchor mobile client";
      }
      enum mm-client-role-foreign {
        value 3;
        description
          "Foreign mobile client";
      }
      enum mm-client-role-export-anchor {
        value 4;
        description
          "Export anchor mobile client";
      }
      enum mm-client-role-export-foreign {
        value 5;
        description
          "Export foreign mobile client";
      }
      enum mm-client-role-handoff {
        value 6;
        description
          "Handoff mobile client";
      }
    }
    description
      "Role of mobility client";
  }

  typedef mm-client-type {
    type enumeration {
      enum mm-client-type-wireless {
        value 0;
        description
          "Wireless mobile client";
      }
      enum mm-client-type-wireless-export {
        value 1;
        description
          "Wireless export mobile client";
      }
      enum mm-client-type-wgb {
        value 2;
        description
          "WGB mobile client";
      }
      enum mm-client-type-wgb-export {
        value 3;
        description
          "WGB export mobile client";
      }
      enum mm-client-type-wgb-wired {
        value 4;
        description
          "WGB wired mobile client";
      }
      enum mm-client-type-wgb-wired-export {
        value 5;
        description
          "WGB wired export mobile client";
      }
      enum mm-client-type-wired-export {
        value 6;
        description
          "Wired export mobility client";
      }
    }
    description
      "Mobility client type";
  }

  typedef mm-client-mode {
    type enumeration {
      enum mm-client-mode-local {
        value 0;
        description
          "Local mobility client";
      }
      enum mm-client-mode-flex-local-sw {
        value 1;
        description
          "Flex, locally switched mobility client";
      }
      enum mm-client-mode-flex-central-sw {
        value 2;
        description
          "Flex, centrally switched mobility client";
      }
      enum mm-client-mode-fabric {
        value 3;
        description
          "Fabric mobility client";
      }
    }
    description
      "Mode of mobility client";
  }

  typedef unified-link-status {
    type enumeration {
      enum status-unknown {
        value 0;
        description
          "Unknown status for mobility tunnel";
      }
      enum data-path-down {
        value 1;
        description
          "Data path is down for mobility tunnel";
      }
      enum ctrl-path-down {
        value 2;
        description
          "Control path is down for mobility tunnel";
      }
      enum ctrl-data-path-down {
        value 3;
        description
          "Control and data path is down for mobility tunnel";
      }
      enum up {
        value 4;
        description
          "mobility tunnel is UP";
      }
    }
    description
      "Combined mobility tunnel state";
  }

  typedef arch-capability {
    type enumeration {
      enum mm-arch-unknown {
        value 0;
        description
          "Unknown mobility architectural";
      }
      enum mm-arch-new {
        value 1;
        description
          "New mobility architecture";
      }
      enum mm-arch-old {
        value 2;
        description
          "Old mobility architecture";
      }
      enum mm-arch-ewlc {
        value 3;
        description
          "EWLC mobility architecture";
      }
    }
    description
      "Mobility architectural capability";
  }

  typedef dtls-capability {
    type enumeration {
      enum mm-dtls-capability-unknown {
        value 0;
        description
          "DTLS capability unknown for mobile client";
      }
      enum mm-dtls-capability-unsupported {
        value 1;
        description
          "DTLS capability not supported for mobile client";
      }
      enum mm-dtls-capability-supported {
        value 2;
        description
          "DTLS capability supported for client";
      }
      enum mm-dtls-capability-any {
        value 3;
        description
          "*DTLS capability ";
      }
    }
    description
      "DTLS capability of moblie client";
  }

  typedef tunnel-capability {
    type enumeration {
      enum mm-unknown-tunnel {
        value 0;
        description
          "Tunnel capability unknown for mobility client";
      }
      enum mm-eoip-tunnel {
        value 1;
        description
          "Mobility client has EOIP tunnel capability";
      }
      enum mm-capwap-tunnel {
        value 2;
        description
          "Mobility client has CAPWAP tunnel capability";
      }
      enum mm-both-tunnel {
        value 3;
        description
          "Mobility client has both EOIP and CAPWAP tunnel
           capability";
      }
    }
    description
      "Tunnel capability for mobility client";
  }

  typedef mm-dtls-status {
    type enumeration {
      enum mm-dtls-disabled {
        value 0;
        description
          "DTLS connection is disabled for mobility client";
      }
      enum mm-dtls-init {
        value 1;
        description
          "DTLS connection is initialised for mobility
           connection";
      }
      enum mm-dtls-in-handshake {
        value 2;
        description
          "DTLS connection is in handshake state for mobility
           client";
      }
      enum mm-dtls-in-cert-verify {
        value 3;
        description
          "DTLS connection is in certificate verification
           state for mobility client";
      }
      enum mm-dtls-sess-established {
        value 4;
        description
          "DTLS connection is in session established state
           for mobility client";
      }
      enum mm-dtls-in-key-plumbing {
        value 5;
        description
          "DTLS connection is in key plumbing state for
           mobility client";
      }
      enum mm-dtls-key-plumbed {
        value 6;
        description
          "DTLS connection has plumbed the key for mobility
           client";
      }
    }
    description
      "DTLS connection status for mobility client";
  }

  typedef mm-assoc-type {
    type enumeration {
      enum mm-non-mlo-assoc {
        value 0;
        description
          "Mobility Association type is Non Multilink Client";
      }
      enum mm-mlo-assoc {
        value 1;
        description
          "Mobility Association type is Multilink Client";
      }
    }
    description
      "Mobility Association type for mobility client";
  }

  grouping capability {
    description
      "Architecture, DTLS and Tunnel capability for mobility";
    leaf arch {
      type wireless-mobility-types:arch-capability;
      description
        "Architecture capability for mobility";
    }
    leaf dtls {
      type wireless-mobility-types:dtls-capability;
      description
        "DTLS capability for mobility";
    }
    leaf tunnel {
      type wireless-mobility-types:tunnel-capability;
      description
        "Tunnel capability for mobility";
    }
  }

  grouping mm-msg-stats {
    description
      "Message statistics for mobility client";
    leaf type {
      type uint32;
      description
        "CAPWAP messages type for mobility client";
    }
    leaf allocs {
      type uint32;
      description
        "Number of CAPWAP messages allocated for mobility
         client";
    }
    leaf frees {
      type uint32;
      description
        "Number of CAPWAP messages freed for mobility client";
    }
    leaf tx {
      type uint32;
      description
        "Number of CAPWAP messages transmitted for mobility
         client";
    }
    leaf rx {
      type uint32;
      description
        "Number of CAPWAP messages received for mobility
         client";
    }
    leaf forwarded {
      type uint32;
      description
        "Number of CAPWAP messages forwarded for mobility
         client";
    }
    leaf tx-errors {
      type uint32;
      description
        "Number of CAPWAP message transmit errors for
         mobility client";
    }
    leaf rx-errors {
      type uint32;
      description
        "Number of CAPWAP message receive errors for mobility
         client";
    }
    leaf tx-retries {
      type uint32;
      description
        "Number of retries for CAPWAP message transmit error
         for mobility client";
    }
    leaf drops {
      type uint32;
      description
        "Number of dropped CAPWAP messages for mobility
         client";
    }
    leaf built {
      type uint32;
      description
        "Number of CAPWAP messages built fot mobility client";
    }
    leaf processed {
      type uint32;
      description
        "Number of processed CAPWAP messages for mobility
         client";
    }
    leaf mm-msg-type {
      type wireless-mobility-types:mm-mobility-msg-type;
      description
        "CAPWAP mobility message type";
    }
  }

  grouping mm-dtls-event-stats {
    description
      "DTLS event statistics for mobility tunnels";
    leaf connect-start {
      type uint32;
      description
        "Connections attempted";
    }
    leaf connect-established {
      type uint32;
      description
        "Connections established";
    }
    leaf close {
      type uint32;
      description
        "Connections closed";
    }
    leaf key-plumb-start {
      type uint32;
      description
        "Data plane key plumb requests";
    }
    leaf key-plumb-acked {
      type uint32;
      description
        "Data plane key plumb acknowledgements";
    }
    leaf tunnel-type {
      type wireless-mobility-types:mm-msg-dgram-type;
      description
        "CAPWAP mobility tunnel type";
    }
  }

  grouping mm-dtls-msg-stats {
    description
      "DTLS message statistics for mobility tunnels";
    leaf handshake-msg-tx {
      type uint32;
      description
        "Handshake messages sent";
    }
    leaf handshake-msg-rx {
      type uint32;
      description
        "Handshake messages received";
    }
    leaf encrypted-msg-tx {
      type uint32;
      description
        "Encrypted messages sent";
    }
    leaf encrypted-msg-rx {
      type uint32;
      description
        "Encrypted messages received";
    }
    leaf tunnel-type {
      type wireless-mobility-types:mm-msg-dgram-type;
      description
        "CAPWAP mobility tunnel type";
    }
  }

  grouping mm-mobility-stats {
    description
      "Mobility event statistics";
    leaf event-data-allocs {
      type uint32;
      description
        "Total number of event data allocations in mobility management state machine";
    }
    leaf event-data-frees {
      type uint32;
      description
        "Total number of event data frees in mobility management state machine";
    }
    leaf fsm-set-allocs {
      type uint32;
      description
        "Total number of mobility management state machine instance allocations";
    }
    leaf fsm-set-frees {
      type uint32;
      description
        "Total number of mobility management state machine instance frees";
    }
    leaf timer-allocs {
      type uint32;
      description
        "Total number of timer allocations in mobility management state machine";
    }
    leaf timer-frees {
      type uint32;
      description
        "Total number of timer freed in mobility management state machine";
    }
    leaf timer-starts {
      type uint32;
      description
        "Total number of timers started in mobility management state machine";
    }
    leaf timer-stops {
      type uint32;
      description
        "Total number of timers stopped in mobility management state machine";
    }
    leaf mcfsm-invalid-events {
      type uint32;
      description
        "Total number of invalid events in mobility management state machine";
    }
    leaf mcfsm-internal-error {
      type uint32;
      description
        "Total number of errors in mobility management state machine";
    }
    leaf joined-as-local {
      type uint32;
      description
        "Total number of clients joined as local on wireless LAN controller";
    }
    leaf joined-as-foreign {
      type uint32;
      description
        "Total number of clients joined as foreign on wireless LAN controller";
    }
    leaf joined-as-export-foreign {
      type uint32;
      description
        "Total number of clients joined as export foreign on wireless LAN controller";
    }
    leaf joined-as-export-anchor {
      type uint32;
      description
        "Total number of clients joined as export anchor on wireless LAN controller";
    }
    leaf local-to-anchor {
      type uint32;
      description
        "Total number of clients whose role changed from local to anchor";
    }
    leaf anchor-to-local {
      type uint32;
      description
        "Total number of clients whose role changed from anchor to local";
    }
    leaf local-delete {
      type uint32;
      description
        "Total number of client deletions that were triggered locally within wireless LAN controller";
    }
    leaf remote-delete {
      type uint32;
      description
        "Total number of client deletions that were triggered by mobility peer controller";
    }
    leaf mcfsm-delete-internal-error {
      type uint32;
      description
        "Total number of clients deleted due to errors in mobility management state machine";
    }
    leaf mcfsm-roam-internal-error {
      type uint32;
      description
        "Total number of clients deleted due to errors in mobility management state machine during roam";
    }
    leaf l2-roam-count {
      type uint32;
      description
        "Total number of L2 roams on wireless LAN controller";
    }
    leaf l3-roam-count {
      type uint32;
      description
        "Total number of L3 roam on wireless LAN controller";
    }
    leaf flex-client-roaming-count {
      type uint32;
      description
        "Total number of inter process roams by flex mode clients within wireless LAN controller";
    }
    leaf inter-wncd-roam-count {
      type uint32;
      description
        "Total number of inter process roams within wireless LAN controller";
    }
    leaf exp-anc-req-sent {
      type uint32;
      description
        "Number of export anchor requests sent";
    }
    leaf exp-anc-req-received {
      type uint32;
      description
        "Number of export anchor requests received";
    }
    leaf exp-anc-resp-ok-sent {
      type uint32;
      description
        "Number of export anchor response OK sent";
    }
    leaf exp-anc-resp-generic-deny-sent {
      type uint32;
      description
        "Number of export anchor response generic deny sent";
    }
    leaf exp-anc-resp-client-blacklisted-sent {
      type uint32;
      description
        "Number of export anchor response deny sent due to client blacklisted";
    }
    leaf exp-anc-resp-limit-reached-sent {
      type uint32;
      description
        "Number of export anchor response deny sent due to client limit reached";
    }
    leaf exp-anc-resp-profile-mismatch-sent {
      type uint32;
      description
        "Number of export anchor response deny sent due to profile mismatch";
    }
    leaf exp-anc-resp-ok-received {
      type uint32;
      description
        "Number of export anchor response OK received";
    }
    leaf exp-anc-resp-generic-deny-received {
      type uint32;
      description
        "Number of export anchor response generic deny received";
    }
    leaf exp-anc-resp-client-blacklisted-received {
      type uint32;
      description
        "Number of export anchor response deny received due to client blacklisted";
    }
    leaf exp-anc-resp-limit-reached-received {
      type uint32;
      description
        "Number of export anchor response deny received due to client limit reached";
    }
    leaf exp-anc-resp-profile-mismatch-received {
      type uint32;
      description
        "Number of export anchor response deny received due to profile mismatch";
    }
    leaf exp-anc-resp-unknown-received {
      type uint32;
      description
        "Number of export anchor response deny with unknown reasons";
    }
    leaf handoff-sent-ms-blacklist {
      type uint32;
      description
        "Total number of handoff status blacklisted client sent";
    }
    leaf handoff-received-ms-blacklist {
      type uint32;
      description
        "Total number of handoff status blacklisted client received";
    }
  }

  grouping mmif-mobility-stats {
    description
      "Mobility Interface statistics";
    leaf event-data-allocs {
      type uint32;
      description
        "Total number of mobility interface event data allocations";
    }
    leaf event-data-frees {
      type uint32;
      description
        "Total number of mobility interface event data frees";
    }
    leaf mmif-fsm-invalid-events {
      type uint32;
      description
        "Total number of invalid events received by mobility interface";
    }
    leaf mmif-schedule-errors {
      type uint32;
      description
        "Total number of mobility interface event scheduling errors";
    }
    leaf mmif-fsm-failure {
      type uint32;
      description
        "Total number of mobility interface event processing failure";
    }
    leaf mmif-ipc-failure {
      type uint32;
      description
        "Total number of mobility interface event processing errors due to IPC messaging failure";
    }
    leaf mmif-db-failure {
      type uint32;
      description
        "Total number of mobility interface event processing errors due to database operation failure";
    }
    leaf mmif-invalid-params-failure {
      type uint32;
      description
        "Total number of mobility interface event processing errors due to invalid mobility message parameters";
    }
    leaf mmif-mm-msg-decode-failure {
      type uint32;
      description
        "Total number of mobility interface event processing errors due to mobility message decode failure";
    }
    leaf mmif-unknown-failure {
      type uint32;
      description
        "Total number of mobility interface event processing errors";
    }
    leaf mmif-client-handoff-failure {
      type uint32;
      description
        "Total number of client handoff failures for mobile stations on wireless LAN controller";
    }
    leaf mmif-client-handoff-success {
      type uint32;
      description
        "Total number of client handoff successes for mobile stations on wireless LAN controller";
    }
    leaf mmif-anchor-deny {
      type uint32;
      description
        "Total number of client deletions due to denials by anchor wireless LAN controller";
    }
    leaf mmif-remote-delete {
      type uint32;
      description
        "Total number of client deletions triggered by peer wireless LAN controller";
    }
    leaf mmif-tunnel-down-delete {
      type uint32;
      description
        "Total number of client deletions due to mobility tunnels going down";
    }
    leaf mmif-mbssid-down-event {
      type uint32;
      description
        "Total number of client deletions due to mobility BSSIDs going down";
    }
    leaf intra-wncd-roam-count {
      type uint32;
      description
        "Total number of intra-process roams within wireless LAN controller";
    }
    leaf remote-inter-ctrlr-roams {
      type uint32;
      description
        "Total number of inter-controller roams performed on peer controllers by anchored clients";
    }
    leaf remote-webauth-pend-roams {
      type uint32;
      description
        "Total number of inter-controller performed by clients in webauth pending state";
    }
    leaf anchor-request-sent {
      type uint32;
      description
        "Total number of anchor requests sent for mobile stations on wireless LAN controller";
    }
    leaf anchor-request-grant-received {
      type uint32;
      description
        "Total number of anchor request grants received for mobile stations on wireless LAN controller";
    }
    leaf anchor-request-deny-received {
      type uint32;
      description
        "Total number of anchor request denies received for mobile stations on wireless LAN controller";
    }
    leaf anchor-request-received {
      type uint32;
      description
        "Total number of anchor requests received for mobile stations on wireless LAN controller";
    }
    leaf anchor-request-grant-sent {
      type uint32;
      description
        "Total number of anchor request grants sent for mobile stations on wireless LAN controller";
    }
    leaf anchor-request-deny-sent {
      type uint32;
      description
        "Total number of anchor request denies sent for mobile stations on wireless LAN controller";
    }
    leaf handoff-received-ok {
      type uint32;
      description
        "Total number of handoff status success received for mobile stations on wireless LAN controller";
    }
    leaf handoff-received-grp-mismatch {
      type uint32;
      description
        "Total number of handoff status group mismatches received for mobile stations on wireless LAN controller";
    }
    leaf handoff-received-ms-unknown {
      type uint32;
      description
        "Total number of handoff status unknown client received for mobile stations on wireless LAN controller";
    }
    leaf handoff-received-ms-ssid {
      type uint32;
      description
        "Total number of handoff status client SSID received for mobile stations on wireless LAN controller";
    }
    leaf handoff-received-deny {
      type uint32;
      description
        "Total number of handoff status deny received for mobile stations on wireless LAN controller";
    }
    leaf handoff-sent-ok {
      type uint32;
      description
        "Total number of handoff status OK sent for mobile stations on wireless LAN controller";
    }
    leaf handoff-sent-grp-mismatch {
      type uint32;
      description
        "Total number of handoff status group mismatches sent for mobile stations on wireless LAN controller";
    }
    leaf handoff-sent-ms-unknown {
      type uint32;
      description
        "Total number of handoff status unknown client sent for mobile stations on wireless LAN controller";
    }
    leaf handoff-sent-ms-ssid {
      type uint32;
      description
        "Total number of handoff status client SSID sent for mobile stations on wireless LAN controller";
    }
    leaf handoff-sent-deny {
      type uint32;
      description
        "Total number of handoff status deny sent for mobile stations on wireless LAN controller";
    }
    leaf handoff-received-l3-vlan-override {
      type uint32;
      description
        "Total number of handoff deny L3 VLAN override received for mobile stations on wireless LAN controller";
    }
    leaf handoff-received-unknown-peer {
      type uint32;
      description
        "Total number of handoffs received with an unknown wireless LAN controller address";
    }
    leaf handoff-sent-l3-vlan-override {
      type uint32;
      description
        "Total number of handoff status deny L3 VLAN override sent for mobile stations on wireless LAN controller";
    }
  }

  grouping mobility-domain-info {
    description
      "Mobility domain information";
    leaf mobility-domain-id {
      type uint16;
      description
        "Mobility domain identifier";
    }
  }
}
