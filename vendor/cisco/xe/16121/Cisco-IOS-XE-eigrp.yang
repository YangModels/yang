module Cisco-IOS-XE-eigrp {
  namespace "http://cisco.com/ns/yang/Cisco-IOS-XE-eigrp";
  prefix ios-eigrp;

  import cisco-semver {
    prefix cisco-semver;
  }

  import ietf-inet-types {
    prefix inet;
  }


  import Cisco-IOS-XE-types {
    prefix ios-types;
  }

  import Cisco-IOS-XE-native {
    prefix ios;
  }

  import Cisco-IOS-XE-features {
    prefix ios-features;
  }

  include Cisco-IOS-XE-eigrp-obsolete;

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native EIGRP Yang model.
     Copyright (c) 2016-2019 by Cisco Systems, Inc.
     All rights reserved.";

  // =========================================================================
  // REVISION
  // =========================================================================

  revision 2019-07-01 {
    description
      "- Establish semantic version baseline
       - Separate Classic and Named Mode
       - Add ipv6 eigrp under interface BD-VIF";
    cisco-semver:module-version "1.0.0";
  }
  revision 2019-01-22 {
     description
      "Added leaf for App-hosting Gigabit Ethernet interface";
  }
  revision 2019-01-14 {
      description
      "Add BGP redistribution under topology and change to container
       under non-topology redistribution.";
  }
  revision 2018-11-07 {
      description
      "Cleanup spelling errors in description statements";
  }
  revision 2018-10-31 {
    description
      "Add ipv6 eigrp command under interface";
  }

  revision 2018-08-16 {
    description
      "Fixes a number of issues and added some missing configuration, some for the usage in SDWAN";
  }

  revision 2018-06-28 {
    description
      "added must constraints for deleting vrf";
  }

  revision 2017-09-21 {
    description
      "fix the regression issue that a cli is split";
  }

  revision 2017-08-22 {
    description
      "Allow to set autonomous-system under address-family ipv4 vrf";
  }

  revision 2017-08-01 {
    description
      "Fix passive interface data model";
  }

  revision 2017-06-27 {
    description
      "NED extension for IWAN 2.x - router eigrp";
  }

  revision 2017-02-07 {
    description
      "Initial revision";
  }

  grouping config-eigrp-address-family-ipv4-classic-grouping {

    uses config-eigrp-auto-summary-ipv4-grouping;

    uses config-eigrp-bfd-classic-ipv4-grouping;

    uses config-eigrp-default-information-grouping;

    uses config-eigrp-default-metric-grouping;

    uses config-eigrp-distance-ipv4-grouping;

    uses config-eigrp-distribute-list-classic-named-ipv4-grouping;

    uses config-eigrp-eigrp-address-family-classic-grouping;

    uses config-eigrp-maximum-paths-grouping;

    uses config-eigrp-maximum-secondary-paths-grouping;

    uses config-eigrp-metric-classic-grouping;

    uses config-eigrp-neighbor-ipv4-grouping;

    uses config-eigrp-network-grouping;

    uses config-eigrp-nsf-grouping;

    uses config-eigrp-offset-list-grouping;

    uses config-eigrp-passive-interface-classic-grouping;

    uses config-eigrp-redistribute-classic-ipv4-grouping;

    uses config-eigrp-summary-metric-ipv4-grouping;

    uses config-eigrp-timers-address-family-classic-ipv4-grouping;

    uses config-eigrp-traffic-share-grouping;

    uses config-eigrp-variance-grouping;
  } // end of config-eigrp-address-family-ipv4-classic-grouping

  grouping config-eigrp-address-family-named-common-grouping {

    uses config-eigrp-eigrp-address-family-named-grouping;

    uses config-eigrp-metric-address-family-named-grouping;

    uses config-eigrp-shutdown-address-family-grouping;

  } // end of config-eigrp-address-family-named-common-grouping

  grouping config-eigrp-address-family-named-ipv4-grouping {

    uses config-eigrp-af-interface-ipv4-grouping;

    uses config-eigrp-address-family-named-common-grouping;

    uses config-eigrp-neighbor-ipv4-grouping;

    uses config-eigrp-network-grouping;

    uses config-eigrp-nsf-grouping;

    uses config-eigrp-soft-sia-grouping;

    uses config-eigrp-timers-address-family-named-grouping;

    container topology {
      description
        "Topology configuration mode";

      list topo-base {
        description
          "Base Topology";
        key "topology-base";
        min-elements 1;
        max-elements 1;

        leaf topology-base {
          description
            "Base Topology";

          type enumeration {
            enum "base";
          }
        }

        uses config-eigrp-topology-ipv4-grouping;
      } // end of topo-base

    } // end of topology
  } // end of config-eigrp-address-family-named-ipv4-grouping

  grouping config-eigrp-address-family-named-ipv4-vrf-grouping {

    uses config-eigrp-af-interface-ipv4-grouping;

    uses config-eigrp-address-family-named-common-grouping;

    uses config-eigrp-neighbor-ipv4-grouping;

    uses config-eigrp-network-grouping;

    uses config-eigrp-nsf-grouping;

    uses config-eigrp-soft-sia-grouping;

    uses config-eigrp-timers-address-family-named-grouping;

    container topology {
      description
        "Topology configuration mode";

      list topo-base {
        description
          "Base Topology";
        key "topology-base";
        min-elements 1;
        max-elements 1;

        leaf topology-base {
          description
            "Base Topology";

          type enumeration {
            enum "base";
          }
        }
        uses config-eigrp-topology-ipv4-grouping;
      } // end of topo-base
    } // end of topology
  } // end of config-eigrp-address-family-named-ipv4-vrf-grouping

  grouping config-eigrp-address-family-named-ipv6-grouping {

    uses config-eigrp-af-interface-ipv6-grouping;

    uses config-eigrp-address-family-named-common-grouping;

    uses config-eigrp-neighbor-ipv6-grouping;

    uses config-eigrp-nsf-grouping;

    uses config-eigrp-soft-sia-grouping;

    uses config-eigrp-timers-address-family-named-grouping;

    container topology {
      description
        "Topology configuration mode";

      list topo-base {
        description
          "Base Topology";
        key "topology-base";
        min-elements 1;
        max-elements 1;

        leaf topology-base {
          description
            "Base Topology";

          type enumeration {
            enum "base";
          }
        }

        uses config-eigrp-topology-ipv6-grouping;
      } // end of topo-base

    } // end of topology
  } // end of config-eigrp-address-family-named-ipv6-grouping

  grouping config-eigrp-address-family-named-ipv6-vrf-grouping {

    uses config-eigrp-af-interface-ipv6-grouping;

    uses config-eigrp-address-family-named-common-grouping;

    uses config-eigrp-neighbor-ipv6-grouping;

    uses config-eigrp-nsf-grouping;

    uses config-eigrp-soft-sia-grouping;

    uses config-eigrp-timers-address-family-named-grouping;

    container topology {
      description
        "Topology configuration mode";

      list topo-base {
        description
          "Base Topology";
        key "topology-base";
        min-elements 1;
        max-elements 1;

        leaf topology-base {
          description
            "Base Topology";

          type enumeration {
            enum "base";
          }
        }

        uses config-eigrp-topology-ipv6-grouping;
      } // end of topo-base
    } // end of topology
  } // end of config-eigrp-address-family-named-ipv6-vrf-grouping

  grouping config-eigrp-af-interface-common-grouping {
    leaf add-path {
      description
        "Advertise add paths";
      type uint8 {
        range "1..4";
      }
    }

    container authentication {
      description
        "authentication subcommands";
      container mode {
        description
          "authentication mode";
        choice md5-sha {
          leaf md5 {
            description
              "Keyed message digest";
            type empty;
          }
          container hmac-sha-256 {
            description
              "HMAC-SHA-256 Authentication";
            leaf auth-type {
              description
                "Encryption type (0 for not yet encrypted, 7 for proprietary)";
              type enumeration {
                enum "0";
                enum "7";
              }
            }
            leaf auth-password {
              description
                "Authentication Password";
              type string {
                length "1..32";
              }
            }
          }
        }
      }

      leaf key-chain {
        description
          "key-chain";
        type string;
      }
    }

    leaf bandwidth-percent {
      description
        "Set percentage of bandwidth percentage limit";
      type uint32 {
        range "1..999999";
      }
      default "50";
    }

    leaf bfd {
      description
        "set peer monitoring method to bfd";
      type boolean;
    }

    container dampening-change {
      description
        "Percent interface metric must change to cause update";
      presence "true";
        must "not (../ios-eigrp:dampening-interval)" {
          error-message "dampening-interval already configured";
        }

      leaf dampening-change-value {
        description
          "Percentage of change";
        type uint8 {
          range "1..100";
        }
        default "50";
      }
    }

    container dampening-interval {
      description
        "Time in seconds to check interface metrics";
      presence "true";
      must "not (../ios-eigrp:dampening-change)" {
          error-message "dampening-change already configured";
      }

      leaf dampening-interval-value {
        description
          "Time in seconds";
        type uint16 {
          range "1..65535";
        }
        default "30";
      }
    }

    leaf hello-interval {
      description
        "Configures hello interval";
      type uint16 {
        range "1..65535";
      }
      default "5";
      units seconds;
    }

    leaf hold-time {
      description
        "Configures hold time";
      type uint16 {
        range "1..65535";
      }
      default "15";
      units seconds;
    }

    choice next-hop-self-choice {
      leaf next-hop-self {
        description
          "Configures EIGRP next-hop-self";
        type boolean;
      }

      container next-hop-self-no-ecmp-mode {
        container next-hop-self {
          leaf no-ecmp-mode {
            type boolean;
          }
        }
      }
    }

    leaf passive-interface {
      description
        "Suppress address updates on an interface";

      type boolean;
      default "false";
    }

    leaf shutdown {
      description
        "Disable Address-Family on interface";

      type boolean;
      default "false";
    }

    leaf split-horizon {
      description
        "Perform split horizon";

      type boolean;
      default "true";
    }

    container stub-site {
      description
        "Stub-Site";
      leaf wan-interface {
        description
          "Wan Interface";

      type boolean;
      default "false";
      }
    }
  } // end of config-eigrp-af-interface-common-grouping

  grouping config-eigrp-af-interface-ipv4-grouping {

    list af-interface {
      description
        "Enter Address Family interface configuration";
      key "interface";

      leaf interface {
        description
          "Interface Name";

        type string;
      }

      uses config-eigrp-af-interface-common-grouping;

      container summary-address {
        description
          "Perform address summarization";

        list ipv4-address-mask {
          key "ipv4-address mask";
          leaf ipv4-address {
            description
              "Summary network address";
            type inet:ipv4-address;
          }
          leaf mask {
            description
              "Network mask";
            type inet:ipv4-address;
          }

          leaf leak-map {
            description
              "Allow dynamic prefixes based on the leak-map";
            type string;
          }
        }

        list ipv4-prefix {
          key "ipv4-prefix";
          leaf ipv4-prefix {
            description
              "Summary <network>/<length>, e.g. 192.168.0.0/16";
            type inet:ipv4-prefix;
          }

          leaf leak-map {
            description
              "Allow dynamic prefixes based on the leak-map";
            type string;
          }
        }
      } // end of summary-address
    } // end of af-interface
  } // end of config-eigrp-af-interface-ipv4-grouping

  grouping config-eigrp-af-interface-ipv6-grouping {

    list af-interface {
      description
        "Enter Address Family interface configuration";
      key "interface";

      leaf interface {
        description
          "Interface Name";

        type string;
      }

      uses config-eigrp-af-interface-common-grouping;

      container summary-address {
        description
          "Perform address summarization";

        list ipv6-prefix {
          key "prefix";

          leaf prefix {
            description
              "Summary network prefix";
            type ios-types:ipv6-prefix;
          }
        }
      } // end of summary-address
    } // end of af-interface
  } // end of config-eigrp-af-interface-ipv6-grouping

  grouping config-eigrp-auto-summary-ipv4-grouping {
    leaf auto-summary {
      description
        "Enable automatic network number summarization";
      type boolean;
      default "false";
    }
  } // end of config-eigrp-auto-summary-ipv4-grouping

  grouping config-eigrp-bfd-classic-ipv4-grouping {
    container bfd {
      description
        "BFD configuration commands";
      choice bfd-interface-choice {
        leaf all-interfaces {
          description
            "Enable BFD on all interfaces";
          type empty;
        }

        leaf-list interface {
          description
            "Enable BFD on specific interface";
          type string;
        }
      }
    } // end of bfd
  } // end of config-eigrp-bfd-classic-ipv4-grouping

  grouping config-eigrp-default-information-grouping {
    container default-information {
      description
        "Control distribution of default information";
      container in {
        description
          "Accept input default routing information";
        presence "true";
        leaf access-list {
          description
            "Standard Access List";
          type ios-types:std-acl-type;
        }
      }

      container out {
        description
          "Accept output default routing information";
        presence "true";
        leaf access-list {
          description
            "Standard Access List";
          type ios-types:std-acl-type;
        }
      }
    } // end of default-information
  } // end of config-eigrp-default-information-grouping

  grouping config-eigrp-default-metric-grouping {
    container default-metric {
      description
        "Set metric of redistributed routes";

      leaf bandwidth {
        description
          "Bandwidth in Kbits per second";
        type uint32 {
          range "1..4294967295";
        }
      }

      leaf delay {
        description
          "delay metric in 10 microsecond units";
        type uint32 {
          range "0..4294967295";
        }
      }

      leaf reliability {
        description
          "Reliability metric where 255 is 100% reliable";
        type uint8 {
          range "0..255";
        }
      }

      leaf load {
        description
          "Effective bandwidth metric (Loading) where 255 is 100% loaded";
        type uint8 {
          range "1..255";
        }
      }

      leaf mtu {
        description
          "Maximum Transmission Unit metric of the path";
        type uint16 {
          range "1..65535";
        }
      }
    }
  } // end of config-eigrp-default-metric-grouping

  grouping config-eigrp-distance-ipv4-grouping {
    container distance {
      description
        "Define an administrative distance";
      list ipv4-distance {
        description
          "Distance for ipv4 address/wildcard";
        key "distance ipv4-address wildcard";

        leaf distance {
          description
            "Set route administrative distance";
          type uint8 {
            range "1..255";
          }
        }

        leaf ipv4-address {
          description
            "IP Source address";
          type inet:ipv4-address;
          }

        leaf wildcard {
          description
            "Wildcard bits";
          type inet:ipv4-address;
        }

        leaf access-list {
          description
            "Standard Access List";
          type ios-types:std-acl-type;
        }
      } // end of admin-distance

      container eigrp {
        description
          "Set distance for internal and external routes";

        leaf internal-route-distance {
          description
          "Distance for internal routes";
          type uint8 {
          range "1..255";
          }
          default "90";
        }

        leaf external-route-distance {
          description
            "Distance for external routes";
          type uint8 {
            range "1..255";
          }
          default "170";
        }
      } // end of eigrp
    } // end of distance
  } // end of config-eigrp-distance-ipv4-grouping

  grouping config-eigrp-distance-ipv6-grouping {
    container distance {
      description
        "Define an administrative distance";

      container eigrp {
        description
          "Set distance for internal and external routes";

        leaf internal-route-distance {
          description
          "Distance for internal routes";
          type uint8 {
            range "1..255";
          }
          default "90";
        }

        leaf external-route-distance {
          description
            "Distance for external routes";
          type uint8 {
            range "1..255";
          }
          default "170";
        }
      } // end of eigrp
    } // end of distance
  } // end of config-eigrp-distance-ipv6-grouping

  grouping config-eigrp-distribute-list-classic-named-ipv4-grouping {
    container distribute-list {
      description
        "Filter entries in eigrp updates";

      container access-list {
        description
          "IP expanded access list";

        list access-list-in {
          description
            "IP expanded access list";
          key "in";

          leaf ex-access-list {
            description
              "IP expanded access list";
            type ios-types:exp-acl-type;
          }

          leaf in {
            description
              "Filter incoming service updates";
            must "(not (../../../ios-eigrp:prefix-list/ios-eigrp:prefix-list-in[ios-eigrp:in=current()]))" {
              error-message "distribute-list prefix already exists";
            }
            must "(not (../../../ios-eigrp:gateway/ios-eigrp:gateway-in[ios-eigrp:in=current()]))" {
              error-message "distribute-list gateway already exists";
            }
            must "(not (../../../ios-eigrp:route-map/ios-eigrp:route-map-in[ios-eigrp:in=current()]))" {
              error-message "distribute-list route-map already exists";
            }
            type enumeration {
              enum "in";
            }
          }
        }

        list access-list-out {
          description
            "IP expanded access list";
          key "out";

          leaf ex-access-list {
            description
              "IP expanded access list";
            type ios-types:exp-acl-type;
          }

          leaf out {
            description
              "Filter outgoing service updates";
            must "(not (../../../ios-eigrp:prefix-list/ios-eigrp:prefix-list-out[ios-eigrp:out=current()]))" {
              error-message "distribute-list prefix already exists";
            }
            must "(not (../../../ios-eigrp:route-map/ios-eigrp:route-map-out[ios-eigrp:out=current()]))" {
              error-message "distribute-list route-map already exists";
            }
            type enumeration {
              enum "out";
            }
          }
        }

        list access-list-in-interface {
          description
            "IP expanded access list";
          key "in interface";

          leaf ex-access-list {
            description
              "IP expanded access list";
            type ios-types:exp-acl-type;
          }

          leaf in {
            description
              "Filter incoming service updates";
            type enumeration {
              enum "in";
            }
          }

          leaf interface {
            description
              "Interface name";
            type string;
            must "(not (../../../ios-eigrp:prefix-list/ios-eigrp:prefix-list-in-interface[ios-eigrp:interface=current()]))" {
              error-message "distribute-list prefix already exists";
            }
            must "(not (../../../ios-eigrp:gateway/ios-eigrp:gateway-in-interface[ios-eigrp:interface=current()]))" {
              error-message "distribute-list gateway already exists";
            }
            must "(not (../../../ios-eigrp:route-map/ios-eigrp:route-map-in-interface[ios-eigrp:interface=current()]))" {
              error-message "distribute-list route-map already exists";
            }
          }
        }

        list access-list-out-interface {
          description
            "IP expanded access list";
          key "out interface";

          leaf ex-access-list {
            description
              "IP expanded access list";
            type ios-types:exp-acl-type;
          }

          leaf out {
            description
              "Filter outgoing service updates";
            type enumeration {
              enum "out";
            }
          }

          leaf interface {
            description
              "Interface name";
            type string;
            must "(not (../../../ios-eigrp:prefix-list/ios-eigrp:prefix-list-out-interface[ios-eigrp:interface=current()]))" {
              error-message "distribute-list prefix already exists";
            }
            must "(not (../../../ios-eigrp:route-map/ios-eigrp:route-map-out-interface[ios-eigrp:interface=current()]))" {
              error-message "distribute-list route-map already exists";
            }

          }
        }
      } // end of access-list

      container gateway {
        description
          "Filtering incoming address updates based on gateway";

        list gateway-in {
          description
            "Filtering incoming address updates based on gateway";
          key "in";

          leaf gateway {
            description
              "Name of an IP prefix-list";
            type string;
          }

          leaf in {
            description
              "Filter incoming service updates";
            must "(not (../../../ios-eigrp:access-list/ios-eigrp:access-list-in[ios-eigrp:in=current()]))" {
              error-message "distribute-list acess-list already exists";
            }
            must "(not (../../../ios-eigrp:prefix-list/ios-eigrp:prefix-list-in[ios-eigrp:in=current()]))" {
              error-message "distribute-list prefix already exists";
            }
            must "(not (../../../ios-eigrp:route-map/ios-eigrp:route-map-in[ios-eigrp:in=current()]))" {
              error-message "distribute-list route-map already exists";
            }
            type enumeration {
              enum "in";
            }
          }
        }

        list gateway-in-interface {
          description
            "Filtering incoming address updates based on gateway";
          key "in interface";
          leaf gateway {
            description
              "Name of an IP prefix-list";
            type string;
          }

          leaf in {
            description
              "Filter incoming service updates";
            type enumeration {
              enum "in";
            }
            }

            leaf interface {
            description
              "Interface name";
            type string;
            must "(not (../../../ios-eigrp:access-list/ios-eigrp:access-list-in-interface[ios-eigrp:interface=current()]))" {
              error-message "distribute-list access-list already exists";
            }
            must "(not (../../../ios-eigrp:prefix-list/ios-eigrp:prefix-list-in-interface[ios-eigrp:interface=current()]))" {
              error-message "distribute-list prefix already exists";
            }
            must "(not (../../../ios-eigrp:route-map/ios-eigrp:route-map-in-interface[ios-eigrp:interface=current()]))" {
              error-message "distribute-list route-map already exists";
            }
          }
        }

      } //end of gateway

      container prefix-list {
        description
          "Filter prefixes in address updates";

        list prefix-list-in {
          description
            "Filter prefixes in address updates";
          key "in";

          leaf prefix-list {
            description
              "Name of an IP prefix-list";
            type string;
          }

          leaf gateway {
            description
              "Filtering incoming address updates based on gateway";
            type string;
          }

          leaf in {
            description
              "Filter incoming service updates";
            must "(not (../../../ios-eigrp:access-list/ios-eigrp:access-list-in[ios-eigrp:in=current()]))" {
              error-message "distribute-list acess-list already exists";
            }
            must "(not (../../../ios-eigrp:gateway/ios-eigrp:gateway-in[ios-eigrp:in=current()]))" {
              error-message "distribute-list gateway already exists";
            }
            must "(not (../../../ios-eigrp:route-map/ios-eigrp:route-map-in[ios-eigrp:in=current()]))" {
              error-message "distribute-list route-map already exists";
            }
            type enumeration {
              enum "in";
            }
          }
        }

        list prefix-list-out {
          description
            "Filter prefixes in address updates";
          key "out";

          leaf prefix-list {
            description
              "Name of an IP prefix-list";
            type string;
          }

          leaf out {
            description
              "Filter outgoing service updates";
            must "(not (../../../ios-eigrp:access-list/ios-eigrp:access-list-out[ios-eigrp:out=current()]))" {
              error-message "distribute-list acess-list already exists";
            }
            must "(not (../../../ios-eigrp:route-map/ios-eigrp:route-map-out[ios-eigrp:out=current()]))" {
              error-message "distribute-list route-map already exists";
            }
            type enumeration {
              enum "out";
            }
          }
        }

        list prefix-list-in-interface {
          description
            "Filter prefixes in address updates";
          key "in interface";

          leaf prefix-list {
            description
              "Name of an IP prefix-list";
            type string;
          }

          leaf gateway {
            description
              "Filtering incoming address updates based on gateway";
            type string;
          }

          leaf in {
            description
              "Filter incoming service updates";
            type enumeration {
              enum "in";
            }
          }

          leaf interface {
            description
              "Interface name";
            type string;
            must "(not (../../../ios-eigrp:access-list/ios-eigrp:access-list-in-interface[ios-eigrp:interface=current()]))" {
              error-message "distribute-list access-list already exists";
            }
            must "(not (../../../ios-eigrp:gateway/ios-eigrp:gateway-in-interface[ios-eigrp:interface=current()]))" {
              error-message "distribute-list gateway already exists";
            }
            must "(not (../../../ios-eigrp:route-map/ios-eigrp:route-map-in-interface[ios-eigrp:interface=current()]))" {
              error-message "distribute-list route-map already exists";
            }
          }
        }

        list prefix-list-out-interface {
          description
            "Filter prefixes in address updates";
          key "out interface";

          leaf prefix-list {
            description
              "Name of an IP prefix-list";
            type string;
          }

          leaf out {
            description
              "Filter outgoing service updates";
            type enumeration {
              enum "out";
            }
          }

          leaf interface {
            description
              "Interface name";
            type string;
            must "(not (../../../ios-eigrp:access-list/ios-eigrp:access-list-out-interface[ios-eigrp:interface=current()]))" {
              error-message "distribute-list access-list already exists";
            }
            must "(not (../../../ios-eigrp:route-map/ios-eigrp:route-map-out-interface[ios-eigrp:interface=current()]))" {
              error-message "distribute-list route-map already exists";
            }
          }
        }

      } // end of prefix

      container route-map {
        description
          "Filter prefixes based on the route-map";

        list route-map-in {
          description
            "Filter prefixes based on the route-map";
          key "in";

          leaf route-map-name {
            description
              "route-map name";
            type string;
          }

          leaf in {
            description
              "Filter incoming/outgoing service updates";
            must "(not (../../../ios-eigrp:access-list/ios-eigrp:access-list-in[ios-eigrp:in=current()]))" {
              error-message "distribute-list acess-list already exists";
            }
            must "(not (../../../ios-eigrp:prefix-list/ios-eigrp:prefix-list-in[ios-eigrp:in=current()]))" {
              error-message "distribute-list prefix already exists";
            }
            must "(not (../../../ios-eigrp:gateway/ios-eigrp:gateway-in[ios-eigrp:in=current()]))" {
              error-message "distribute-list gateway already exists";
            }
            type enumeration {
              enum "in";
            }
          }
        }

        list route-map-out {
          description
            "Filter prefixes based on the route-map";
          key "out";

          leaf route-map-name {
            description
              "route-map name";
            type string;
          }

          leaf out {
            description
              "Filter incoming/outgoing service updates";
            must "(not (../../../ios-eigrp:access-list/ios-eigrp:access-list-out[ios-eigrp:out=current()]))" {
              error-message "distribute-list acess-list already exists";
            }
            must "(not (../../../ios-eigrp:prefix-list/ios-eigrp:prefix-list-out[ios-eigrp:out=current()]))" {
              error-message "distribute-list prefix already exists";
            }
            type enumeration {
              enum "out";
            }
          }
        }

        list route-map-in-interface {
          description
            "Filter prefixes based on the route-map";
          key "in interface";

          leaf route-map-name {
            description
              "route-map name";
            type string;
          }

          leaf in {
            description
              "Filter incoming service updates";
            type enumeration {
              enum "in";
            }
          }

          leaf interface {
            description
              "Interface name";
            type string;
            must "(not (../../../ios-eigrp:access-list/ios-eigrp:access-list-in-interface[ios-eigrp:interface=current()]))" {
              error-message "distribute-list access-list already exists";
            }
            must "(not (../../../ios-eigrp:prefix-list/ios-eigrp:prefix-list-in-interface[ios-eigrp:interface=current()]))" {
              error-message "distribute-list prefix already exists";
            }
            must "(not (../../../ios-eigrp:gateway/ios-eigrp:gateway-in-interface[ios-eigrp:interface=current()]))" {
              error-message "distribute-list gateway already exists";
            }
          }
        }

        list route-map-out-interface {
          description
            "Filter prefixes based on the route-map";
          key "out interface";

          leaf route-map-name {
            description
              "route-map name";
            type string;
          }

          leaf out {
            description
              "Filter outgoing service updates";
            type enumeration {
              enum "out";
            }
          }

          leaf interface {
            description
              "Interface name";
            type string;
            must "(not (../../../ios-eigrp:access-list/ios-eigrp:access-list-out-interface[ios-eigrp:interface=current()]))" {
              error-message "distribute-list access-list already exists";
            }
            must "(not (../../../ios-eigrp:prefix-list/ios-eigrp:prefix-list-out-interface[ios-eigrp:interface=current()]))" {
              error-message "distribute-list prefix already exists";
            }
          }
        }

      } // end of route-map
    } // end of distribute-list
  } // end of config-eigrp-distribute-list-classic-named-ipv4-grouping

  grouping config-eigrp-distribute-list-classic-ipv6-grouping {
    container distribute-list {
      description
        "Filter networks in routing updates";

      container prefix-list {
        description
          "Filter connections based on an IPv6 prefix-list";

        list prefix-list-in {
          description
            "Filter connections based on an IPv6 prefix-list";
          key "in";

          leaf prefix-list-name {
            description
              "Prefix-list name";
            type string;
          }

          leaf in {
            description
              "Filter incoming service updates";
            type enumeration {
              enum "in";
            }
          }
        } // end of prefix-list-in

        list prefix-list-out {
          description
            "Filter connections based on an IPv6 prefix-list";
          key "out";

          leaf prefix-list-name {
            description
              "Prefix-list name";
            type string;
          }

          leaf out {
            description
              "Filter outgoing service updates";
            type enumeration {
              enum "out";
            }
          }
        } // end of prefix-list-out

        list prefix-list-in-interface {
          description
            "Filter connections based on an IPv6 prefix-list";
          key "in interface";

          leaf prefix-list-name {
            description
              "Prefix-list name";
            type string;
          }

          leaf in {
            description
              "Filter incoming service updates";
            type enumeration {
              enum "in";
            }
          }

          leaf interface {
            description
              "Interface name";
            type string;
          }
        } // end of prefix-list-in-interface

        list prefix-list-out-interface {
          description
            "Filter connections based on an IPv6 prefix-list";
          key "out interface";

          leaf prefix-list-name {
            description
              "Prefix-list name";
            type string;
          }

          leaf out {
            description
              "Filter outgoing service updates";
            type enumeration {
              enum "out";
            }
          }

          leaf interface {
            description
              "Interface name";
            type string;
          }
        } // end of prefix-list-out-interface

      } // end of prefix-list
    } // end of distribute-list
  } // end of config-eigrp-distribute-list-ipv6-grouping

  grouping config-eigrp-distribute-list-named-ipv6-grouping {
    container distribute-list {
      description
        "Filter networks in eigrp updates";

      container prefix-list {
        description
          "Filter connections based on an IPv6 prefix-list";

        list prefix-list-in {
          description
            "Filter connections based on an IPv6 prefix-list";
          key "in";

          leaf prefix-list-name {
            description
              "Prefix-list name";
            type string;
          }

          leaf in {
            description
              "Filter incoming service updates";
            type enumeration {
              enum "in";
            }
            must "(not (../../../ios-eigrp:route-map/ios-eigrp:route-map-in[ios-eigrp:in=current()]))" {
              error-message "distribute-list route-map already exists";
            }
          }
        }

        list prefix-list-out {
          description
            "Filter connections based on an IPv6 prefix-list";
          key "out";

          leaf prefix-list-name {
            description
              "Prefix-list name";
            type string;
          }

          leaf out {
            description
              "Filter outgoing service updates";
            type enumeration {
              enum "out";
            }
            must "(not (../../../ios-eigrp:route-map/ios-eigrp:route-map-out[ios-eigrp:out=current()]))" {
              error-message "distribute-list route-map already exists";
            }
          }
        }

        list prefix-list-in-interface {
          description
            "Filter connections based on an IPv6 prefix-list";
          key "in interface";

          leaf prefix-list-name {
            description
              "Prefix-list name";
            type string;
          }

          leaf in {
            description
              "Filter incoming service updates";
            type enumeration {
              enum "in";
            }
          }

          leaf interface {
            description
              "Interface name";
            type string;
            must "(not (../../../ios-eigrp:route-map/ios-eigrp:route-map-in-interface[ios-eigrp:interface=current()]))" {
              error-message "distribute-list route-map already exists";
            }
          }
        }

        list prefix-list-out-interface {
          description
            "Filter connections based on an IPv6 prefix-list";
          key "out interface";

          leaf prefix-list-name {
            description
              "Prefix-list name";
            type string;
          }

          leaf out {
            description
              "Filter outgoing service updates";
            type enumeration {
              enum "out";
            }
          }

          leaf interface {
            description
              "Interface name";
            type string;
            must "(not (../../../ios-eigrp:route-map/ios-eigrp:route-map-out-interface[ios-eigrp:interface=current()]))" {
              error-message "distribute-list route-map already exists";
            }
          }
        }

      } // end of prefix-list

      container route-map {
        description
          "Filter prefixes based on the route-map";

        list route-map-in {
          description
            "Filter prefixes based on the route-map";
          key "in";

          leaf route-map-name {
            description
              "route-map name";
            type string;
          }

          leaf in {
            description
              "Filter incoming service updates";
            type enumeration {
              enum "in";
            }
            must "(not (../../../ios-eigrp:prefix-list/ios-eigrp:prefix-list-in[ios-eigrp:in=current()]))" {
              error-message "distribute-list prefix-list already exists";
            }
          }
        }

        list route-map-out {
          description
            "Filter prefixes based on the route-map";
          key "out";

          leaf route-map-name {
            description
              "route-map name";
            type string;
          }

          leaf out {
            description
              "Filter outgoing service updates";
            type enumeration {
              enum "out";
            }
            must "(not (../../../ios-eigrp:prefix-list/ios-eigrp:prefix-list-out[ios-eigrp:out=current()]))" {
              error-message "distribute-list prefix-list already exists";
            }
          }
        }

        list route-map-in-interface {
          description
            "Filter prefixes based on the route-map";
          key "in interface";

          leaf route-map-name {
            description
              "route-map name";
            type string;
          }

          leaf in {
            description
              "Filter incoming service updates";
            type enumeration {
              enum "in";
            }
          }

          leaf interface {
            description
              "Interface name";
            type string;
            must "(not (../../../ios-eigrp:prefix-list/ios-eigrp:prefix-list-in-interface[ios-eigrp:interface=current()]))" {
              error-message "distribute-list prefix-list for interface already exists";
            }

          }
        }

        list route-map-out-interface {
          description
            "Filter prefixes based on the route-map";
          key "out interface";

          leaf route-map-name {
            description
              "route-map name";
            type string;
          }

          leaf out {
            description
              "Filter outgoing service updates";
            type enumeration {
              enum "out";
            }
          }

          leaf interface {
            description
              "Interface name";
            type string;
            must "(not (../../../ios-eigrp:prefix-list/ios-eigrp:prefix-list-out-interface[ios-eigrp:interface=current()]))" {
              error-message "distribute-list prefix-list for interface already exists";
            }
          }
        }

      } // end of route-map
    } // end of distribute-list
  } // end of config-eigrp-distribute-list-ipv6-grouping

  grouping config-eigrp-eigrp-address-family-classic-grouping {
    container eigrp {
      description
        "EIGRP specific commands";

      leaf event-log-size {
        description
          "Set EIGRP maximum event log entries";
        type uint64;
        default "500";
      }

      leaf log-neighbor-changes {
        description
          "Enable/Disable EIGRP neighbor logging";
        type boolean;
        default "true";
      }

      choice log-neighbor-warnings-choice {
        default "log-neighbor-warnings-interval";
        container log-neighbor-warnings-no-interval {
          leaf log-neighbor-warnings {
            type boolean;
          }
        }

        container log-neighbor-warnings-interval {
          container log-neighbor-warnings {
            leaf warning-interval {
              description
                "Neighbor warning interval in seconds";
              type uint16 {
                range "1..65535";
              }
              default "10";
            }
          }
        }
      }

      leaf router-id {
        description
          "router id for this EIGRP process";
        type inet:ipv4-address;
      }

      uses config-eigrp-stub-grouping;

    } // end of eigrp
  } // end of config-eigrp-eigrp-address-family-classic-grouping

  grouping config-eigrp-eigrp-address-family-named-grouping {
    container eigrp {
      description
        "EIGRP Address Family specific commands";

      leaf default-route-tag {
        description
          "Default Route Tag for the Internal Routes";
        type union {
          type uint32 {
            range "0..4294967295";
          }
          type inet:ipv4-address;
        }
      }


      leaf log-neighbor-changes {
        description
          "Enable/Disable EIGRP neighbor logging";
        type boolean;
        default "true";
      }

      choice log-neighbor-warnings-choice {
        default "log-neighbor-warnings-interval";
        leaf log-neighbor-warnings {
          type boolean;
        }

        container log-neighbor-warnings-interval {
          container log-neighbor-warnings {
            leaf warning-interval {
              description
                "Neighbor warning interval in seconds";
              type uint16 {
                range "1..65535";
              }
              default "10";
            }
          }
        }
      }

      leaf router-id {
        description
          "router id for this EIGRP process";
        type inet:ipv4-address;
      }

      uses config-eigrp-stub-grouping;

      leaf stub-site {
        description
          "ASN:nn, Dotted-Decimal:nn or 4BASN:nn  Stub-Site ID in aa:nn format";
        type string {
          pattern "(\\d+:\\d+)";
        }
      }
    } // end of eigrp
  } // end config-eigrp-eigrp-address-family-named-grouping

  grouping config-eigrp-eigrp-topology-grouping {
    container eigrp {
      description
        "EIGRP specific commands";

      leaf event-log-size {
        description
          "Set EIGRP maximum event log entries";
        type uint64;
        default "500";
      }
    }
  } // end of config-eigrp-eigrp-topology-grouping

  grouping config-eigrp-interface-classic-ipv4-grouping {
    container authentication-eigrp {
      description
        "EIGRP Authentication subcommands";
      container authentication {
        description
          "authentication subcommands";
        list key-chain {
          description
            "key-chain";
          key "eigrp";

          leaf eigrp {
            description
              "Enhanced Interior Gateway Routing Protocol (EIGRP)";

            must "/ios:native/ios:router/ios-eigrp:router-eigrp/ios-eigrp:eigrp/ios-eigrp:classic-mode[ios-eigrp:autonomous-system=current()] or" +
                  "/ios:native/ios:router/ios-eigrp:router-eigrp/ios-eigrp:eigrp/ios-eigrp:classic-mode/ios-eigrp:address-family/ios-eigrp:ipv4/ios-eigrp:af-ipv4-vrf[ios-eigrp:autonomous-system=current()]" {
              error-message "router eigrp does not exist.";
            }
            type uint16 {
              range "1..65535";
            }
          }
          leaf key-chain-name {
            description
              "name of key-chain";
            type string;
          }
        }

        list mode {
          description
            "mode";
          key "eigrp";
          leaf eigrp {
            description
              "Enhanced Interior Gateway Routing Protocol (EIGRP)";

            must "/ios:native/ios:router/ios-eigrp:router-eigrp/ios-eigrp:eigrp/ios-eigrp:classic-mode[ios-eigrp:autonomous-system=current()] or" +
                  "/ios:native/ios:router/ios-eigrp:router-eigrp/ios-eigrp:eigrp/ios-eigrp:classic-mode/ios-eigrp:address-family/ios-eigrp:ipv4/ios-eigrp:af-ipv4-vrf[ios-eigrp:autonomous-system=current()]" {
              error-message "router eigrp does not exist.";
            }
            type uint16 {
              range "1..65535";
            }
          }
          leaf md5 {
            description
              "Keyed message digest";
            type empty;
          }
        }
      }
    }

    container hello-interval-eigrp {
      description
        "Configures EIGRP-IPv4 hello interval";
      list hello-interval {
        description
          "Configures EIGRP-IPv4 hello interval";
        key "eigrp";

        leaf eigrp {
          description
            "Enhanced Interior Gateway Routing Protocol (EIGRP)";

          must "/ios:native/ios:router/ios-eigrp:router-eigrp/ios-eigrp:eigrp/ios-eigrp:classic-mode[ios-eigrp:autonomous-system=current()] or" +
                "/ios:native/ios:router/ios-eigrp:router-eigrp/ios-eigrp:eigrp/ios-eigrp:classic-mode/ios-eigrp:address-family/ios-eigrp:ipv4/ios-eigrp:af-ipv4-vrf[ios-eigrp:autonomous-system=current()]" {
            error-message "router eigrp does not exist.";
          }
          type uint16 {
            range "1..65535";
          }
        }

        leaf hello-interval-value {
          description
            "Seconds between hello transmissions";
          type uint16 {
            range "1..65535";
          }
          default "5";
          units seconds;
        }
      }
    }

    container hold-time-eigrp {
      description
        "Configures EIGRP hold time";
      list hold-time {
        description
          "Configures hold time";
        key "eigrp";

        leaf eigrp {
          description
            "Enhanced Interior Gateway Routing Protocol (EIGRP)";

          must "/ios:native/ios:router/ios-eigrp:router-eigrp/ios-eigrp:eigrp/ios-eigrp:classic-mode[ios-eigrp:autonomous-system=current()] or" +
                "/ios:native/ios:router/ios-eigrp:router-eigrp/ios-eigrp:eigrp/ios-eigrp:classic-mode/ios-eigrp:address-family/ios-eigrp:ipv4/ios-eigrp:af-ipv4-vrf[ios-eigrp:autonomous-system=current()]" {
            error-message "router eigrp does not exist.";
          }
          type uint16 {
            range "1..65535";
          }
        }

        leaf hold-time-value {
          description
            "Seconds before neighbor is considered down";
          type uint16 {
            range "1..65535";
          }
          default "15";
          units seconds;
        }
      }
    }

    list bandwidth-percent {
      description
        "Set EIGRP bandwidth limit";
      key "eigrp";

      leaf eigrp {
        description
          "Enhanced Interior Gateway Routing Protocol (EIGRP)";

        must "/ios:native/ios:router/ios-eigrp:router-eigrp/ios-eigrp:eigrp/ios-eigrp:classic-mode[ios-eigrp:autonomous-system=current()] or" +
              "/ios:native/ios:router/ios-eigrp:router-eigrp/ios-eigrp:eigrp/ios-eigrp:classic-mode/ios-eigrp:address-family/ios-eigrp:ipv4/ios-eigrp:af-ipv4-vrf[ios-eigrp:autonomous-system=current()]" {
          error-message "router eigrp does not exist.";
        }
        type uint16 {
          range "1..65535";
        }
      }

      leaf bandwidth-percent {
        description
          "Maximum bandwidth percentage that EIGRP may use";
        type uint32 {
          range "1..999999";
        }
        default "50";
      }
    }
  } // end of config-eigrp-interface-classic-ipv4-grouping

  grouping config-eigrp-interface-classic-ipv6-grouping {
    list hello-interval {
      description
        "Configures EIGRP-IPv6 hello interval";
      key "eigrp";

      leaf eigrp {
        description
          "Enhanced Interior Gateway Routing Protocol (EIGRP)";

        must "/ios:native/ios:ipv6/ios:router/ios-eigrp:router-eigrp/ios-eigrp:eigrp[ios-eigrp:autonomous-system=current()]" {
          error-message "ipv6 router eigrp does not exist.";
        }
        type uint16 {
          range "1..65535";
        }
      }

      leaf hello-interval-value {
        description
          "Seconds between hello transmissions";
        type uint16 {
          range "1..65535";
        }
        default "5";
        units seconds;
      }
    }

    list hold-time {
      description
        "Configures EIGRP-IPv6 hold time";
      key "eigrp";

      leaf eigrp {
        description
          "Enhanced Interior Gateway Routing Protocol (EIGRP)";

        must "/ios:native/ios:ipv6/ios:router/ios-eigrp:router-eigrp/ios-eigrp:eigrp[ios-eigrp:autonomous-system=current()]" {
          error-message "ipv6 router eigrp does not exist.";
        }
        type uint16 {
          range "1..65535";
        }
      }

      leaf hold-time-value {
        description
          "Seconds before neighbor is considered down";
        type uint16 {
          range "1..65535";
        }
        default "15";
        units seconds;
      }
    }

    container router-eigrp {
      description
        "Interface command for IPv6 EIGRP";
      list eigrp {
        description
          "Configure EIGRP IPv6 on interface";
        key "as-number";

        leaf as-number {

          must "/ios:native/ios:ipv6/ios:router/ios-eigrp:router-eigrp/ios-eigrp:eigrp[ios-eigrp:autonomous-system=current()]" {
            error-message "ipv6 router eigrp does not exist.";
          }
          type uint16 {
            range "1..65535";
          }
        }
      }
    }

    list bandwidth-percent {
      description
        "Set EIGRP bandwidth limit";
      key "eigrp";

      leaf eigrp {
        description
          "Enhanced Interior Gateway Routing Protocol (EIGRP)";

        must "/ios:native/ios:ipv6/ios:router/ios-eigrp:router-eigrp/ios-eigrp:eigrp[ios-eigrp:autonomous-system=current()]" {
          error-message "ipv6 router eigrp does not exist.";
        }
        type uint16 {
          range "1..65535";
        }
      }

      leaf bandwidth-percent {
        description
          "Maximum bandwidth percentage that EIGRP may use";
        type uint32 {
          range "1..999999";
        }
        default "50";
      }
    }
  } // end of config-eigrp-interface-classic-ipv6-grouping

  grouping config-eigrp-interface-summary-address-ipv4-grouping {
    list eigrp {
      description
        "Enhanced Interior Gateway Routing Protocol (EIGRP)";
      key "as-number ip-address ip-mask";

      leaf as-number {
        description
          "AS number";
        must "/ios:native/ios:router/ios-eigrp:router-eigrp/ios-eigrp:eigrp/ios-eigrp:classic-mode[ios-eigrp:autonomous-system=current()] or" +
              "/ios:native/ios:router/ios-eigrp:router-eigrp/ios-eigrp:eigrp/ios-eigrp:classic-mode/ios-eigrp:address-family/ios-eigrp:ipv4/ios-eigrp:af-ipv4-vrf[ios-eigrp:autonomous-system=current()]" {
          error-message "router eigrp does not exist.";
        }
        type uint16 {
          range "1..65535";
        }
      }

      leaf ip-address {
        description
          "Summary IP address";
        type inet:ipv4-address;
      }

      leaf ip-mask {
        description
          "IP network mask";
        type inet:ipv4-address;
      }

      leaf leak-map {
        description
          "Allow dynamic prefixes based on the leak-map";
        type string;
      }
    }
  } //end of config-eigrp-interface-summary-address-ipv4-grouping

  grouping config-eigrp-maximum-paths-grouping {
    leaf maximum-paths {
      description
        "Forward packets over multiple paths";
      type uint8 {
        range "1..32";
      }
    }
  } // end of config-eigrp-maximum-paths-grouping

  grouping config-eigrp-maximum-secondary-paths-grouping {
    leaf maximum-secondary-paths {
      description
        "Maximum secondary paths";
      type uint8 {
        range "1..32";
      }
    }
  } // end of config-eigrp-maximum-secondary-paths-grouping

  grouping config-eigrp-neighbor-ipv4-grouping {
    container neighbor {
      description
        "Specify a neighbor router";
      list neighbor-address {
        description
          "Specify a neighbor router";
        key "ipv4-address interface";

        leaf ipv4-address {
          description
            "Neighbor address";
          type inet:ipv4-address;
        }

        leaf interface {
          description
            "Specify interface for global address";
          type string;
        }
      }
    }
  } // end of config-eigrp-neighbor-ipv4-grouping

  grouping config-eigrp-neighbor-ipv6-grouping {
    container neighbor {
      description
        "Specify a neighbor router";
      list neighbor-address {
        description
          "Specify a neighbor router";
        key "ipv6-address interface";

        leaf ipv6-address {
          description
            "Neighbor address";
          type inet:ipv6-address;
        }

        leaf interface {
          description
            "Specify interface for global address";
          type string;
        }
      }
    }
  } // end of config-eigrp-neighbor-ipv6-grouping

  grouping config-eigrp-network-grouping {
    container network {
      description
        "Enable routing on an IP network";
      list address-wildcard {
        description
          "ipv4 address and wildcard";
        key "ipv4-address wildcard";
        leaf ipv4-address {
          description
            "Network number";
          type inet:ipv4-address;
        }

        leaf wildcard {
          description
            "EIGRP wild card bits";

          type inet:ipv4-address;
        }
      } // end of address-wildcard

      list address {
        description
          "ipv4 address only";
        key "ipv4-address";
        leaf ipv4-address {
          description
            "Network number";

          type inet:ipv4-address;
        }
      } // end of address
    } // end of network
  } // end of config-eigrp-network-grouping

  grouping config-eigrp-metric-address-family-named-grouping {
    container metric {
      description
        "Modify metrics and parameters for advertisement";

      leaf rib-scale {
        description
          "set scaling value for rib installation";
        type uint8 {
          range "1..255";
        }
        default "128";
      }

      uses config-eigrp-metric-weigths-named;
    }
  } // end of config-eigrp-metric-address-family-grouping

  grouping config-eigrp-metric-classic-grouping {
    container metric {
      description
        "Modify metrics and parameters for advertisement";

      uses config-eigrp-metric-maximum-hops-grouping;

      uses config-eigrp-metric-weigths-classic;
    } // end of metric
  } // end of config-eigrp-metric-classic-grouping

  grouping config-eigrp-metric-topology-grouping {
    container metric {
      description
        "Modify metrics and parameters for advertisement";
      uses config-eigrp-metric-maximum-hops-grouping;
    }
  } // end of config-eigrp-metric-topology-grouping

  grouping config-eigrp-metric-weigths-classic {
    container weights {
      description
      "Modify metric coefficients";

      leaf tos {
        description
          "Type (Only TOS 0 supported)";
        type uint8 {
          range "0..8";
        }
        default "0";
      }

      leaf K1 {
        description
          "K1";
        type uint8 {
          range "0..255";
        }
        default "1";
      }

      leaf K2 {
        description
          "K2";
        type uint8 {
          range "0..255";
        }
        default "0";
      }

      leaf K3 {
        description
          "K3";
        type uint8 {
          range "0..255";
        }
        default "1";
      }

      leaf K4 {
        description
          "K4";
        type uint8 {
          range "0..255";
        }
        default "0";
      }

      leaf K5 {
        description
          "K5";
        type uint8 {
          range "0..255";
        }
        default "0";
      }
    }
  } // end of config-eigrp-metric-weigths-classic

  grouping config-eigrp-metric-weigths-named {
    container weights {
      description
      "Modify metric coefficients";

      leaf tos {
        description
          "Type (Only TOS 0 supported)";
        type uint8 {
          range "0..8";
        }
        default "0";
      }

      leaf K1 {
        description
          "K1";
        type uint8 {
          range "0..255";
        }
        default "1";
      }

      leaf K2 {
        description
          "K2";
        type uint8 {
          range "0..255";
        }
        default "0";
      }

      leaf K3 {
        description
          "K3";
        type uint8 {
          range "0..255";
        }
        default "1";
      }

      leaf K4 {
        description
          "K4";
        type uint8 {
          range "0..255";
        }
        default "0";
      }

      leaf K5 {
        description
          "K5";
        type uint8 {
          range "0..255";
        }
        default "0";
      }

      leaf K6 {
        description
          "K6";
        type uint8 {
          range "0..255";
        }
        default "0";
      }
    }
  } // end of config-eigrp-metric-weigths-named

  grouping config-eigrp-metric-maximum-hops-grouping {
    leaf maximum-hops {
      description
        "Advertise greater than <hops> as unreachable";
      type uint8 {
        range "1..255";
      }
      default "100";
    }
  } // end of config-eigrp-metric-maximum-hops-grouping

  grouping config-eigrp-nsf-grouping {
    leaf nsf {
      description
        "Non-stop forwarding";

      type boolean;
      default "false";
    }
  } // end of config-eigrp-nsf-grouping

  grouping config-eigrp-offset-list-grouping {
    container offset-list {
      description
        "Add or subtract offset from EIGRP metrics";

      list access-list-direction {
        description
          "Access list with direction only";
        key "access-list direction";

        leaf access-list {
          description
            "Access list of networks to apply offset";
          type ios-types:std-acl-type;
        }

        leaf direction {
          description
            "Perform offset";
          type enumeration {
            enum "in";
            enum "out";
          }
        }

        leaf offset {
          description
            "Offset";
          type uint32 {
            range "0..2147483647";
          }
        }
      }

      list access-list-direction-interface {
        description
          "Access list with direction and interface";
        key "direction interface";

        leaf access-list {
          description
            "Access list of networks to apply offset";

          type ios-types:std-acl-type;
        }

        leaf direction {
          description
            "Perform offset";

          type enumeration {
            enum "in";
            enum "out";
          }
        }

        leaf offset {
          description
            "Offset";
          

          type uint32 {
            range "0..2147483647";
          }
        }

        leaf interface {
          description
            "Interface name";
          type string;
        }
      }
    }
  } // end of config-eigrp-offset-list-grouping

  grouping config-eigrp-passive-interface-classic-grouping {
    container passive-interface {
      description
        "Suppress routing updates on an interface";
      choice passive-interface-choice {
        default "default";
        leaf default {
          description
            "Suppress routing updates on all interfaces";
          type boolean;
          default "false";
        }
        leaf-list interface {
          type string;
        }
      }
    }
  } // end of config-eigrp-passive-interface-classic-grouping

  grouping config-eigrp-redist-application-grouping {
    list application {
      description
        "Application";

      key "application-name";
      max-elements 1;

      leaf application-name {
        description
          "Application name";
        type string;
      }

      uses config-eigrp-redist-metric-route-map-grouping;
    }
  } // end of config-eigrp-redist-application-grouping

  grouping config-eigrp-redist-bgp-grouping {
    list bgp {
      description
        "Border Gateway Protocol (BGP)";

      key "as";
      max-elements 1;

      leaf as {
        description
          "Autonomous system number";
        type ios-types:bgp-as-number-type;
      }
      uses config-eigrp-redist-metric-route-map-grouping;
    }
  } // end of config-eigrp-redist-bgp-grouping

  grouping config-eigrp-redist-eigrp-ipv4-grouping {
    list eigrp {
      description
        "Enhanced Interior Gateway Routing Protocol (EIGRP)";

      key "as";
      leaf as {
        description
          "Autonomous system number";
        type uint16 {
          range "1..65535";
        }
      }

      uses config-eigrp-redist-metric-route-map-grouping;
    }
  } // end of config-eigrp-redist-eigrp-ipv4-grouping

  grouping config-eigrp-redist-eigrp-ipv6-grouping {
    list eigrp {
      description
        "Enhanced Interior Gateway Routing Protocol (EIGRP)";

      key "as";
      leaf as {
        description
          "Autonomous system number";
        type uint16 {
          range "1..65535";
        }
      }

      uses config-eigrp-redist-metric-route-map-grouping;

      uses config-eigrp-redist-include-connected-grouping;
    }
  } // end of config-eigrp-redist-eigrp-ipv6-grouping

  grouping config-eigrp-redist-connected-grouping {
    container connected {
      description
        "Connected";
      presence "true";

      uses config-eigrp-redist-metric-route-map-grouping;
    }
  } // end of config-eigrp-redist-connected-grouping

  grouping config-eigrp-redist-include-connected-grouping {
    leaf include-connected {
      description
        "Include connected";
      type empty;
    }
  } // end of config-eigrp-redist-include-connected-grouping


  grouping config-eigrp-redist-isis-ipv4-grouping {
    container isis {
      description
        "ISO IS-IS";
      presence "true";

      uses config-eigrp-redist-isis-levels-grouping;

      uses config-eigrp-redist-metric-route-map-grouping;
    }

    container isis-area-tag {
      description
        "ISO IS-IS area-tag";

      list isis {
        description
          "ISO IS-IS";

        key "area-tag";
        leaf area-tag {
          description
            "ISO IS-IS area-tag";
          type string;
        }

        uses config-eigrp-redist-isis-levels-grouping;

        uses config-eigrp-redist-metric-route-map-grouping;
      }
    }
  } // end of config-eigrp-redist-isis-ipv4-grouping

  grouping config-eigrp-redist-isis-ipv6-grouping {
    container isis {
      description
        "ISO IS-IS";
      presence "true";

      uses config-eigrp-redist-isis-levels-grouping;

      uses config-eigrp-redist-metric-route-map-grouping;

      uses config-eigrp-redist-include-connected-grouping;
    }

    container isis-area-tag {
      description
        "ISO IS-IS area-tag";

      list isis {
        description
          "ISO IS-IS";

        key "area-tag";
        leaf area-tag {
          description
            "ISO IS-IS area-tag";
          type string;
        }

        uses config-eigrp-redist-isis-levels-grouping;

        uses config-eigrp-redist-metric-route-map-grouping;

        uses config-eigrp-redist-include-connected-grouping;
      }
    }
  } // end of config-eigrp-redist-isis-ipv6-grouping

  grouping config-eigrp-redist-isis-levels-grouping {
    leaf routes {
      type enumeration {
        enum "level-1";
        enum "level-2";
        enum "level-1-2";
      }
      default "level-2";
    }
  } // end of config-eigrp-redist-isis-levels-grouping

  grouping config-eigrp-redist-lisp-ipv4-grouping {
    container lisp {
      description
        "Locator ID Separation Protocol (LISP)";
      presence "true";

      uses config-eigrp-redist-metric-route-map-grouping;
    }
  } // end of config-eigrp-redist-lisp-ipv4-grouping

  grouping config-eigrp-redist-lisp-ipv6-grouping {
    container lisp {
      description
        "Locator ID Separation Protocol (LISP)";
      presence "true";

      uses config-eigrp-redist-metric-route-map-grouping;

      uses config-eigrp-redist-include-connected-grouping;
    }
  } // end of config-eigrp-redist-lisp-ipv6-grouping

  grouping config-eigrp-redist-metric-route-map-grouping {
    container metric {
      description
        "Metric for redistributed routes";

      leaf bandwidth {
        description
          "Bandwidth in Kbits per second";
        type uint32 {
          range "1..4294967295";
        }
      }

      leaf delay {
        description
          "delay metric in 10 microsecond units";
        type uint32 {
          range "0..4294967295";
        }
      }

      leaf reliability {
        description
          "Reliability metric where 255 is 100% reliable";
        type uint8 {
          range "0..255";
        }
      }

      leaf load {
        description
          "Effective bandwidth metric (Loading) where 255 is 100% loaded";
        type uint8 {
          range "1..255";
        }
      }

      leaf mtu {
        description
          "Maximum Transmission Unit metric of the path";
        type uint16 {
          range "1..65535";
        }
      }
    }

    leaf route-map {
      description
       "Route map reference";
      type string;
    }
  } // end of config-eigrp-redist-metric-route-map-grouping

  grouping config-eigrp-redist-mobile-grouping {
    container mobile {
      description
        "Mobile routes";
      presence "true";

      uses config-eigrp-redist-metric-route-map-grouping;
    }
  } // end of config-eigrp-redist-mobile-grouping

  grouping config-eigrp-redist-nat-route-ipv4-grouping {
    container nat-route {
      if-feature ios-features:sdwan;
      description
        "NAT Route";

      leaf dia {
        description
          "Redistribute NAT Direct Internet Access routes";
        type empty;
      }
      leaf outside {
        description
          "Redistribute NAT Outside routes";
        type empty;
      }
      uses config-eigrp-redist-metric-route-map-grouping;
    }
  } // end of config-eigrp-redist-nat-route-ipv4-grouping

  grouping config-eigrp-redist-nat-route-ipv6-grouping {
    container nat-route {
      if-feature ios-features:sdwan;
      description
        "NAT Route";

      leaf dia {
        description
          "Redistribute NAT Direct Internet Access routes";
        type empty;
      }
      leaf outside {
        description
          "Redistribute NAT Outside routes";
        type empty;
      }
      uses config-eigrp-redist-metric-route-map-grouping;
    }
  } // end of config-eigrp-redist-nat-route-ipv6-grouping

  grouping config-eigrp-redist-nemo-grouping {
    container nemo {
      description
        "Network Mobility (NEMO)";
      presence "true";

      uses config-eigrp-redist-metric-route-map-grouping;

      uses config-eigrp-redist-include-connected-grouping;
    }
  } // end of config-eigrp-redist-nemo-grouping

  grouping config-eigrp-redist-nhrp-grouping {
    list nhrp {
      description
        "Next Hop Resolution Protocol (NHRP)";

      key "process-id";
      leaf process-id {
        description
          "Process ID";
        type uint16 {
          range "1..65535";
        }
      }

      uses config-eigrp-redist-metric-route-map-grouping;
    }
  } // end of config-eigrp-redist-nhrp-grouping

  grouping config-eigrp-redist-omp-ipv4-grouping {
    container omp {
      if-feature ios-features:omp;
      description
        "Overlay Management Protocol (OMP)";
      presence true;

      uses config-eigrp-redist-metric-route-map-grouping;
    }
  } // end of config-eigrp-redist-omp-ipv4-grouping

  grouping config-eigrp-redist-omp-ipv6-grouping {
    container omp {
      if-feature ios-features:omp;
      description
        "Overlay Management Protocol (OMP)";
      presence true;

      uses config-eigrp-redist-metric-route-map-grouping;

      uses config-eigrp-redist-include-connected-grouping;
    }
  } // end of config-eigrp-redist-omp-ipv6-grouping

  grouping config-eigrp-redist-odr-grouping {
    container odr {
      description
        "On Demand stub Routes";
      presence "true";

      uses config-eigrp-redist-metric-route-map-grouping;
    }
  } // end of config-eigrp-redist-odr-grouping

  grouping config-eigrp-redist-ospf-ipv4-grouping {
    list ospf {
      description
        "Open Shortest Path First (OSPF)";

      key "process-id";
      leaf process-id {
        description
          "Process ID";
        type uint16 {
          range "1..65535";
        }
      }

      uses config-eigrp-redist-ospf-match-ipv4-grouping;

      uses config-eigrp-redist-metric-route-map-grouping;
    }
  } // end of config-eigrp-redist-ospf-ipv4-grouping

  grouping config-eigrp-redist-ospf-ipv6-grouping {
    list ospf {
      description
        "Open Shortest Path First (OSPFv3)";

      key "process-id";
      leaf process-id {
        description
          "Process ID";
        type uint16 {
          range "1..65535";
        }
      }

      uses config-eigrp-redist-ospf-match-ipv6-grouping;

      uses config-eigrp-redist-metric-route-map-grouping;

      uses config-eigrp-redist-include-connected-grouping;
    }
  } // end of config-eigrp-redist-ospf-ipv6-grouping

  grouping config-eigrp-redist-ospfv3-grouping {
    list ospfv3 {
      description
        "OSPFv3";

      key "process-id";
      leaf process-id {
        description
          "Process ID";
        type uint16 {
          range "1..65535";
        }
      }

      uses config-eigrp-redist-ospf-match-ipv4-grouping;

      uses config-eigrp-redist-metric-route-map-grouping;
    }
  } // end of config-eigrp-redist-ospfv3-grouping

  grouping config-eigrp-redist-ospf-match-ipv4-grouping {
    container match {
      description
        "Redistribution of OSPF routes";

      leaf internal {
        description
          "Redistribute OSPF internal routes";
        type empty;
      }

      leaf external1 {
        description
          "Redistribute OSPF external routes";
        type ios-types:redist-ospf-external-type;
      }

      leaf external2 {
        description
          "Redistribute OSPF external routes";
        type ios-types:redist-ospf-external-type;
      }

      leaf nssa-external1 {
        description
          "Redistribute OSPF NSSA external routes";
        type ios-types:redist-ospf-external-type;
      }

      leaf nssa-external2 {
        description
          "Redistribute OSPF NSSA external routes";
        type ios-types:redist-ospf-external-type;
      }

      uses config-eigrp-redist-metric-route-map-grouping;
    } // end of match
  } // end of config-eigrp-redist-ospf-match-grouping

  grouping config-eigrp-redist-ospf-match-ipv6-grouping {
    container match {
      description
        "Redistribution of OSPF routes";

      leaf internal {
        description
          "Redistribute OSPF internal routes";
        type empty;
      }

      leaf external1 {
        description
          "Redistribute OSPF external routes";
        type ios-types:redist-ospf-external-type;
      }

      leaf external2 {
        description
          "Redistribute OSPF external routes";
        type ios-types:redist-ospf-external-type;
      }

      leaf nssa-external1 {
        description
          "Redistribute OSPF NSSA external routes";
        type ios-types:redist-ospf-external-type;
      }

      leaf nssa-external2 {
        description
          "Redistribute OSPF NSSA external routes";
        type ios-types:redist-ospf-external-type;
      }

      uses config-eigrp-redist-metric-route-map-grouping;

      uses config-eigrp-redist-include-connected-grouping;
    } // end of match
  } // end of config-eigrp-redist-ospf-match-grouping

  grouping config-eigrp-redist-rip-ipv4-grouping {
    container rip {
      description
        "Routing Information Protocol (RIP)";
      presence "true";

      uses config-eigrp-redist-metric-route-map-grouping;
    }
  } // end of config-eigrp-redist-rip-ipv4-grouping

  grouping config-eigrp-redist-rip-ipv6-grouping {
    list rip {
      description
        "IPv6 Routing Information Protocol (RIPv6)";
      key "id";

      leaf "id" {
        description
          "User selected string identifying this process";
        type string;
      }

      uses config-eigrp-redist-metric-route-map-grouping;

      uses config-eigrp-redist-include-connected-grouping;
    }
  } // end of config-eigrp-redist-rip-ipv6-grouping

  grouping config-eigrp-redist-static-grouping {
    container static {
      description
        "Static routes";
      presence "true";

      uses config-eigrp-redist-metric-route-map-grouping;
    }
  } // end of config-eigrp-redist-static-grouping

  grouping config-eigrp-redistribute-classic-ipv4-grouping {
    container redistribute {
      description
        "Redistribute IPv4 routes from another routing protocol";

      uses config-eigrp-redist-bgp-grouping;

      uses config-eigrp-redist-connected-grouping;

      uses config-eigrp-redist-eigrp-ipv4-grouping;

      uses config-eigrp-redist-isis-ipv4-grouping;

      uses config-eigrp-redist-lisp-ipv4-grouping;

      uses config-eigrp-redist-mobile-grouping;

      uses config-eigrp-redist-nhrp-grouping;

      uses config-eigrp-redist-odr-grouping;

      uses config-eigrp-redist-ospf-ipv4-grouping;

      uses config-eigrp-redist-rip-ipv4-grouping;

      uses config-eigrp-redist-static-grouping;

      list  vrf {
        description
          "Specify a source virtual routing/forwarding instance";

        key "vrf-name";
        leaf vrf-name {
          description
            "Virtual Routing/Forwarding instance name";

          type union {
            type string;
            type enumeration {
              enum "global";
            }
          }
        }
        uses config-eigrp-redist-connected-grouping;

        uses config-eigrp-redist-eigrp-ipv4-grouping;

        uses config-eigrp-redist-ospf-ipv4-grouping;

        uses config-eigrp-redist-static-grouping;
      }
    }
  } // end of config-eigrp-redistribute-classic-ipv4-grouping

  grouping config-eigrp-redistribute-classic-ipv6-grouping {
    container redistribute {
      description
        "Redistribute IPv6 routes from another routing protocol";

      uses config-eigrp-redist-bgp-grouping;

      uses config-eigrp-redist-connected-grouping;

      uses config-eigrp-redist-eigrp-ipv6-grouping;

      uses config-eigrp-redist-isis-ipv6-grouping;

      uses config-eigrp-redist-lisp-ipv6-grouping;

      uses config-eigrp-redist-mobile-grouping;

      uses config-eigrp-redist-nat-route-ipv6-grouping;

      uses config-eigrp-redist-nemo-grouping;

      uses config-eigrp-redist-omp-ipv6-grouping;

      uses config-eigrp-redist-ospf-ipv6-grouping;

      uses config-eigrp-redist-rip-ipv6-grouping;

      uses config-eigrp-redist-static-grouping;

    }
  } // end of config-eigrp-redistribute-classic-ipv6-grouping

  grouping config-eigrp-redistribute-named-ipv4-grouping {
    container redistribute {
      description
        "Redistribute IPv4 routes from another routing protocol";

      uses config-eigrp-redist-application-grouping;

      uses config-eigrp-redist-bgp-grouping ;

      uses config-eigrp-redist-connected-grouping;

      uses config-eigrp-redist-eigrp-ipv4-grouping;

      uses config-eigrp-redist-isis-ipv4-grouping;

      uses config-eigrp-redist-lisp-ipv4-grouping;

      uses config-eigrp-redist-mobile-grouping;

      uses config-eigrp-redist-nat-route-ipv4-grouping;

      uses config-eigrp-redist-nhrp-grouping;

      uses config-eigrp-redist-omp-ipv4-grouping;

      uses config-eigrp-redist-odr-grouping;

      uses config-eigrp-redist-ospf-ipv4-grouping;

      uses config-eigrp-redist-ospfv3-grouping;

      uses config-eigrp-redist-rip-ipv4-grouping;

      uses config-eigrp-redist-static-grouping;

      list  vrf {
        description
          "Specify a source virtual routing/forwarding instance";
        key "vrf-name";

        leaf vrf-name {
          description
            "Virtual Routing/Forwarding instance name";
          type union {
            type string;
            type enumeration {
              enum "global";
            }
          }
        }
        uses config-eigrp-redist-connected-grouping;

        uses config-eigrp-redist-eigrp-ipv4-grouping;

        uses config-eigrp-redist-nhrp-grouping;

        uses config-eigrp-redist-ospf-ipv4-grouping;

        uses config-eigrp-redist-static-grouping;
      } // end of vrf
    }
  } // end of config-eigrp-redistribute-named-ipv4-grouping

  grouping config-eigrp-redistribute-named-ipv6-grouping {
    container redistribute {
      description
        "Redistribute IPv6 routes from another routing protocol";

      uses config-eigrp-redist-bgp-grouping;

      uses config-eigrp-redist-connected-grouping;

      uses config-eigrp-redist-eigrp-ipv6-grouping;

      uses config-eigrp-redist-isis-ipv6-grouping;

      uses config-eigrp-redist-lisp-ipv6-grouping;

      uses config-eigrp-redist-mobile-grouping;

      uses config-eigrp-redist-nat-route-ipv6-grouping;

      uses config-eigrp-redist-nemo-grouping;

      uses config-eigrp-redist-omp-ipv6-grouping;

      uses config-eigrp-redist-ospf-ipv6-grouping;

      uses config-eigrp-redist-rip-ipv6-grouping;

      uses config-eigrp-redist-static-grouping;
    }
  } // end of config-eigrp-redistribute-named-ipv6-grouping

  grouping config-eigrp-router-grouping {
    container router-eigrp {
      description
        "EIGRP Router Commands";
      container eigrp {
        description
          "Enhanced Interior Gateway Routing Protocol (EIGRP)";

        uses config-eigrp-router-classic-grouping;

        uses config-eigrp-router-named-grouping;
      }
    }
  } // end of config-eigrp-router-grouping

  grouping config-eigrp-router-classic-grouping {
    list classic-mode {
      description
        "EIGRP Classic Mode";
      key "autonomous-system";

      leaf autonomous-system {
        description
          "Autonomous System";
        type uint16 {
          range "1..65535";
        }
      }

      container address-family {
        description
          "Enter Address Family command mode";

        container ipv4 {
          description
            "Address Family IPv4";

          list af-ipv4-vrf {
            description
              "VRF List";
            key "vrf";

            leaf vrf {
              description
                "Specify a specific virtual routing/forwarding instance";

          must "(/ios:native/ios:vrf/ios:definition[ios:name=current()] and " +
                "/ios:native/ios:vrf/ios:definition[ios:name=current()]/ios:address-family/ios:ipv4) or " +
                "/ios:native/ios:ip/ios:vrf[ios:name=current()]" {
            error-message "ipv4 VRF must be created 1st, deleted last";
          }
              type string;
            }

            leaf unicast {
              description
                "Address Family Unicast";
              type enumeration {
                enum "unicast";
              }
              default unicast;
            }

            leaf autonomous-system {
              description
                "Specify Address-Family Autonomous System Number";
              type uint16 {
                range "1..65535";
              }
              mandatory "true";
            }

            uses config-eigrp-address-family-ipv4-classic-grouping;
            uses config-eigrp-shutdown-address-family-grouping;
          } // end of af-ipv4-vrf
        } // end of ipv4
      } // end of address-family
      uses config-eigrp-address-family-ipv4-classic-grouping;
      uses config-eigrp-shutdown-router-grouping;
    } // end of autonomous-system
  } // end of config-eigrp-router-classic-grouping

  grouping config-eigrp-router-ipv6-grouping {
    container router-eigrp {
      description
        "Router EIGRP";
      list eigrp {
        description
          "Enhanced Interior Gateway Routing Protocol (EIGRP)";

        key "autonomous-system";

        leaf autonomous-system {
          description
            "Autonomous System ID";
          type uint16 {
            range "1..65535";
          }
        }

        uses config-eigrp-default-metric-grouping;

        uses config-eigrp-distance-ipv6-grouping;

        uses config-eigrp-distribute-list-classic-ipv6-grouping;

        uses config-eigrp-eigrp-address-family-classic-grouping;

        uses config-eigrp-maximum-paths-grouping;

        uses config-eigrp-metric-classic-grouping;

        uses config-eigrp-neighbor-ipv6-grouping;

        uses config-eigrp-passive-interface-classic-grouping;

        uses config-eigrp-redistribute-classic-ipv6-grouping;

        uses config-eigrp-shutdown-router-grouping;

        uses config-eigrp-summary-metric-ipv6-grouping;

        uses config-eigrp-timers-address-family-classic-ipv6-grouping;

        uses config-eigrp-variance-grouping;
      } // end of eigrp
    } // end of router-eigrp
  } // end of config-eigrp-router-ipv6-grouping

  grouping config-eigrp-router-named-grouping {
    list named-mode {
      description
        "EIGRP Named Mode";
      key "name";
      leaf name {
        description
          "EIGRP Virtual-Instance Name";
        type string;
      }

      container address-family {
        description
          "Enter Address Family command mode";

        container ipv4 {
          description
            "Address family IPv4";

          list af-ipv4 {
            description
              "Address family IPv4";
            key "unicast";

            leaf unicast {
              type enumeration {
                enum "unicast";
              }
            }

            leaf autonomous-system {
              description
                "Specify Address-Family Autonomous System Number";
              type uint16 {
                range "1..65535";
              }
              mandatory "true";
            }

            uses config-eigrp-address-family-named-ipv4-grouping;
          } // end of af-ipv4

          list af-ipv4-vrf {
            description
              "Address family IPv4 VRF";
            key "vrf";

            leaf vrf {

              must "(/ios:native/ios:vrf/ios:definition[ios:name=current()] and " +
                    "/ios:native/ios:vrf/ios:definition[ios:name=current()]/ios:address-family/ios:ipv4) or " +
                    "/ios:native/ios:ip/ios:vrf[ios:name=current()]" {
                error-message "ipv4 VRF must be created 1st, deleted last";
              }
              type string;
            }

            leaf unicast {
              type enumeration {
                enum "unicast";
              }
              default unicast;
            }

            leaf autonomous-system {
              description
              "Specify Address-Family Autonomous System Number?";
              type uint16 {
                range "1..65535";
              }
              mandatory "true";
            }
            uses config-eigrp-address-family-named-ipv4-vrf-grouping;
          } // end of af-ip-vrf
        } // end of ipv4

        container ipv6 {
          description
            "Address family IPv6";

          list af-ipv6 {
            description
              "Address family IPv6";
            key "unicast";

            leaf unicast{
              type enumeration {
                enum "unicast";
              }
            }

            leaf autonomous-system {
              description
                "Specify Address-Family Autonomous System Number";
              type uint16 {
                range "1..65535";
              }
              mandatory "true";
            }
            uses config-eigrp-address-family-named-ipv6-grouping;
          } // end of af-ipv6

          list af-ipv6-vrf {
            description
              "Address family IPv4/IPv6 VRF";
            key "vrf";

            leaf vrf {

              must "(/ios:native/ios:vrf/ios:definition[ios:name=current()] and " +
                    "/ios:native/ios:vrf/ios:definition[ios:name=current()]/ios:address-family/ios:ipv4)" {
                error-message "ipv6 VRF must be created 1st, deleted last";
              }
              type string;
            }

            leaf unicast {
              type enumeration {
                enum "unicast";
              }
              default unicast;
            }

            leaf autonomous-system {
              description
              "Specify Address-Family Autonomous System Number?";
              type uint16 {
                range "1..65535";
              }
              mandatory "true";
            }
            uses config-eigrp-address-family-named-ipv6-vrf-grouping;
          } // end of af-ipv6-vrf
        } // end of ipv6
      } // end of address-family

      uses config-eigrp-shutdown-router-grouping;
    } // end of Virtual-Instance
  } // end of config-eigrp-router-named-grouping

  grouping config-eigrp-shutdown-router-grouping {
    leaf shutdown {
      description
        "Shutdown this instance of EIGRP";

      type boolean;
      default "false";
    }
  } // end of config-eigrp-shutdown-router-grouping

  grouping config-eigrp-shutdown-address-family-grouping {
    leaf shutdown {
      description
        "Shutdown address family";

      type boolean;
      default "false";
    }
  } // end of config-eigrp-shutdown-address-family-grouping

  grouping config-eigrp-soft-sia-grouping {
    leaf soft-sia {
      description
        "Enable graceful restart for stuck-in-active neighbors";
      type boolean;
      default "false";
    }
  } // end of config-eigrp-soft-sia-grouping

  grouping config-eigrp-stub-grouping {
    container stub {
      description
        "Set address-family in stubbed mode";

      choice stub-type-choice {
        leaf receive-only {
          description
            "Set receive only neighbor";
          type empty;
        }

        container advertise {
          description
            "Routes to Advertise";
          leaf connected {
            description
              "Do advertise connected routes";
            type empty;
          }

          leaf static {
            description
              "Do advertise static routes";
            type empty;
          }

          leaf summary {
            description
              "Do advertise summary routes";
            type empty;
          }

          leaf redistributed {
            description
              "Do advertise redistributed routes";
            type empty;
          }

          leaf leak-map {
            description
              "Allow dynamic prefixes based on the leak-map";
            type string;
            must "(../ios-eigrp:connected) or (../ios-eigrp:static) or " +
                  "(../ios-eigrp:summary) or (../ios-eigrp:redistributed)" {
              error-message "atleast one stub type needed";
            }
          }
        } // end of advertise
      } //  end of stub-type-choice
    } // end of stub
  } // end of config-eigrp-stub-grouping

  grouping config-eigrp-summary-metric-grouping {
    container metric {
      description
        "Set metric of summary routes";

      leaf bandwidth {
        description
          "Bandwidth metric in Kbits per second";
        type uint32 {
          range "1..4294967295";
        }
      }

      leaf delay {
        description
          "delay metric in 10 microsecond units";
        type uint32 {
          range "1..4294967295";
        }
      }

      leaf reliability {
        description
          "Reliability metric where 255 is 100% reliable";
        type uint8 {
          range "0..255";
        }
      }

      leaf load {
        description
          "Effective bandwidth metric (Loading) where 255 is 100% loaded";
        type uint8 {
          range "1..255";
        }
      }

      leaf mtu {
        description
          "Maximum Transmission Unit metric of the path";
        type uint16 {
          range "1..65535";
        }
      }
    } // end of metric

    leaf distance {
      description
        "Set administrative distance for summary route";

      type uint8 {
        range "1..255";
      }
    } // end of distance

  } // end of config-eigrp-summary-metric-grouping

  grouping config-eigrp-summary-metric-ipv4-grouping {
    container summary-metric {
      description
        "Specify summary to apply metric/filtering";

      list summary-prefix {
        key "ipv4-prefix";

        leaf ipv4-prefix {
          description
            "Summary <network>/<length>, e.g., 192.168.0.0/16";
          type inet:ipv4-prefix;
        }

        uses config-eigrp-summary-metric-grouping;
      }
    } // end of summary-metric
  } // end of config-eigrp-summary-metric-ipv4-grouping

  grouping config-eigrp-summary-metric-ipv6-grouping {
    container summary-metric {
      description
        "Specify summary to apply metric/filtering";
      list summary-prefix {
        key "ipv6-prefix";

        leaf ipv6-prefix {
          description
            "Summary to configure static metric";
          type ios-types:ipv6-prefix;
        }

        uses config-eigrp-summary-metric-grouping;
      }
    } // end of summary-metric
  } // end of config-eigrp-summary-metric-ipv6-grouping

  grouping config-eigrp-timers-active-time-grouping {
    container active-time {
      description
        "time limit for active state";

      choice active-timer-choice {
        default "timer";
        leaf timer {
          description
            "active state time limit in minutes";
          type uint16 {
            range "1..65535";
          }
          default "3";
        }

        leaf disabled {
          description
            "disable time limit for active state";
          type empty;
        }
      }
    } // end of active-time
  } // end of config-eigrp-timers-active-time-grouping

  grouping config-eigrp-timers-address-family-classic-ipv4-grouping {
    container timers {
      description
        "Adjust routing timers";

      uses config-eigrp-timers-active-time-grouping;

      container graceful-restart {
        description
          "EIGRP Graceful Restart timer";

        leaf purge-time {
          description
            "EIGRP stale route purge time";
          type uint16 {
            range "20..300";
          }
          default "240";
        }
      } // end of graceful-restart

      container nsf {
        description
          "EIGRP NSF timer";

        leaf converge {
          description
            "EIGRP time limit for convergence after switchover";
          type uint8 {
            range "60..180";
          }
          default "120";
        }

        leaf signal {
          description
            "EIGRP time limit for signaling NSF restart";
          type uint8 {
            range "10..30";
          }
          default "20";
        }
      } // end of nsf
    } // end of timers
  } // end of config-eigrp-timers-address-family-classic-ipv4-grouping

  grouping config-eigrp-timers-address-family-classic-ipv6-grouping {
    container timers {
      description
        "Adjust routing timers";

      uses config-eigrp-timers-active-time-grouping;
    } // end of timers
  } // end of config-eigrp-timers-address-family-classic-ipv6-grouping

  grouping config-eigrp-timers-address-family-named-grouping {
    container timers {
      description
        "Adjust routing timers";

      container graceful-restart {
        description
          "EIGRP Graceful Restart timer";

        leaf purge-time {
          description
            "EIGRP stale route purge time";
          type uint16 {
            range "20..300";
          }
          default "240";
        }
      }

      container nsf {
        description
          "EIGRP NSF timer";

        leaf converge {
          description
            "EIGRP time limit for convergence after switchover";
          type uint8 {
            range "60..180";
          }
          default "120";
        }

        leaf signal {
          description
            "EIGRP time limit for signaling NSF restart";
          type uint8 {
            range "10..30";
          }
          default "20";
        }
      } // end of nsf
    } // end of timers
  } // end of config-eigrp-timers-address-family-named-grouping

  grouping config-eigrp-timers-topology-grouping {
    container timers {
      description
        "Adjust routing timers";

      uses config-eigrp-timers-active-time-grouping;
    } // end of timers
  } // end of config-eigrp-timers-topology-grouping

  grouping config-eigrp-topology-common-grouping {

    uses config-eigrp-default-metric-grouping;

    uses config-eigrp-eigrp-topology-grouping;

    uses config-eigrp-maximum-paths-grouping;

    uses config-eigrp-metric-topology-grouping;

    uses config-eigrp-timers-topology-grouping;

    uses config-eigrp-traffic-share-grouping;

    uses config-eigrp-variance-grouping;
  } // end of config-eigrp-topology-common-grouping

  grouping config-eigrp-topology-ipv4-grouping {

    uses config-eigrp-auto-summary-ipv4-grouping;

    uses config-eigrp-default-information-grouping;

    uses config-eigrp-distance-ipv4-grouping;

    uses config-eigrp-distribute-list-classic-named-ipv4-grouping;

    uses config-eigrp-maximum-secondary-paths-grouping;

    uses config-eigrp-offset-list-grouping;

    uses config-eigrp-redistribute-named-ipv4-grouping;

    uses config-eigrp-summary-metric-ipv4-grouping;

    uses config-eigrp-topology-common-grouping;
  } // end of config-eigrp-topology-ipv4-grouping

  grouping config-eigrp-topology-ipv6-grouping {

    uses config-eigrp-distance-ipv6-grouping;

    uses config-eigrp-distribute-list-named-ipv6-grouping;

    uses config-eigrp-summary-metric-ipv6-grouping;

    uses config-eigrp-redistribute-named-ipv6-grouping;

    uses config-eigrp-topology-common-grouping;
  } // end of config-eigrp-topology-ipv6-grouping

  grouping config-eigrp-traffic-share-grouping {
    container traffic-share {
      description
        "How to compute traffic share over alternate paths";
      choice balanced-min-choice {
        default "balanced";
        leaf balanced {
          description
            "Share inversely proportional to metric";
          type enumeration {
            enum "balanced";
          }
          default "balanced";
        }

        container min {
          description
            "All traffic shared among min metric paths";
          leaf across-interfaces {
            description
              "Use different interfaces for equal-cost paths";
            type empty;
          }
        }
      }
    } // end of traffic-share
  } // end ofg config-eigrp-traffic-share-grouping

  grouping config-eigrp-variance-grouping {
    leaf variance {
      description
        "Control load balancing variance";
      type uint8 {
        range "1..128";
      }
      default "1";
    }
  } // end of config-eigrp-variance-grouping

  /////////////////////////////////////////////////////////
  // native / router / eigrp
  /////////////////////////////////////////////////////////

  augment "/ios:native/ios:router" {
    uses config-eigrp-router-grouping;
    uses config-router-eigrp-grouping {
      status deprecated;
    }
  }

  /////////////////////////////////////////////////////////
  // native / interface * / ip
  /////////////////////////////////////////////////////////
  augment "/ios:native/ios:interface/ios:Ethernet/ios:ip" {
    uses config-eigrp-interface-classic-ipv4-grouping;
  }

  augment "/ios:native/ios:interface/ios:FastEthernet/ios:ip" {
    uses config-eigrp-interface-classic-ipv4-grouping;
  }

  augment "/ios:native/ios:interface/ios:GigabitEthernet/ios:ip" {
    uses config-eigrp-interface-classic-ipv4-grouping;
  }

  augment "/ios:native/ios:interface/ios:TenGigabitEthernet/ios:ip" {
    uses config-eigrp-interface-classic-ipv4-grouping;
  }

  augment "/ios:native/ios:interface/ios:FiveGigabitEthernet/ios:ip" {
    uses config-eigrp-interface-classic-ipv4-grouping;
  }

  augment "/ios:native/ios:interface/ios:AppGigabitEthernet/ios:ip" {
    uses config-eigrp-interface-classic-ipv4-grouping;
  }

  augment "/ios:native/ios:interface/ios:TwentyFiveGigE/ios:ip" {
    uses config-eigrp-interface-classic-ipv4-grouping;
  }

  augment "/ios:native/ios:interface/ios:TwoGigabitEthernet/ios:ip" {
    uses config-eigrp-interface-classic-ipv4-grouping;
  }

  augment "/ios:native/ios:interface/ios:FortyGigabitEthernet/ios:ip" {
    uses config-eigrp-interface-classic-ipv4-grouping;
  }

  augment "/ios:native/ios:interface/ios:HundredGigE/ios:ip" {
    uses config-eigrp-interface-classic-ipv4-grouping;
  }

  augment "/ios:native/ios:interface/ios:Port-channel/ios:ip" {
    uses config-eigrp-interface-classic-ipv4-grouping;
  }

  augment "/ios:native/ios:interface/ios:Port-channel-subinterface/ios:Port-channel/ios:ip" {
    uses config-eigrp-interface-classic-ipv4-grouping;
  }

  augment "/ios:native/ios:interface/ios:Loopback/ios:ip" {
    uses config-eigrp-interface-classic-ipv4-grouping;
  }

  augment "/ios:native/ios:interface/ios:Tunnel/ios:ip" {
    uses config-eigrp-interface-classic-ipv4-grouping;
  }

  augment "/ios:native/ios:interface/ios:BDI/ios:ip" {
    uses config-eigrp-interface-classic-ipv4-grouping;
  }

  augment "/ios:native/ios:interface/ios:Vlan/ios:ip" {
    uses config-eigrp-interface-classic-ipv4-grouping;
  }

  augment "/ios:native/ios:interface/ios:Dialer/ios:ip" {
    uses config-eigrp-interface-classic-ipv4-grouping;
  }

  augment "/ios:native/ios:interface/ios:BD-VIF/ios:ip" {
    uses config-eigrp-interface-classic-ipv4-grouping;
  }

  /////////////////////////////////////////////////////////
  // native / interface * / ip / summary-address
  /////////////////////////////////////////////////////////
  augment "/ios:native/ios:interface/ios:Ethernet/ios:ip/ios:summary-address" {
    uses config-eigrp-interface-summary-address-ipv4-grouping;
  }

  augment "/ios:native/ios:interface/ios:FastEthernet/ios:ip/ios:summary-address" {
    uses config-eigrp-interface-summary-address-ipv4-grouping;
  }

  augment "/ios:native/ios:interface/ios:GigabitEthernet/ios:ip/ios:summary-address" {
    uses config-eigrp-interface-summary-address-ipv4-grouping;
  }

  augment "/ios:native/ios:interface/ios:TenGigabitEthernet/ios:ip/ios:summary-address" {
    uses config-eigrp-interface-summary-address-ipv4-grouping;
  }

  augment "/ios:native/ios:interface/ios:FiveGigabitEthernet/ios:ip/ios:summary-address" {
    uses config-eigrp-interface-summary-address-ipv4-grouping;
  }

  augment "/ios:native/ios:interface/ios:AppGigabitEthernet/ios:ip/ios:summary-address" {
    uses config-eigrp-interface-summary-address-ipv4-grouping;
  }

  augment "/ios:native/ios:interface/ios:TwentyFiveGigE/ios:ip/ios:summary-address" {
    uses config-eigrp-interface-summary-address-ipv4-grouping;
  }

  augment "/ios:native/ios:interface/ios:TwoGigabitEthernet/ios:ip/ios:summary-address" {
    uses config-eigrp-interface-summary-address-ipv4-grouping;
  }

  augment "/ios:native/ios:interface/ios:FortyGigabitEthernet/ios:ip/ios:summary-address" {
    uses config-eigrp-interface-summary-address-ipv4-grouping;
  }

  augment "/ios:native/ios:interface/ios:HundredGigE/ios:ip/ios:summary-address" {
    uses config-eigrp-interface-summary-address-ipv4-grouping;
  }

  augment "/ios:native/ios:interface/ios:Port-channel/ios:ip/ios:summary-address" {
    uses config-eigrp-interface-summary-address-ipv4-grouping;
  }

  augment "/ios:native/ios:interface/ios:Port-channel-subinterface/ios:Port-channel/ios:ip/ios:summary-address" {
    uses config-eigrp-interface-summary-address-ipv4-grouping;
  }

  augment "/ios:native/ios:interface/ios:Loopback/ios:ip/ios:summary-address" {
    uses config-eigrp-interface-summary-address-ipv4-grouping;
  }

  augment "/ios:native/ios:interface/ios:Tunnel/ios:ip/ios:summary-address" {
    uses config-eigrp-interface-summary-address-ipv4-grouping;
  }

  augment "/ios:native/ios:interface/ios:BDI/ios:ip/ios:summary-address" {
    uses config-eigrp-interface-summary-address-ipv4-grouping;
  }

  augment "/ios:native/ios:interface/ios:Vlan/ios:ip/ios:summary-address" {
    uses config-eigrp-interface-summary-address-ipv4-grouping;
  }

  augment "/ios:native/ios:interface/ios:Dialer/ios:ip/ios:summary-address" {
    uses config-eigrp-interface-summary-address-ipv4-grouping;
  }

  augment "/ios:native/ios:interface/ios:BD-VIF/ios:ip/ios:summary-address" {
    uses config-eigrp-interface-summary-address-ipv4-grouping;
  }

  /////////////////////////////////////////////////////////
  // native / ipv6 / router
  /////////////////////////////////////////////////////////

  augment "/ios:native/ios:ipv6/ios:router" {
    uses config-eigrp-router-ipv6-grouping;
  }

  /////////////////////////////////////////////////////////
  // native / ipv6 / router / eigrp
  /////////////////////////////////////////////////////////

  augment "/ios:native/ios:ipv6/ios:router/ios:eigrp" {
    uses config-router-ipv6-eigrp-grouping {
      status obsolete;
    }
  }

  /////////////////////////////////////////////////////////
  // native / interface * / ipv6
  /////////////////////////////////////////////////////////

  augment "/ios:native/ios:interface/ios:Ethernet/ios:ipv6" {
    uses config-eigrp-interface-classic-ipv6-grouping;
    uses config-interface-ipv6-eigrp-grouping {
      status obsolete;
    }
  }

  augment "/ios:native/ios:interface/ios:FastEthernet/ios:ipv6" {
    uses config-eigrp-interface-classic-ipv6-grouping;
    uses config-interface-ipv6-eigrp-grouping {
      status obsolete;
    }
  }

  augment "/ios:native/ios:interface/ios:GigabitEthernet/ios:ipv6" {
    uses config-eigrp-interface-classic-ipv6-grouping;
    uses config-interface-ipv6-eigrp-grouping {
      status obsolete;
    }
  }

  augment "/ios:native/ios:interface/ios:TenGigabitEthernet/ios:ipv6" {
    uses config-eigrp-interface-classic-ipv6-grouping;
    uses config-interface-ipv6-eigrp-grouping {
      status obsolete;
    }
  }

  augment "/ios:native/ios:interface/ios:FiveGigabitEthernet/ios:ipv6" {
    uses config-eigrp-interface-classic-ipv6-grouping;
    uses config-interface-ipv6-eigrp-grouping {
      status obsolete;
    }
  }

  augment "/ios:native/ios:interface/ios:AppGigabitEthernet/ios:ipv6" {
    uses config-eigrp-interface-classic-ipv6-grouping;
    uses config-interface-ipv6-eigrp-grouping {
      status obsolete;
    }
  }

  augment "/ios:native/ios:interface/ios:TwentyFiveGigE/ios:ipv6" {
    uses config-eigrp-interface-classic-ipv6-grouping;
    uses config-interface-ipv6-eigrp-grouping {
      status obsolete;
    }
  }

  augment "/ios:native/ios:interface/ios:TwoGigabitEthernet/ios:ipv6" {
    uses config-eigrp-interface-classic-ipv6-grouping;
    uses config-interface-ipv6-eigrp-grouping {
      status obsolete;
    }
  }

  augment "/ios:native/ios:interface/ios:FortyGigabitEthernet/ios:ipv6" {
    uses config-eigrp-interface-classic-ipv6-grouping;
    uses config-interface-ipv6-eigrp-grouping {
      status obsolete;
    }
  }

  augment "/ios:native/ios:interface/ios:HundredGigE/ios:ipv6" {
    uses config-eigrp-interface-classic-ipv6-grouping;
    uses config-interface-ipv6-eigrp-grouping {
      status obsolete;
    }
  }

  augment "/ios:native/ios:interface/ios:Port-channel/ios:ipv6" {
    uses config-eigrp-interface-classic-ipv6-grouping;
    uses config-interface-ipv6-eigrp-grouping {
      status obsolete;
    }
  }

  augment "/ios:native/ios:interface/ios:Port-channel-subinterface/ios:Port-channel/ios:ipv6" {
    uses config-eigrp-interface-classic-ipv6-grouping;
    uses config-interface-ipv6-eigrp-grouping {
      status obsolete;
    }
  }

  augment "/ios:native/ios:interface/ios:Loopback/ios:ipv6" {
    uses config-eigrp-interface-classic-ipv6-grouping;
    uses config-interface-ipv6-eigrp-grouping {
      status obsolete;
    }
  }

  augment "/ios:native/ios:interface/ios:Tunnel/ios:ipv6" {
    uses config-eigrp-interface-classic-ipv6-grouping;
    uses config-interface-ipv6-eigrp-grouping {
      status obsolete;
    }
  }

  augment "/ios:native/ios:interface/ios:BDI/ios:ipv6" {
    uses config-eigrp-interface-classic-ipv6-grouping;
    uses config-interface-ipv6-eigrp-grouping {
      status obsolete;
    }
  }

  augment "/ios:native/ios:interface/ios:Vlan/ios:ipv6" {
    uses config-eigrp-interface-classic-ipv6-grouping;
    uses config-interface-ipv6-eigrp-grouping {
      status obsolete;
    }
  }

  augment "/ios:native/ios:interface/ios:Dialer/ios:ipv6" {
    uses config-eigrp-interface-classic-ipv6-grouping;
    uses config-interface-ipv6-eigrp-grouping {
      status obsolete;
    }
  }

  augment "/ios:native/ios:interface/ios:BD-VIF/ios:ipv6" {
    uses config-eigrp-interface-classic-ipv6-grouping;
    uses config-interface-ipv6-eigrp-grouping {
      status obsolete;
    }
  }

  /////////////////////////////////////////////////////////
  // native / route-tag
  /////////////////////////////////////////////////////////
  augment "/ios:native/ios:route-tag" {
    uses config-route-tag-grouping;
  }
}
