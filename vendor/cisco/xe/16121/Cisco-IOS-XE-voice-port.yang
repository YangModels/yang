module Cisco-IOS-XE-voice-port {
  namespace "http://cisco.com/ns/yang/Cisco-IOS-XE-voice-port";
  prefix ios-voice-port;

  import cisco-semver {
    prefix cisco-semver;
  }
 
  import Cisco-IOS-XE-native {
    prefix ios;
  }


  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Voice Port Yang model.
     Copyright (c) 2019 by Cisco Systems, Inc.
     All rights reserved.";

  // =========================================================================
  // REVISION
  // =========================================================================
  revision 2019-07-01 {
    description "Establish semantic version baseline";
    cisco-semver:module-version "1.0.0";
  }
  revision 2019-02-20 {
    description
      "add pattern '.*' to description where cli-preformatted is used";
  }
  revision 2019-01-29 {
    description
      "Initial revision";
  }

  grouping config-voice-port-grouping {
    list voice-port {
      description "Voice port configuration";
      key "id";
      leaf id {
        type string;
      }
      leaf description {
        description
          "Description of what this port is connected to";
        type string {
          pattern '.*';
          length "1..64";
        }
      }
      leaf compand-type {
        description
          "The quantization and coding type for this voice port";
        type enumeration {
          enum "a-law";
          enum "u-law";
        }
        default "u-law";
      }
      container busyout {
        description
          "Configure busyout trigger event and procedure";
        choice busyout-choice {
          leaf forced {
            description
              "Force the voice port in busyout";
            type empty;
          }
          leaf graceful {
            description
              "Put the voice port in graceful busyout mode";
            type empty;
          }
        }
      }
      container caller-id {
        description
          "Configure port caller id parameters";
        leaf enable {
          description "Enable caller id on this port";
          type empty;
        }
      } 
      container connection {
        description
          "Specify Connection Parameters";
        choice conn-choice {
          case tie-line-case {
            leaf tie-line {
              description
                "A tie line";
              type string;
            }
          }
          case trunk-case {
            container trunk {
              description
                "A Straight Tie Line";
              
              leaf trunk-num {
                description
                  "Connection trunk calling number";
                type string;
              }
              choice additional-choice {
                leaf answer-mode {
                  description
                    "Slave mode trunking";
                  type empty;
                }
                leaf retry-timer {
                  description
                    "Timer value for retry connection";
                  type uint8 {
                    range "0..5";
                  }
                }
              }
            }
          }
          case plar-case {
            container plar {
              description
                "Private Line Auto Ring down";
              choice plar-choice {
                leaf plar-num {
                  type string;
                }
                container opx {
                  description
                    "Off-Premises eXtension option";
                  
                  choice opx-choice {
                    case immediate-case {
                      leaf immediate {
                        description
                          "Ring the destination immediately";
                        type string;
                      }
                    }
                    case opx-num-only-case {
                      leaf opx-num-only {
                        description
                          "Off-Premises eXtension number";
                        type string;
                      }
                    }
                    case opx-cut-through-case {
                      leaf opx-num {
                        description
                          "Off-Premises eXtension number";
                        type string;
                      }
                      leaf cut-through-wait {
                        description
                          "Cut through audio after off hook to Central Office on inbound calls";
                        type uint16 {
                          range "150..750";
                        }
                      }
                    }
                  }
                }
              }
            }
          }
        }
      }
      leaf cptone {
        description
          "Configure voice call progress tone locale";
        type enumeration {
          enum "AR";
          enum "AU";
          enum "AT";
          enum "BE";
          enum "BR";
          enum "CA";
          enum "CL";
          enum "CN";
          enum "CO";
          enum "C1";
          enum "C2";
          enum "CY";
          enum "CZ";
          enum "OK";
          enum "EG";
          enum "FI";
          enum "FR";
          enum "DE";
          enum "GH";
          enum "GR";
          enum "HK";
          enum "HU";
          enum "IS";
          enum "IN";
          enum "ID";
          enum "IE";
          enum "IL";
          enum "IT";
          enum "JP";
          enum "JO";
          enum "KE";
          enum "KR";
          enum "KW";
          enum "LB";
          enum "LU";
          enum "MY";
          enum "MT";
          enum "MX";
          enum "NP";
          enum "NL";
          enum "NZ";
          enum "NG";
          enum "NO";
          enum "OM";
          enum "PK";
          enum "PA";
          enum "PE";
          enum "PH";
          enum "PL";
          enum "PT";
          enum "RU";
          enum "SA";
          enum "SG";
          enum "SK";
          enum "SI";
          enum "ZA";
          enum "ES";
          enum "SE";
          enum "CH";
          enum "TW";
          enum "TH";
          enum "TR";
          enum "AE";
          enum "GB";
          enum "US";
          enum "VE";
          enum "ZW";
        }
        default "US";
      }
      container impedance {
        description
          "Specify the terminating impedance of the interface";
        leaf imp-type {
          type enumeration {
            enum "600c";
            enum "600r";
            enum "900c";
            enum "900r";
            enum "complex1";
            enum "complex2";
            enum "complex3";
            enum "complex4";
            enum "complex5";
            enum "complex6";
          }
          default "600r";
        }
      }
      container battery-reversal {
        description
          "Enable battery-reversal generation";
        presence true;
        leaf answer {
          description
            "Enable answer supervision";
          type empty;
        }
        leaf detection-delay {
          description
            "Battery Reversal Detection Delay";
          type uint16 {
            range "0..800";
          }
          default "0";
        }
      }
      leaf dial-type {
        description
          "Configure digit forward tone type";
        type enumeration {
          enum "dtmf";
          enum "mf";
          enum "pulse";
        }
        default "dtmf";
      }
      container echo-cancel {
        description
          "Echo-cancellation option";
        leaf enable {
          description
            "Echo Cancel Enable";
          type boolean;
          default true;
        }
      }
      container input {
        description
          "Configure input gain for voice";
        leaf gain {
          description
            "Configure gain in db for voice input";
          type int8 {
            range "-6..14";
          }
          default "0";
        }
      }
      leaf loop-length {
        description
          "Configure loop length";
        type enumeration {
          enum "long";
          enum "short";
        }
        default "short";
      }
      container output {
        description
          "Configure output attenuation for voice";
        leaf attenuation {
          description
            "Amount of attenuation inserted at transmit side of the interface";
          type int8 {
            range "-6..14";
          }
          default "3";
        }
      }
      leaf pre-dial-delay {
        description
          "Pre-dial Delay";
        type uint8 {
          range "0..10";
        }
        default "1";
      }
      leaf pulse-digit-detection {
        description
          "Enable/Disable pulse digit detection";
        type boolean; 
        default true;
      }
      container ren {
        description
          "Ringer Equivalence Number";
        leaf ren-long-loop {
          when "../../loop-length = 'long'";
          type uint8 {
            range "1..2";
          }
          default "1";
        }
        leaf ren-short-loop {
          when "../../loop-length = 'short'";
          type uint8 {
            range "1..5";
          }
          default "1";
        }
      }
      container ring {
        description
          "Ringing parameters";
        leaf frequency {
          description
            "The ring frequency to be used in this voice port";
          type enumeration {
            enum "20";
            enum "25";
            enum "30";
            enum "50";
          }
          default "25";
        }
        leaf dc-offset {
          description
            "Ringing DC-offset values";
          when "../../loop-length = 'long'";
          type enumeration {
            enum "10-volts";
            enum "20-volts";
            enum "24-volts";
            enum "30-volts";
            enum "35-volts";
          }
        }
      }
      container secondary {
        description
          "Secondary call service";
        leaf dialtone {
          description
            "Secondary dial tone option";
          type empty;
        }
      }
      container signal {
        description
          "Configure signaling parameters for the voice port";
        
        choice signal-choice {
          leaf groundStart {
            description
              "Ground Start signaling type";
            type empty;
          } 
          container loopStart {
            description
              "Loop Start signaling type";
            presence true;
            leaf live-feed {
              description
                "Live Feed option";
              type empty;
            }
          } 
          container did {
            description
              "Direct Inward Dialing signaling type";
            leaf did-type {
              type enumeration {
                enum "delay-dial";
                enum "immediate";
                enum "wink-start";
              }
            }
          }
        }
      }
      container station-id {
        description
          "Configure station ID";
        leaf name {
          description
            "A string describing station name";
          type string {
            pattern '.*';
            length "1..50";
          }
        }
        leaf number {
          description
            "A full E.164 telephone number";
          type string;
        }
      }
      container supervisory {
        description
          "Configure disconnect supervision options";

        leaf custom-cptone {
          description
            "Configure custom call progress tones for call supervision";
          type string {
          }
        }
        container disconnect {
          description
            "Configure supervisory disconnect signal";
          choice disconnect-type {
            leaf anytone {
              description
                "All call progressing tones will be detected";
              type empty;
            }
            leaf dualtone {
              description
                "Specify dual tone will be detected";
              type enumeration {
                enum "mid-call";
                enum "pre-connect";
              }
            }
            leaf signal { 
              description
                "Configure supervisory disconnect signal";
              type empty;
            }
          }
        }
        leaf dualtone-detect-params {
          description
            "Configure dual tone detection parameters for call supervision";
          type uint32 {
            range "1..10000";
          }
        }
      }
      container timing {
        description
          "Configure voice timing parameters";
        container hookflash-in {
          description
            "Hook flash input duration in milliseconds";
          
          leaf max-value {
            description
              "Maximum time";
            type uint16 {
              range "50..1550";
            }
            default "1000";
          }
          leaf min-value {
            description
              "Minimum time";
            type uint16 {
              range "0..400";
            }
            default "150";
          }
        }
        leaf guard-out {
          description
            "A time window after call disconnect, no outgoing cal is allowed";
          type uint16 {
            range "300..3000";
          }
          default "2000";
        }
        leaf hookflash-out {
          description
            "Hook flash output duration in milliseconds";
          type uint16 {
            range "50..1550";
          }
          default "400";
        }
        leaf pulse-inter-digit {
          description
            "Pulse dialing inter-digit timing in milliseconds";
          type uint16 {
            range "100..1000";
          }
          default "750";
        }
        leaf sup-disconnect {
          description
            "Minimum timing for supervisory disconnect";
          type uint16 {
            range "50..1500";
          }
          default "350";
        }
        leaf answer-winkwidth {
          description
            "Min time delay between start of incoming seizure and wink in msecs, DID only";
          type uint16 {
            range "110..290";
          }
          default "210";
        }
        leaf clear-wait {
          description
            "Time of inactive seizure signal to declare call cleared in msecs. DID only";
          type uint16 {
            range "200..2000";
          }
          default "400";
        }
        leaf dialout-delay {
          description
            "Delay before sending out digit or cut-thru. DID only";
          type uint16 {
            range "50..5000";
          }
          default "70";
        }
        leaf delay-duration {
          description
            "Max delay signal duration for delay dial signalling in msecs. DID only";
          type uint16 {
            range "100..5000";
          }
          default "2000";
        }
        leaf delay-start {
          description
            "Timing of generation of delay start sig from detect incoming seizure. DID only";
          type uint16 {
            range "20..2000";
          }
          default "300";
        }
        container dial-pulse {
          description
            "Dial pulse. DID only";
          leaf min-delay {
            description
              "Minimum delay";
            type uint16 {
               range "0 | 140..5000";
            }
            default "140";
          }
        }
        leaf wait-wink {
          description
            "Max time to wait for wink signal after sending outgoing seizure. DID only";
          type uint16 {
            range "100..6500";
          }
          default "550";
        }
        leaf wink-duration {
          description
            "Wink duration for wink start signalling in msecs. DID only";
          type uint16 {
            range "50..3000";
          }
          default "200";
        }
        leaf wink-wait {
          description
            "Time to wait before sending wink signal after detecting incoming seizure. DID only";
          type uint16 {
            range "100..6500";
          }
          default "200";
        }
      }
      container translation-profile {
        description
          "Translation profile";
        leaf incoming {
          description
            "Translation Profile for incoming call leg";
          type string;
        }
        leaf outgoing {
          description
            "Translation Profile for outgoing call leg";
          type string;
        }
      } 
      leaf vad {
        description
          "Voice Activity Detection";
        type boolean;
        default true;
      }
      leaf shutdown {
        description
          "Take voice-port offline";
        type boolean;
        default false;
      }
    }
  }

  /////////////////////////////////////////////////////////
  // native / voice-port
  /////////////////////////////////////////////////////////
  augment "/ios:native" {
    uses config-voice-port-grouping;
  }
} //module
