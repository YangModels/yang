submodule Cisco-IOS-XE-logging {
  belongs-to Cisco-IOS-XE-native {
    prefix ios;
  }

  import cisco-semver {
    prefix cisco-semver;
  }
 
  import ietf-inet-types {
    prefix inet;
  }


  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Logging Yang Model.
     Copyright (c) 2016-2018 by Cisco Systems, Inc.
     All rights reserved.";

  // =========================================================================
  // REVISION
  // =========================================================================
  revision 2019-07-01 {
    description 
       "- Establish semantic version baseline
        - Add support for logging buffered xml
        - Remove default values for logging buffered
        - Add missing descriptions to logging buffered";
    cisco-semver:module-version "1.0.0";
  }
  revision 2018-11-07 {
      description
      "Cleanup spelling errors in description statements";
  }
  revision 2018-07-11 {
    description
      "Add full support for logging discriminator";
  }
  revision 2018-05-22 {
    description
      "Add default cli/value for logging buffered 4096 debugging";
  }
  revision 2018-03-18 {
    description
      "Add diff-dependency for logging discriminator,
       logging-level-type enumeration order fixed,
       Change logging remote-host to work correctly for 
       oc-system mapping";
  }
  revision 2018-03-15 {
    description
      "Add dependency to buffered for persistent";
  }
  revision 2017-11-10 {
    description
      "Add more nodes under logging persistent";
  }
  revision 2017-08-25 {
    description
      "enforce order of deleting logging cli";
  }

  revision 2017-06-02 {
    description
      "logging host ipv6 more support";
  }

  revision 2017-03-01 {
    description
      "logging host/source-interface fix & enhancement";
  }

  revision 2017-02-07 {
    description
      "Initial revision";
  }

  typedef logging-level-type {
    type union {
      type uint16 {
        range "0..7";
      }
      type enumeration {
        enum "emergencies";
        enum "alerts";
        enum "critical";
        enum "errors";
        enum "warnings";
        enum "notifications";
        enum "informational";
        enum "debugging";
        enum "bogus";
      }
    }
  }

  typedef severity-group-type {
    type string {
      pattern
        "([0|1|3|6|7],){0,4}[0|1|3|6|7]";
    }
  }

  /////////////////////////////////////////////////////////
  // native / logging
  /////////////////////////////////////////////////////////

  grouping logging-host-option-group {
    leaf discriminator {
      description
        "Specify a message discriminator identifier for this logging session";
        type string;
      }
      //  filtered              Enable filtered logging
      //  sequence-num-session  Include session sequence number tag in
      //                        syslog message
      //  session-id            Specify syslog message session ID tagging
      //  xml                   Enable logging in XML
  } 

  grouping logging-host-transport-group {
    container transport {
      container udp {
        leaf-list port {
          type uint16;
        }
      }
      container tcp {
        leaf-list port {
          type uint16;
        }
      }
    }
  }

  grouping logging-rate-limit-common-group {
    list ranges {
      key "range";
      leaf range {
        description
          "Messages per second";
        type uint16 {
          range "1..10000";
        }
      }
      container except {
        description
          "Messages of this severity or higher";
        presence true;
        leaf range {
          description
            "Logging severity level";
          type logging-level-type;
        }
      }
    }
  }

  grouping config-logging-discriminator-severity-actions {
    choice actions {
      leaf drops {
        description
           "To drop messages including the specified regular expression string";
        type severity-group-type; 
      }
      leaf includes {
        description
         "To deliver messages including the specified regular expression string";
        type severity-group-type; 
      } 
    }
  }

  grouping config-logging-discriminator-common-actions {
    choice actions {
      leaf drops {
        description
           "To drop messages including the specified regular expression string";
        type string;
      }
      leaf includes {
        description
         "To deliver messages including the specified regular expression string";
        type string;
      } 
    }
  }
  
  grouping config-logging-grouping {
    container logging {
      description
        "Modify message logging facilities";
      
      // logging descriminator 
      list discriminator {
        description
          "Create or modify a message discriminator";
        key "name";
        leaf name {
          type string;
        }
        container severity {
          description
            "Msg-body pattern for message filtering";
          uses config-logging-discriminator-severity-actions;
        }
        container facility {
          description
            "Facility pattern for message filtering";
          uses config-logging-discriminator-common-actions;
        }
        container mnemonics {
          description
            "Mnemonics pattern for message filtering";
          uses config-logging-discriminator-common-actions;
        }
        leaf rate-limit {
          description
            "Rate-limit value for message rate control"; 
          type uint16 {
            range "1..10000";
          }
        }
        container msg-body {
          description
            "Msg-body pattern for message filtering";
          uses config-logging-discriminator-common-actions;
        }
      }

      container persistent {
        description
          "Set persistent logging parameters";
        presence "true";
        leaf url {
          description
            "URL to store logging messages";
          type string;
        }
        leaf size {
          description
            "Set disk space for writing log messages";
          type uint32 {
            range "16384..2147483647";
          }
        }
        leaf filesize {
          description
            "Set size of individual log files";
          type uint32 {
            range "8192..2147483647";
          }
        }
        leaf batch {
          description
            "Batch size for writing to persistent storage";
          type uint32 {
            range "4096..2147483647";
          }
        }
        leaf threshold {
          description
            "Setting threshold capacity. When setting circular logging is disabled";
          type uint8 {
            range "1..99";
          }
        }
        leaf immediate {
          description
            "Write log entry to storage immediately (no buffering).";
          type empty;
        }
        leaf notify {
          description
            "Notify when show logging [persistent] is activated.";
          type empty;
        }
        leaf protected {
          description
            "Eliminates manipulation on logging-persistent files";
          type empty;
        }
      }
      // <no> logging monitor
      container monitor-conf {
        leaf monitor {
          type boolean;
        }
      }
      // logging monitor
      container monitor {
        description
          "Set terminal line (monitor) logging parameters";
        presence "true";
        leaf severity {
          type logging-level-type;
        }
        list discriminator {
          description
            "Establish MD-Console association";
          key "name";
          leaf name {
            type string;
          }
          leaf severity {
            type logging-level-type;
          }
        }
      }
      leaf alarm {
        description
          "Configure syslog for alarms";
        type union {
          type uint8 {
            range "1..4";
          }
          type enumeration {
            enum "critical";
            enum "informational";
            enum "major";
            enum "minor";
          }
        }
      }
      container buffered {
        description
          "Set buffered logging parameters";
        choice buffered-params {
          leaf discriminator-config {
            description
              "Establish MD-Buffer association";
            type string;
          }
          leaf yxml {
            description
              "Enable logging in XML to XML logging buffer";
            type empty;
          }
        }
        leaf size-value {
          description
            "Logging buffer size";
          type uint32 {
            range "4096..2147483647";
          }
        }
        leaf severity-level {
          description
            "Logging severity level";
          type logging-level-type;
        }  
        container size {
          status deprecated;
          leaf size-value {
            type uint32 {
              range "4096..2147483647";
            }
            default 4096;
          }
          leaf severity {
            type logging-level-type;
            default "debugging";
          }
        }
        choice buffered-param {
          case discriminator-param {
            list discriminator {
              status deprecated;
              description "(DEPRECATED, use discriminator-config)";
              key "name";
              leaf name {
                type string;
              }
              leaf size-value {
                type uint32 {
                  range "4096..2147483647";
                }
              }
              leaf severity {
                type logging-level-type;
              }
            }
          }
          case severity-level {
            leaf severity {
              status deprecated;
              type logging-level-type;
            }
          }
          case xxml-buffer {
            leaf xxml {
              status deprecated;
              description
                "Enable logging in XML to XML logging buffer(DEPRECATED)";
              type uint32 {
                range "4096..2147483647";
              }
            }
          }
        }
      }  
      container console-conf {
        leaf console {
          description
            "Set console logging parameters";
          type boolean;
        }
      }
      container console {
        description
          "Set console logging parameters";
        presence "true";
        list discriminator {
          description
            "Establish MD-Console association";
          key "name";
          leaf name {
            type string;
          }
          leaf severity {
            type logging-level-type;
          }
        }
        leaf filtered {
          description
            "Enable filtered logging";
          type empty;
        }
        leaf guaranteed {
          description
            "Guarantee console messages";
          type empty;
        }
        leaf xxml {
          description
            "Enable logging in XML";
          type logging-level-type;
        }
        leaf severity {
          type logging-level-type;
        }
      }
      container event {
        description
          "Global interface events";
        container link-status {
          description
            "Globally enable/disable link UPDOWN message";
          leaf boot {
            description
              "Suppress/Allow link UPDOWN messages during boot";
            type empty;
          }
          leaf global {
            type empty;
          }
          leaf default {
            description
              "Link UPDOWN messages for all interfaces";
            type empty;
          }
        }
      }
      container esm {
        description
          "Set ESM filter restrictions";
        leaf config {
          description
            "Permit/Deny configuration changes from ESM filters";
          type empty;
        }
      }
      leaf facility {
        description
          "Facility parameter for syslog messages";
        type enumeration {
          enum "auth";
          enum "cron";
          enum "daemon";
          enum "kern";
          enum "local0";
          enum "local1";
          enum "local2";
          enum "local3";
          enum "local4";
          enum "local5";
          enum "local6";
          enum "local7";
          enum "lpr";
          enum "mail";
          enum "news";
          enum "sys10";
          enum "sys11";
          enum "sys12";
          enum "sys13";
          enum "sys14";
          enum "sys9";
          enum "syslog";
          enum "user";
          enum "uucp";
        }
      }
      container history {
        description
          "Configure syslog history table";
        leaf size {
          description
            "Set history table size";
          type uint16;
        }
        leaf severity-level {
          type union {
            type uint8 {
              range "0..7";
            }
            type enumeration {
              enum "emergencies";
              enum "alerts";
              enum "critical";
              enum "errors";
              enum "warnings";
              enum "notifications";
              enum "informational";
              enum "debugging";
            }
          }
        }
      }
      // logging host *
      container host {
        description
          "Set syslog server IP address and parameters";
        list ipv4-host-list {
          key "ipv4-host";
          leaf ipv4-host {
            type inet:host;
          }
        }
        list ipv4-host-transport-list {
          key "ipv4-host";
          leaf ipv4-host {
            type inet:host;
          }
          uses logging-host-transport-group;
          uses logging-host-option-group;
        }
        list ipv4-host-vrf-list {
          key "ipv4-host vrf";
          leaf ipv4-host {
            type inet:host;
          }
          leaf vrf {
            description
            "Set VRF option";
            type string;
          }
          uses logging-host-option-group;
        }
        list ipv4-host-vrf-transport-list {
          key "ipv4-host vrf";
          leaf ipv4-host {
            type inet:host;
          }
          leaf vrf {
            description "Set VRF option";
            type string;
          }
          uses logging-host-transport-group;
          uses logging-host-option-group;
        }

        // logging host ipv6 *
        container ipv6 {
          description
            "Set syslog server IPv6 address";
          list ipv6-host-list {
            key "ipv6-host";
            leaf ipv6-host {
              type ios-types:ipv6-host;
            }
          }
          list ipv6-host-transport-list {
            key "ipv6-host";
            leaf ipv6-host {
              type ios-types:ipv6-host;
            }
            uses logging-host-transport-group;
            uses logging-host-option-group;
          }
          list ipv6-host-vrf-list {
            key "ipv6-host vrf";
            leaf ipv6-host {
              type ios-types:ipv6-host;
            }
            leaf vrf {
              description
              "Set VRF option";
              type string;
            }
            uses logging-host-option-group;
          }
          list ipv6-host-vrf-transport-list {
            key "ipv6-host vrf";
            leaf ipv6-host {
              type ios-types:ipv6-host;
            }
            leaf vrf {
              description "Set VRF option";
              type string;
            }
            uses logging-host-transport-group;
            uses logging-host-option-group;
          }
        }
      }
      container origin-id {
        description 
          "Add origin ID to syslog messages";
        choice origin-choice {
          case origin-type { 
            leaf type-value {
              description 
                "Use origin hostname/ip/ipv6 as ID";
              type enumeration {
                enum "hostname" {
                }
                enum "ip" {
                }
                enum "ipv6" {
                }
              }
            } 
          }     
          case origin-name {
            leaf string {
              description 
                "Define a unique text string as ID";
              type string;
            }
          }
        } 
      }
      // <no> logging rate-limit
      container rate-limit-conf {
        leaf rate-limit {
          type boolean;
        }
      }
      // logging rate-limit
      container rate-limit {
        description
          "Set messages per second limit";
        presence true;
        uses logging-rate-limit-common-group;
        container console {
          description
            "Rate limit only console messages";
          uses logging-rate-limit-common-group;
          container all {
            description "all";
             uses logging-rate-limit-common-group;
          }
        }
        container all {
          description
            "Rate limit only console messages";
          uses logging-rate-limit-common-group;
        }
      }

      // logging source-interface
      list source-interface {
        description 
          "Specify interface for source address in logging transactions";
        key interface-name;
        leaf interface-name {
          type string;
        }
        leaf vrf {
          description
            "Specify the vrf of source interface for logging transactions";
          type string;
        }
      }

      // logging snmp-trap
      container snmp-trap {
        description
          "Set SNMP trap logging level";
        leaf alerts {
          description
            "Immediate action needed           (severity=1)";
          type empty;
        }
        leaf critical {
          description
            "Critical conditions               (severity=2)";
          type empty;
        }
        leaf debugging {
          description
            "Debugging messages                (severity=7)";
          type empty;
        }
        leaf emergencies {
          description
            "System is unusable                (severity=0)";
          type empty;
        }
        leaf errors {
          description
            "Error conditions                  (severity=3)";
          type empty;
        }
        leaf informational {
          description
            "Informational messages            (severity=6)";
          type empty;
        }
        leaf notifications {
          description
            "Normal but significant conditions (severity=5)";
          type empty;
        }
        leaf warnings {
          description
            "Warning conditions                (severity=4)";
          type empty;
        }
      }
      // logging trap
      container trap {
        description
          "Set trap server logging level";
        presence "true";
        choice level {
          case set-default {
            leaf trap-default {
              type empty;
            }
          }
          case set-level {
            leaf severity {
              type union {
                type uint8 {
                  range "0..7";
                }
                type enumeration {
                  enum "alerts";
                  enum "critical";
                  enum "debugging";
                  enum "emergencies";
                  enum "errors";
                  enum "informational";
                  enum "notifications";
                  enum "warnings";
                }
              }
              default "informational";
            }
          }
        }
      }
      leaf hostip {
            type inet:host;
      }	
      container file {
        description
          "Set logging file parameters";
        
        leaf name {
          type string;
        }
        leaf max-size {
          type uint32;
        }
        leaf min-size {
          type uint32;
        }
        leaf severity {
          type logging-level-type;
        }
      }
      leaf snmp-authfail {
        type empty;
      }
      leaf buginf {
        description "Enable buginf logging for debugging";
        type empty;
      }
      leaf userinfo {
        description "Enable logging of user info on privileged mode enabling";
        type empty;
      }
    }
  }
}
