module Cisco-IOS-XE-cellular-rpc {
  namespace "http://cisco.com/ns/yang/Cisco-IOS-XE-cellular-rpc";
  prefix ios-xe-cell-rpc;

  import cisco-semver {
    prefix cisco-semver;
  }
 

  import Cisco-IOS-XE-rpc {
    prefix ios-xe-rpc;
  }

  organization "Cisco Systems";

  contact
    <mailto:cs-yang@cisco.com>;

  description
    "NED Cellular RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2018-12-06 {
    description
      "created for NED RPC modularisation";
  }

  rpc cellular {
    input {
      leaf if-name-drop-node-name {
          type string;
      }
      container lte {
        choice action {
          case tech  {
            container technology {
              choice action {
                case lte {
                   leaf lte {
                     type empty;
                   }
                }
                case auto {
                  leaf auto {
                    type empty;
                  }
                }
                case umts {
                  leaf umts {
                    type empty;
                  }
                }
              }
            }
          }
          case modem-reset {
              leaf modem-reset {
                  type empty;
              }
          }
          case profile {
            container profile {
               choice prof {
                  case delete  {
                    description "Cellular Profile configuration";
                    container delete {
                      description "Delete a Profile";
                        leaf profile-id-drop-node-name {
                          description "Profile ID";
                          type uint8 {
                            range "1..16";
                          }
                        }
                    }
                  }
                  case create {
                    container create {
                      description "Create a Profile";
                      leaf profile-id-drop-node-name {
                        description "Profile ID";
                        type uint8 {
                          range "1..16";
                        }
                      }
                      leaf prof-name-drop-node-name {
                        description "Profile name";
                        type string;
                      }
                      choice auth {
                        case none {
                          leaf none {
                            type empty;
                          }
                        }
                        case chap {
                          leaf chap {
                            type empty;
                          }
                        }
                        case pap {
                          leaf pap {
                            type empty;
                          }
                        }
                        case pap-chap {
                          leaf pap-chap {
                            type empty;
                          }
                        }
                      }
                      leaf user-name-drop-node-name {
                        description "Username for authentication";
                        type string;
                      }
                      leaf password-drop-node-name {
                        description "Password for authentication";
                        type string;
                      }
                      choice pdn {
                        case ipv4 {
                          leaf ipv4 {
                            type empty;
                          }
                        }
                        case ipv6 {
                          leaf ipv6 {
                            type empty;
                          }
                        }
                        case ipv4v6 {
                          leaf ipv4v6 {
                            type empty;
                          }
                        }
                      }
                    }
                  }
                }
              }
            }
          }
        }
      }
    output {
      uses ios-xe-rpc:cisco-xe-rpc-output;
    }
  }
}
