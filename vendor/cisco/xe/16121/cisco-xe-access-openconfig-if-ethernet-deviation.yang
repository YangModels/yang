module cisco-xe-access-openconfig-if-ethernet-deviation {
  // namespace
  namespace "http://openconfig.net/yang/cisco-xe-access-openconfig-if-ethernet-deviation";

  prefix cisco-xe-access-oc-if-eth-devs;

  import openconfig-interfaces {
    prefix oc-if;
  }
  import openconfig-if-ethernet {
    prefix oc-if-eth;
  }

  organization
    "Cisco Systems, Inc.";

  contact
    " Cisco Systems, Inc.
    Customer Service

    Postal: 170 W Tasman Drive
    San Jose, CA 95134

    Tel: +1 1800 553-NETS

    E-mail: cs-yang@cisco.com";

  description
    "This module defines deviation statements for openconfig-if-ethernet model applicable to IOS XE SP Access platforms.";
 
  revision 2018-12-12 {
    description
      "Initial Revision";

    reference
      "RFC 6020: YANG - A Data Modeling Language for the
       Network Configuration Protocol (NETCONF)";
  }

  deviation "/oc-if:interfaces/oc-if:interface/oc-if-eth:ethernet" +
            "/oc-if-eth:config/oc-if-eth:enable-flow-control" {
      deviate replace {
        default true;
      }
      description
        "Setting default flow control is not compatible with all interface types.";
  }
  deviation "/oc-if:interfaces/oc-if:interface/oc-if-eth:ethernet" +
            "/oc-if-eth:config/oc-if-eth:auto-negotiate" {
      deviate replace {
        default false;
      }
  }
}
