module Cisco-IOS-XE-utd-oper {
  yang-version 1;
  namespace "http://cisco.com/ns/yang/Cisco-IOS-XE-utd-oper";
  prefix utd-ios-xe-oper;

  import Cisco-IOS-XE-utd-common-oper {
    prefix utd-common-ios-xe-oper;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions for
     monitoring Unified Threat Defense (UTD).
     Copyright (c) 2018-2019 by Cisco Systems, Inc.
     All rights reserved.";

  revision 2019-05-01 {
    description
      "Added semantic version";
    reference "1.3.0";
    cisco-semver:module-version "1.3.0";
  }
  revision 2018-11-05 {
    description
      "- Add UTD file reputation/analysis status
       - Cleaned up spelling errors in descriptions.";
    reference "1.2.0";
    cisco-semver:module-version "1.2.0";
  }
  revision 2018-06-18 {
    description
      "Add UTD version status";
    reference "1.1.0";
    cisco-semver:module-version "1.1.0";
  }
  revision 2018-04-04 {
    description
      "Initial revision";
    reference "1.0.0";
    cisco-semver:module-version "1.0.0";
  }

  typedef utd-oper-status-val {
    type enumeration {
      enum "utd-oper-status-unknown" {
        value 0;
        description
          "Unified Threat Defense (UTD) operational status is unknown - Unable to determine status";
      }
      enum "utd-oper-status-green" {
        value 1;
        description
          "Unified Threat Defense (UTD) operational status is green - Working as expected";
      }
      enum "utd-oper-status-yellow" {
        value 2;
        description
          "Unified Threat Defense (UTD) operational status is yellow - Minor problem";
      }
      enum "utd-oper-status-red" {
        value 3;
        description
          "Unified Threat Defense (UTD) operational status is red - Major problem";
      }
      enum "utd-oper-status-down" {
        value 4;
        description
          "Unified Threat Defense (UTD) operational status is down - Communication has been lost";
      }
    }
    description
      "Unified Threat Defense (UTD) operational status";
  }

  typedef utd-file-reputation-status-states {
    type enumeration {
      enum "utd-file-repu-stat-process-unknown" {
        value 0;
        description
          "UTD Integration Advanced Malware Protection beaker process down";
      }
      enum "utd-file-repu-stat-process-up" {
        value 1;
        description
          "UTD Integration Advanced Malware Protection beaker process up";
      }
      enum "utd-file-repu-stat-process-down" {
        value 2;
        description
          "UTD Integration Advanced Malware Protection beaker process down";
      }
      enum "utd-file-repu-stat-amp-module-load-fail" {
        value 3;
        description
          "UTD Integration Advanced Malware Protection beaker AMP module load fail";
      }
      enum "utd-file-repu-stat-connected" {
        value 4;
        description
          "UTD Integration Advanced Malware Protection beaker connected";
      }
      enum "utd-file-repu-stat-not-connected" {
        value 5;
        description
          "UTD Integration Advanced Malware Protection beaker not connected";
      }
    }
    description
      "UTD Integration Advanced Malware Protection AMP status";
  }

  typedef utd-file-analysis-states {
    type enumeration {
      enum "tg-client-stat-unknown" {
        value 0;
        description
          "UTD Integration Advanced Malware Protection TG health status client unknown";
      }
      enum "tg-client-stat-down" {
        value 1;
        description
          "UTD Integration Advanced Malware Protection TG health status client down";
      }
      enum "tg-client-stat-up" {
        value 2;
        description
          "UTD Integration Advanced Malware Protection TG health status client up";
      }
      enum "api-key-stat-not-present" {
        value 3;
        description
          "UTD Integration Advanced Malware Protection TG health status apikey not present";
      }
      enum "api-key-stat-invalid" {
        value 4;
        description
          "UTD Integration Advanced Malware Protection TG health status apikey invalid";
      }
      enum "file-upload-stat-limit-reached" {
        value 5;
        description
          "UTD Integration Advanced Malware Protection TG health status file upload limit reached";
      }
    }
    description
      "UTD Integration Advanced Malware Protection TG health status";
  }

  grouping utd-update-status {
    description
      "Unified Threat Defense (UTD) update status";
    leaf version {
      type string;
      description
        "Version";
    }
    leaf last-update-time {
      type yang:date-and-time;
      description
        "Time of last attempted update";
    }
    leaf last-update-status {
      type utd-common-ios-xe-oper:utd-update-status-val;
      description
        "Status of last attempted update";
    }
    leaf last-update-reason {
      type string;
      description
        "Reason for last attempted update failure";
    }
    leaf last-successful-update-time {
      type yang:date-and-time;
      description
        "Time of last successful update";
    }
  }

  grouping utd-ips-update-status {
    description
      "Unified Threat Defense (UTD) Intrusion Prevention System (IPS) update status";
    container ips-update-status {
      description
        "Intrusion Prevention System (IPS) update status";
      uses utd-ios-xe-oper:utd-update-status;
    }
  }

  grouping utd-urlf-update-status {
    description
      "Unified Threat Defense (UTD) URL-Filtering (URLF) update status";
    container urlf-update-status {
      description
        "URL-Filtering (URLF) update status";
      uses utd-ios-xe-oper:utd-update-status;
    }
  }

  grouping utd-engine-instance-status {
    description
      "Unified Threat Defense (UTD) engine instance status";
    leaf id {
      type uint32;
      description
        "Engine instance ID";
    }
    leaf running {
      type boolean;
      description
        "Engine instance running";
    }
    leaf status {
      type utd-ios-xe-oper:utd-oper-status-val;
      description
        "Engine instance status";
    }
    leaf reason {
      type string;
      description
        "Engine instance status reason";
    }
  }

  grouping utd-engine-status {
    description
      "Unified Threat Defense (UTD) engine status";
    leaf version {
      type string;
      description
        "Engine version";
    }
    leaf profile {
      type string;
      description
        "Profile";
    }
    leaf status {
      type utd-ios-xe-oper:utd-oper-status-val;
      description
        "Overall status";
    }
    leaf reason {
      type string;
      description
        "Overall status reason";
    }
    leaf memory-usage {
      type decimal64 {
        fraction-digits 2;
      }
      units "percent";
      description
        "Percentage of memory used";
    }
    leaf memory-status {
      type utd-ios-xe-oper:utd-oper-status-val;
      description
        "Status of memory usage";
    }
    list utd-engine-instance-status {
      key "id";
      description
        "Status of engine instances";
      uses utd-ios-xe-oper:utd-engine-instance-status;
    }
  }

  grouping utd-version-status {
    description
      "Unified Threat Defense (UTD) version status";
    leaf recommended-version {
      type string;
      description
        "Unified Threat Defense (UTD) version recommended to run";
    }
    leaf supported-regex {
      type string;
      description
        "Unified Threat Defense (UTD) version regular expression- describes version support";
    }
    leaf installed-version {
      type string;
      description
        "Unified Threat Defense (UTD) version currently installed";
    }
    leaf supported {
      type boolean;
      description
        "Unified Threat Defense (UTD) supported flag - indicates if the installed UTD version is compatible with the supported version";
    }
  }

  grouping utd-file-reputation-status {
    description
      "UTD Integration Advanced Malware Protection beaker general status";
    leaf version {
      type string;
      description
        "UTD Integration Advanced Malware Protection beaker version";
    }
    leaf status {
      type utd-ios-xe-oper:utd-file-reputation-status-states;
      description
        "UTD Integration Advanced Malware Protection beaker status";
    }
    leaf message {
      type string;
      description
        "UTD Integration Advanced Malware Protection beaker status messages";
    }
  }

  grouping utd-file-analysis-status {
    description
      "UTD Integration Advanced Malware Protection TG status";
    leaf status {
      type utd-ios-xe-oper:utd-file-analysis-states;
      description
        "UTD Integration Advanced Malware Protection TG status health status";
    }
    leaf backoff-interval {
      type uint64;
      description
        "UTD Integration Advanced Malware Protection TG status number of seconds for backoff";
    }
    leaf message {
      type string;
      description
        "UTD Integration Advanced Malware Protection TG status messages";
    }
  }

  container utd-oper-data {
    config false;
    description
      "Unified Threat Defense (UTD) operational data";
    container utd-engine-status {
      presence "utd-engine-status";
      description
        "Unified Threat Defense (UTD) engine status";
      uses utd-ios-xe-oper:utd-engine-status;
    }
    container utd-ips-update-status {
      presence "utd-ips-update-status";
      description
        "Unified Threat Defense (UTD) Intrusion Prevention System (IPS) update status";
      uses utd-ios-xe-oper:utd-ips-update-status;
    }
    container utd-urlf-update-status {
      presence "utd-urlf-update-status";
      description
        "Unified Threat Defense (UTD) URL-Filtering (URLF) update status";
      uses utd-ios-xe-oper:utd-urlf-update-status;
    }
    container utd-version-status {
      presence "utd-version-status";
      description
        "Unified Threat Defense (UTD) version status";
      uses utd-ios-xe-oper:utd-version-status;
    }
    container utd-file-reputation-status {
      presence "utd-file-reputation-status";
      description
        "UTD Integration Advanced Malware Protection beaker status";
      uses utd-ios-xe-oper:utd-file-reputation-status;
    }
    container utd-file-analysis-status {
      presence "utd-file-analysis-status";
      description
        "UTD Integration Advanced Malware Protection TG status";
      uses utd-ios-xe-oper:utd-file-analysis-status;
    }
  }
}
