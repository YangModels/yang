module Cisco-IOS-XE-wireless-fqdn-cfg {
  yang-version 1;
  namespace "http://cisco.com/ns/yang/Cisco-IOS-XE-wireless-fqdn-cfg";
  prefix wireless-fqdn-ios-cfg;

  import Cisco-IOS-XE-wireless-types {
    prefix wireless-types;
  }
  import ietf-inet-types {
    prefix inet;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing fqdn configurations
     Copyright (c) 2016-2019 by Cisco Systems, Inc.
     All rights reserved.";

  revision 2019-05-01 {
    description
      "Added semantic version";
    reference "2.1.0";
    cisco-semver:module-version "2.1.0";
  }
  revision 2018-08-20 {
    description
      "Data type changed for redirect-server ipv4 and redirect-server ipv6";
    reference "2.0.0";
    cisco-semver:module-version "2.0.0";
  }
  revision 2018-01-01 {
    description
      "Initial revision";
    reference "1.0.0";
    cisco-semver:module-version "1.0.0";
  }

  grouping st-fqdn-urllist {
    description
      "This structure stores the domain names for the corresponding url-filter list";
    leaf fqdn-url {
      type string;
      description
        "Each entry represents a url domain name configured in the given url-filter list";
    }
  }

  grouping st-fqdn-cfg {
    description
      "This structure stores the details for the url-filter list";
    leaf url-list-name {
      type string;
      description
        "This is the name for url-filter name which will contain the url domain names";
    }
    leaf action {
      type wireless-types:ewlc-url-rule-type;
      default "urllist-bl";
      description
        "This is Action on the url-filter list which is boolean, may have blacklist or whitelist";
    }
    leaf ipv4-redirect-server {
      type inet:ipv4-address;
      description
        "This is the IPv4 address redirect server to redirect the user if trying to access any unauthorized domain";
    }
    leaf ipv6-redirect-server {
      type inet:ipv6-address;
      description
        "This is the IPv6 address redirect server to redirect the user if trying to access any unauthorized domain";
    }
    leaf filter-type {
      type wireless-types:ewlc-url-filter-type;
      default "pre-auth-url-type";
      description
        "This is the filter type for the given url-filter list which dictates if it has to be used as have post auth or pre auth filter";
    }
    container fqdn-urllists {
      description
        "This object encompasses the url domain names configurations";
      list fqdn-urllist {
        key "fqdn-url";
        description
          "This object encompasses the url domain name configurations";
        uses wireless-fqdn-ios-cfg:st-fqdn-urllist;
      }
    }
  }

  container fqdn-cfg-data {
    description
      "Top container for fqdn url-filter list config";
    container fqdn-configs {
      description
        "This object encompasses the url-filter lists configurations";
      list fqdn-config {
        key "url-list-name";
        description
          "This object encompasses the url-filter list configurations";
        uses wireless-fqdn-ios-cfg:st-fqdn-cfg;
      }
    }
  }
}
