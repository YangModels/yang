submodule Cisco-IOS-XE-voice-register {
  belongs-to Cisco-IOS-XE-voice {
    prefix ios-voice;
  }

  import cisco-semver {
    prefix cisco-semver;
  }


  import ietf-inet-types {
    prefix inet;
  }

  import Cisco-IOS-XE-types {
    prefix ios-types;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Voice Register Yang model.
     Copyright (c) 2019 by Cisco Systems, Inc.
     All rights reserved.";

  // =========================================================================
  // REVISION
  // =========================================================================
  revision 2019-07-01 {
    description "Establish semantic version baseline";
    cisco-semver:module-version "1.0.0";
  }

  grouping config-voice-register-grouping {
    container register {
      description
        "voice register commands";
      container global {
        description
          "Define global commands";
        presence true;
        leaf max-dn {
          description
            "Maximum directory numbers supported";
          type uint32 {
            range "1..3500";
          }
        }
        leaf max-pool {
          description
            "Maximum pools to support";
          type uint32 {
            range "1..2000";
          }
          default 2000;
        }
        container system {
          description
            "Define system message";
          leaf message {
            description
              "Define system message";
            type string {
              length "1..32";
            }
          }
        }
      }
      list pool {
        description
          "voice-register-pool tag";
        key pool-tag;
        leaf pool-tag {
          description
            "voice register pool commands";
          must ". <= ../../global/max-pool" {
            error-message "pool-tag cannot exceed max-pool value set under voice register global";
          }
          type uint16 {
            range "1..2000";
          }
        }

        container id {
          description
            "define phone or device id";
          container network {
            description
              "define phone or device network address";
            choice ipaddress {
              case ipv4 {
                container ipv4address {
                  
                  leaf address {
                    description
                      "IPv4 Address";
                    type inet:ipv4-address;
                  }
                  leaf mask {
                    description
       	              "IPv4 Address Mask";
       	            type inet:ipv4-address;
                  }
                }
              }
              case ipv6 {
                leaf ippv6 {
              	  description
                    "IPv6 network and mask";
              	  type ios-types:ipv6-prefix;
                }
              }
            }            
          }
        }

        container voice-class {
          description
            "Set voice class parameters";
          leaf codec {
            description
              "Set Global Codec parameters";
            type leafref {
              path "../../../../ios-voice:class/ios-voice:codec/codec-tag";
            }
          }
        }

        container dtmf-relay {
          description
            "Transport DTMF digits across IP link";
          leaf rtp-nte {
            description
              "RTP Named Telephone Event RFC 2833";
            type empty;
          }
          leaf sip-kpml {
            description
              "DTMF Relay via KPML messages";
            type empty;
          }
          leaf sip-notify {
            description
              "DTMF Relay via SIP NOTIFY messages";
            type empty;
          }
        }
      }
    }
  }

  grouping config-voice-moh-file-location-grouping {
    leaf filename {
      description
        "Example: bootflash:MOH filename";
      type string {
        pattern "(((bootflash:)|(flash:)|(nvram:)|(webui:)).*)";
      }
    }
  }

  grouping config-voice-call-manager-fallback-grouping {
    container call-manager-fallback {
      description 
        "SRST for Cisco Call Manager fallback";
      presence true;
      container moh {
        description 
          "Define music-on-hold filename";
        container g729 {
          description
            "File for G.729/G.729A";
          uses config-voice-moh-file-location-grouping;
        }
        uses config-voice-moh-file-location-grouping;
      }
    }
  }
}
