module cisco-xe-openconfig-lldp-deviation {
  namespace "http://cisco.com/ns/cisco-xe-openconfig-lldp-deviation";

  prefix lldp-devs;

  import openconfig-lldp {
    prefix oc-lldp;
  }

  organization
    "Cisco Systems, Inc.";

  contact
    "Cisco Systems, Inc.
    Customer Service

    Postal: 170 W Tasman Drive
    San Jose, CA 95134

    Tel: +1 1800 553-NETS

    E-mail: cs-yang@cisco.com";

  description
    "This module defines deviation statements for openconfig-lldp module.";

 revision 2018-07-25 {
    description
      "Removed deviation for the capabilities under the neighbor";
  }

 revision 2018-07-24 {
    description
      "Added deviation to define the default value for hello-timer leaf";
  }

 revision 2018-07-17 {
    description
      "Added deviations for the enabled leaf and the container config under the neighbor list";
  }
  
  revision 2018-06-13 {
    description
      "Initial revision";
  }

  deviation "/oc-lldp:lldp/oc-lldp:config/oc-lldp:enabled" {
      deviate replace {
        default false;
       }
      description
        "By default LLDP is disabled in IOS XE.";
  }

  deviation "/oc-lldp:lldp/oc-lldp:config/oc-lldp:hello-timer" {
      deviate add {
        default 30; 
       }
      description
        "Added the default value for hello-timer to match IOS XE.";
  }


  deviation "/oc-lldp:lldp/oc-lldp:config/oc-lldp:system-name" {
   deviate not-supported;
      description
        "Not supported on IOS-XE.";
  }

  deviation "/oc-lldp:lldp/oc-lldp:config/oc-lldp:system-description" {
   deviate not-supported;
      description
        "Not supported on IOS-XE.";
  }

 deviation "/oc-lldp:lldp/oc-lldp:config/oc-lldp:chassis-id" {
   deviate not-supported;
      description
        "Not supported on IOS-XE.";
  }

 deviation "/oc-lldp:lldp/oc-lldp:config/oc-lldp:chassis-id-type" {
   deviate not-supported;
      description
        "Not supported on IOS-XE.";
  }

 deviation "/oc-lldp:lldp/oc-lldp:state/oc-lldp:counters/oc-lldp:last-clear" {
   deviate not-supported;
      description
        "Not supported on IOS-XE.";
  }

 deviation "/oc-lldp:lldp/oc-lldp:state/oc-lldp:counters/oc-lldp:tlv-accepted" {
   deviate not-supported;
      description
        "Not supported on IOS-XE.";
  }

 deviation "/oc-lldp:lldp/oc-lldp:interfaces/oc-lldp:interface/oc-lldp:state/oc-lldp:counters" {
   deviate not-supported;
      description
        "Not supported on IOS-XE.";
  }

 deviation "/oc-lldp:lldp/oc-lldp:interfaces/oc-lldp:interface/oc-lldp:neighbors/oc-lldp:neighbor/oc-lldp:custom-tlvs" {
   deviate not-supported;
      description
        "Not supported on IOS-XE.";
  }

  deviation "/oc-lldp:lldp/oc-lldp:interfaces/oc-lldp:interface/oc-lldp:neighbors/oc-lldp:neighbor/oc-lldp:config" {
   deviate not-supported;
      description
        "Not supported on IOS-XE.";
  }

}
