submodule Cisco-IOS-XE-aaa-rpc {
  belongs-to Cisco-IOS-XE-rpc {
    prefix ios-xe-rpc;
  }

  import cisco-semver {
    prefix cisco-semver;
  }

  organization "Cisco Systems";

  contact
    <mailto:cs-yang@cisco.com>;

  description
    "NED AAA RPC YANG module for IOS
     Copyright (c) 2016-2019 by Cisco Systems, Inc.
     All rights reserved.";

  // =========================================================================
  // REVISION
  // =========================================================================
  revision 2019-07-01 {
    description "Establish semantic version baseline";
    cisco-semver:module-version "1.0.0";
  }
  revision 2018-12-06 {
    description
      "created for NED RPC modularisation";
  }

  grouping clear-choice-aaa-case-grouping {
    container aaa {
      description
        "Clear AAA values";
      container local {
        description
          "Clear AAA local method options";
        container user {
          description
            "Clear local AAA users";
          container lockout {
            description
              "Clear locked out local AAA users";
            leaf username {
              description
                "Username of the locked-user";
              type string;
            }
          }
        }
      }
    }
  }
}
