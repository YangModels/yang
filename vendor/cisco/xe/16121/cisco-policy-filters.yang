/*-------------------------------------------------------------------
 *  cisco-policy-filters.yang - Definition of extended filters for 
 *  IOS Yang Common Model 
 * 
 *  April 2015, Nazanin Magharei 
 *                                                               
 *-------------------------------------------------------------------
 */

module cisco-policy-filters {
    namespace "urn:ietf:params:xml:ns:yang:cisco-policy-filters";
    
    prefix cisco-filter;


    import cisco-semver {
    prefix cisco-semver;
  }
 
  import ietf-diffserv-classifier {
        prefix classifier;
    }
   
    import policy-attr {
        prefix policy-attr;
    }
    
    import policy-types {
        prefix policy-types;
    }
    
    organization "Cisco Systems, Inc.";
    contact
    "Cisco Systems, Inc.
    Customer Service

    Postal: 170 W Tasman Drive
    San Jose, CA 95134

    Tel: +1 1800 553-NETS

    E-mail: cs-yang@cisco.com
     
    Editor:   Nazanin Magharei
               <mailto:nmaghare@cisco.com>";
    description
    "This module contains a collection of YANG definitions 
     extending classmap module based on IETF-diffserv classifier.
     Copyright (c) 2016 by Cisco Systems, Inc.
     All rights reserved.";

    revision 2019-07-01 {
    description "Establish semantic version baseline";
    cisco-semver:module-version "1.0.0";
  }
  revision "2016-03-30" {
      description
        "Update description with copyright notice.";
    }
     
    revision "2015-04-27" {
        description "First revision";
        reference "TBD";
    }

  
   augment  "/classifier:classifiers/classifier:classifier-entry" {
        description
       "Augment class type to  Diffserv Classifier Entry";
       leaf classifier-entry-type {
          type identityref {
            base policy-types:class-type;
            }
          description "Type of the class-map";
       }    
    }   
   
    augment  "/classifier:classifiers/classifier:classifier-entry/classifier:filter-entry/classifier:filter-param" {
        description
        "Augment Cisco policy filters to Diffserv Classifier Entry";
        
       case cos {
            if-feature policy-types:match-cos-support;
            container cos-cfgs {
                list cos-cfg{
                    must "cos-min <= cos-max" {
                        description "The configuration is a range, 
                        for individual values min and max should 
                        be equal.";
                    }
                    key "cos-min cos-max";
                    uses policy-attr:cos-cfg;  
                    description "Match Type COS configuration";    
                }
           }
              
        }
      
        case cos-inner-filter {
            if-feature policy-types:match-cos-inner-support;
            container cos-inner-cfgs {
                list cos-inner-cfg {
                    must "cos-min <= cos-min"{
                        description "The configuration is a range, 
                        for individual values min and max should 
                        be equal.";
                    }
                    key "cos-min cos-max";
                    uses policy-attr:cos-cfg;
                    description "Match Type COS-INNER configuration";
                }
                description "Match Type COS-INNER";
            }
        }
        
        case ipv4-acl-name-filter {
            if-feature policy-types:match-ipv4-acl-name-support;
            container ipv4-acl-name-cfgs {
                list ipv4-acl-name-cfg {
                    key "ip-acl-name";
                    uses policy-attr:ip-acl-name-cfg;
                    description "Match IPv4 Access-list name
                     configuration";
                }
                description "Match IPv4 Access-list name";
            }
        }
        
        case ipv6-acl-name-filter {
            if-feature policy-types:match-ipv6-acl-name-support;
            container ipv6-acl-name-cfgs{
                list ipv6-acl-name-cfg {
                    key "ip-acl-name";
                    uses policy-attr:ip-acl-name-cfg;
                    description "Match IPv6 Access-list name
                     configuration";
                }
                description "Match IPv6 Access-list name";
            }
        }
        
        case ipv4-acl-filter {
            if-feature policy-types:match-ipv4-acl-support;
            container ipv4-acl-cfgs {
                list ipv4-acl-cfg {
                    key "ip-acl";
                    uses policy-attr:ip-acl-cfg;       
                    description "Match IPv4 Access-list number
                     configuration";         
                }
                description "Match IPv4 Access-list number";
            }
        }
        
        case ipv6-acl-filter {
            if-feature policy-types:match-ipv6-acl-support;
            container ipv6-acl-cfgs {
                list ipv6-acl-cfg {
                    key "ip-acl";
                    uses policy-attr:ip-acl-cfg;     
                    description "Match IPv6 Access-list number
                     configuration";           
                }
                description "Match IPv6 Access-list number";
            }
        }
        
        case input-interface {
            if-feature policy-types:match-input-interface-support;
              container input-interface-cfgs {
                  list input-interface-cfg {
                      key "if-name";
                      uses policy-attr:input-interface-cfg;
                      description "Match type Input interface 
                      configuration";
                  }             
                  description "Match type Input interface"; 
              } 
        }
  
        case src-mac {
            if-feature policy-types:match-src-mac-support;
            container src-mac-cfgs {
                list src-mac-cfg{
                    key "mac";
                    uses policy-attr:mac-cfg;
                    description "Match Type Source MAC Address 
                    configuration";
                }
                description "Match Type Source MAC Address";
            }
        }
 
        case dst-mac {
            if-feature policy-types:match-dst-mac-support;
            container dst-mac-cfgs {
                list dst-mac-cfg{
                    key "mac";
                    uses policy-attr:mac-cfg;
                    description "Match Type Destination MAC Address
                     configuration";
                }
                description "Match Type Destination MAC Address";
            }
        }
        
        case protocol-name {
            if-feature policy-types:protocol-name-support;
            container protocol-name-cfgs {
                list protocol-name-cfg{
                    key "protocol-name";
                    uses policy-attr:protocol-name-cfg;
                    description "Match Type name-based protocol
                     configuration";
                }
                description "Match Type name-based protocol";
            }
        }
        case mpls-exp-top {
            if-feature policy-types:match-mpls-exp-top-support;
            container mpls-exp-top-cfgs {
                list mpls-exp-top-cfg{
                    must "exp-min <= exp-max" {
                        description "The configuration is a range, 
                        for individual values min and max should
                         be equal. ";
                    }
                    key "exp-min exp-max";
                    uses policy-attr:mpls-exp-cfg;
                    description "Match MPLS experimental Topmost 
                    configuration";
                }
                description "Match MPLS experimental Topmost";
            }
        }
        case mpls-exp-imp {
            if-feature policy-types:match-mpls-exp-imp-support;
            container mpls-exp-imp-cfgs{
                list mpls-exp-imp-cfg{
                    must "exp-min <= exp-max" {
                        description "The configuration is a range, 
                        for individual values min and max should
                         be equal. ";
                    }
                    key "exp-min exp-max";
                    uses policy-attr:mpls-exp-cfg;
                    description "Match MPLS experimental Imposition 
                    configuration";
                }
                description "Match MPLS experimental Imposition";
            }
        }
        case packet-length {
            if-feature policy-types:match-packet-length-support;
            container pkt-len-cfgs {
                list pkt-len-cfg{
                    must "min-pkt-len <= max-pkt-len" {
                        description "The configuration is a range, 
                        for individual values min and max should
                         be equal. ";
                    }
                    key "min-pkt-len max-pkt-len";
                    uses policy-attr:pkt-len-cfg;
                    description "Match Type Packet Length 
                    configuration";
                }
                description "Match Type Packet Length";
            }
        }
        case prec {
            if-feature policy-types:match-prec-support;
            container prec {
                choice prec-par {
                    case prec-value{
                        container prec-val-cfgs {
                            list prec-val-cfg{
                                key "prec-val";
                                uses policy-attr:prec-val-cfg;
                                description "Match Type Precedence 
                                based on value configuration";
                            } 
                            description "Match Type Precedence 
                                based on value";
                        }
                    }
                    case prec-attr{
                        container prec-attr-cfgs {
                            list prec-attr-cfg{
                                key "prec-attr";
                                uses policy-attr:prec-attr-cfg;
                                description "Match Type Precedence 
                                based on attribute configuration";
                            }
                            description "Match Type Precedence 
                                based on attribute";
                        }
                    }
                    description "Match Type Precedence in 
                IPv4 and IPv6 packets based on value or attribute";
                }
                description "Match Type Precedence in 
                IPv4 and IPv6 packets";
            }
        }
        case qos-group {
            if-feature policy-types:match-qos-group-support;
            container qos-group-cfgs {
                list qos-group-cfg {
                    must "qos-group-min<qos-group-max" {
                        description "The configuration is a range, 
                        for individual values min and max should
                         be equal. ";
                    }
                    key "qos-group-min qos-group-max";
                    uses policy-attr:qos-group-cfg;
                    description "Match Type QoS Group configuration";
                }
                description "Match Type QoS Group";              
            }
        }
        
        case vlan {
            if-feature policy-types:match-vlan-support;
            container vlan-cfgs {
                list vlan-cfg {
                    must "vlan-min<=vlan-max" {
                        description "The configuration is a range, 
                        for individual values min and max should
                         be equal. ";
                    }
                    key "vlan-min vlan-max";
                    uses policy-attr:vlan-cfg;
                    description "Match Type VLAN configuration";
                }
                description "Match Type VLAN"; 
            }
        }
        case vlan-inner {
            if-feature policy-types:match-vlan-inner-support;
            container vlan-inner-cfgs {
                list vlan-inner-cfg {
                    must "vlan-min<=vlan-max" {
                        description "The configuration is a range, 
                        for individual values min and max should
                         be equal. ";
                    }
                    key "vlan-min vlan-max";
                    uses policy-attr:vlan-cfg;
                    description "Match Type Inner VLAN 
                    configuration";
                }
                description "Match Type Inner VLAN"; 
            }
        }
        //Not in IOS/XE asr1k
        case atm-clp {
            if-feature policy-types:match-atm-clp-support;
            container atm-clp-cfg {
                uses policy-attr:atm-clp-cfg;
                description "Match ATM Cell Loss Priority (CLP)";
            }
        }
        case atm-vci {
            if-feature policy-types:match-atm-vci-support;
            container atm-vci-cfgs {
                list atm-vci-cfg{
                    must "atm-vci-min<=atm-vci-max" {
                        description "The configuration is a range, 
                        for individual values min and max should
                         be equal. ";
                    }
                    key "atm-vci-min atm-vci-max";
                    uses policy-attr:atm-vci-cfg; 
                    description "Match ATM Virtual Channel 
                    Identifier (VCI) configuration";
                }
                description "Match ATM Virtual Channel Identifier 
                (VCI)";
            }
        }
        //Not in IOS/XE asr1k
        case dei {
            if-feature policy-types:match-dei-support;
            container dei-cfg{
                uses policy-attr:dei-cfg;
                description "Match Type DEI Bit configuration";
            }
        }
        //Not in IOS/XE asr1k
        case dei-inner {
            if-feature policy-types:match-dei-inner-support;
            container dei-inner-cfg{
                uses policy-attr:dei-cfg;
                description "Match Type Inner DEI Bit";
            }
        }
        //Not in IOS/XE asr1k
        case flow-ip{
            if-feature policy-types:match-flow-ip-support;
            container flow-ip-cfg{
                uses policy-attr:flow-cfg;
                description "Match Type flow";
            }
        }
        //Not in IOS/XE asr1k
        case flow-record {
            container flow-record-cfg{
                uses policy-attr:flow-record-cfg;
                description "Match Type flow Record Name";
            }
        }
        case fr-de {
            if-feature policy-types:match-fr-de-support;
            container fr-de-cfg {
                uses policy-attr:fr-de-cfg;
                description "Match Frame Relay DE";
            }
        }
        case fr-dlci {
            if-feature policy-types:match-fr-dlci-support;
            container fr-dlci-cfgs {
                list fr-dlci-cfg{
                    must "dlci-min<=dlci-max" {
                        description "The configuration is a range, 
                        for individual values min and max should
                         be equal. ";
                    }
                    key "dlci-min dlci-max";
                    uses policy-attr:fr-dlci-cfg;  
                    description "Match Frame Relay DLCI 
                    configuration";
                }
                description "Match Frame Relay DLCI";
            }
        }
        //Not in IOS/XE asr1k
        case wlan-user-priority {
            if-feature policy-types:match-wlan-user-priority-support;
            container wlan-user-priority-cfgs {
                list wlan-user-priority-cfg{
                    must "wlan-prio-min<=wlan-prio-max" {
                        description "The configuration is a range, 
                        for individual values min and max should
                         be equal. ";
                    }
                    key "wlan-prio-min wlan-prio-max";
                    uses policy-attr:wlan-user-priority-cfg;
                    description "Match Type Wlan User Priority 
                    configuration";
                }
                description "Match Type Wlan User Priority";
            }
        }

        case discard-class {
            if-feature policy-types:match-discard-class-support;
            container discard-class-cfgs {
                list discard-class-cfg{
                    key "discard-class";
                    uses policy-attr:discard-class-cfg;
                    description "Match Type Discard Class 
                    configuration";
                }
                description "Match Type Discard Class";
            }
        }

        case class-map {
            if-feature policy-types:match-class-map-support;
            container class-map-cfgs {
                list class-map-cfg{
                    key "class-map-name";
                    uses policy-attr:class-map-cfg;
                    description "Match Type cls-map Name 
                    configuration";
                }
                description "Match Type cls-map Name";
            }
        }

        case metadata {
            if-feature policy-types:match-metadata-support;
            container metadata-cfg {
                uses policy-attr:metadata-cfg;
                description "Match Type Metadata";
            }
        }
        
        case application{
            if-feature policy-types:match-application-support;
            container application-cfgs { 
                list application-cfg{
                    key "application-name application-cfg";
                    uses policy-attr:application-cfg;
                    description "Match Type Application 
                    configuration";
                }
                description "Match Type Application";    
            }
        }  
        case security-group {
            if-feature policy-types:match-security-group-support;
            container security-group {
                choice group-par {
                    case group-name{
                        container security-group-name-cfgs {
                            list security-group-name-cfg{
                                key "src-dst security-name";
                                uses policy-attr:security-group-name-cfg;
                                description "Match Type security 
                                group based on name configuration";
                            }                           
                            description "Match Type security 
                            group based on name";
                        }
                    }
                    case group-tag{
                        container security-group-tag-cfgs {
                            list security-group-tag-cfg{
                                key "id";
                                uses policy-attr:security-group-tag-cfg;
                                description "Match Type security 
                                group based on tag configuration";
                            }     
                            description "Match Type security 
                            group based on tag";                   
                        }
                    }
                    description "Match Type security tag 
                    based on tag or id.";
                }
                description "Match Type security tag.";
            }
        }
        
        case ip-rtp {
            if-feature policy-types:match-ip-rtp-support;
            container ip-rtp-cfgs { 
                list ip-rtp-cfg{
                    must "starting-port-number<=port-range" {
                        description "The configuration is lower 
                        bound and range of UDP ports.";
                    }
                    key "starting-port-number port-range";
                    uses policy-attr:ip-rtp-cfg;
                    description "Match Type IP RTP configuration.";
                }
                description "Match Type IP RTP.";
            }
        }
        
        case vpls {
            if-feature policy-types:match-vpls-support;
            container vpls-cfg {
                uses policy-attr:vpls-cfg;
                description "Match Type VPLS.";
            }
        }
    }   
}
