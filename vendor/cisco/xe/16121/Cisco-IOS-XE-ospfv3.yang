module Cisco-IOS-XE-ospfv3 {
  namespace "http://cisco.com/ns/yang/Cisco-IOS-XE-ospfv3";
  prefix ios-ospfv3;

  import cisco-semver {
    prefix cisco-semver;
  }

  import ietf-inet-types {
    prefix inet;
  }


  import Cisco-IOS-XE-types {
    prefix ios-types;
  }

  import Cisco-IOS-XE-native {
    prefix ios;
  }

  import Cisco-IOS-XE-interface-common {
    prefix ios-ifc;
  }

  import Cisco-IOS-XE-features {
    prefix ios-features;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Open Shortest Path First (OSPFv3) Yang model.
     Copyright (c) 2016-2017 by Cisco Systems, Inc.
     All rights reserved.";

  // =========================================================================
  // REVISION
  // =========================================================================
  revision 2019-07-01 {
    description 
      "- Establish semantic version baseline
       - Updated range of distance for different address families";
    cisco-semver:module-version "1.0.0";
  }
  revision 2019-01-22 {
     description
      "Added leaf for App-hosting Gigabit Ethernet interface";
  }
  revision 2018-11-07 {
      description
      "Cleanup spelling errors in description statements";
  }
  revision 2018-07-28{
    description
        "Support on vlan interface";
  }
  revision 2018-06-28{
    description
        "Added must constraints for deleting vrf";
  }

  revision 2017-11-27 {
     description
       "Added Change 25GE name";
  }

  revision 2017-11-14 {
    description
      "This revision has changes for new 40 and 100GE interface addition";
  }

  revision 2017-09-15 {
    description
      "This revision has changes for new 2gig interface addition";
  }
  revision 2017-08-16 {
    description
      "This revision has changes for new 5gig and 25gig interfaces addition";
  }

  revision 2017-04-28 {
    description
      "inet:ipv6-prefix changed to ios-types:ipv6-prefix";
  }
  revision 2017-04-20 {
    description
      "Remove tailf:cli-flatten-container for address-family ipv4 unicast option";
  }

  revision 2017-02-07 {
    description
      "Initial revision";
  }

  grouping ospf-redistribute-grouping {
    container redist-options {
      uses ospf-iso-igrp-redistribute-grouping;
      leaf route-map {
        description
          "Route map reference";
        type string;
      }
      leaf nssa-only {
        description
          "Limit redistributed routes to NSSA areas";
        type empty;
      }
    }
  }

  grouping ospf-redistribute-grouping-deprecated {
    status deprecated;
    container redist-options {
      status deprecated;
      uses ospf-iso-igrp-redistribute-grouping-deprecated {
        status deprecated;
      }
      leaf route-map {
        status deprecated;
        description
          "Route map reference";
        type string;
      }
      leaf nssa-only {
        status deprecated;
        description
          "Limit redistributed routes to NSSA areas";
        type empty;
      }
    }
  }

  grouping ospf-redistribute-grouping-obsolete {
    status obsolete;
    container redist-options {
      status obsolete;
      uses ospf-iso-igrp-redistribute-grouping-obsolete {
        status obsolete;
      }
      leaf route-map {
        status obsolete;
        description
          "Route map reference";
        type string;
      }
      leaf nssa-only {
        status obsolete;
        description
          "Limit redistributed routes to NSSA areas";
        type empty;
      }
    }
  }

  grouping ospfv3-ipv6-redistribute-top-grouping {
    container application-config {
      presence "true";
      description
        "Application";
      uses ospf-redistribute-grouping;
    }
    list application {
      status deprecated;
      description
        "Application";
      key "name";
      leaf name {
        status deprecated;
        type string;
      }
      uses ospf-redistribute-grouping-deprecated {
        status deprecated;
      }
    }
    list bgp {
      description
        "Border Gateway Protocol (BGP)";
      
      max-elements "1";
      key "as-number";
      uses ospf-redistribute-bgp-grouping;
    }
    container connected {
      description
        "Connected";
      presence "Connected";
      uses ospf-redistribute-grouping;
    }
    list eigrp-config {
      description
        "Enhanced Interior Gateway Routing Protocol (EIGRP)";
      key "as-number";
      leaf as-number {
        type uint32 {
          range "1..65535";
        }
      }
      uses ospf-redistribute-grouping;
    }
    list eigrp {
      status deprecated;
      description
        "Enhanced Interior Gateway Routing Protocol (EIGRP)";
      key "as-number";
      uses ospf-redistribute-bgp-grouping-deprecated {
        status deprecated;
      }
    }
    container isis {
      presence "ISO IS-IS";
      description
        "ISO IS-IS";
      choice isis-level-routes-isis-area-choice {
        leaf isis-level-routes {
          type enumeration {
            enum "level-1";
            enum "level-2";
            enum "level-1-2";
          }
        }
        list isis-area {
          key "name";
          leaf name {
            type string;
          }
          leaf isis-level-routes {
            type enumeration {
              enum "level-1";
              enum "level-2";
              enum "level-1-2";
            }
          }
          uses ospf-redistribute-grouping;
        }
      }
      uses ospf-redistribute-grouping;
    }
    container iso-igrp {
      status obsolete;
      description
        "IGRP for OSI networks";
      presence "IGRP for OSI networks";
      choice area-tag-route-map-choice {
        status obsolete;
        container area-tag-route-map-container {
          status obsolete;
          leaf area-tag {
            status obsolete;
            type string;
          }
          leaf route-map {
            status obsolete;
            description
              "Route map reference";
            type string;
          }
        }
        leaf route-map {
          status obsolete;
          description
            "Route map reference";
          type string;
        }
      }
      container iso-igrp-container {
        status obsolete;
        uses ospf-iso-igrp-redistribute-grouping-obsolete {
          status obsolete;
        }
      }
    }
    container lisp-config {
      description
        "Locator ID Separation Protocol (LISP)";
      presence "true";
      uses ospf-redistribute-grouping;
    }
    container lisp {
      description
        "Locator ID Separation Protocol (LISP)";
      status deprecated;
      uses ospf-redistribute-grouping-deprecated {
        status deprecated;
      }
    }
    container nd {
      description
        "Neighbour Discovery";
       presence "nd";
       uses ospf-redistribute-grouping;
    }
    container mobile {
      status obsolete;
      description
        "Mobile routes";
      presence "Mobile routes";
      uses ospf-redistribute-grouping-obsolete{
        status obsolete;
      }
    }
    container nat-route-config {
      if-feature ios-features:sdwan;
      description
        "NAT Route";
      presence "true";
      leaf dia {
        description
          "Redistribute NAT Direct Internet Access routes";
        type empty;
      }
      leaf outside {
        description
          "Redistribute NAT outside routes";
        type empty;
      }
      uses ospf-redistribute-grouping;
    }
    container nat-route {
      status deprecated;
      if-feature ios-features:sdwan;
      description
        "NAT Route";
      leaf dia {
        status deprecated;
        description
          "Redistribute NAT Direct Internet Access routes";
        type empty;
      }
      leaf outside {
        status deprecated;
        description
          "Redistribute NAT outside routes";
        type empty;
      }
      uses ospf-redistribute-grouping-deprecated {
        status deprecated;
      }
    }
    container odr {
      status obsolete;
      description
        "On Demand stub Routes";
      presence "On Demand stub Routes";
      uses ospf-redistribute-grouping-obsolete{
        status obsolete;
      }
    }
    container omp {
      description
        "Overlay Management Protocol (OMP)";
       presence "omp";
       uses ospf-redistribute-grouping;
    }
    list ospf {
      description
        "Open Shortest Path First (OSPF)";
      key "id";
      leaf id {
        type uint32 {
          range "1 .. 65535";
        }
      }
      uses ospf-redistribute-top-match-grouping;
      uses ospf-redistribute-match-grouping;
      leaf vrf {
        description
          "VPN Routing/Forwarding Instance";
        must "/ios:native/ios:vrf/ios:definition[ios:name=current()] or /ios:native/ios:ip/ios:vrf[ios:name=current()]" {
          error-message "VRF must be created 1st, deleted last";
        }
        type string;
      }
    }
    list ospfv3 {
      status obsolete;
      description
        "OSPFv3";
      key "id";
      leaf id {
        status obsolete;
        type uint32 {
          range "1 .. 65535";
        }
      }
      uses ospf-redistribute-top-match-grouping-obsolete {
        status obsolete;
      }
      uses ospf-redistribute-match-grouping-obsolete {
        status obsolete;
      }
    }
    list rip {
      description
        "Routing Information Protocol (RIP)";
      key "id";
      leaf id {
        description
          "User selected string identifying this rip process";
        type string;
      }
      uses ospf-redistribute-grouping;
    }
    container static {
      description
        "Static routes";
      presence "Static routes";
      uses ospf-redistribute-grouping;
    }
  }
  grouping ospfv3-common-address-family-vrf-grouping {
    container redistribute {
      description
        "Redistribute information from another routing protocol";
      uses ospf-redistribute-top-grouping;
      container maximum-prefix {
        description
          "Maximum number of prefixes redistributed to protocol";
        leaf number {
          type uint32 {
            range "1 .. 4294967295";
          }
        }
        container threshold-warning-only-container {
          leaf threshold {
            type uint32 {
              range "1 .. 100";
            }
          }
          leaf warning-only {
            description
              "Only give warning message when limit is exceeded";
            type empty;
          }
        }
      }
      container vrf {
        description
          "Specify a source VRF";
        list non-global-vrf {
          key "name";
          leaf name {
      must "/ios:native/ios:vrf/ios:definition[ios:name=current()] or /ios:native/ios:ip/ios:vrf[ios:name=current()]" {
        error-message "VRF must be created 1st, deleted last";
            }
            type string;
          }
          uses ospf-redistribute-top-grouping;
        }
        container global {
          description
            "global VRF";
          uses ospf-redistribute-top-grouping;
        }
      }
    }
  }

  grouping ospfv3-ipv6-address-family-vrf-grouping {
    container redistribute {
      description
        "Redistribute information from another routing protocol";
      uses ospfv3-ipv6-redistribute-top-grouping;
      container maximum-prefix {
        description
          "Maximum number of prefixes redistributed to protocol";
        leaf number {
          type uint32 {
            range "1 .. 4294967295";
          }
        }
        container threshold-warning-only-container {
          leaf threshold {
            type uint32 {
              range "1 .. 100";
            }
          }
          leaf warning-only {
            description
              "Only give warning message when limit is exceeded";
            type empty;
          }
        }
      }
      container vrf {
        status obsolete;
        description
          "Specify a source VRF";
        list non-global-vrf {
          status obsolete;
          key "name";
          leaf name {
            status obsolete;
                 must "/ios:native/ios:vrf/ios:definition[ios:name=current()] or /ios:native/ios:ip/ios:vrf[ios:name=current()]" {
                   error-message "VRF must be created 1st, deleted last";
            }
            type string;
          }
          uses ospf-redistribute-top-grouping-obsolete{
            status obsolete;
          }
        }
        container global {
          status obsolete;
          description
            "global VRF";
          uses ospf-redistribute-top-grouping-obsolete{
            status obsolete;
          }
        }
      }
    }
  }

  grouping ospfv3-authentication-key-grouping {
    status deprecated;
    container authentication-key {
      status deprecated;
      description
        "Set authentication key";
      leaf auth-type {
        status deprecated;
        type uint8 {
          range "0 .. 7";
        }
      }
      leaf auth-key {
        status deprecated;
        type string;
      }
    }
  }

  grouping ospfv3-spi-md5-sha1-authentication-grouping {

    choice md5-sha1-choice {

      container md5 {
        description
          "Use MD5 authentication";
        when "../spi";  
        leaf encrypt-type {
          description
            "Encryption type (0 - is not encrypted, 7 is encrypted)";
          type enumeration {
            enum "0";
            enum "7";
          }
        }
        leaf hex-string {
          description
            "MD5 key (32 chars)";
          type string {
            pattern "[0-9a-fA-F]{32}";
          }
        }
      }

      container sha1 {
        description
          "Use SHA-1 authentication";
        when "../spi";  
        leaf encrypt-type {
          description
            "Encryption type (0 - is not encrypted, 7 is encrypted)";
          type enumeration {
            enum "0";
            enum "7";
          }
        }
        leaf hex-string {
          description
            "SHA-1 key (40 chars)";
          type string {
            pattern "[0-9a-fA-F]{40}";
          }
        }
      }
    }
  }

  grouping ospfv3-md5-sha1-authentication-grouping {

    choice md5-sha1-choice {

      container md5 {
        description
          "Use MD5 authentication";
        leaf encrypt-type {
          description
            "Encryption type (0 - is not encrypted, 7 is encrypted)";
          type enumeration {
            enum "0";
            enum "7";
          }
        }
        leaf hex-string {
          description
            "MD5 key (32 chars)";
          type string {
            pattern "[0-9a-fA-F]{32}";
          }
        }
      }

      container sha1 {
        description
          "Use SHA-1 authentication";
        leaf encrypt-type {
          description
            "Encryption type (0 - is not encrypted, 7 is encrypted)";
          type enumeration {
            enum "0";
            enum "7";
          }
        }
        leaf hex-string {
          description
            "SHA-1 key (40 chars)";
          type string {
            pattern "[0-9a-fA-F]{40}";
          }
        }
      }
    }
  }

  grouping interface-ospfv3-encryption-grouping {

    container encryption-config {
      description
        "Enable encryption";

      choice encryption-choice {
        leaf null {
          description
            "No IPsec encryption on this interface";
          type empty;
        }

        container ipsec {
          description
            "Use IPsec encryption";
          leaf spi {
            description
              "Set the SPI (Security Parameters Index)";
            type uint64 {
              range "256..4294967295";
            }
          }

          container esp {
            description
              "Use ESP encapsulation";
            when "../spi";
            choice encryption-type {

              container encrypt-3des {
                description
                  "Use 3DES encryption";
                leaf encrypt-type {
                  description
                    "Encryption type (0 - is not encrypted, 7 is encrypted)";
                  type enumeration {
                    enum "0";
                    enum "7";
                  }
                }
                leaf hex-string {
                  description
                    "192 bit key (48 chars)";
                  type string {
                    pattern "[0-9a-fA-F]{48}";
                  }
                }
                uses ospfv3-md5-sha1-authentication-grouping;
              }

              container aes-cbc {
                description
                  "Use AES-CBC encryption";

                choice aes-choice {

                  container aes-128 {
                    description
                      "Use 128 bit key";
                    leaf encrypt-type {
                      description
                        "Encryption type (0 - is not encrypted, 7 is encrypted)";
                      type enumeration {
                        enum "0";
                        enum "7";
                      }
                    }
                    leaf hex-string {
                      description
                        "128 bit key (32 chars)";
                      type string {
                        pattern "[0-9a-fA-F]{32}";
                      }
                    }
                    uses ospfv3-md5-sha1-authentication-grouping; 
                  }

                  container aes-192 {
                    description
                      "Use 192 bit key";
                    leaf encrypt-type {
                      description
                        "Encryption type (0 - is not encrypted, 7 is encrypted)";
                      type enumeration {
                        enum "0";
                        enum "7";
                      }
                    }
                    leaf hex-string {
                      description
                        "192 bit key (48 chars)";
                      type string {
                        pattern "[0-9a-fA-F]{48}";
                      }
                    }
                    uses ospfv3-md5-sha1-authentication-grouping; 
                  }

                  container aes-256 {
                    description
                      "Use 128 bit key";
                    leaf encrypt-type {
                      description
                        "Encryption type (0 - is not encrypted, 7 is encrypted)";
                      type enumeration {
                        enum "0";
                        enum "7";
                      }
                    }
                    leaf hex-string {
                      description
                        "256 bit key (64 chars)";
                      type string {
                        pattern "[0-9a-fA-F]{64}";
                      }
                    }
                    uses ospfv3-md5-sha1-authentication-grouping; 
                  }
                }
              }

              container des {
                description
                  "Use DES encryption";
                leaf encrypt-type {
                  description
                    "Encryption type (0 - is not encrypted, 7 is encrypted)";
                  type enumeration {
                    enum "0";
                    enum "7";
                  }
                }
                leaf hex-string {
                  description
                    "64 bit key (16 chars)";
                  type string {
                    pattern "[0-9a-fA-F]{16}";
                  }
                }
                uses ospfv3-md5-sha1-authentication-grouping;
              }

              container null {
                description
                  "ESP with no encryption";
                uses ospfv3-md5-sha1-authentication-grouping;
              }
            }
          }
        }
      }
    }
    container encryption {
      description
        "Enable encryption (DEPRECATED, use encryption-config)";
      status deprecated;
      leaf null {
        status deprecated;
        description
          "No IPsec encryption on this interface";
        type empty;
      }
      container ipsec {
        status deprecated;
        description
          "Use IPsec encryption";
        leaf spi {
          status deprecated;
          description
            "Set the SPI (Security Parameters Index)";
          type uint64 {
            range "256..4294967295";
          }
        }
        leaf esp {
          status deprecated;
          description
            "Use ESP encapsulation";
          type empty;
        }
        container ipsec_3des {
          status deprecated;
          description
            "Use 3DES encryption";
          container key-string {
            status deprecated;
            leaf encrypt {
            status deprecated;
              type enumeration {
                enum "0";
                enum "7";
              }
            }
            leaf string {
              status deprecated;
              type string;
            }
          }
        }
        container aes-cbc {
          status deprecated;
          description
            "Use AES-CBC encryption";
          container aes-cbc-128 {
            status deprecated;
            description
              "Use 128 bit key";
            container key-string {
              status deprecated;
              leaf encrypt {
                status deprecated;
                type enumeration {
                  enum "0";
                  enum "7";
                }
              }
              leaf string {
                status deprecated;
                type string;
              }
            }
          }
          container aes-192 {
            status deprecated;
            description
              "Use 192 bit key";
            container key-string {
              status deprecated;
              leaf encrypt {
                status deprecated;
                type enumeration {
                  enum "0";
                  enum "7";
                }
              }
              leaf string {
                status deprecated;
                type string;
              }
            }
          }
          container aes-256 {
            status deprecated;
            description
              "Use 256 bit key";
            container key-string {
              status deprecated;
              leaf encrypt {
                status deprecated;
                type enumeration {
                  enum "0";
                  enum "7";
                }
              }
              leaf string {
                status deprecated;
                type string;
              }
            }
          }
        }
      }
    }
  }

  grouping interface-ospfv3-authentication-grouping {
    container authentication-config {
      description
        "Enable authentication";
      leaf key-chain {
        description
          "Use a key-chain for cryptographic authentication keys";
        type string;
      }
      choice authentication-choice {
        leaf null {
          description
            "Use no authentication";
          type empty;
        }
        container ipsec {
          description
            "Use IPsec authentication";
          leaf spi {
            description
              "Set the SPI (Security Parameters Index)";
            type uint64 {
              range "256..4294967295";
            }
          }
          uses ospfv3-spi-md5-sha1-authentication-grouping;
        }
      }
    }
  }

  grouping authentication-ipsec-grouping {
    status deprecated;
    container ipsec {
      status deprecated;
      description
        "Use IPsec authentication";
      leaf spi {
        status deprecated;
        description
          "Set the SPI (Security Parameters Index)";
        type uint64 {
          range "256..4294967295";
        }
      }
      container md5 {
        status deprecated;
        description
          "Use MD5 authentication";
        container key-string {
          status deprecated;
          leaf encrypt {
            status deprecated;
            type enumeration {
              enum "0";
              enum "7";
            }
          }
          leaf string {
            status deprecated;
            type string;
          }
        }
      }
      container sha1 {
        status deprecated;
        description
          "Use SHA-1 authentication";
        container key-string {
          status deprecated;
          leaf encrypt {
            status deprecated;
            type enumeration {
              enum "0";
              enum "7";
            }
          }
          leaf string {
            status deprecated;
            type string;
          }
        }
      }
    }
  }

  grouping interface-ospfv3-transmit-delay-grouping {
    leaf transmit-delay {
      description
        "Link state transmit delay";
      type uint32 {
        range "1..65535";
      }
      default "1";
    }
  }

  grouping interface-ospfv3-priority-grouping {
    leaf priority {
      description
        "Router priority";
      type uint8 {
        range "0..255";
      }
      default "1";
    }
  }

  grouping interface-ospfv3-retransmit-interval-grouping {
    leaf retransmit-interval {
      description
        "Time between retransmitting lost link state advertisements";
      type uint32 {
        range "1..65535";
      }
      default "5";
    }
  }

  grouping interface-ospfv3-prefix-suppression-grouping {
    container prefix-suppression {
      description
        "OSPF prefix suppression";
      presence "true";
      leaf disable {
        description
          "Disable prefix suppression";
        type empty;
      }
    }
  }

  grouping interface-ospfv3-network-grouping {

    container network-type {
      description
        "Network type";
      choice network-type-choice {
        leaf broadcast {
          description
            "Specify OSPF broadcast multi-access network";
          type empty;
        }
        leaf manet {
          description
            "Specify MANET OSPF interface type";
          type empty;
        }
        leaf non-broadcast {
          description
            "Specify OSPF NBMA network";
          type empty;
        }
        container point-to-multipoint {
          description
            "Specify OSPF point-to-multipoint network";
          presence "true";
          leaf non-broadcast {
            description
              "Specify non-broadcast point-to-mpoint network";
            type empty;
          }
        }
        leaf point-to-point {
          description
            "Specify OSPF point-to-point network";
          type empty;
        }
      }
    }

    container network {
      status deprecated;
      description
        "Network type (DEPRECATED, use network-type)";
      leaf broadcast {
        status deprecated;
        description
          "Specify OSPF broadcast multi-access network";
        type empty;
      }
      leaf manet {
        status deprecated;
        description
          "Specify MANET OSPF interface type";
        type empty;
      }
      leaf non-broadcast {
        status deprecated;
        description
          "Specify OSPF NBMA network";
        type empty;
      }
      container point-to-multipoint {
        status deprecated;
        description
          "Specify OSPF point-to-multipoint network";
        presence "true";
        leaf non-broadcast {
          status deprecated;
          description
            "Specify non-broadcast point-to-mpoint network";
          type empty;
        }
      }
      leaf point-to-point {
        status deprecated;
        description
          "Specify OSPF point-to-point network";
        type empty;
      }
    }
  }

  grouping interface-ospfv3-neighbor-grouping {
    list neighbor {
      description
        "OSPF neighbor";
      ordered-by user;
      must "count(*) > 1" {
      }
      key "id";
      leaf id {
        type inet:ipv6-address;
      }
      leaf cost {
        description
          "OSPF cost for point-to-multipoint neighbor";
        type uint16 {
          range "1..65535";
        }
      }
      container database-filter {
        description
          "Filter OSPF LSA during synchronization and flooding for point-to-multipoint neighbor";
        choice database {
          leaf all {
            description
              "Filter all LSA";
            type enumeration {
              enum "out";
            }
          }
        }
      }
      leaf poll-interval {
        description
          "OSPF dead-router polling interval";
        type uint32 {
          range "0..65535";
        }
      }
      leaf priority {
        description
          "OSPF priority of non-broadcast neighbor";
        type uint8 {
          range "0..255";
        }
      }
    }
  }

  grouping interface-ospfv3-hello-interval-grouping {
    leaf hello-interval {
      description
        "Time between HELLO packets";
      type uint32 {
        range "1..65535";
      }
      default "10";
    }
  }

  grouping interface-ospfv3-dead-interval-grouping {
    leaf dead-interval {
      description
        "Interval after which a neighbor is declared dead";
      type uint16 {
        range "1..65535";
      }
      default "40";
    }
  }

  grouping interface-ospfv3-bfd-grouping {
    container bfd {
      description
        "Enable BFD on this interface";
      presence "true";
      leaf disable {
        description
          "Disable BFD on this interface";
        type empty;
      }
    }
  }

  grouping ospfv3-ipv6-distance-grouping {
    container distance-ipv6 {
      description
        "Define an administrative distance";
      leaf distance {
        type uint32 {
          range "1 .. 254";
        }
        default "110";
      }
      container ospf {
        description
          "OSPF routes Administrative distance";
        leaf external {
          description
            "External routes";
          type uint32 {
            range "1 .. 254";
          }
        }
        leaf inter-area {
          description
            "Inter-area routes";
          type uint32 {
            range "1 .. 254";
          }
        }
        leaf intra-area {
          description
            "Intra-area routes";
          type uint32 {
            range "1 .. 254";
          }
        }
      }
    }
  }

  grouping ospfv3-ipv4-distance-grouping {
    container distance-ipv4 {
      description
        "Define an administrative distance";
      leaf distance {
        type uint32 {
          range "1 .. 255";
        }
        default "110";
      }
    }
  }

  grouping ospfv3-common-address-family-grouping {
    container capability {
      status deprecated;
      description
        "Enable specific OSPF feature";
      leaf capability-type {
        status deprecated;
        description "capability-type (DEPRECATED, use capability)";
        type enumeration {
          enum "lls";
          enum "opaque";
          enum "transit";
          enum "vrf-lite";
        }
      }
    }
    container compatible {
      description
        "OSPF compatibility list";
      leaf rfc1583 {
        description
          "Compatible with RFC 1583";
        type boolean;
        default "true";
      }
      leaf rfc1587 {
        description
          "Compatible with RFC 1587";
        type boolean;
        default "false";
      }
      leaf rfc5243 {
        description
          "Compatible with RFC 5243";
        type boolean;
        default "true";
      }
    }
    container default-information {
      description
        "Control distribution of default information";
      container originate {
        description
          "Distribute a default route";
        presence "Distribute a default route";
        leaf always {
          description
            "Always advertise default route";
          type empty;
        }
        leaf metric {
          description
            "OSPF default metric";
          type uint32 {
            range "0 .. 16777214";
          }
        }
        leaf metric-type {
          description
            "OSPF metric type for default routes";
          type ios-types:ospf-metric-type;
        }
        leaf route-map {
          description
            "Route map reference";
          type string;
        }
      }
    }
    leaf default-metric {
      description
        "Set metric of redistributed routes";
      type uint32 {
        range "1 .. 16777214";
      }
    }

    container discard-route-config {
      description
        "Enable or disable discard-route installation";
      leaf external {
        description
          "Discard route for summarised redistributed routes";
        type boolean;
        default "true";
      }
      leaf internal {
        description
          "Discard route for summarised inter-area routes";
        type boolean;
        default "true";
      }
    }

    container discard-route {
      status deprecated;
      description
        "Enable or disable discard-route installation (DEPRECATED, use discard-route-config)";
      presence "Enable or disable discard-route installation";
      leaf external {
        status deprecated;
        description
          "Discard route for redistributed summarised routes";
        type empty;
      }
      leaf internal {
        status deprecated;
        description
          "Discard route for summarised internal routes";
        type empty;
      }
      leaf metric {
        status obsolete;
        type uint32 {
          range "1 .. 255";
        }
      }
    }

    container distance {
      status deprecated;
      description
        "Define an administrative distance (DEPRECATED, use
        distance-ipv4/distance-ipv6)";
      container ospf-distance {
        status deprecated;
        leaf distance {
          status deprecated;
          type uint32 {
            range "1 .. 255";
          }
        }
        leaf ip {
          status deprecated;
          type inet:ipv4-address;
        }
        leaf wildcard {
          status deprecated;
          type inet:ipv4-address;
        }
        leaf acl-name {
          status deprecated;
          type ios-types:access-list-standard-id-type;
        }
      }
      container ospf {
        status deprecated;
        description
          "OSPF routes Administrative distance (DEPRECATED, use ospf under
          distance-ipv4/distance-ipv6)";
        leaf external {
          status deprecated;
          description
            "External routes";
          type uint32 {
            range "1 .. 255";
          }
        }
        leaf inter-area {
          status deprecated;
          description
            "Inter-area routes";
          type uint32 {
            range "1 .. 255";
          }
        }
        leaf intra-area {
          status deprecated;
          description
            "Intra-area routes";
          type uint32 {
            range "1 .. 255";
          }
        }
      }
    }
    leaf maximum-paths {
      description
        "Forward packets over multiple paths";
      type uint32 {
        range "1 .. 32";
      }
    }
  }

  grouping ospfv3-af-area-ipv6-vlink-grouping {
    list virtual-link {
      when "not(../area-id = '0')";
      description
        "Define a virtual link and its parameters";
      key "id";
      leaf id {
        type inet:ip-address;
      }
      container authentication {
        description
          "Set authentication type";
        choice authentication-choice {
          leaf key-chain {
            description
              "Use a key-chain for cryptographic authentication keys";
            type string;
          }
          leaf null {
            description
              "No authentication";
            type empty;
          }
        }
      }
      leaf hello-interval {
        description
          "Hello packet interval";
        type int32 {
          range "1 .. 8192";
        }
      }
      leaf dead-interval {
        description
          "Dead router detection time";
        type uint16 {
          range "1 .. 8192";
        }
      }
      leaf retransmit-interval {
        description
          "LSA retransmit interval";
        type uint16 {
          range "1 .. 8192";
        }
      }
      leaf transmit-delay {
        description
          "LSA transmission delay";
        type uint16 {
          range "1 .. 8192";
        }
      }
      container ttl-security {
        description
          "TTL security check";
        leaf hops {
          description
            "IP hops";
          type uint8 {
            range "1..254";
          }
        }
      }
    }
  }

  grouping ospfv3-af-area-common-vrf-grouping {
    list sham-link {
      description
        "Define a sham link and its parameters";
      key "source dest";
      leaf source {
        type inet:ip-address;
      }
      leaf dest {
        type inet:ip-address;
      }
      leaf cost {
        description
          "Associate a cost with the sham-link";
        type uint16 {
          range "0 .. 65535";
        }
      }
      container ttl-security {
        description
          "TTL security check";
        leaf hops {
          description
            "IP hops";
          type uint8;
        }
      }
    }
  }

  grouping ospfv3-area-common-grouping {
    leaf default-cost {
      when "not(../area-id = '0')";
      description
        "Set the summary default-cost of a NSSA/stub area";
      type uint32 {
        range "0 .. 16777214";
      }
    }
    container nssa {
      when "not(../area-id = '0')";
      description
        "Specify a NSSA area";
      presence "Specify a NSSA area";
      container default-information-originate {
        description
          "Originate Type 7 default into NSSA area";
        presence "Originate Type 7 default into NSSA area";
        leaf metric {
          description
            "OSPF default metric";
          type int32 {
            range "0 .. 16777214";
          }
        }
        leaf metric-type {
          description
            "OSPF metric type for default routes";
          type ios-types:ospf-metric-type;
        }
        leaf no-redistribution {
          description
            "No redistribution into this NSSA area";
          type empty;
        }
        leaf no-summary {
          description
            "Do not send summary LSA into NSSA";
          type empty;
        }
        leaf nssa-only {
          description
            "Limit default advertisement to this NSSA area";
          type empty;
        }
        container translate {
          description
            "Translate LSA";
          container type7 {
            description
              "From Type 7 to Type 5";
            leaf always {
              description
                "Always translate LSAs on this ABR";
              type empty;
            }
            leaf suppress-fa {
              description
                "Suppress forwarding address in translated LSAs";
              type empty;
            }
          }
        }
      }
      leaf no-redistribution {
        description
          "No redistribution into this NSSA area";
        type empty;
      }
      leaf no-summary {
        description
          "Do not send summary LSA into NSSA";
        type empty;
      }
      container translate {
        description
          "Translate LSA";
        container type7 {
          description
            "From Type 7 to Type 5";
          leaf always {
            description
              "Always translate LSAs on this ABR";
            type empty;
          }
          leaf suppress-fa {
            description
              "Suppress forwarding address in translated LSAs";
            type empty;
          }
        }
      }
    }
    container stub {
      when "not(../area-id = '0')";
      description
        "Specify a stub area";
      presence "Specify a stub area";
      leaf no-ext-capability {
        description
          "Do not send domain specific capabilities into stub area";
        type empty;
      }
      leaf no-summary {
        description
          "Do not send summary LSA into stub area";
        type empty;
      }
    }
  }

  grouping ospfv3-area-base-grouping {
    list area-config {
      description
        "OSPF area parameters";
      key "area-id";
      leaf area-id {
        type ios-types:ospf-area-type;
      }
      uses ospfv3-area-common-grouping;
    }
  }

  grouping ospfv3-router-area-grouping {
    uses ospfv3-area-base-grouping {
      augment area-config {
        container authentication {
          description
            "Enable authentication";
          leaf key-chain {
            description
              "key chain";
            type string;
          }
          container ipsec {
            description
              "Use IPsec encryption";
            leaf spi {
              description
                "Set the SPI (Security Parameters Index)";
              type uint64 {
                range "256..4294967295";
              }
            }
            uses ospfv3-md5-sha1-authentication-grouping;
          }
        }
      }
    }
  }

  grouping ospfv3-af-area-common-grouping {
    leaf normal {
      description
        "Specify a normal area type";
      type empty;
    }
    container authentication {
      description
        "Enable authentication";
      choice authentication-choice {
        leaf key-chain {
          description
            "key chain";
          type string;
        }
        leaf null {
          description
            "Use null authentication";
          type empty;
        }
      }
    }
    list filter-list {
      description
        "Filter networks between OSPF areas";
      key "in-out";
      leaf in-out {
        type enumeration {
          enum "in";
          enum "out";
        }
      }
      leaf prefix {
        mandatory true;
        description
          "Filter prefixes between OSPF areas";
        type string;
      }
    }
  }

  grouping ospfv3-af-ipv4-unicast-area-grouping {
    uses ospfv3-area-base-grouping {
      augment area-config {
        uses ospfv3-af-area-common-grouping;
        uses ospfv3-af-area-ipv4-range-grouping;
      }
    }
  }

  grouping ospfv3-af-ipv4-vrf-area-grouping {
    uses ospfv3-area-base-grouping {
      augment area-config {
        uses ospfv3-af-area-common-grouping;
        uses ospfv3-af-area-common-vrf-grouping;
        uses ospfv3-af-area-ipv4-range-grouping;
      }
    }
  }

  grouping ospfv3-af-ipv6-unicast-area-grouping {
    uses ospfv3-area-base-grouping {
      augment area-config {
        uses ospfv3-af-area-common-grouping;
        uses ospfv3-af-area-ipv6-vlink-grouping;
        uses ospfv3-af-area-ipv6-range-grouping;
      }
    }
  }

  grouping ospfv3-af-ipv6-vrf-area-grouping {
    uses ospfv3-area-base-grouping {
      augment area-config {
        uses ospfv3-af-area-common-grouping;
        uses ospfv3-af-area-ipv6-vlink-grouping;
        uses ospfv3-af-area-ipv6-range-grouping;
        uses ospfv3-af-area-common-vrf-grouping;
      }
    }
  }

  grouping ospfv3-af-area-ipv4-range-grouping{
    list range {
      description 
        "Summarize routes matching address/mask (border routers only)";
      key "ip mask";
      leaf ip {
        type inet:ipv4-address;
      }
      leaf mask {
        type inet:ipv4-address;
      }
      choice advertise-choice {
        leaf advertise {
          description 
            "Advertise this range (default)";
          type empty;
        }
        leaf not-advertise {
          description 
            "DoNotAdvertise this range";
          type empty;
        }
      }
      leaf cost {
        description 
          "User specified metric for this range";
        type uint32 {
          range "0 .. 16777214";
        }
      }
    }
  }

  grouping ospfv3-af-area-ipv6-range-grouping{
    list range {
      description
        "Summarize routes matching address/mask (border routers only)";
      key "ip";
      leaf ip {
        type ios-types:ipv6-prefix;
      }
      choice advertise-choice {
        leaf advertise {
          description 
            "Advertise this range (default)";
          type empty;
        }
        leaf not-advertise {
          description 
            "DoNotAdvertise this range";
          type empty;
        }
      }
      leaf cost {
        description 
          "User specified metric for this range";
        type uint32 {
          range "0 .. 16777214";
        }
      }
    }
  }

  grouping ospfv3-common-grouping {
    list area {
      status deprecated;
      description
        "OSPF area parameters (DEPRECATED: use area-config)";
      key "id";
      leaf id {
        status deprecated;
        type ios-types:ospf-area-type;
      }
      container authentication {
        status deprecated;
        description
          "Enable authentication";
        presence "true";
        leaf message-digest {
          status deprecated;
          description
            "Use message-digest authentication";
          type empty;
        }
      }
      container capability {
        status deprecated;
        description
          "Enable area specific capability, DEPRECATED";
        leaf default-exclusion {
          status deprecated;
          description
            "Enable exclusion of links from base topology";
          type empty;
        }
      }
      leaf default-cost {
        status deprecated;
        when "not(../id = '0')";
        description
          "Set the summary default-cost of a NSSA/stub area";
        type uint32 {
          range "0 .. 16777214";
        }
      }
      list filter-list {
        status deprecated;
        description
          "Filter networks between OSPF areas";
        key "in-out";
        leaf in-out {
          status deprecated;
          type enumeration {
            enum "in";
            enum "out";
          }
        }
        leaf prefix {
          status deprecated;
          mandatory true;
          description
            "Filter prefixes between OSPF areas";
          type string;
        }
      }
      container nssa {
        status deprecated;
        when "not(../id = '0')";  
        description
          "Specify a NSSA area";
        presence "Specify a NSSA area";
        container default-information-originate {
          status deprecated;
          description
            "Originate Type 7 default into NSSA area";
          presence "Originate Type 7 default into NSSA area";
          leaf metric {
            status deprecated;
            description
              "OSPF default metric";
            type int32 {
              range "0 .. 16777214";
            }
          }
          leaf metric-type {
            status deprecated;
            description
              "OSPF metric type for default routes";
            type ios-types:ospf-metric-type;
          }
          leaf no-ext-capability {
            status deprecated;
            description
              "Do not send domain specific capabilities into NSSA";
            type empty;
          }
          leaf no-redistribution {
            status deprecated;
            description
              "No redistribution into this NSSA area";
            type empty;
          }
          leaf no-summary {
            status deprecated;
            description
              "Do not send summary LSA into NSSA";
            type empty;
          }
          leaf nssa-only {
            status deprecated;
            description
              "Limit default advertisement to this NSSA area";
            type empty;
          }
          container translate {
            status deprecated;
            description
              "Translate LSA";
            container type7 {
              status deprecated;
              description
                "From Type 7 to Type 5";
              leaf always {
                status deprecated;
                description
                  "Always translate LSAs on this ABR";
                type empty;
              }
              leaf suppress-fa {
                status deprecated;
                description
                  "Suppress forwarding address in translated LSAs";
                type empty;
              }
            }
          }
        }
        leaf no-ext-capability {
          status deprecated;
          description
            "Do not send domain specific capabilities into NSSA";
          type empty;
        }
        leaf no-redistribution {
          status deprecated;
          description
            "No redistribution into this NSSA area";
          type empty;
        }
        leaf no-summary {
          status deprecated;
          description
            "Do not send summary LSA into NSSA";
          type empty;
        }
        leaf nssa-only {
          status deprecated;
          description
            "Limit default advertisement to this NSSA area";
          type empty;
        }
        container translate {
          status deprecated;
          description
            "Translate LSA";
          container type7 {
            status deprecated;
            description
              "From Type 7 to Type 5";
            leaf always {
              status deprecated;
              description
                "Always translate LSAs on this ABR";
              type empty;
            }
            leaf suppress-fa {
              status deprecated;
              description
                "Suppress forwarding address in translated LSAs";
              type empty;
            }
          }
        }
      }
      container ipv4-range {
        status deprecated;
        list range {
          status deprecated;
          description 
            "Summarize routes matching address/mask (border routers only)";
          key "ip mask";
          leaf ip {
            status deprecated;
            type inet:ipv4-address;
          }
          leaf mask {
            status deprecated;
            type inet:ipv4-address;
          }
          choice advertise-choice {
            status deprecated;
            leaf advertise {
              status deprecated;
              description 
                "Advertise this range (default)";
              type empty;
            }
            leaf not-advertise {
              status deprecated;
              description 
                "DoNotAdvertise this range";
              type empty;
            }
          }
          leaf cost {
            status deprecated;
            description 
              "User specified metric for this range";
            type uint32 {
              range "0 .. 16777214";
            }
          }
        }
      } 
      container ipv6-range {
        status deprecated;
        list range {
          status deprecated;
          description 
            "Summarize routes matching address/mask (border routers only)";
          key "ip";
          leaf ip {
            status deprecated;
            type ios-types:ipv6-prefix;
          }
          choice advertise-choice {
            status deprecated;
            leaf advertise {
              status deprecated;
              description 
                "Advertise this range (default)";
              type empty;
            }
            leaf not-advertise {
              status deprecated;
              description 
                "DoNotAdvertise this range";
              type empty;
            }
          }
          leaf cost {
            status deprecated;
            description 
              "User specified metric for this range";
            type uint32 {
              range "0 .. 16777214";
            }
          }
        }
      } 
      list sham-link {
        status deprecated;
        description
          "Define a sham link and its parameters";
        key "source dest";
        leaf source {
          status deprecated;
          type inet:ip-address;
        }
        leaf dest {
          status deprecated;
          type inet:ip-address;
        }
        leaf cost {
          status deprecated;
          description
            "Associate a cost with the sham-link";
          type uint16 {
            range "0 .. 65535";
          }
        }
        container ttl-security {
          status deprecated;
          description
            "TTL security check";
          leaf hops {
            status deprecated;
            description
              "IP hops";
            type uint8;
          }
        }
      }
      container stub {
        status deprecated;
        when "not(../id = '0')";
        description
          "Specify a stub area";
        presence "Specify a stub area";
        leaf no-ext-capability {
          status deprecated;
          description
            "Do not send domain specific capabilities into stub area";
          type empty;
        }
        leaf no-summary {
          status deprecated;
          description
            "Do not send summary LSA into stub area";
          type empty;
        }
      }
      list virtual-link {
        status deprecated;
        description
          "Define a virtual link and its parameters";
        key "id";
        leaf id {
          status deprecated;
          type inet:ip-address;
        }
        container authentication {
          status deprecated;
          description
            "Set authentication type";
          uses ospf-area-virtual-link-grouping {
            status deprecated;
          }
          container key-chain {
            status deprecated;
            description
              "Use a key-chain for cryptographic authentication keys";
            leaf name {
              status deprecated;
              type string;
            }
            uses ospf-area-virtual-link-grouping {
              status deprecated;
            }
          }
          container message-digest {
            status deprecated;
            description
              "Message-digest authentication";
            uses ospf-area-virtual-link-grouping {
              status deprecated;
            }
          }
          leaf null {
            status deprecated;
            description
              "No authentication";
            type empty;
          }
        }
        container hello-interval {
          status deprecated;
          description
            "Hello packet interval";
          leaf hello-interval-value {
            status deprecated;
            type int32 {
              range "1 .. 8192";
            }
          }
        }
        container dead-interval {
          status deprecated;
          description
            "Dead router detection time";
          leaf dead-interval-value {
            status deprecated;
            type uint16 {
              range "1 .. 8192";
            }
          }
        }
        container retransmit-interval {
          status deprecated;
          description
            "LSA retransmit interval";
          leaf retransmit-interval-value {
            status deprecated;
            type uint16 {
              range "1 .. 8192";
            }
          }
        }
        container transmit-delay {
          status deprecated;
          description
            "LSA transmission delay";
          leaf transmit-delay-value {
            status deprecated;
            type uint16 {
              range "1 .. 8192";
            }
          }
        }
        container topology {
          status deprecated;
          description
            "Disable virtual link on topology";
          leaf disable {
            status deprecated;
            description
              "Disable virtual link";
            type empty;
          }
        }
        container ttl-security {
          status deprecated;
          description
            "TTL security check";
          leaf hops {
            status deprecated;
            description
              "IP hops";
            type uint8 {
              range "1..254";
            }
          }
        }
        uses ospf-area-virtual-link-grouping {
          status deprecated;
        }
      }
    }
    container auto-cost {
      description
        "Calculate OSPF interface cost according to bandwidth";
      presence "Calculate OSPF interface cost according to bandwidth";
      leaf reference-bandwidth {
        description
          "Use reference bandwidth method to assign OSPF cost";
        type uint32 {
          range "1 .. 4294967";
        }
      }
    }
    container event-log {
      description
        "OSPF Event Logging";
      presence "true";
      leaf size {
        description
          "Maximum Number of Events Stored in the Event Log";
        type uint32 {
          range "1..65534";
        }
        default "1000";
      }
      leaf one-shot {
        description
          "Disable Logging When Log Buffer Becomes Full";
        type empty;
      }
      leaf pause {
        description
          "Pause Event Logging";
        type empty;
      }
    }
    container bfd {
      description
        "BFD configuration commands";
      leaf all-interfaces {
        description
          "Enable BFD on all interfaces";
        type empty;
      }
    }
    container interface-id {
      description
        "Source of the interface ID";
      leaf snmp-if-index {
        description
          "SNMP MIB ifIndex";
        type empty;
      }
    }
    container log-adjacency-changes {
      description
        "Log changes in adjacency state";
      presence "true";
      leaf detail {
        description
          "Log all state changes";
        type empty;
      }
    }
    container max-lsa {
      description
        "maximum number of LSAs OSPF process will receive";
      leaf number {
        type uint32 {
          range "1 .. 4294967294";
        }
      }
      leaf threshold-value {
        type uint32 {
          range "1 .. 100";
        }
      }
      leaf ignore-count {
        description
          "maximum number of times adjacencies can be suppressed";
        type uint32 {
          range "1 .. 65535";
        }
      }
      leaf ignore-time {
        description
          "Number of minutes during which all adjacencies are suppressed";
        type uint32 {
          range "1 .. 65535";
        }
      }
      leaf reset-time {
        description
          "Number of minutes after which ignore-count is reset to zero";
        type uint32 {
          range "2 .. 65535";
        }
      }
      leaf warning-only {
        description
          "Maximum route lifetime following restart, in seconds";
        type empty;
      }
    }
    container max-metric {
      description
        "Set maximum metric";
      container router-lsa-config {
        description
          "Maximum metric in self-originated router-LSAs";
        presence "true";

        leaf stub-prefix-lsa {
          description
            "Set maximum metric for stub links in prefix LSAs";
          type empty;
        }

        container inter-area-lsas {
          description
            "Override inter-area-lsas metric with max-metric value";
          presence "true";
          leaf metric {
            description
              "Overriding metric in inter-area-LSAs (default 16711680)";
            type uint32 {
              range "1 .. 16777215";
            }
            default "16711680";
          }
        }

        container external-lsa {
          presence "true";
          description
            "Override external-lsa metric with max-metric value";
          leaf metric {
            description
              "Overriding metric in external-LSAs (default 16711680)";
            type uint32 {
              range "1 .. 16777215";
            }
            default "16711680";
          }
        }

        container on-startup {
          description
            "Set maximum metric temporarily after reboot";
          choice time-wait-for-bgp-choice {
            leaf time {
              type uint32 {
                range "5 .. 86400";
              }
            }
            leaf wait-for-bgp {
              description
                "Let BGP decide when to originate router-LSA with normal metric";
              type empty;
            }
          }
        }
      }

      container router-lsa {
        status deprecated;
        description
          "Maximum metric in self-originated router-LSAs (DEPRECATED, use router-lsa-config)";
        presence "Maximum metric in self-originated router-LSAs";
        container external-lsa {
          status deprecated;
          presence "Override external-lsa metric with max-metric value";
          description
            "Override external-lsa metric with max-metric value";
          leaf metric {
            status deprecated;
            type uint32 {
              range "1 .. 16777214";
            }
          }
        }
        leaf include-stub {
          status obsolete;
          description
            "Set maximum metric for stub links in router-LSAs";
          type empty;
        }
        container on-startup {
          status deprecated;
          description
            "Set maximum metric temporarily after reboot";
          presence "Set maximum metric temporarily after reboot";
          choice time-wait-for-bgp-choice {
            status deprecated;
            leaf time {
              status deprecated;
              type uint32 {
                range "5 .. 86400";
              }
            }
            leaf wait-for-bgp {
              status deprecated;
              description
                "Let BGP decide when to originate router-LSA with normal metric";
              type empty;
            }
          }
        }
        container summary-lsa {
          status obsolete;
          description
            "Override summary-lsa metric with max-metric value";
          presence "Override summary-lsa metric with max-metric value";
          leaf metric {
            status obsolete;
            type uint32 {
              range "1 .. 16777214";
            }
          }
        }
      }
    }

    uses ios-ifc:passive-interface-grouping;
    container queue-depth {
      description
        "OSPF Hello/Router process queue depth";
      container hello {
        description
          "OSPF Hello process queue depth";
        uses queue-depth-grouping;
      }
      container update {
        description
          "OSPF Router process queue depth";
        uses queue-depth-grouping;
      }
    }
    container timers {
      description
        "Adjust routing timers";
      container lsa {
        description
          "OSPF LSA timers";
        leaf arrival {
          description
            "OSPF LSA arrival timer";
          type uint32 {
            range "0 .. 600000";
          }
        }
      }
      container pacing {
        description
          "OSPF pacing timers";
        leaf flood {
          description
            "OSPF flood pacing timer";
          type uint32 {
            range "5 .. 100";
          }
        }
        leaf lsa-group {
          description
            "OSPF LSA group pacing timer";
          type uint32 {
            range "10 .. 1800";
          }
        }
        leaf retransmission {
          description
            "OSPF retransmission pacing timer";
          type uint32 {
            range "5 .. 200";
          }
        }
      }
      container throttle {
        description
          "OSPF throttle timers";
        container lsa {
          description
            "OSPF LSA throttle timers";
          container all {
            description
              "For all type of OSPF LSAs";
            leaf delay {
              type uint32 {
                range "0 .. 600000";
              }
            }
            leaf min-delay {
              type uint32 {
                range "1 .. 600000";
              }
            }
            leaf max-delay {
              type uint32 {
                range "1 .. 600000";
              }
            }
          }
        }
        container spf {
          description
            "OSPF SPF throttle timers";
          leaf delay {
            type uint32 {
              range "1 .. 600000";
            }
          }
          leaf min-delay {
            type uint32 {
              range "1 .. 600000";
            }
          }
          leaf max-delay {
            type uint32 {
              range "1 .. 600000";
            }
          }
        }
      }
    }
    leaf router-id {
      description
        "Override configured router identifier (peers will reset)";
      type inet:ipv4-address;
    }
    leaf nsr {
      description
        "Enable non-stop routing";
      type empty;
    }
    container traffic-share {
      status obsolete;
      description
        "How to compute traffic share over alternate paths";
      leaf min {
        status obsolete;
        description
          "All traffic shared among min metric paths";
        type empty;
      }
      leaf across-interfaces {
        status obsolete;
        description
          "Use different interfaces for equal-cost paths";
        type empty;
      }
    }
    container ttl-security {
      status obsolete;
      description
        "TTL security check";
      leaf all-interfaces {
        status obsolete;
        description
          "Enable TTL Security on all interfaces";
        type empty;
      }
      leaf hops {
        status obsolete;
        description
          "IP hops";
        type uint8 {
          range "1..254";
        }
      }
    }
  }

  grouping interface-ospfv3-manet-grouping {
    container manet {
      description
        "Mobile Adhoc Networking options";
      container peering {
        description
          "MANET Peering options";
        container cost {
          description
            "Redundant path cost improvement required to peer";
          leaf percent {
            description
              "Relative incremental path cost";
            type uint8 {
              range "0..100";
            }
          }
          leaf threshold {
            description
              "Absolute incremental path cost";
            type uint32 {
              range "0..65535";
            }
          }
        }

        container link-metrics-config {
          description
            "Require link metrics";
          presence "true";
          leaf link-metrics-value {
            description
              "Minimum link cost threshold";
            type uint32 {
              range "0..65535";
            }
          }
        }

        leaf link-metrics {
          status deprecated;
          description
            "Require link metrics (DEPRECATED, use link-metrics-config)";
          type uint32 {
            range "0..65535";
          }
        }
      }
    }
  }

  grouping interface-ospfv3-cost-grouping {
    container cost {
      description
        "Route cost of this interface";
      leaf value {
        type uint32 {
          range "1..65535";
        }
      }
      container dynamic {
        description
          "Specify dynamic cost options";
        presence "true";
        leaf default {
          description
            "Specify default link metric value";
          type uint32 {
            range "0..65535";
          }
        }
        container hysteresis {
          description
            "Specify hysteresis value for LSA dampening";
          presence "true";
          leaf percent {
            description
              "Specify hysteresis percent changed";
            type uint8 {
              range "1..100";
            }
          }
          leaf threshold {
            description
              "Specify hysteresis threshold value";
            type uint32 {
              range "0..65535";
            }
          }
        }
        container weight {
          description
            "Specify weight to be placed on individual metrics";
          container L2-factor {
            description
              "Specify weight to be given to L2-factor metric";
            presence "true";
            leaf value {
              type uint8 {
                range "0..100";
              }
            }
          }
          container latency {
            description
              "Specify weight to be given to latency metric";
            presence "true";
            leaf value {
              type uint8 {
                range "0..100";
              }
            }
          }
          container resources {
            description
              "Specify weight to be given to resources metric";
            presence "true";
            leaf value {
              type uint8 {
                range "0..100";
              }
            }
          }
          container throughput {
            description
              "Specify weight to be given to throughput metric";
            presence "true";
            leaf value {
              type uint8 {
                range "0..100";
              }
            }
          }
        }
      }
    }
  }

  grouping interface-ospfv3-process-id-grouping {
    // interface * / ospfv3 * authentication
    container authentication {
      description
        "Enable authentication";
      leaf key-chain {
        description
          "Use a key-chain for cryptographic authentication keys";
        type string;
      }
      leaf null {
        description
          "Use no authentication";
        type empty;
      }
    }

    // interface * / ospfv3 * bfd
    uses interface-ospfv3-bfd-grouping;

    // interface * / ospfv3 * cost
    uses interface-ospfv3-cost-grouping;

    // interface * / ospfv3 * database-filter
    container database-filter {
      description
        "Filter OSPF LSA during synchronization and flooding";
      choice database {
        leaf all {
          description
            "Filter all LSA";
          type enumeration {
            enum "out";
          }
        }
        leaf disable {
          description
            "Disable LSA Filter on this interface";
          type empty;
        }
      }
    }
    // interface * / ospfv3 * dead-interval
    uses interface-ospfv3-dead-interval-grouping;

    // interface * / ospfv3 * demand-circuit
    container demand-circuit {
      description
        "OSPF demand circuit";
      presence "true";
      leaf disable {
        description
          "Disable demand circuit on this interface";
        type empty;
      }
      leaf ignore {
        description
          "Ignore demand circuit auto-negotiation requests";
        type empty;
      }
    }

    // interface * / ospfv3 * flood-reduction
    container flood-reduction {
      description
        "OSPF Flood Reduction";
      presence "true";
      leaf disable {
        type empty;
      }
    }

    // interface * / ospfv3 * hello-interval
    uses interface-ospfv3-hello-interval-grouping;

    // interface * / ospfv3 * manet
    uses interface-ospfv3-manet-grouping;

    // interface * / ospfv3 * mtu-ignore
    container mtu-ignore {
      description
        "Ignores the MTU in DBD packets";
      presence "true";
      leaf disable {
        description
          "Disable Ignore MTU on this interface";
        type empty;
      }
    }

    // interface * /  ospfv3 * multi-area
    container multi-area {
      description
        "Set the OSPF multi-area ID";
      leaf id {
        type union {
          type uint32 {
            range "0..4294967295";
          }
          type inet:ipv4-address;
        }
      }
      leaf cost {
        description
          "Interface cost";
        type uint32 {
          range "1..65535";
        }
      }
      leaf disable {
        description
          "disable OSPF multi-area";
        type empty;
      }
    }

    // interface * /  ospfv3 * neighbor
    uses interface-ospfv3-neighbor-grouping;

    // interface * /  ospfv3 * network
    uses interface-ospfv3-network-grouping;

    // interface * / ospfv3 * prefix-suppression
    uses interface-ospfv3-prefix-suppression-grouping;

    // interface * /  ospfv3 * priority
    uses interface-ospfv3-priority-grouping;

    // interface * /  ospfv3 * retransmit-interval
    uses interface-ospfv3-retransmit-interval-grouping;

    // interface * / ospfv3 * shutdown
    container shutdown {
      description
        "Shut down the interface in OSPFv3";
      presence "true";
      leaf disable {
        description
          "Disable inherited shutdown";
        type empty;
      }
    }

    // interface * / ospfv3 * transmit-delay
    uses interface-ospfv3-transmit-delay-grouping;
  }

  // interface * / ospfv3
  grouping config-interface-ospfv3-grouping {
    container ospfv3 {
      description
        "OSPFv3 interface commands";
      list process-id {
        key "id";
        leaf id {
          type uint16 {
            range "1..65535";
          }
        }

        uses interface-ospfv3-process-id-grouping;

        //interface * / ospfv3 * ipv4
        container ipv4 {
          description
            "Specify parameters for IPv4";
          list area {
            description
              "Set the OSPF area ID";
            key "id";
            leaf id {
              type ios-types:ospf-area-type;
            }
            leaf instance {
              description
                "Set the OSPF instance";
              type uint8 {
                range "64..95";
              }
            }
          }
          uses interface-ospfv3-process-id-grouping;
        }

        //interface * / ospfv3 * ipv6
        container ipv6 {
          description
            "Specify parameters for IPv6";
          list area {
            description
              "Set the OSPF area ID";
            key "id";
            leaf id {
              type ios-types:ospf-area-type;
            }
            leaf instance {
              description
                "Set the OSPF instance";
              type uint8 {
                range "0..31";
              }
            }
          }
          uses interface-ospfv3-process-id-grouping;
        }
      }
      
      // interface * / ospfv3 authentication
      uses interface-ospfv3-authentication-grouping;

      container authentication {
        description
          "Enable authentication (DEPRECATED, use authentication-config)";
        status deprecated;
        leaf key-chain {
          status deprecated;
          description
            "Use a key-chain for cryptographic authentication keys";
          type string;
        }
        leaf null {
          status deprecated;
          description
            "Use no authentication";
          type empty;
        }
        uses authentication-ipsec-grouping {
          status deprecated;
        }
      }

      // interface * / ospfv3 bfd
      uses interface-ospfv3-bfd-grouping;

      // interface * / ospfv3 cost
      uses interface-ospfv3-cost-grouping;

      // interface * / ospfv3 database-filter
      container database-filter {
        description
          "Filter OSPF LSA during synchronization and flooding";
        leaf all {
          description
            "Filter all LSA";
          type enumeration {
            enum "out";
          }
        }
      }
      // interface * / ospfv3 dead-interval

      uses interface-ospfv3-dead-interval-grouping;

      // interface * / ospfv3 demand-circuit
      container demand-circuit {
        description
          "OSPF Demand Circuit";
        presence "true";
        leaf ignore {
          description
            "Ignore demand circuit auto-negotiation requests";
          type empty;
        }
      }

      // interface * / ospfv3 encryption
      uses interface-ospfv3-encryption-grouping;

      // interface * / ospfv3 flood-reduction
      leaf flood-reduction {
        description
          "OSPF Flood Reduction";
        type empty;
      }

      // interface * / ospfv3 hello-interval
      uses interface-ospfv3-hello-interval-grouping;

      // interface * / ospfv3 manet
      uses interface-ospfv3-manet-grouping;

      // interface * / ospfv3 mtu-ignore
      leaf mtu-ignore {
        description
          "Ignores the MTU in DBD packets";
        type empty;
      }

      // interface * /  ospfv3 multi-area
      container multi-area {
        description
          "Set the OSPF multi-area ID";
        leaf id {
          type ios-types:ospf-area-type;
        }
        leaf cost {
          description
            "Interface cost";
          type uint32 {
            range "1..65535";
          }
        }
      }

      // interface * /  ospfv3 neighbor
      uses interface-ospfv3-neighbor-grouping;

      // interface * /  ospfv3 network
      uses interface-ospfv3-network-grouping;

      // interface * / ospfv3 prefix-suppression
      uses interface-ospfv3-prefix-suppression-grouping;

      // interface * /  ospfv3 priority
      uses interface-ospfv3-priority-grouping;

      // interface * /  ospfv3 retransmit-interval
      uses interface-ospfv3-retransmit-interval-grouping;

      // interface * / ospfv3 shutdown
      leaf shutdown {
        description
          "Shut down the interface in OSPFv3";
        type empty;
      }

      // interface * / ospfv3 transmit-delay
      uses interface-ospfv3-transmit-delay-grouping;
    }
  }

  grouping ospf-redistribute-bgp-grouping {
    leaf as-number {
      type ios-types:bgp-as-number-type;
    }
    uses ospf-redistribute-grouping;
  }

  grouping ospf-redistribute-bgp-grouping-deprecated {
    status deprecated;
    leaf as-number {
      status deprecated;
      type ios-types:bgp-as-number-type;
    }
    uses ospf-redistribute-grouping-deprecated {
      status deprecated;
    }
  }

  grouping ospf-redistribute-bgp-grouping-obsolete {
    status obsolete;
    leaf as-number {
      status obsolete;
      type ios-types:bgp-as-number-type;
    }
    uses ospf-redistribute-grouping-obsolete {
      status obsolete;
    }
  }

  grouping ospf-redistribute-match-grouping {
    leaf metric {
      description
        "Metric for redistributed routes";
      type uint32 {
        range "0 .. 16777214";
      }
    }
    leaf metric-type {
      description
        "OSPF/IS-IS exterior metric type for redistributed routes";
      type enumeration {
        enum "1" {
        }
        enum "2" {
        }
      }
    }
    leaf nssa-only {
      description
        "Limit redistributed routes to NSSA areas";
      type empty;
    }
    leaf route-map {
      description
        "Route map reference";
      type string;
    }
    leaf tag {
      description
        "Set tag for routes redistributed into OSPF";
      type uint32 {
        range "0 .. 4294967295";
      }
    }
    leaf subnets {
      status obsolete;
      description
        "Consider subnets for redistribution into OSPF";
      type empty;
    }
  }

  grouping ospf-redistribute-match-grouping-obsolete {
    status obsolete;
    leaf metric {
      status obsolete;
      description
        "Metric for redistributed routes";
      type uint32 {
        range "0 .. 16777214";
      }
    }
    leaf metric-type {
      status obsolete;
      description
        "OSPF/IS-IS exterior metric type for redistributed routes";
      type enumeration {
        enum "1" {
        }
        enum "2" {
        }
      }
    }
    leaf nssa-only {
      status obsolete;
      description
        "Limit redistributed routes to NSSA areas";
      type empty;
    }
    leaf route-map {
      status obsolete;
      description
        "Route map reference";
      type string;
    }
    leaf tag {
      status obsolete;
      description
        "Set tag for routes redistributed into OSPF";
      type uint32 {
        range "0 .. 4294967295";
      }
    }
    leaf subnets {
      status obsolete;
      description
        "Consider subnets for redistribution into OSPF";
      type empty;
    }
  }
  grouping ospf-redistribute-top-match-grouping {
    container match {
      description
        "Redistribution of OSPF routes";
      container internal {
        presence "Redistribute OSPF internal routes";
        description
          "Redistribute OSPF internal routes";
        uses ospf-redistribute-match-grouping;
      }
      container external {
        description
          "Redistribute OSPF external routes";
        presence "Redistribute OSPF external routes";
        leaf external-routes {
          type ios-types:redist-ospf-external-type;
        }
        uses ospf-redistribute-match-grouping;
      }
      container nssa-external {
        description
          "Redistribute OSPF NSSA external routes";
        presence "Redistribute OSPF NSSA external routes";
        leaf nssa-external-routes {
          type ios-types:redist-ospf-external-type;
        }
        uses ospf-redistribute-match-grouping;
      }
    }
  }

  grouping ospf-redistribute-top-match-grouping-obsolete {
    status obsolete;
    container match {
      status obsolete;
      description
        "Redistribution of OSPF routes";
      container internal {
        status obsolete;
        presence "Redistribute OSPF internal routes";
        description
          "Redistribute OSPF internal routes";
        uses ospf-redistribute-match-grouping-obsolete {
          status obsolete;
        }
      }
      container external {
        status obsolete;
        description
          "Redistribute OSPF external routes";
        presence "Redistribute OSPF external routes";
        leaf external-routes {
          status obsolete;
          type ios-types:redist-ospf-external-type;
        }
        uses ospf-redistribute-match-grouping-obsolete {
          status obsolete;
        }
      }
      container nssa-external {
        status obsolete;
        description
          "Redistribute OSPF NSSA external routes";
        presence "Redistribute OSPF NSSA external routes";
        leaf nssa-external-routes {
          status obsolete;
          type ios-types:redist-ospf-external-type;
        }
        uses ospf-redistribute-match-grouping-obsolete {
          status obsolete;
        }
      }
    }
  }

  grouping ospf-iso-igrp-redistribute-grouping {
    leaf metric {
      description
        "Metric for redistributed routes";
      type uint32 {
        range "0..16777214";
      }
    }
    leaf metric-type {
      description
        "OSPF/IS-IS exterior metric type for redistributed routes";
      type enumeration {
        enum "1" {
        }
        enum "2" {
        }
      }
    }
    leaf tag {
      description
        "Set tag for routes redistributed into OSPF";
      type uint32 {
        range "0 .. 4294967295";
      }
    }
    leaf subnets {
      status obsolete;
      description
        "Consider subnets for redistribution into OSPF";
      type empty;
    }
  }

  grouping ospf-iso-igrp-redistribute-grouping-deprecated {
    status deprecated;
    leaf metric {
      status deprecated;
      description
        "Metric for redistributed routes";
      type uint32 {
        range "0..16777214";
      }
    }
    leaf metric-type {
      status deprecated;
      description
        "OSPF/IS-IS exterior metric type for redistributed routes";
      type enumeration {
        enum "1" {
        }
        enum "2" {
        }
      }
    }
    leaf tag {
      status deprecated;
      description
        "Set tag for routes redistributed into OSPF";
      type uint32 {
        range "0 .. 4294967295";
      }
    }
    leaf subnets {
      status deprecated;
      description
        "Consider subnets for redistribution into OSPF";
      type empty;
    }
  }

  grouping ospf-iso-igrp-redistribute-grouping-obsolete {
    status obsolete;
    leaf metric {
      status obsolete;
      description
        "Metric for redistributed routes";
      type uint32 {
        range "0..16777214";
      }
    }
    leaf metric-type {
      status obsolete;
      description
        "OSPF/IS-IS exterior metric type for redistributed routes";
      type enumeration {
        enum "1" {
        }
        enum "2" {
        }
      }
    }
    leaf tag {
      status obsolete;
      description
        "Set tag for routes redistributed into OSPF";
      type uint32 {
        range "0 .. 4294967295";
      }
    }
    leaf subnets {
      status obsolete;
      description
        "Consider subnets for redistribution into OSPF";
      type empty;
    }
  }

  grouping ospf-redistribute-top-grouping {
    list application {
      description
        "Application";
      key "name";
      leaf name {
        type string;
      }
      uses ospf-redistribute-grouping;
    }
    list bgp {
      description
        "Border Gateway Protocol (BGP)";
      max-elements "1";
      key "as-number";
      uses ospf-redistribute-bgp-grouping;
    }
    container connected {
      description
        "Connected";
      presence "Connected";
      uses ospf-redistribute-grouping;
    }
    list eigrp-config {
      description
        "Enhanced Interior Gateway Routing Protocol (EIGRP)";
      key "as-number";
      leaf as-number {
        type uint32 {
          range "1..65535";
        }
      }
      uses ospf-redistribute-grouping;
    }
    list eigrp {
      status deprecated;
      description
        "Enhanced Interior Gateway Routing Protocol (EIGRP)";
      key "as-number";
      uses ospf-redistribute-bgp-grouping-deprecated {
        status deprecated;
      }
    }
    container isis {
      presence "ISO IS-IS";
      description
        "ISO IS-IS";
      choice isis-level-routes-isis-area-choice {
        leaf isis-level-routes {
          type enumeration {
            enum "level-1";
            enum "level-2";
            enum "level-1-2";
          }
        }
        list isis-area {
          key "name";
          leaf name {
            type string;
          }
          leaf isis-level-routes {
            type enumeration {
              enum "level-1";
              enum "level-2";
              enum "level-1-2";
            }
          }
          uses ospf-redistribute-grouping;
        }
      }
      uses ospf-redistribute-grouping;
    }
    container iso-igrp {
      description
        "IGRP for OSI networks";
      presence "IGRP for OSI networks";
      choice area-tag-route-map-choice {
        container area-tag-route-map-container {
          leaf area-tag {
            type string;
          }
          leaf route-map {
            description
              "Route map reference";
            type string;
          }
        }
        leaf route-map {
          description
            "Route map reference";
          type string;
        }
      }
      container iso-igrp-container {
        uses ospf-iso-igrp-redistribute-grouping;
      }
    }
    container lisp-config {
      description
        "Locator ID Separation Protocol (LISP)";
      presence "Locator ID Separation Protocol (LISP)";
      uses ospf-redistribute-grouping;
    }
    container lisp {
      description
        "Locator ID Separation Protocol (LISP)";
      status deprecated;
      uses ospf-redistribute-grouping-deprecated {
        status deprecated;
      }
    }
    container mobile {
      description
        "Mobile routes";
      presence "Mobile routes";
      uses ospf-redistribute-grouping;
    }
    container nat-route-config {
      if-feature ios-features:sdwan;
      description
        "NAT Route";
      presence "true";
      leaf dia {
        description
          "Redistribute NAT Direct Internet Access routes";
        type empty;
      }
      leaf outside {
        description
          "Redistribute NAT outside routes";
        type empty;
      }
      uses ospf-redistribute-grouping;
    }
    container nat-route {
      status deprecated;
      if-feature ios-features:sdwan;
      description
        "NAT Route";
      leaf dia {
        status deprecated;
        description
          "Redistribute NAT Direct Internet Access routes";
        type empty;
      }
      leaf outside {
        status deprecated;
        description
          "Redistribute NAT outside routes";
        type empty;
      }
      uses ospf-redistribute-grouping-deprecated {
        status deprecated;
      }
    }
    container odr {
      description
        "On Demand stub Routes";
      presence "On Demand stub Routes";
      uses ospf-redistribute-grouping;
    }
    container omp {
      description
        "Overlay Management Protocol";
      presence "omp";
      uses ospf-redistribute-grouping;
    }
    list ospf {
      description
        "Open Shortest Path First (OSPF)";
      key "id";
      leaf id {
        type uint32 {
          range "1 .. 65535";
        }
      }
      uses ospf-redistribute-top-match-grouping;
      uses ospf-redistribute-match-grouping;
      leaf vrf {
        description
          "VPN Routing/Forwarding Instance";
        must "/ios:native/ios:vrf/ios:definition[ios:name=current()] or /ios:native/ios:ip/ios:vrf[ios:name=current()]" {
          error-message "VRF must be created 1st, deleted last";
        }
        type string;
      }
    }
    list ospfv3 {
      description
        "OSPFv3";
      key "id";
      leaf id {
        type uint32 {
          range "1 .. 65535";
        }
      }
      uses ospf-redistribute-top-match-grouping;
      uses ospf-redistribute-match-grouping;
    }
    container rip-config {
      description
        "Routing Information Protocol (RIP)";
      presence "true";
      uses ospf-redistribute-grouping;
    }
    list rip {
      status deprecated;
      description
        "Routing Information Protocol (RIP)";
      key "id";
      leaf id {
        status deprecated;
        description
          "User selected string identifying this rip process";
        type string;
      }
      uses ospf-redistribute-grouping-deprecated {
        status deprecated;
      }
    }
    container static {
      description
        "Static routes";
      presence "Static routes";
      uses ospf-redistribute-grouping;
    }
  }

  grouping queue-depth-grouping {
    leaf options {
      type union {
        type uint32 {
          range "1 .. 2147483647";
        }
        type enumeration {
          enum "unlimited";
        }
      }
    }
  }

  grouping ospf-area-virtual-link-grouping {
    status deprecated;
    uses ospfv3-authentication-key-grouping {
      status deprecated;
    }
    list message-digest-key {
      status deprecated;
      description
        "Set message digest key";
      key "id";
      leaf id {
        status deprecated;
        type uint8 {
          range "1 .. 255";
        }
      }
      container md5 {
        status deprecated;
        description
          "Use MD5 algorithm";
        leaf auth-type {
          status deprecated;
          type uint8 {
            range "0 .. 7";
          }
        }
        leaf auth-key {
          status deprecated;
          type string {
            length "1 .. 16";
          }
        }
      }
    }
  }

  grouping ospfv3-af-ipv4-summary-prefix-grouping {
    list summary-prefix {
      key "prefix";
      leaf prefix {
        type inet:ipv4-prefix;
      }
      choice tag-no-advertise-choice {
        leaf nssa-only {
          type empty;
        }
        leaf tag {
          type uint32 {
            range "0 .. 4294967295";
          }
        }
        leaf not-advertise {
          type empty;
        }
      }
    }
  }

  grouping ospfv3-af-ipv6-summary-prefix-grouping {
    list summary-prefix {
      description
        "Configure IPv6 summary prefix";
      key "prefix";
      leaf prefix {
        type ios-types:ipv6-prefix;
      }
      choice tag-no-advertise-choice {
        leaf nssa-only {
          description
            "Limit summary to NSSA areas";
          type empty;
        }
        leaf tag {
          description
            "Set tag";
          type uint32 {
            range "0 .. 4294967295";
          }
        }
        leaf not-advertise {
          description
            "Do not advertise when translating OSPF type-7 LSA";
          type empty;
        }
      }
    }
  }

  grouping ospfv3-grouping {
    container authentication {
      description
        "Authentication parameters";
      leaf mode {
        description
          "Authentication operation mode";
        type enumeration {
          enum "deployment";
          enum "strict";
        }
      }
    }
    container graceful-restart {
      description
        "Graceful-restart options";
      presence "true";
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16 {
          range "1..1800";
        }
      }
    }
    container manet {
      description
        "Specify MANET OSPF parameters";
      container cache {
        description
          "Specify MANET cache sizes";
        leaf acknowledgement {
          description
            "Specify MANET acknowledgement cache size";
          type uint64 {
            range "0..4294967295";
          }
        }
        leaf update {
          description
            "Specify MANET LSA cache size";
          type uint64 {
            range "0..4294967295";
          }
        }
      }
      leaf hello {
        description
          "Unicast Hellos rather than multicast";
        type enumeration {
          enum "unicast";
        }
      }
      container peering {
        description
          "MANET OSPF Smart Peering";
        container selective {
          description
            "Enable selective peering";
          leaf disable {
            description
              "Disable selective peering";
            type empty;
          }
          leaf per-interface {
            description
              "Select peers per interface rather than per node";
            type empty;
          }
          leaf redundancy {
            description
              "Redundant paths";
            type uint8 {
              range "0..10";
            }   
          }
        }
      }
      leaf willingness {
        description
          "Specify Relay willingness value";
        type uint8 {
          range "0..255";
        }
      }
    }
  }

  grouping ospfv3-address-family-grouping {
    container authentication {
      description
        "Authentication parameters";
      leaf mode {
        description
          "Authentication operation mode";
        type enumeration {
          enum "deployment";
          enum "normal";
          enum "strict";
        }
      }
    }
    container graceful-restart {
      description
        "Graceful-restart options";
      presence "true";
      leaf disable {
        description
          "Graceful restart disable";
        type empty;
      }
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16 {
          range "1..1800";
        }
      }
    }
    container manet {
      description
        "Specify MANET OSPF parameters";
      container cache {
        description
          "Specify MANET cache sizes";
        leaf acknowledgement {
          description
            "Specify MANET acknowledgement cache size";
          type uint64 {
            range "0..4294967295";
          }
        }
        leaf update {
          description
            "Specify MANET LSA cache size";
          type uint64 {
            range "0..4294967295";
          }
        }
      }
      leaf hello {
        description
          "Unicast Hellos rather than multicast";
        type enumeration {
          enum "unicast";
          enum "multicast";
        }
      }
      container peering {
        description
          "MANET OSPF Smart Peering";
        container selective {
          description
            "Enable selective peering";
          leaf disable {
            description
              "Disable selective peering";
            type empty;
          }
          leaf per-interface {
            description
              "Select peers per interface rather than per node";
            type empty;
          }
          leaf redundancy {
            description
              "Redundant paths";
            type uint8 {
              range "0..10";
            }
          }
        }
      }
      leaf willingness {
        description
          "Specify Relay willingness value";
        type uint8 {
          range "0..255";
        }
      }
    }
  }

  grouping config-router-ospfv3-grouping {
    list ospfv3 { 
      description
        "OSPFv3";
      key "id";
      leaf id {
        type uint16 {
          range "1..65535";
        }
      }

      uses ospfv3-router-area-grouping;

      uses ospfv3-common-grouping;
      uses ospfv3-grouping;
      // router ospfv3 * / address-family
      container address-family {
        description
          "Enter Address Family command mode";
        container ipv4 {
          description
            "IPv4 Address family";
          container unicast {
            description
              "Address Family Modifier";
            presence "true";
            uses ospfv3-af-ipv4-unicast-area-grouping;
            uses ospfv3-common-grouping;
            uses ospfv3-ipv4-distance-grouping;
            uses ospfv3-common-address-family-grouping;
            uses ospfv3-common-address-family-vrf-grouping;
            uses ospfv3-address-family-grouping;
            uses ospfv3-af-ipv4-summary-prefix-grouping;
          }
          list vrf {
            description
              "Specify parameters for a VPN Routing/Forwarding instance";
            key "vrf";
            leaf vrf {
              must "/ios:native/ios:vrf/ios:definition[ios:name=current()] or /ios:native/ios:ip/ios:vrf[ios:name=current()]" {
                error-message "VRF must be created 1st, deleted last";
              }
              type string;
            }
            leaf unicast {
              type empty;
            }
            uses ospfv3-af-ipv4-vrf-area-grouping;
            uses ospfv3-common-grouping;

            leaf capability-vrf {
              description
                "Enable specific OSPF feature";
              type enumeration {
                enum "vrf-lite";
              }
            }
            uses ospfv3-ipv4-distance-grouping;
            uses ospfv3-common-address-family-grouping;
            uses ospfv3-common-address-family-vrf-grouping;
            uses ospfv3-address-family-grouping;
            uses ospfv3-af-ipv4-summary-prefix-grouping;
          }
        }
        container ipv6 {
          description
            "IPv6 Address family";
          container unicast {
            presence "true";
            uses ospfv3-af-ipv6-unicast-area-grouping;
            uses ospfv3-common-grouping;
            uses ospfv3-ipv6-distance-grouping;
            uses ospfv3-common-address-family-grouping;
            uses ospfv3-ipv6-address-family-vrf-grouping;
            uses ospfv3-address-family-grouping;
            uses ospfv3-af-ipv6-summary-prefix-grouping;
          }
          list vrf {
            description
              "Specify parameters for a VPN Routing/Forwarding instance";
            key "vrf";
            leaf vrf {
              must "/ios:native/ios:vrf/ios:definition[ios:name=current()] or /ios:native/ios:ip/ios:vrf[ios:name=current()]" {
                error-message "VRF must be created 1st, deleted last";
              }
              type string;
            }
            leaf unicast {
              type empty;
            }
            uses ospfv3-af-ipv6-unicast-area-grouping;
            uses ospfv3-common-grouping;
            leaf capability-vrf {
              description
                "Enable specific OSPF feature";
              type enumeration {
                enum "vrf-lite";
              }
            }
            uses ospfv3-ipv6-distance-grouping;
            uses ospfv3-common-address-family-grouping;
            uses ospfv3-ipv6-address-family-vrf-grouping;
            uses ospfv3-address-family-grouping;
            uses ospfv3-af-ipv6-summary-prefix-grouping;
          }
        }
      }
    }
  }

  // interface * ipv6 ospf
  grouping config-interface-ipv6-ospf-grouping {
    container ospf {
      description
        "OSPF interface commands";
      container process {
        leaf id {
          must "/ios:native/ios:ipv6/ios:router/ios:ospf[ios:id=current()] or " +
               "/ios:native/ios:router/ios-ospfv3:ospfv3[ios-ospfv3:id=current()]" {
            error-message "ipv6 ospf <id> area <id> can't exist without (ipv6 router ospf) or (router ospfv3)";
          }
          type uint16 {
            range "1..65535";
          }
        }
        leaf area {
          description
            "Set the OSPF area ID";
          type ios-types:ospf-area-type;
        }
        leaf instance {
          description
            "Set the OSPF instance";
          type uint8 {
            range "0..31";
          }
        }
      }

      // interface * / ipv6 ospf authentication
      container authentication {
        description
          "Enable authentication";
        choice authentication-choice {
          leaf null {
            description
              "Use no authentication";
            type empty;
          }
          container ipsec {
            description
              "Use IPsec authentication";
            leaf spi {
              description
                "Set the SPI (Security Parameters Index)";
              type uint64 {
                range "256..4294967295";
              }
            }
            uses ospfv3-spi-md5-sha1-authentication-grouping;
          }
        }
      }

      // interface * / ipv6 ospf bfd
      uses interface-ospfv3-bfd-grouping;

      // interface * / ipv6 ospf cost
      leaf cost {
        description
          "Route cost of this interface";
        type uint16 {
          range "1..65535";
        }
        default "10";
      }

      // interface * / ipv6 ospf database-filter
      container database-filter {
        description
          "Filter OSPF LSA during synchronization and flooding";
        choice database {
          leaf all {
            description
              "Filter all LSA";
            type enumeration {
              enum "out";
            }
          }
          leaf disable {
            description
              "Disable LSA Filter on this interface";
            type empty;
          }
        }
      }
      // interface * / ipv6 ospf dead-interval
      uses interface-ospfv3-dead-interval-grouping;

      // interface * / ipv6 ospf demand-circuit
      container demand-circuit {
        description
          "OSPF demand circuit";
        presence "true";
        choice disable-or-ignore {
          leaf disable {
            description
              "Disable demand circuit on this interface";
            type empty;
          }
          leaf ignore {
            description
              "Ignore demand circuit auto-negotiation requests";
            type empty;
          }
        }
      }

      // interface * / ipv6 ospf encryption
      uses interface-ospfv3-encryption-grouping;

      // interface * / ipv6 ospf flood-reduction
      container flood-reduction {
        description
          "OSPF Flood Reduction";
        presence "true";
        leaf disable {
          description
            "Disable Flood Reduction on this interface";
          type empty;
        }
      }

      // interface * / ipv6 ospf hello-interval
      uses interface-ospfv3-hello-interval-grouping;

      // interface * / ipv6 ospf mtu-ignore
      container mtu-ignore {
        description
          "Ignores the MTU in DBD packets";
        presence "true";
        leaf disable {
          description
            "Disable Ignore MTU on this interface";
          type empty;
        }
      }

      // interface * / ipv6 ospf neighbor
      uses interface-ospfv3-neighbor-grouping;

      //  interface * / ipv6 ospf network
      uses interface-ospfv3-network-grouping;

      // interface * / ipv6 ospf priority
      uses interface-ospfv3-priority-grouping;
      // interface * / ipv6 ospf retransmit-interval

      uses interface-ospfv3-retransmit-interval-grouping;

      // interface * / ipv6 ospf shutdown
      container shutdown {
        description
          "Shut down the interface in OSPFv3";
        presence "true";
        leaf disable {
          description
            "Disable inherited shutdown";
          type empty;
        }
      }

      // interface * / ipv6 ospf transmit-delay
      uses interface-ospfv3-transmit-delay-grouping;
    }
  }

  grouping ipv6-router-ospf-redistribute-static-grouping {
    container static {
      description
        "Static routes";
      presence "Static routes";
      uses ospf-redistribute-grouping;
    }
  }

  grouping ipv6-router-ospf-graceful-restart-grouping {
    container graceful-restart {
      description
        "Graceful-restart options";
      presence "true";
      container helper {
        description
          "helper support";
        presence "true";
        leaf disable {
          description
            "disable helper support";
          type empty;
        }
        leaf strict-lsa-checking {
          description
            "enable helper strict LSA checking";
          type empty;
        }
      }
      leaf restart-interval {
        description
          "Graceful restart interval";
        type uint16 {
          range "1..1800";
        }
      }
    }
  }

  grouping ipv6-router-ospf-redistribute-grouping {
    container redistribute {
      description
        "Redistribute information from another routing protocol";
      uses ipv6-router-ospf-redistribute-static-grouping;
    }
  }

  grouping config-ipv6-router-ospf-grouping {
    
    uses ipv6-router-ospf-graceful-restart-grouping;

    uses ipv6-router-ospf-redistribute-grouping;
  }

  grouping ospf-redistribute-top-grouping-obsolete {
    status obsolete;
    list application {
      status obsolete;
      description
        "Application";
      key "name";
      leaf name {
        status obsolete;
        type string;
      }
      uses ospf-redistribute-grouping-obsolete {
        status obsolete;
      }
    }
    list bgp {
      status obsolete;
      description
        "Border Gateway Protocol (BGP)";
      max-elements "1";
      key "as-number";
      uses ospf-redistribute-bgp-grouping-obsolete {
        status obsolete;
      }
    }
    container connected {
      status obsolete;
      description
        "Connected";
      presence "Connected";
      uses ospf-redistribute-grouping-obsolete {
        status obsolete;
      }
    }
    list eigrp {
      status obsolete;
      description
        "Enhanced Interior Gateway Routing Protocol (EIGRP)";
      key "as-number";
      uses ospf-redistribute-bgp-grouping-obsolete {
        status obsolete;
      }
    }
    container isis {
      status obsolete;
      presence "ISO IS-IS";
      description
        "ISO IS-IS";
      choice isis-level-routes-isis-area-choice {
        status obsolete;
        leaf isis-level-routes {
          status obsolete;
          type enumeration {
            enum "level-1";
            enum "level-2";
            enum "level-1-2";
          }
        }
        list isis-area {
          status obsolete;
          key "name";
          leaf name {
            status obsolete;
            type string;
          }
          leaf isis-level-routes {
            status obsolete;
            type enumeration {
              enum "level-1";
              enum "level-2";
              enum "level-1-2";
            }
          }
          uses ospf-redistribute-grouping-obsolete {
            status obsolete;
          }
        }
      }
      uses ospf-redistribute-grouping-obsolete {
        status obsolete;
      }
    }
    container iso-igrp {
      status obsolete;
      description
        "IGRP for OSI networks";
      presence "IGRP for OSI networks";
      choice area-tag-route-map-choice {
        status obsolete;
        container area-tag-route-map-container {
          status obsolete;
          leaf area-tag {
            status obsolete;
            type string;
          }
          leaf route-map {
            status obsolete;
            description
              "Route map reference";
            type string;
          }
        }
        leaf route-map {
          status obsolete;
          description
            "Route map reference";
          type string;
        }
      }
      container iso-igrp-container {
        status obsolete;
        uses ospf-iso-igrp-redistribute-grouping-obsolete {
          status obsolete;
        }
      }
    }
    container lisp {
      description
        "Locator ID Separation Protocol (LISP)";
      status obsolete;
      uses ospf-redistribute-grouping-obsolete {
        status obsolete;
      }
    }
    container mobile {
      status obsolete;
      description
        "Mobile routes";
      presence "Mobile routes";
      uses ospf-redistribute-grouping-obsolete {
        status obsolete;
      }
    }
    container nat-route {
      status obsolete;
      if-feature ios-features:sdwan;
      description
        "NAT Route";
      leaf dia {
        status obsolete;
        description
          "Redistribute NAT Direct Internet Access routes";
        type empty;
      }
      leaf outside {
        status obsolete;
        description
          "Redistribute NAT outside routes";
        type empty;
      }
      uses ospf-redistribute-grouping-obsolete {
        status obsolete;
      }
    }
    container odr {
      status obsolete;
      description
        "On Demand stub Routes";
      presence "On Demand stub Routes";
      uses ospf-redistribute-grouping-obsolete {
        status obsolete;
      }
    }
    container omp {
      status obsolete;
      description
        "Overlay Management Protocol";
      presence "omp";
      uses ospf-redistribute-grouping-obsolete {
        status obsolete;
      }
    }
    list ospf {
      status obsolete;
      description
        "Open Shortest Path First (OSPF)";
      key "id";
      leaf id {
        status obsolete;
        type uint32 {
          range "1 .. 65535";
        }
      }
      uses ospf-redistribute-top-match-grouping-obsolete {
        status obsolete;
      }
      uses ospf-redistribute-match-grouping-obsolete {
        status obsolete;
      }
      leaf vrf {
        status obsolete;
        description
          "VPN Routing/Forwarding Instance";
        must "/ios:native/ios:vrf/ios:definition[ios:name=current()] or /ios:native/ios:ip/ios:vrf[ios:name=current()]" {
          error-message "VRF must be created 1st, deleted last";
        }
        type string;
      }
    }
    list ospfv3 {
      status obsolete;
      description
        "OSPFv3";
      key "id";
      leaf id {
        status obsolete;
        type uint32 {
          range "1 .. 65535";
        }
      }
      uses ospf-redistribute-top-match-grouping-obsolete {
        status obsolete;
      }
      uses ospf-redistribute-match-grouping-obsolete {
        status obsolete;
      }
    }
    list rip {
      status obsolete;
      description
        "Routing Information Protocol (RIP)";
      key "id";
      leaf id {
        status obsolete;
        description
          "User selected string identifying this rip process";
        type string;
      }
      uses ospf-redistribute-grouping-obsolete {
        status obsolete;
      }
    }
    container static {
      status obsolete;
      description
        "Static routes";
      presence "Static routes";
      uses ospf-redistribute-grouping-obsolete {
        status obsolete;
      }
    }
  }

  /////////////////////////////////////////////////////////
  // ipv6/ router / ospf
  /////////////////////////////////////////////////////////
  augment "/ios:native/ios:ipv6/ios:router/ios:ospf" {
    uses config-ipv6-router-ospf-grouping;
  }

  /////////////////////////////////////////////////////////
  // router / ospfv3
  /////////////////////////////////////////////////////////
  augment "/ios:native/ios:router" {
    uses config-router-ospfv3-grouping;
  }

  /////////////////////////////////////////////////////////
  // native / interface *
  /////////////////////////////////////////////////////////
  augment "/ios:native/ios:interface/ios:Ethernet" {
    uses config-interface-ospfv3-grouping;
  }

  augment "/ios:native/ios:interface/ios:FastEthernet" {
    uses config-interface-ospfv3-grouping;
  }

  augment "/ios:native/ios:interface/ios:GigabitEthernet" {
    uses config-interface-ospfv3-grouping;
  }

  augment "/ios:native/ios:interface/ios:TenGigabitEthernet" {
    uses config-interface-ospfv3-grouping;
  }

  augment "/ios:native/ios:interface/ios:FiveGigabitEthernet" {
    uses config-interface-ospfv3-grouping;
  }

  augment "/ios:native/ios:interface/ios:AppGigabitEthernet" {
    uses config-interface-ospfv3-grouping;
  }

  augment "/ios:native/ios:interface/ios:TwentyFiveGigE" {
    uses config-interface-ospfv3-grouping;
  }

  augment "/ios:native/ios:interface/ios:TwoGigabitEthernet" {
    uses config-interface-ospfv3-grouping;
  }

  augment "/ios:native/ios:interface/ios:FortyGigabitEthernet" {
    uses config-interface-ospfv3-grouping;
  }

  augment "/ios:native/ios:interface/ios:HundredGigE" {
    uses config-interface-ospfv3-grouping;
  }

  augment "/ios:native/ios:interface/ios:Port-channel" {
    uses config-interface-ospfv3-grouping;
  }

  augment "/ios:native/ios:interface/ios:Port-channel-subinterface" {
    uses config-interface-ospfv3-grouping;
  }

  augment "/ios:native/ios:interface/ios:Loopback" {
    uses config-interface-ospfv3-grouping;
  }

  augment "/ios:native/ios:interface/ios:Tunnel" {
    uses config-interface-ospfv3-grouping;
  }

  augment "/ios:native/ios:interface/ios:BDI" {
    uses config-interface-ospfv3-grouping;
  }

  augment "/ios:native/ios:interface/ios:Vlan" {
    uses config-interface-ospfv3-grouping;
  }

  augment "/ios:native/ios:interface/ios:Dialer" {
    uses config-interface-ospfv3-grouping;
  }

  augment "/ios:native/ios:interface/ios:BD-VIF" {
    uses config-interface-ospfv3-grouping;
  }

  /////////////////////////////////////////////////////////
  // native / interface * / ipv6
  /////////////////////////////////////////////////////////
  augment "/ios:native/ios:interface/ios:Ethernet/ios:ipv6" {
    uses config-interface-ipv6-ospf-grouping;
  }

  augment "/ios:native/ios:interface/ios:FastEthernet/ios:ipv6" {
    uses config-interface-ipv6-ospf-grouping;
  }

  augment "/ios:native/ios:interface/ios:GigabitEthernet/ios:ipv6" {
    uses config-interface-ipv6-ospf-grouping;
  }

  augment "/ios:native/ios:interface/ios:TenGigabitEthernet/ios:ipv6" {
    uses config-interface-ipv6-ospf-grouping;
  }

  augment "/ios:native/ios:interface/ios:FiveGigabitEthernet/ios:ipv6" {
    uses config-interface-ipv6-ospf-grouping;
  }

  augment "/ios:native/ios:interface/ios:AppGigabitEthernet/ios:ipv6" {
    uses config-interface-ipv6-ospf-grouping;
  }

  augment "/ios:native/ios:interface/ios:TwentyFiveGigE/ios:ipv6" {
    uses config-interface-ipv6-ospf-grouping;
  }

  augment "/ios:native/ios:interface/ios:TwoGigabitEthernet/ios:ipv6" {
    uses config-interface-ipv6-ospf-grouping;
  }

  augment "/ios:native/ios:interface/ios:FortyGigabitEthernet/ios:ipv6" {
    uses config-interface-ipv6-ospf-grouping;
  }

  augment "/ios:native/ios:interface/ios:HundredGigE/ios:ipv6" {
    uses config-interface-ipv6-ospf-grouping;
  }

  augment "/ios:native/ios:interface/ios:Port-channel/ios:ipv6" {
    uses config-interface-ipv6-ospf-grouping;
  }

  augment "/ios:native/ios:interface/ios:Port-channel-subinterface/ios:Port-channel/ios:ipv6" {
    uses config-interface-ipv6-ospf-grouping;
  }

  augment "/ios:native/ios:interface/ios:Loopback/ios:ipv6" {
    uses config-interface-ipv6-ospf-grouping;
  }

  augment "/ios:native/ios:interface/ios:Tunnel/ios:ipv6" {
    uses config-interface-ipv6-ospf-grouping;
  }

  augment "/ios:native/ios:interface/ios:BDI/ios:ipv6" {
    uses config-interface-ipv6-ospf-grouping;
  }

  augment "/ios:native/ios:interface/ios:Vlan/ios:ipv6" {
    uses config-interface-ipv6-ospf-grouping;
  }

  augment "/ios:native/ios:interface/ios:Dialer/ios:ipv6" {
    uses config-interface-ipv6-ospf-grouping;
  }

  augment "/ios:native/ios:interface/ios:BD-VIF/ios:ipv6" {
    uses config-interface-ipv6-ospf-grouping;
  }
}
