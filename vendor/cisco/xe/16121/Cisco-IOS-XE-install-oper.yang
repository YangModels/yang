module Cisco-IOS-XE-install-oper {
  yang-version 1;
  namespace "http://cisco.com/ns/yang/Cisco-IOS-XE-install-oper";
  prefix install-ios-xe-oper;

  import Cisco-IOS-XE-common-types {
    prefix common-types-ios-xe;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for install-infra operational data.
     Copyright (c) 2018-2019 by Cisco Systems, Inc.
     All rights reserved.";

  revision 2019-04-15 {
    description
      "Initial revision";
    reference "1.0.0";
    cisco-semver:module-version "1.0.0";
  }

  typedef pkg-type {
    type enumeration {
      enum "pkg-type-unknown" {
        value 0;
        description
          "Package is unknown";
      }
      enum "pkg-type-img" {
        value 1;
        description
          "Package is an image";
      }
      enum "pkg-type-smu" {
        value 2;
        description
          "Package is a Software Maintenance Unit";
      }
      enum "pkg-type-subpkg" {
        value 3;
        description
          "Package is a Sub Package";
      }
      enum "pkg-type-dmp" {
        value 4;
        description
          "Package is a Data Model Package";
      }
      enum "pkg-type-apdp" {
        value 5;
        description
          "Package is a Access Point Device Pack";
      }
      enum "pkg-type-apsp" {
        value 6;
        description
          "Package is a Access Point Service Pack";
      }
    }
    description
      "Type of package (image/Software Maintenance Unit/Sub Package)";
  }

  typedef pkg-state {
    type enumeration {
      enum "pkg-state-unknown" {
        value 0;
        description
          "Package state is unknown";
      }
      enum "pkg-state-inactive" {
        value 1;
        description
          "Package is in inactive installation state";
      }
      enum "pkg-state-activated-uncommitted" {
        value 2;
        description
          "Package is in activated yet uncommitted installation state";
      }
      enum "pkg-state-activated-committed" {
        value 3;
        description
          "Package is in activate and committed installation state";
      }
      enum "pkg-state-deactivated-uncommitted" {
        value 4;
        description
          "Package is in deactivated and uncommitted installation state";
      }
    }
    description
      "The current installation state of the package";
  }

  grouping pkg-entry {
    description
      "Package entry";
    leaf smu-id {
      type uint32;
      description
        "Identifier of the Package";
    }
    leaf type {
      type install-ios-xe-oper:pkg-type;
      description
        "Type of package";
    }
    leaf state {
      type install-ios-xe-oper:pkg-state;
      description
        "Current installation state of package";
    }
    leaf pkg-name {
      type string;
      description
        "Name of package";
    }
  }

  grouping pkg-entries {
    description
      "The collection of installed software";
    list software-packages {
      key "smu-id";
      description
        "Type of package (image/Software Maintenance Unit/Sub Package)";
      uses install-ios-xe-oper:pkg-entry;
    }
  }

  grouping rollback-point {
    description
      "The software roll back point";
    leaf id {
      type uint32;
      description
        "The identifier of the roll back point";
    }
    leaf type {
      type install-ios-xe-oper:pkg-type;
      description
        "The type of package for the roll back point, 
         such as image or sub package.";
    }
    leaf state {
      type install-ios-xe-oper:pkg-state;
      description
        "The state of the package at the time that the
         roll back point was created";
    }
    leaf label {
      type string;
      description
        "The label associated with the roll back point";
    }
    leaf description {
      type string;
      description
        "A description of the roll back point";
    }
    leaf creation-time {
      type yang:date-and-time;
      description
        "The time the roll back point was created";
    }
    leaf pkg-name {
      type string;
      description
        "The name of the package that is at this roll back point";
    }
  }

  grouping install-log {
    description
      "The install logs";
    leaf id {
      type uint32;
      description
        "The log line identifier";
    }
    leaf log-line {
      type string;
      description
        "The log line";
    }
  }

  container install-oper-data {
    config false;
    description
      "install operational data";
    list software-installation {
      key "fru slot bay chassis";
      description
        "The software that is installed on the device";
      uses common-types-ios-xe:internal-location;
      uses install-ios-xe-oper:pkg-entries;
    }
    list rollback-point {
      key "id";
      description
        "The recorded roll back points of the software
         installed on the device";
      uses install-ios-xe-oper:rollback-point;
    }
    list install-log {
      key "id";
      description
        "A collection of all the installation logs";
      uses install-ios-xe-oper:install-log;
    }
  }
}
