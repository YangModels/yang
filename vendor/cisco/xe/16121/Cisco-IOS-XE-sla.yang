module Cisco-IOS-XE-sla {
  namespace "http://cisco.com/ns/yang/Cisco-IOS-XE-sla";
  prefix ios-sla;

  import cisco-semver {
    prefix cisco-semver;
  }
 

  import ietf-inet-types {
    prefix inet;
  }

  import Cisco-IOS-XE-native {
    prefix ios;
  }

  import Cisco-IOS-XE-types {
    prefix ios-types;
  }

  organization
    "Cisco Systems, Inc.";

  contact
    "Cisco Systems, Inc.
     Customer Service
     Postal: 170 W Tasman Drive
     San Jose, CA 95134
     Tel: +1 1800 553-NETS
     E-mail: cs-yang@cisco.com";

  description
    "Cisco XE Native Service Level Agreements (SLA) Yang model.
     Copyright (c) 2016, 2018-2019 by Cisco Systems, Inc.
     All rights reserved.";

  // =========================================================================
  // REVISION
  // =========================================================================
  revision 2019-07-01 {
    description
      "- Establish semantic version baseline
       - Extended the model to support probe - 'auto ip sla mpls-lsp-monitor'
       - Extended the model to support probe - 'service-performance'
       - Support for ethernet echo probe
       - Support for ethernet jitter probe
       - Support for ethernet y1731 probe";
    cisco-semver:module-version "1.0.0";
  }
  revision 2018-11-07 {
    description
    "Cleanup spelling errors in description statements";
  }

  revision 2018-08-03 {
    description
      "Added loss support for ethernet-y1731.";
  }

  revision 2018-07-04 {
    description
      "Add icmp-jitter, tcp-connect, dns cases and its options. Add
       other options for the existing cases.";
  }

  revision 2018-06-28{
    description
        "Added leafref for ip sla schedule entry-number";
  }

  revision 2018-05-23 {
    description
      "Add http-raw request support and the other options for http probe";
  }
  revision 2018-04-11 {
    description
      "Add source-port, control and codec options for ip sla udp-jitter probe";
  }
  revision 2018-01-15 {
    description
      "Add ethernet case and its options under ip sla";
  }
  revision 2017-08-31 {
    description
      "Add dependency between ip sla schedule and ip sla reaction configuration";
  }
  revision 2017-08-03 {
    description
      "Add dependency between ip sla schedule and ip sla entry";
  }
  revision 2017-02-07 {
    description
      "Initial revision";
  }

  grouping ip-sla-sub-mode-commands-grouping {
    leaf owner {
      description
        "Owner of Entry";
      type string;
    }
    leaf tag {
      description
        "User defined tag";
      type string;
    }
    leaf frequency {
      description
        "Frequency of an operation";
      units seconds;
      type uint32 {
        range "1..604800";
      }
      default 60;
    }
    leaf timeout {
      description
        "Timeout of an operation";
      units miliseconds;
      type uint32 {
        range "0..604800000";
      }
      default 5000;
    }
    leaf threshold {
      description
        "Operation threshold in milliseconds";
      units miliseconds;
      type uint32 {
        range "0..60000";
      }
      default 5000;
    }
  }
  
  grouping ip-sla-full-history-grouping {
    container history {
      description
        "History and Distribution Data";
      container enhanced {
        description
          "Enable enhanced history collection";
        leaf interval {
          description
            "Aggregation interval";
          type uint16 {
            range "1..3600";
          }
          default 900;
        }
        leaf buckets {
          description
            "Number of buckets to collect data";
          type uint8 {
            range "1..100";
          }
          default 100;
        }
      }
      leaf buckets-kept {
          description
            "Maximum number of history buckets to collect";
          type uint8 {
            range "1..60";
          }
          default 50;
      }
      leaf distributions-of-statistics-kept {
        description
          "Maximum number of statistics distribution buckets to capture";
        type uint8 {
          range "1..20";
        }
        default 1;
      }
      leaf filter {
        description
          "Add operation to History when...";
        type enumeration {
          enum "all";
          enum "failures";
          enum "none";
          enum "overThreshold";
        }
        default none;
      }
      leaf hours-of-statistics-kept {
        description
          "Maximum number of statistics hour groups to capture";
        type uint8 {
          range "0..25";
        }
        default 2;
      }
      leaf lives-kept {
        description
          "Maximum number of history lives to collect";
        type uint8 {
          range "0..2";
        }
        default 0;
      }
      leaf statistics-distribution-interval {
        description
          "Statistics distribution interval size";
        type uint8 {
          range "1..100";
        }
        default 20;
      }
    }
  }//end ip-sla-full-history-grouping

  grouping ip-sla-history-without-enhanced-grouping {
    container history {
    description
      "History and Distribution Data";
      leaf buckets-kept {
        description
          "Maximum number of history buckets to collect";
        type uint8 {
          range "1..60";
        }
        default 50;
      }
      leaf distributions-of-statistics-kept {
        description
          "Maximum number of statistics distribution buckets to capture";
        type uint8 {
          range "1..20";
        }
        default 1;
      }
      leaf filter {
        description
          "Add operation to History when...";
        type enumeration {
          enum "all";
          enum "failures";
          enum "none";
          enum "overThreshold";
        }
        default none;
      }
      leaf hours-of-statistics-kept {
        description
          "Maximum number of statistics hour groups to capture";
        type uint8 {
          range "0..25";
        }
      }
      leaf lives-kept {
        description
          "Maximum number of history lives to collect";
        type uint8 {
          range "0..2";
        }
      }
      leaf statistics-distribution-interval {
        description
          "Statistics distribution interval size";
        type uint8 {
          range "1..100";
        }
      }
    }
  }//end ip-sla-history-without-enhanced-grouping

  grouping ip-sla-jitter-percentile {
    container percentile {
      description
        "Set percentile statistics levels";
      leaf jitteravg {
        description
          "% of Average Jitter values to use (default 100%)";
        type uint8 {
          range "90..100";
        }
      }
      leaf jitterds {
        description
          "% of destination to source Jitter value to use (default 100%)";
        type uint8 {
          range "90..100";
        }
      }
      leaf jittersd {
        description
          "% of source to destination value to use (default 100%)";
        type uint8 {
          range "90..100";
        }
      }
      leaf owds {
        description
          "% of One way destination to source Jitter value to use (default 100%)";
        type uint8 {
          range "90..100";
        }
      }
      leaf owsd {
        description
          "% of One way source to destination value to use (default 100%)";
        type uint8 {
          range "90..100";
        }
      }
      leaf rtt {
        description
          "% of Round trip time value to use (default 100%)";
        type uint8 {
          range "90..100";
        }
      }
    }
  }
  
  grouping ip-sla-path-echo-grouping {
    leaf paths-of-statistics-kept {
      description
        "Maximum number of statistics paths to capture";
      type uint8 {
        range "1..128";
      }
      default 5;
    }
    leaf samples-of-history-kept {
      description
        "Maximum number of history samples to collect";
      type uint8 {
        range "1..30";
      }
    }
    leaf hops-of-statistics-kept {
      description
        "Maximum number of statistics hops to capture";
      type uint8 {
        range "1..30";
      }
      default 16;
    }
    leaf-list lsr-path {
      description
        "Loose Source Routing Path";
      type union {
        type string;
        type inet:ipv4-address;
      }
    }
    leaf request-data-size {
      description
        "Request data size";
      type uint32 {
        range "0..16384";
      }
      default 28;
    }
    choice tos-param {
      case tos {
        leaf tos {
          description
            "Type Of Service";
          type uint8 {
            range "0..255";
          }
          default 0;
        }
      }
      case traffic-class {
        leaf traffic-class {
          description
            "Traffic class";
          type uint8 {
            range "0..255";
          }
        }
      }
    }
    leaf verify-data {
      description
        "Verify data";
      type boolean;
    }
    leaf vrf {
      description
        "Configure IP SLAs for a VPN Routing/Forwarding instance";
      type string;
    }
    uses ip-sla-history-without-enhanced-grouping;
  }//end of ip-sla-path-echo-grouping

  grouping ip-sla-path-jitter-grouping {
    leaf-list lsr-path {
      description
        "Loose Source Routing Path";
      type union {
        type string;
        type inet:ipv4-address;
      }
    }
    leaf request-data-size {
      description
        "Request data size";
      type uint32 {
        range "0..16384";
      }
    }
    choice tos-param {
      case tos {
        leaf tos {
          description
            "Type Of Service";
          type uint8 {
            range "0..255";
          }
        }
      }
      case traffic-class {
        leaf traffic-class {
          description
            "Traffic class";
         type uint8 {
            range "0..255";
          }
        }
      }
    }
    leaf flow-label {
      description "Flow Label Value for IPv6 destination";
      type uint64 {
        range "0..1048575";
      }
    }
    leaf verify-data {
      description
        "Verify data";
      type boolean;
    }
    leaf vrf {
      description
        "Configure IP SLAs for a VPN Routing/Forwarding instance";
      type string;
    }
  }//end of ip-sla-path-jitter-grouping

  grouping ip-sla-default-path-jitter-grouping {
    leaf frequency {
      description
        "Frequency of an operation";
      type empty;
    }
    leaf lsr-path {
      description
        "Loose Source Routing Path";
      type empty;
    }
    leaf owner {
      description
        "Owner of Entry";
      type empty;
    }
    leaf request-data-size {
      description
        "Request data size";
      type empty;
    }
    leaf tag {
      description
        "User defined tag";
      type empty;
    }
    leaf threshold {
      description
        "Operation threshold in milliseconds";
      type empty;
    }
    leaf timeout {
      description
        "Timeout of an operation";
      type empty;
    }
    leaf tos {
      description
        "Type Of Service";
      type empty;
    }
    leaf verify-data {
      description
        "Verify data";
      type boolean;
    }
    leaf vrf {
      description
        "Configure IP SLAs for a VPN Routing/Forwarding instance";
      type empty;
    }
  }//end of ip-sla-default-path-jitter-grouping

  grouping ip-sla-udp-jitter-grouping {
    container history {
      description
        "History and Distribution Data";
      leaf distributions-of-statistics-kept {
        description
          "Maximum number of statistics distribution buckets to capture";
        type uint8 {
          range "1..20";
        }
        default 1;
      }
      container enhanced {
        description
          "Enable enhanced history collection";
        leaf interval {
          description
            "Aggregation interval";
          type uint16 {
            range "1..3600";
          }
        }
        leaf buckets {
          description
            "Number of buckets to collect data";
          type uint8 {
            range "1..100";
          }
        }
      }
      leaf hours-of-statistics-kept {
        description "Maximum number of statistics hour groups to capture";
        type uint8 {
          range "0..25";
        }
      }
      leaf statistics-distribution-interval {
        description "Statistics distribution interval size";
        type uint8 {
          range "1..100";
        }
      }
    }//end history
    container control_sub_mode {            //Since there is 'control' option available in the udp-jitter probe, both under the sub-command level and main command level. Using this dummy container to wrap the 'control' container for the sub-command. 
      container control {
        description
          "Set control protocol parameters";
        leaf retry {
          description "How often the control message should do a retry (default 3 times)";
          type uint8 {
            range "1..5";
          }
          default 3;
        }
        leaf timeout {
          description "How long to wait for control message timeout (default 5 seconds)";
          type uint16 {
            range "1..10000";
          }
          default 5;
        }
      }
    }
    leaf data-pattern {
      status obsolete;
      description
        "Data Pattern in Hex 0-FFFFFFFF (OBSOLETE)";
      type string;
    }
    leaf request-data-size {
      description
      "Number of bytes in payload";
      type uint16 {
        range "16..17512";
      }
      default 32;
    }
    leaf response-data-size {
      description
      "Number of bytes in response payload";
      type uint16 {
        range "20..17512";
      }
    }
    choice tos-param {
      case tos {
        leaf tos {
          description
            "Type Of Service";
          type uint8 {
            range "0..255";
          }
        }
      }
      case traffic-class {
        leaf traffic-class {
          description
            "Traffic class";
          type uint8 {
            range "0..255";
          }
        }
      }
    }
    leaf vrf {
      description
        "Configure IP SLAs for a VPN Routing/Forwarding instance";
      type string;
    }
    leaf verify-data {
      description
        "Verify data";
      type boolean;
    }
    leaf precision {
      description "Set precision of measurement";
      type enumeration {
        enum "microseconds" {
        }
        enum "milliseconds" {
        }
      }
    }
    leaf optimize{
      description
        "Optimize timestamp of measurement";
      type enumeration {
        enum "timestamp" {
        }
      }
    }
    leaf enhanced {
      description
        "Improve the accuracy of measurement";
      type enumeration {
        enum "timestamp" {
        }
      }
    }
    leaf operation-packet-priority {
      description
        "Set operation packet properties";
      type enumeration {
        enum "high" {
        }
        enum "normal" {
        }
      }
    }
    container clock-tolerance-config {
      description "Set acceptable clock synchronization error";
      container ntp {
        description
          "Acceptable clock synchronization error due to NTP";
        container oneway {
          description
            "Acceptable clock synchronization error in one-way measurement";
          choice clock-tolerance-param {
            case absolute-type {
              leaf absolute {
                description "Acceptable error in microseconds";
                type uint32 {
                  range "0..100000";
                }
              }
            }
            case percent-type {
              leaf percent {
                description
                  "Acceptable error as percent of value measured";
                type uint8 {
                  range "0..100";
                }
              }
            }
          } // end choice
        } // end container oneway
      } // end ntp
    } // end clock-tolerance-config
    container clock-tolerance {
      status deprecated;
      description "Set acceptable clock synchronization error. (DEPRECATED, use clock-tolerance-config container)";
      presence true;
      container ntp {
        description
          "Acceptable clock synchronization error due to NTP";
        presence true;
        container oneway {
          description
            "Acceptable clock synchronization error in one way measurement";
          choice clock-tolerance-param {
            case absolute-type {
              leaf absolute {
                description "Acceptable error in microseconds";
                type uint32 {
                  range "0..100000";
                }
              }
            }
            case percent-type {
              leaf percent {
                description
                  "Acceptable error as percent of value measured";
                type uint8 {
                  range "0..100";
                }
              }
            }
          } // end choice
        } // end container oneway
      } // end ntp
    } // end clock-tolerance
  }//end of ip-sla-udp-jitter-grouping

  grouping ip-sla-udp-echo-grouping {
    uses ip-sla-full-history-grouping;
    leaf request-data-size {
      description
      "Number of bytes in payload";
      type uint16 {
        range "4..1500";
      }
    }
    choice tos-param {
      case tos {
        leaf tos {
          description
            "Type Of Service";
          type uint8 {
            range "0..255";
          }
        }
      }
      case traffic-class {
        leaf traffic-class {
          description
            "Traffic class";
          type uint8 {
            range "0..255";
          }
        }
      }
    }
    leaf verify-data {
      description
        "Verify data";
      type boolean;
    }
    leaf vrf {
      description
        "Configure IP SLAs for a VPN Routing/Forwarding instance";
      type string;
    }
    leaf data-pattern {
      description
        "Data Pattern in Hex 0-FFFFFFFF";
      type string;
    }
  }//end of ip-sla-udp-echo-grouping

  grouping ip-sla-ethernet-delay-grouping {
    container aggregate {
      description
        "Aggregate parameters";
      leaf interval {
        description
          "Specify interval period";
        type uint32 {
          range "1..65535";
        }
      }
    }
    container history {
      description
        "History parameters";
      leaf interval {
        description
          "Specify number of intervals";
        type uint8 {
          range "1..10";
        }
      }
    }
  }//end grouping
  
  grouping ip-sla-ethernet-distribution-grouping {
    container distribution {
      description "Specify the distribution statistics parameters";
      container delay {
        description "Specify delay distribution parameters";
        container one-way {
          leaf one-way {
            description "Specify one-way distribution parameters";
            type uint8 {
              range "1..10";
            }
          }//end of one-way
          leaf bin-upper-boundry {
            description "Specify a comma separated list of bin upper boundaries in micro-second";
            type string;
          }//end of bin-upper-boundry
        }//end of one-way
        container two-way {
          when "../../../ios-sla:name='DMM' or
                ../../../ios-sla:name='DMMv1'";
          leaf two-way {
            description "Specify two-way distribution parameters";
            type uint8 {
              range "1..10";
            }
          }//end of two-way
          leaf bin-upper-boundry {
            description "Specify a comma separated list of bin upper boundaries in micro-second";
            type string;
          }//end of bin-upper-boundry
        }//end of two-way
      }//end of delay
      container delay-variation {
        description "Specify delay-variation distribution parameters";
        container one-way {
          leaf one-way {
            description "Specify one-way distribution parameters";
            type uint8 {
              range "1..10";
            }
          }//end of one-way
          leaf bin-upper-boundry {
            description "Specify a comma separated list of bin upper boundaries in micro-second";
            type string;
          }//end of bin-upper-boundry
        }//end of one-way
        container two-way {
          when "../../../ios-sla:name='DMM' or
                ../../../ios-sla:name='DMMv1'";
          leaf two-way {
            description "Specify two-way distribution parameters";
            type uint8 {
              range "1..10";
            }
          }//end of two-way
          leaf bin-upper-boundry {
            description "Specify a comma separated list of bin upper boundaries in micro-second";
            type string;
          }//end of bin-upper-boundry
        }//end of two-way
      }//end of delay-variation
    }//end of distribution
  }//end of ip-sla-ethernet-distribution-grouping
  
  grouping ip-sla-ethernet-y1731-grouping {
    choice delay-or-loss {
      case delay-case {
        container delay {
          description
            "Y1731 Delay and Delay Variation Operation";
          choice sender-or-receiver {
            case sender-case {
              container sender {
                leaf name {
                  description
                    "Y1731 Delay option";
                  type enumeration {
                    enum "1DM";
                    enum "DMM";
                    enum "DMMv1";
                  }
                }
                leaf burst {
                  description
                    "Enable bursting of delay frames";
                  type empty;
                }
                uses ip-sla-ethernet-delaysender-loss-common-grouping;
                container clock {
                  description "Specify clock parameters";
                  when "../ios-sla:name='DMM' or
                        ../ios-sla:name='DMMv1'";
                  leaf sync {
                    description "Clocks are in sync on sender and responder";
                    type boolean;
                  }
                }
                uses ip-sla-ethernet-distribution-grouping;
                container frame {
                  description "Specify frame parameters";
                  leaf interval {
                    description "Specify inter-frame period";
                    type frame-interval-type;
                  }//end of interval
                  leaf size {
                    description "Specify payload size in 4 octet increments";
                    type uint16 {
                      range "64..1400";
                    }
                  }//end of size
                  leaf burst {
                    description "Number of frames to send per burst";
                    when "(../../burst)";
                    type uint16 {
                      range "1..65535";
                    }
                  }//end of burst 
                  leaf offset {
                    description "Specify the frame offset to be used for calculations";
                    when "../../ios-sla:name='DMM' or
                      ../../ios-sla:name='DMMv1' or
                      ../../../ios-sla:receive/ios-sla:name='1DM'";
                    type uint8 {
                      range "1..10";
                    }
                  }//end of offset
                }//end of frame
              }//sender
            }//end of sender-case
            case receive-case {
              container receive {
                leaf name {
                  description
                    "Y1731 Delay option";
                  type enumeration {
                    enum "1DM";
                  }
                }
                leaf domain {
                  description
                    "Specify the Ethernet OAM domain";
                  type string;
                }
                choice evc-or-vlan {
                   leaf evc {
                      description
                        "Specify the Ethernet Virtual Circuit Identifier";
                      type string;
                   }
                   leaf vlan {
                     description
                       "Specify the VLAN";
                     type uint16 {
                       range "1..4096";
                     }
                   }
                }//evc-or-vlan-choice
                leaf cos {
                  description
                    "Specify the Class of Service";
                  type uint8 {
                    range "0..7";
                  }
                }
                choice mac-or-mpid {
                  leaf mac-address {
                    description
                      "Specify the remote mac-address";
                    type ios-types:cisco-mac-address-type;
                  }
                  leaf mpid {
                    description
                      "Specify the remote MPID";
                    type uint16 {
                      range "1..8191";
                    }
                  }
                }//end of mac-or-mpid
                uses ip-sla-ethernet-sub-command-grouping;
                container aggregate {
                  description
                    "Aggregate parameters";
                  leaf interval {
                    description "Specify interval period";
                    type uint16 {
                      range "1..65535";
                    }
                  }//end of interval
                }//end of aggregate
                container frame {
                  description "Specify frame parameters";
                  leaf offset {
                    description "Specify the frame offset to be used for calculations";
                    type uint8 {
                      range "1..10";
                    }
                  }//end of offset
                }//end of frame
                container distribution {
                  description "Specify the distribution statistics parameters";
                  container delay {
                    description "Specify delay distribution parameters";
                    container one-way {
                      leaf one-way {
                        description "Specify one-way distribution parameters";
                        type uint8 {
                          range "1..10";
                        }
                      }//end of one-way
                      leaf bin-upper-boundry {
                        description "Specify a comma separated list of bin upper boundaries in micro-second";
                        type string;
                      }//end of bin-upper-boundry
                    }//end of one-way
                  }// end of delay
                  container delay-variation {
                    description "Specify delay-variation distribution parameters";
                    container one-way {
                      leaf one-way {
                        description "Specify one-way distribution parameters";
                        type uint8 {
                          range "1..10";
                        }
                      }//end of one-way
                      leaf bin-upper-boundry {
                        description "Specify a comma separated list of bin upper boundaries in micro-second";
                        type string;
                      }//end of bin-upper-boundry
                    }//end of one-way container
                  } // end of delay-variation
                } // end of distribution 
              }//end of receive
            }//end of receive-case
          }//end of choice-sender-or-receive
        }//end of delay
      }//end of delay-case
      case loss-case {
        container loss {
          description
            "Y1731 Loss Operation";
          container wrapper-container {                     //This is a dummy container, it has no significance on the CLI cmd formation. Just to keep the grouping "ip-sla-ethernet-sub-command-grouping" at the same depth under both delay and loss containers.
            leaf name {
              description
                "Y1731 Delay option";
              type enumeration {
                enum "LMM" {
                  description "Loss Measurement Message/Loss Measurement Reply frames";
                }
                enum "SLM" {
                  description "Synthetic Loss Message/Synthetic Loss Reply frames";
                }
              }
            }//end of name
            leaf burst {
              description
                "Enable bursting of delay frames. Applicable only to SLM option";
              when "../name='SLM'";
              type empty;
            }//end of burst
            uses ip-sla-ethernet-delaysender-loss-common-grouping;
            container frame {
              description "Specify frame parameters";
              leaf interval {
                description "Specify inter-frame period";
                type frame-interval-type;
              }//end of interval
              leaf consecutive {
                description "Specify the consecutive frames to be used for calculations";
                type uint16 {
                  range "1..10";
                }
              }//end of consecutive
              leaf size {
                description "Specify payload size in 4 octet increments";
                when "../../name='SLM'";
                type uint16 {
                  range "64..1400";
                }
              }//end of size
              leaf burst {
                description "Number of frames to send per burst";
                when "(../../burst)";
                type uint16 {
                  range "1..65535";
                }
              }//end of burst 
            }//end of frame
            container availability {
              description "Specify the availability parameters";
              container algorithm {
                description "Specify the algorithm to use";
                leaf sliding-window {
                  description "Use a sliding window";
                  type boolean;
                }
                leaf static-window {
                  description "Use a static window";
                  type boolean;
                }
              }//end of alogorithm
            }//end of availability
          }//end of wrapper-container
        }//end of loss
      }//end of loss-case
    }//end of choice-delay-or-loss
  }//grouping ip-sla-ethernet-y1731
  
  grouping ip-sla-ethernet-delaysender-loss-common-grouping {
    leaf domain {
      description
        "Specify the Ethernet OAM domain";
      type string;
    }
    choice evc-or-vlan {
      leaf evc {
        description
          "Specify the Ethernet Virtual Circuit Identifier";
        type string;
      }
      leaf vlan {
        description
          "Specify the VLAN";
      type uint16 {
        range "1..4096";
        }
      }
    }//evc-or-vlan-choice
    choice mac-or-mpid {
      leaf mac-address {
        description
          "Specify the remote mac-address";
        type ios-types:cisco-mac-address-type;
      }
      leaf mpid {
        description
          "Specify the remote MPID";
        type uint16 {
          range "1..8191";
        }
      }
    }//mac-or-mpid
    leaf cos {
      description
        "Specify the Class of Service";
      type uint8 {
        range "0..7";
      }
    }
    container source {
      description
        "Specify the local MPID or MAC-Address";
      choice mac-or-mpid {
        leaf mac-address {
          description
            "Specify the local mac-address";
          type ios-types:cisco-mac-address-type;
        }
        leaf mpid {
          description
            "Specify the local MPID";
          type uint16 {
            range "1..8191";
          }
        }
      }
    }//source
    uses ip-sla-ethernet-sub-command-grouping;
    container aggregate {
      description
        "Aggregate parameters";
      container interval {
        description "Specify interval period";
        leaf interval-period {
          description "Specify interval period";
          when "not (current()/../../../ios-sla:burst)";
          type uint32 {
            range "1..65535";
          }
        }//end of interval
        leaf burst-cycles {
          description "Specify number of burst cycles";
          when "current()/../../../ios-sla:burst";
          type uint16 {
            range "1..900";
          }
        }//end of burst-cycle
      }//end of interval
    }//end of aggregate
    leaf frequency {
      description "Number of seconds after which to repeat burst";
      when "current()/../ios-sla:burst";
      type uint16 {
        range "1..60";
      }
    }//end of frequency
  }//end of ip-sla-ethernet-delaysender-loss-common-grouping
  
  grouping ip-sla-ethernet-sub-command-grouping {
    container history {
      description
        "History parameters";
      leaf interval {
        description
          "Specify number of intervals";
        type uint8 {
          range "1..10";
        }
      }
    }
    leaf max-delay {
      description "Specify the max delay";
      when "../ios-sla:name = 'DMM' or 
            ../ios-sla:name = 'DMMv1' or
            ../ios-sla:name = '1DM' or
            ../ios-sla:name = 'LMM'";
      type uint16 {
        range "1..65535";
      }
    }//end of max-delay
    leaf owner {
      description "Specify operation owner";
      type string;
    }//end of owner
  }//end ip-sla-ethernet-sub-command-grouping
  
  grouping ip-sla-service-performance-packet-direction-sub-command-grouping {
    container packet {
      description "Packet Profiles";
      leaf outer-vlan {
        description "Specify the Outer VLAN";
        type uint16 {
          range "0..4095";
        }
      }//end of outer-vlan
      leaf packet-size {
        description "Packet Size";
        type packet-size-type;
      }//end of packet-size
    }//end of packet
  }//end of ip-sla-service-performance-packet-direction-sub-command-grouping
  
  grouping ip-sla-service-performance-traffic-direction-sub-command-grouping {
    container traffic {
      description "Service Performance traffic profile";
      leaf direction {
        description "Traffic direction";
        type enumeration {
          enum "external" {
            description "external direction";
          }
          enum "internal" {
            description "internal direction";
          }
        }
      }//end of direction
      leaf cbs {
        description "Committed Burst Size";
        type uint32 {
          range "0..16000000";
        }
        units Kbps;
      }
      leaf cir {
        description "Committed Information Rate. The range mentioned is for 10G interface. For 1G interface, the range is 0..1000000";
        type uint32 {
          range "0..10000000";
        }
        units Kbps;
      }
      leaf ebs {
        description "Excess Burst Size";
        type uint32 {
          range "0..16000000";
        }
        units Kbps;
      }
      leaf eir {
        description "Excess Information Rate. The range mentioned is for 10G interface. For 1G interface, the range is 0..1000000";
        type uint32 {
          range "0..10000000";
        }
        units Kbps;
      }
      container rate-step {
        description "Rate Step";
        choice Kbps_or_pps {
          container Kbps {
            description "Kilobits per second rate. The range mentioned is for 10G interface. For 1G interface, the range is 0..1000000";
            leaf step1 {
              description "Step 1 (Kbps/pps)";
              type uint32 {
                range "1..10000000";
              }
              units Kbps/pps;
            }//end of step1
            leaf step2 {
              description "Step 2 (Kbps/pps), Step 2 >= Step 1";
              type uint32 {
                range "1..10000000";
              }
              units Kbps/pps;
            }//end of step2
            leaf step3 {
              description "Step 3 (Kbps/pps), Step 3 >= Step 2";
              type uint32 {
                range "1..10000000";
              }
              units Kbps/pps;
            }//end of step3
            leaf step4 {
              description "Step 4 (Kbps/pps), Step 4 >= Step 3";
              type uint32 {
                range "1..10000000";
              }
              units Kbps/pps;
            }//end of step4
            leaf step5 {
              description "Step 5 (Kbps/pps), Step 5 >= Step 4";
              type uint32 {
                range "1..10000000";
              }
              units Kbps/pps;
            }//end of step5
            leaf step6 {
              description "Step 6 (Kbps/pps), Step 6 >= Step 5";
              type uint32 {
                range "1..10000000";
              }
              units Kbps/pps;
            }//end of step6
            leaf step7 {
              description "Step 7 (Kbps/pps), Step 7 >= Step 6";
              type uint32 {
                range "1..10000000";
              }
              units Kbps/pps;
            }//end of step7
            leaf step8 {
              description "Step 8 (Kbps/pps), Step 8 >= Step 7";
              type uint32 {
                range "1..10000000";
              }
              units Kbps/pps;
            }//end of step8
            leaf step9 {
              description "Step 9 (Kbps/pps), Step 9 >= Step 8";
              type uint32 {
                range "1..10000000";
              }
              units Kbps/pps;
            }//end of step9
            leaf step10 {
              description "Step 10 (Kbps/pps), Step 10 >= Step 9";
              type uint32 {
                range "1..10000000";
              }
              units Kbps/pps;
            }//end of step10
          }//end of Kbps
          container pps {
            description "Packet per second rate";
            leaf step1 {
              description "Step 1 (Kbps/pps)";
              type uint32 {
                range "1..15000000";
              }
              units Kbps/pps;
            }//end of step1
            leaf step2 {
              description "Step 2 (Kbps/pps), Step 2 >= Step 1";
              type uint32 {
                range "1..15000000";
              }
              units Kbps/pps;
            }//end of step2
            leaf step3 {
              description "Step 3 (Kbps/pps), Step 3 >= Step 2";
              type uint32 {
                range "1..15000000";
              }
              units Kbps/pps;
            }//end of step3
            leaf step4 {
              description "Step 4 (Kbps/pps), Step 4 >= Step 3";
              type uint32 {
                range "1..15000000";
              }
              units Kbps/pps;
            }//end of step4
            leaf step5 {
              description "Step 5 (Kbps/pps), Step 5 >= Step 4";
              type uint32 {
                range "1..15000000";
              }
              units Kbps/pps;
            }//end of step5
            leaf step6 {
              description "Step 6 (Kbps/pps), Step 6 >= Step 5";
              type uint32 {
                range "1..15000000";
              }
              units Kbps/pps;
            }//end of step6
            leaf step7 {
              description "Step 7 (Kbps/pps), Step 7 >= Step 6";
              type uint32 {
                range "1..15000000";
              }
              units Kbps/pps;
            }//end of step7
            leaf step8 {
              description "Step 8 (Kbps/pps), Step 8 >= Step 7";
              type uint32 {
                range "1..15000000";
              }
              units Kbps/pps;
            }//end of step8
            leaf step9 {
              description "Step 9 (Kbps/pps), Step 9 >= Step 8";
              type uint32 {
                range "1..15000000";
              }
              units Kbps/pps;
            }//end of step9
            leaf step10 {
              description "Step 10 (Kbps/pps), Step 10 >= Step 9";
              type uint32 {
                range "1..15000000";
              }
              units Kbps/pps;
            }//end of step10
          }//end of pps
        }//end of choice Kbps_or_pps
      }//end of rate-step
    }//end of traffic
  }//end of ip-sla-service-performance-traffic-direction-sub-command-grouping
  
  grouping ip-sla-service-performance-measurement-type-sub-command-grouping {
    leaf direction {
      description "Measurement direction";
      type enumeration {
        enum "external" {
          description "external direction";
        }
        enum "internal" {
          description "internal direction";
        }
      }
    }//end of direction
    container conform-color {
      description "conform-color";
    }//end of conform-color
    container exceed-color {
      description "exceed-color";
    }//end of exceed-color
    leaf delay {
      description "Delay measurement";
      type empty;
    }//end of delay
    leaf jitter {
      description "Jitter measurement";
      type empty;
    }//end of jitter
    leaf loss {
      description "loss measurement";
      type empty;
    }//end of loss
    leaf receive {
      description "Received bytes/packets measurement";
      type empty;
    }//end of receive
    leaf throughput {
      description "Throughput measurement";
      type empty;
    }//end of throughput
  }//end of ip-sla-service-performance-measurement-type-sub-command-grouping
  
  grouping ip-sla-service-performance-sub-command-grouping {
    container aggregation {
      description "Statistics aggregation";
      container interval {
        description "Statistics aggregation period";
        leaf buckets {
          description "interval statistic buckets";
          type uint8 {
            range "1..30";
          }
        }
      }
    }//end of aggregation
    leaf description {
      description "Operation Description";
      type string;
    }//end of description
    container duration {
      description "Service Performance duration configuration";
      leaf time {
        description "Time based duration";
        type uint16 {
          range "10..40950";
        }
      }
    }//end of duration
    container frequency_serv_perf {
      description "Scheduled frequency";
      leaf time {
        description "Frequency period";
        type uint32 {
          range "20..604800";
        }
      }//end of time
      container frequency-iteration {
        description
          "Frequency iteration configuration";
        leaf iteration {
          description "Iteration number";
          type uint8 {
            range "1..100";
          }
        }//end of iteration
        leaf delay {
          description "Delay between interactions";
          type uint8 {
            range "0..10";
          }
        }//end of delay
      }// end of frequency iteration container
    }//end of frequency
    container loopback {
      description "loopback";
      container direction {
        description "loopback direction";
        leaf internal {
          description "internal direction";
          
          type boolean;
        }//end of internal
        leaf external {
          description "external direction";
          
          type boolean;
        }//end of external
      }//end of direction
    }//end of loopback
    container profile {
      description "Service Performance Profile";
    }
    container measurement-type {
      description "Measurement";
    }//end of measurement-type
    leaf signature {
      description "Payload Contents";
      type string;
    }//end of signature
  }//end of ip-sla-service-performance-sub-command-grouping

  grouping config-ip-sla-react-threshold-type-grouping {
    container threshold-type {
      choice threshold-type-param {
        case xOfy-type {
          container xOfy {
            presence true;
            leaf x-val {
              description
                "X value";
              type uint8 {
                range "1..16";
              }
            }
            leaf y-val {
              description
                "Y value";
              type uint8 {
                range "1..16";
              }
            }
          }
        }
        case average-type {
          container average {
            presence true;
            description "Average over N attempts";
            leaf average-val {
              description
                "N value";
              type uint8 {
                range "1..16";
              }
            }
          }
        }
        case consecutive-type {
          container consecutive {
            presence true;
            description "Consecutive occurrences";
            leaf consecutive-val {
              description
                "Number of occurrences";
              type uint8 {
                range "1..16";
              }
            }
          }
        }
        case immediate-type {
          leaf immediate {
            description
              "React immediately";
            type empty;
          }
        }
        case never-type {
          leaf never {
            description
              "Never react";
            type empty;
          }
        }
      }
    }
  } //end grouping

  grouping config-ip-sla-react-threshold-value-grouping {
    container threshold-value {
      description "Threshold value";
      leaf upper-limit-val {
        description
          "Upper limit";
        type uint32 {
          range "1..60000";
        }
      }
      leaf lower-limit-val {
        description
          "Lower limit";
        type uint32 {
          range "1..60000";
        }
      }
    }
  }
  
  typedef hour-min {
    type string {
      pattern '(0[0-9]|1[0-9]|2[0-3]):[0-5][0-9]';
    }
  }
  
  typedef hour-min-sec {
    type string {
      pattern '(0[0-9]|1[0-9]|2[0-3]):[0-5][0-9]:[0-5][0-9]';
    }
  }

  typedef reply-dscp-bits-type {
    type enumeration {
      enum "af11" {
          value 100;
          description "Match packets with AF11 dscp (001010)";
      }
      enum "af12" {
        description "Match packets with AF12 dscp (001100)";
      }
      enum "af13" {
        description "Match packets with AF13 dscp (001110)";
      }
      enum "af21" {
        description "Match packets with AF21 dscp (010010)";
      }
      enum "af22" {
        description "Match packets with AF22 dscp (010100)";
      }
      enum "af23" {
        description "Match packets with AF23 dscp (010110)";
      }
      enum "af31" {
        description "Match packets with AF31 dscp (011010)";
      }
      enum "af32" {
        description "Match packets with AF32 dscp (011100)";
      }
      enum "af33" {
        description "Match packets with AF33 dscp (011110)";
      }
      enum "af41" {
        description "Match packets with AF41 dscp (100010)";
      }
      enum "af42" {
        description "Match packets with AF42 dscp (100100)";
      }
      enum "af43" {
        description "Match packets with AF43 dscp (100110)";
      }
      enum "cs1" {
        description "Match packets with CS1(precedence 1) dscp (001000)";
      }
      enum "cs2" {
        description "Match packets with CS2(precedence 2) dscp (010000)";
      }
      enum "cs3" {
        description "Match packets with CS3(precedence 3) dscp (011000)";
      }
      enum "cs4" {
        description "Match packets with CS4(precedence 4) dscp (100000)";
      }
      enum "cs5" {
        description "Match packets with CS5(precedence 5) dscp (101000)";
      }
      enum "cs6" {
        description "Match packets with CS6(precedence 6) dscp (110000)";
      }
      enum "cs7" {
        description "Match packets with CS7(precedence 7) dscp (111000)";
      }
      enum "default" {
        description "Match packets with default dscp (000000)";
      }
      enum "ef" {
        description "Match packets with EF dscp (101110)";
      }
    }
  }//end of reply-dscp-bits-type
  
  typedef frame-interval-type {
    type enumeration {
      enum "10" {
        description "Frame interval 10 ms";
      }
      enum "100" {
        description "Frame interval 100 ms";
      }
      enum "1000" {
        description "Frame interval 1000 ms";
      }
      enum "20" {
        description "Frame interval 20 ms";
      }
      enum "25" {
        description "Frame interval 25 ms";
      }
      enum "50" {
        description "Frame interval 50 ms";
      }
    }
  }//end of frame-interval-type
  
  typedef packet-size-type {
    type enumeration {
      enum "1024" {
        description "1024 byte";
      }
      enum "128" {
        description "128 byte";
      }
      enum "1280" {
        description "1280 byte";
      }
      enum "1518" {
        description "1518 byte";
      }
      enum "256" {
        description "256 byte";
      }
      enum "512" {
        description "512 byte";
      }
      enum "64" {
        description "64 byte";
      }
      enum "9216" {
        description "9216 byte";
      }
      enum "imix" {
        description "imix packet size";
      }
    }
  }//end of packet-size-type
  
  grouping mpls-lsp-monitor-type-common-grouping {
    leaf access-list {
      description "Apply Access-List";
      type uint16 {
        range "1..9";
      }
    }
    leaf delete-scan-factor {
      description "Scan Factor for automatic deletion";
      type uint32 {
        range "0..2147483647";
      }
    }
    leaf exp {
      description "EXP value";
      type uint8 {
        range "0..7";
      }
    }
    leaf lsp-selector {
      description "Local-Host address used to select the LSP";
      type inet:ipv4-address;
    }
    leaf scan-interval {
      description "Scan Interval for automatic discovery in minutes";
      type uint32 {
        range "1..70560";
      }
    }
    leaf tag {
      description "User defined tag";
      type string;
    }
    leaf threshold {
      description "Operation threshold in milliseconds";
      type uint16 {
        range "1..60000";
      }
    }
    leaf timeout {
      description "Timeout of an operation";
      type uint32 {
        range "0..604800000";
      }
    }
  }
  
  grouping mpls-lsp-monitor-type-echo-grouping {
    uses mpls-lsp-monitor-type-common-grouping;
    leaf force-explicit-null {
      description "force an explicit null label to be added";
      type boolean;
    }
    
    leaf reply-dscp-bits {
      description "DSCP bits in reply IP header";
      type union {
        type uint8 {
          range "0..63";
        }
        type reply-dscp-bits-type;
      }
    }
    container reply-mode {
      description "Reply for LSP echo request";
      leaf ipv4 {
        description "Send reply via IPv4";
        type boolean;
      }
      leaf router-alert {
        description "Send reply via IPv4 UDP with router alert";
        type boolean;
      }
    }
    leaf request-data-size {
      description "Request data size";
      type uint16 {
        range "100..1500";
      }
    }
    container secondary-frequency {
      description "Frequency to be used if there is any violation condition happens";
      leaf both {
        description "Enable secondary freq for timeout and connection loss";
        type uint32 {
          range "1..604800";
        }
      }
      leaf connection-loss {
        description "Enable secondary freq for connection loss";
        type uint32 {
          range "1..604800";
        }
      }
      leaf timeout {
        description "Enable secondary freq for timeout";
        type uint32 {
          range "1..604800";
        }
      }
    }
    leaf ttl {
      description "Time to live";
      type uint8 {
        range "1..255";
      }
    }
  }//end of mpls-lsp-monitor-type-echo-grouping
  
  grouping mpls-lsp-monitor-type-jitter-grouping {
    uses mpls-lsp-monitor-type-common-grouping;
    
    leaf dest-port {
      description "Destination Port";
      type uint16 {
        range "1..65535";
      }
    }
    leaf interval {
      description "Inter Packet Interval";
      type uint16 {
        range "4..60000";
      }
    }
    leaf num-packets {
      description "Number of Packets to be transmitted";
      type uint16 {
        range "1..60000";
      }
    }
    leaf request-data-size {
      description "Request data size";
      type uint16 {
        range "100..1500";
      }
    }
    container secondary-frequency {
      description "Frequency to be used if there is any violation condition happens";
      leaf both {
        description "Enable secondary freq for timeout and connection loss";
        type uint32 {
          range "1..604800";
        }
      }
      leaf connection-loss {
        description "Enable secondary freq for connection loss";
        type uint32 {
          range "1..604800";
        }
      }
      leaf timeout {
        description "Enable secondary freq for timeout";
        type uint32 {
          range "1..604800";
        }
      }
    }
    leaf verify-data {
      description "Verify data";
      type boolean;
    }
  }//end of mpls-lsp-monitor-type-jitter-grouping
  
  grouping mpls-lsp-monitor-type-pathEcho-grouping {
    uses mpls-lsp-monitor-type-common-grouping;
    leaf force-explicit-null {
      description "force an explicit null label to be added";
      type boolean;
    }
    leaf reply-dscp-bits {
      description "DSCP bits in reply IP header";
      type union {
        type uint8 {
          range "0..63";
        }
        type reply-dscp-bits-type;
      }
    }
    container reply-mode {
      description "Reply for LSP echo request";
      leaf ipv4 {
        description "Send reply via IPv4";
        type boolean;
      }
      leaf router-alert {
        description "Send reply via IPv4 UDP with router alert";
        type boolean;
      }
    }
    leaf ttl {
      description "Time to live";
      type uint8 {
        range "1..30";
      }
    }//end of ttl
  }//end of mpls-lsp-monitor-type-pathEcho-grouping
  
  grouping config-auto-ip-sla-react-action-type-grouping {
    leaf action-type {
      description "IP SLAs Reaction Action Type";
      type enumeration {
        enum "none";
        enum "trapOnly";
      }
      default none;
    }
  }
  
  grouping config-auto-ip-sla-react-threshold-type-grouping {
    container threshold-type {
      description "Threshold Type";
      choice threshold-type-param {
        case consecutive-type {
          container consecutive {
            description "Consecutive Occurrences";
            presence true;
            leaf consecutive-value {
              description "Number of Occurrences";
              type uint8 {
                range 1..16;
              }
              default 5;
            }
          }
        }
        case immediate-type {
          leaf immediate {
            description "React Immediately";
            type empty;
          }
        }
        case never-type {
          leaf never {
            description "Never React";
            type empty;
          }
        }
      }//end of choice
    }//end of threshold-type
  }
  
  grouping config-auto-ip-sla-grouping {
    container auto {
      description "Configure Automation";
      container ip {
        description "Configure Auto IP Service Level Agreement";
        container sla {
          description "IP Service Level Agreement";
          container mpls-lsp-monitor {
            description "IP SLAs MPLS LSP Monitor Configuration";
            list entry {
              key "number";
              leaf number {
                type uint32;
              }
              container type {
                description "Type of entry";
                choice type {
                  case echo-case {
                    container echo {
                      description "Perform MPLS LSP Ping operation";
                      choice vrf {
                        case ipsla-vrf-all-case {
                          container ipsla-vrf-all {
                            description "Configure IP SLAs MPLS LSP Monitor for all Virtual Private Networks";
                            presence true;
                            
                            uses mpls-lsp-monitor-type-echo-grouping;
                          }//end of ipsla-vrf-all
                        }//end of ipsla-vrf-all
                        case vrf_container-case {
                          container vrf_container {
                            
                            leaf vrf {
                              description "vrf Name";
                              must "/ios:native/ios:vrf/ios:definition[ios:name=current()] or /ios:native/ios:ip/ios:vrf[ios:name=current()]" {
                                error-message "VRF must be created 1st, deleted last";
                              }
                              type string;
                            }
                            uses mpls-lsp-monitor-type-echo-grouping;
                          }//end of vrf_container
                        }//end of vrf_container
                      }//end of vrf-choice
                    }//end of echo
                  }//end of echo-case
                  case jitter-case {
                    container jitter {
                      description "Perform MPLS Jitter operation";
                      choice vrf {
                        case ipsla-vrf-all-case {
                          container ipsla-vrf-all {
                            description "Configure IP SLAs MPLS LSP Monitor for all Virtual Private Networks";
                            presence true;
                            
                            uses mpls-lsp-monitor-type-jitter-grouping;
                          }//end of ipsla-vrf-all
                        }//end of ipsla-vrf-all-case
                        case vrf_container-case {
                          container vrf_container {
                            
                            leaf vrf {
                              description "vrf Name";
                              must "/ios:native/ios:vrf/ios:definition[ios:name=current()] or /ios:native/ios:ip/ios:vrf[ios:name=current()]" {
                                error-message "VRF must be created 1st, deleted last";
                              }
                              type string;
                            }
                            uses mpls-lsp-monitor-type-jitter-grouping;
                          }//end of vrf_container
                        }//end of vrf_container-case
                      }//end of vrf-choice
                    }//end of jitter
                  }//end of jitter-case
                  case pathEcho-case {
                    container pathEcho {
                      description "Perform MPLS LSP Trace operation";
                      choice vrf {
                        case ipsla-vrf-all-case {
                          container ipsla-vrf-all {
                            description "Configure IP SLAs MPLS LSP Monitor for all Virtual Private Networks";
                            presence true;
                            
                            uses mpls-lsp-monitor-type-pathEcho-grouping;
                          }//end of ipsla-vrf-all
                        }//end of ipsla-vrf-all-case
                        case vrf_container-case {
                          container vrf_container {
                            
                            leaf vrf {
                              description "vrf Name";
                              must "/ios:native/ios:vrf/ios:definition[ios:name=current()] or /ios:native/ios:ip/ios:vrf[ios:name=current()]" {
                                error-message "VRF must be created 1st, deleted last";
                              }
                              type string;
                            }
                            uses mpls-lsp-monitor-type-pathEcho-grouping;
                          }//end of vrf_container
                        }//end of vrf_container-case
                      }//end of vrf-choice
                    }//end of pathEcho
                  }//end of pathEcho-case
                }//end of type-choice
              }//end of type
                
              container modification-configuration {
                leaf access-list {
                  description "Apply Access-List";
                  when "../../type/echo or
                    ../../type/jitter or
                    ../../type/pathEcho";
                  type uint16 {
                    range "1..9";
                  }
                }
                leaf delete-scan-factor {
                  description "Scan Factor for automatic deletion";
                  when "../../type/echo or
                    ../../type/jitter or
                    ../../type/pathEcho";
                  type uint32 {
                    range "0..2147483647";
                  }
                }
                leaf exp {
                  description "EXP value";
                  when "../../type/echo or
                    ../../type/jitter or
                    ../../type/pathEcho";
                  type uint8 {
                    range "0..7";
                  }
                }
                leaf lsp-selector {
                  description "Local-Host address used to select the LSP";
                  when "../../type/echo or
                    ../../type/jitter or
                    ../../type/pathEcho";
                  type inet:ipv4-address;
                }
                leaf scan-interval {
                  description "Scan Interval for automatic discovery in minutes";
                  when "../../type/echo or
                    ../../type/jitter or
                    ../../type/pathEcho";
                  type uint32 {
                    range "1..70560";
                  }
                }
                leaf tag {
                  description "User defined tag";
                  when "../../type/echo or
                    ../../type/jitter or
                    ../../type/pathEcho";
                  type string;
                }
                leaf threshold {
                  description "Operation threshold in milliseconds";
                  when "../../type/echo or
                    ../../type/jitter or
                    ../../type/pathEcho";
                  type uint16 {
                    range "1..60000";
                  }
                }
                leaf timeout {
                  description "Timeout of an operation";
                  when "../../type/echo or
                    ../../type/jitter or
                    ../../type/pathEcho";
                  type uint32 {
                    range "0..604800000";
                  }
                }
                
                leaf force-explicit-null {
                  description "force an explicit null label to be added";
                  when "../../type/echo or
                    ../../type/pathEcho";
                  type boolean;
                }
                leaf reply-dscp-bits {
                  description "DSCP bits in reply IP header";
                  when "../../type/echo or
                    ../../type/pathEcho";
                  type union {
                    type uint8 {
                      range "0..63";
                    }
                    type reply-dscp-bits-type;
                  }
                }
                container reply-mode {
                  description "Reply for LSP echo request";
                  when "../../type/echo or
                    ../../type/pathEcho";
                  leaf ipv4 {
                    description "Send reply via IPv4";
                    type boolean;
                  }
                  leaf router-alert {
                    description "Send reply via IPv4 UDP with router alert";
                    type boolean;
                  }
                }
                leaf request-data-size {
                  description "Request data size";
                  when "../../type/echo or
                    ../../type/jitter";
                  type uint16 {
                    range "100..1500";
                  }
                }
                container secondary-frequency {
                  description "Frequency to be used if there is any violation condition happens";
                  when "../../type/echo or
                    ../../type/jitter";
                  leaf both {
                    description "Enable secondary freq for timeout and connection loss";
                    type uint32 {
                      range "1..604800";
                    }
                  }
                  leaf connection-loss {
                    description "Enable secondary freq for connection loss";
                    type uint32 {
                      range "1..604800";
                    }
                  }
                  leaf timeout {
                    description "Enable secondary freq for timeout";
                    type uint32 {
                      range "1..604800";
                    }
                  }
                }
                leaf ttl {
                  description "Time to live";
                  when "../../type/echo or
                    ../../type/pathEcho";
                  type uint8 {
                    range "1..255";
                  }
                }
                
                leaf dest-port {
                  description "Destination Port";
                  when "../../type/jitter";
                  type uint16 {
                    range "1..65535";
                  }
                }
                leaf interval {
                  description "Inter Packet Interval";
                  when "../../type/jitter";
                  type uint16 {
                    range "4..60000";
                  }
                }
                leaf num-packets {
                  description "Number of Packets to be transmitted";
                  when "../../type/jitter";
                  type uint16 {
                    range "1..60000";
                  }
                }
                leaf verify-data {
                  description "Verify data";
                  when "../../type/jitter";
                  type boolean;
                }
              }//end of modification-configuration
            } //end of entry
            list reaction-configuration {
              description "IP SLAs MPLS LSP Monitor Reaction Configuration";
              key "entry-number";
              leaf entry-number {
                description
                  "Entry number";
                type leafref {
                  path "/ios:native/ios-sla:auto/ios-sla:ip/ios-sla:sla/ios-sla:mpls-lsp-monitor/ios-sla:entry/ios-sla:number";
                }
              }
              container react {
                description "Reaction Variable To Be Configured";
                container connectionLoss {
                  description "Connection Loss";
                  presence true;
                  uses config-auto-ip-sla-react-action-type-grouping;
                  uses config-auto-ip-sla-react-threshold-type-grouping;
                }//end of connectionLoss
                container lpd {
                  description "IP SLAs LSP Path Discover";
                  container lpd-group {
                    description "LSP Path Discover Group";
                    presence true;
                    leaf retry {
                      description "Retry Count";
                      type uint8 {
                        range "1..16";
                      }
                    }
                    leaf action-type {
                      description "LSP Path Discover Reaction Action Type";
                      type enumeration {
                        enum "trapOnly";
                      }
                    }
                  }
                  container tree-trace {
                    description "Tree Trace";
                    presence true;
                    leaf action-type {
                      description "LSP Path Discover Reaction Action Type";
                      type enumeration {
                        enum trapOnly;
                      }
                    }
                  }
                }//end of lpd
                container timeout {
                  description "Timeout";
                  presence true;
                  uses config-auto-ip-sla-react-action-type-grouping;
                  uses config-auto-ip-sla-react-threshold-type-grouping;
                }//end of timeout
              }//end of react
            }//end of reaction-configuration
            
            list schedule {
              description "IP SLAs MPLS LSP Monitor Schedule";
              key "entry";
              leaf entry {
                description "Entry Number";
                type leafref {
                  path "/ios:native/ios-sla:auto/ios-sla:ip/ios-sla:sla/ios-sla:mpls-lsp-monitor/ios-sla:entry/ios-sla:number";
                } 
              }
              leaf schedule-period {
                description "Group schedule period range";
                type uint32 {
                  range "1..604800";
                }
              }
              leaf frequency {
                description "Group operation frequency";
                type uint32 {
                  range "1..604800";
                }
              }
              container start-time {
                description "When to start this entry";
                choice start-time-param {
                  case after-type {
                    leaf after {
                      description "Start after a certain amount of time from now";
                      type ios-sla:hour-min-sec;
                    }
                  }
                  case hour-min-type {
                    container hour-min {
                      
                      leaf hour-min {
                        description "Start time (hh:mm)";
                        type ios-sla:hour-min;
                      }
                      leaf date-of-month {
                        description "Day of the month";
                        type uint8 {
                          range "1..31";
                        }
                      }
                      leaf month {
                        description "Month of the year";
                        type string {
                          pattern "(Jan|Feb|Mar|Apr|May|Jun|Jul|Aug|Sep|Oct|Nov|Dec)";
                        }
                      }
                    }
                  }
                  case hour-min-sec-type {
                    container hour-min-sec {
                      
                      leaf hour-min-sec {
                        description "Start time (hh:mm)";
                        type ios-sla:hour-min-sec;
                      }
                      leaf date-of-month {
                        description "Day of the month";
                        type uint8 {
                          range "1..31";
                        }
                      }
                      leaf month {
                        description "Month of the year";
                        type string {
                          pattern "(Jan|Feb|Mar|Apr|May|Jun|Jul|Aug|Sep|Oct|Nov|Dec)";
                        }
                      }
                    }
                  }
                  case now-type {
                    leaf now {
                      description "Start now";
                      type empty;
                    }
                  }
                  case pending-type {
                    leaf pending {
                      description "Start pending";
                      type empty;
                    }
                  }
                }//end of start-time-param
              }//end of start-time
            }//end of schedule
          } //end of mpls-lsp-monitor
        } //end of sla
      } //end of ip
    } //end of auto
  } //end of config-auto-ip-sla-grouping
  
  grouping config-ip-sla-grouping {
    container sla {
      description
        "IP Service Level Agreement";
      list entry {
        key "number";
        leaf number {
          description "Entry Number";
          type uint32 {
            range "1..2147483647";
          }
        }
        
        choice sla-param {
          case icmp-echo-case {
            container icmp-echo {
              description
                "ICMP Echo Operation";
              leaf destination {
                mandatory true;
                type union {
                  type string;
                  type inet:ip-address;
                }
              }
              choice source-param {
                case source-interface {
                  leaf source-interface {
                    description
                      "Source Interface (ingress icmp packet interface)";
                    type string;
                  }
                }
                case source-ip {
                  leaf source-ip {
                    description
                      "Source Address";
                    type union {
                      type string;
                      type inet:ip-address;
                    }
                  }
                }
              }
              leaf data-pattern {
                description
                  "Data Pattern";
                type string;
              }
              uses ip-sla-sub-mode-commands-grouping;
              uses ip-sla-full-history-grouping;
              leaf request-data-size {
                description
                  "Request data size";
                type uint32 {
                  range "0..16384";
                }
                default 28;
              }
              choice tos-param {
                case tos {
                  leaf tos {
                    description
                      "Type Of Service";
                    type uint8 {
                      range "0..255";
                    }
                  }
                }
                case traffic-class {
                  leaf traffic-class {
                    description
                      "Traffic class";
                   type uint8 {
                      range "0..255";
                    }
                  }
                }
              }
              leaf verify-data {
                description
                  "Verify data";
                type boolean;
              }
              leaf vrf {
                description
                  "Configure IP SLAs for a VPN Routing/Forwarding instance";
                type string;
              }
            }
          } // end icmp-echo-case
          case icmp-jitter-case {
            container icmp-jitter {
              description "ICMP-jitter Operations";
              leaf dst-ip {
                description
                "Destination IP address or hostname, broadcast disallowed";
                type union {
                  type string;
                  type inet:ipv4-address;
                }
              }
              leaf interval {
                description
                  "Inter Packet Interval";
                units milliseconds;
                type uint16 {
                  range "4..60000";
                }
              }
              leaf num-packets {
                description
                  "Number of Packets to be transmitted";
                units packets;
                type uint16 {
                  range "1..60000";
                }
              }
              leaf source-ip {
                description
                  "IP address or hostname, broadcast disallowed";
                type union {
                  type string;
                  type inet:ipv4-address;
                }
              }
              uses ip-sla-sub-mode-commands-grouping;
              container history {
                description
                  "History and Distribution Data";
                leaf distributions-of-statistics-kept {
                  description
                    "Maximum number of statistics distribution buckets to capture";
                  type uint8 {
                    range "1..20";
                  }
                  default 1;
                }
                container enhanced {
                  description
                    "Enable enhanced history collection";
                  leaf interval {
                    description
                      "Aggregation interval";
                    type uint16 {
                      range "1..3600";
                    }
                  }
                  leaf buckets {
                    description
                      "Number of buckets to collect data";
                    type uint8 {
                      range "1..100";
                    }
                  }
                }
                leaf hours-of-statistics-kept {
                  description
                    "Maximum number of statistics hour groups to capture";
                  type uint8 {
                    range "0..25";
                  }
                }
                leaf statistics-distribution-interval {
                  description
                    "Statistics distribution interval value in msec";
                  units milliseconds;
                  type uint8 {
                    range "1..100";
                  }
                }
              } // end History
              leaf tos {
                description
                  "Type Of Service";
                type uint8 {
                  range "0..255";
                }
              }
              leaf vrf {
                description
                  "Configure IP SLAs for a VPN Routing/Forwarding instance";
                type string;
              }
            }// end imcp-jitter
          } // end icmp-jitter case
          case path-echo-case {
            container path-echo {
              description
                "Path Discovered ICMP Echo Operation";
              leaf dst-ip {
                description
                  "Destination IP address or hostname, broadcast disallowed";
                type union {
                  type string;
                  type inet:ipv4-address;
                }
              }
              leaf source-ip {
                description
                  "IP address or hostname, broadcast disallowed";
                type union {
                  type string;
                  type inet:ipv4-address;
                }
              }
              uses ip-sla-sub-mode-commands-grouping;
              uses ip-sla-path-echo-grouping;
            }
          } // end path-echo-case
          case path-jitter-case {
            container path-jitter {
              description
                "Path Discovered ICMP Jitter Operation";
              leaf dst-ip {
                type union {
                  type string;
                  type inet:ipv4-address;
                  type inet:ipv6-address;
                }
              }
              leaf source-ip {
                description
                  "Source IP Address";
                type union {
                  type string;
                  type inet:ipv4-address;
                }
              }
              container default {
                description
                  "Set a command to its defaults";
                uses ip-sla-default-path-jitter-grouping;
              }
              uses ip-sla-sub-mode-commands-grouping;
              uses ip-sla-path-jitter-grouping;
            }
          } // end path-jitter-case
          case udp-echo-case {
            // ip sla * /udp-echo
            container udp-echo {
              description
               "UDP echo operation";
              leaf dest-addr {
                description
                 "Hostname or A.B.C.D  Destination IP address or hostname, broadcast disallowed";
                type union {
                  type inet:ip-address;
                  type string;
                }
              }
              leaf dest-port {
                description
                 "Port Number (Recommended ports greater than 1023)";
                type uint16 {
                  range "1..65535";
                }
              }
              leaf source-ip {
                description
                 "Source address: Hostname or A.B.C.D IP address or hostname, broadcast disallowed";
                type union {
                  type inet:ip-address;
                  type string;
                }
              }
              leaf source-port {
                description
                 "Source Port: Port Number (Recommended ports greater than 1023)";
                type uint16 {
                  range "1..65535";
                }
              }
              leaf control {
                description "Enable or disable control packets";
                type enumeration {
                  enum "disable";
                  enum "enable";
                }
              }
              uses ip-sla-sub-mode-commands-grouping;
              uses ip-sla-udp-echo-grouping;
            }
          } // end udp-echo-case
          case udp-jitter-case {
            // ip sla * /udp-jitter
            container udp-jitter {
              description
                "UDP jitter operation";
              leaf dest-addr {
                description
                  "Hostname or A.B.C.D/X:X:X:X::X  Destination IP/IPv6 address";
                type union {
                  type inet:ip-address;
                  type inet:ipv6-address;
                  type string;
                }
              }
              leaf portno {
                description
                  "Port Number";
                type uint16 {
                  range "1..65535";
                }
              }
              choice type-param {
                case codec {
                   leaf codec {
                     description "codec type to be configured";
                     type enumeration {
                       enum "g711alaw" {
                       }
                       enum "g711ulaw" {
                       }
                       enum "g729a" {
                       }
                     }
                   }
                   leaf advantage-factor {
                     description "Advantage Factor";
                     type uint16 {
                       range "0..20";
                     }
                   }
                   leaf codec-interval {
                     description "Inter Packet Interval";
                     type uint32 {
                       range "4..60000";
                     }
                   }
                   leaf codec-numpackets {
                     description "Number of Packets";
                     type uint32 {
                       range "1..60000";
                     }
                   }
                   leaf codec-size {
                     description "Number of Packets";
                     type uint16 {
                       range "16..16384";
                     }
                   }
                }
                case non-codec {
                   leaf num-packets {
                     description "Number of Packets (default 10)";
                     type uint16 {
                       range "1..60000";
                     }
                   }
                   leaf interval {
                     description "Delay (default 20)";
                     type uint16 {
                       range "4..60000";
                     }
                   }
                }
              }
              leaf source-ip {
                description
                  "Hostname or A.B.C.D/X:X:X:X::X Source IP/IPv6 address";
                type union {
                  type inet:ip-address;
                  type inet:ipv6-address;
                  type string;
                }
              }
              leaf source-port {
                description
                  "Source port";
                type uint16 {
                  range "1..65535";
                }
              }
              leaf control {
                description "Enable or disable control packets";
                type enumeration {
                  enum "enable" {
                  }
                  enum "disable" {
                  }
                }
              }
              uses ip-sla-sub-mode-commands-grouping;
              uses ip-sla-udp-jitter-grouping;
              uses ip-sla-jitter-percentile;
            }
          } //end udp-jitter-case
          case http-case {
            //ip sla * / http
            container http {
              description
               "HTTP Operation";
              choice http-choice {
               case http-get {
                  container get {
                    description
                      "HTTP get operation";
                    
                    leaf url {
                      description
                        "URL";
                      type string;
                    }
                    leaf cache {
                      description "Enable or Disable download of cached HTTP page";
                      type enumeration {
                        enum "enable" {
                        }
                        enum "disable" {
                        }
                      }
                    }
                    leaf source-ip {
                      description
                        "Source Hostname or A.B.C.D/X:X:X:X::X  IPv4/IPv6 address";
                      type union {
                        type inet:ipv6-address;
                        type inet:ip-address;
                        type string;
                      }
                    }
                    leaf source-port {
                      description
                        "Source port";
                      type uint16 {
                        range "1..65535";
                      }
                    }
                    leaf name-server {
                      description
                        "Hostname or A.B.C.D/X:X:X:X::X  IPv4/IPv6 address";
                      type union {
                        type string;
                        type inet:ip-address;
                        type inet:ipv6-address;
                      }
                    }
                    leaf proxy {
                      description "Proxy information string";
                      type string;
                    }
                    leaf version {
                      description "Http Version";
                      type enumeration {
                        enum "1.0" {
                        }
                        enum "1.1" {
                        }
                      }
                    }
                  }//end of get
                }//end of http-get-case
                case http-raw {
                  container raw {
                    description
                      "HTTP raw operation";
                    
                    leaf url {
                      type string;
                    }
                    leaf cache {
                      description "Enable or Disable download of cached HTTP page";
                      type enumeration {
                        enum "enable" {
                        }
                        enum "disable" {
                        }
                      }
                    }
                    leaf source-ip {
                      description
                        "Source Hostname or A.B.C.D/X:X:X:X::X  IPv4/IPv6 address";
                      type union {
                        type inet:ip-address;
                        type inet:ipv6-address;
                        type string;
                      }
                    }
                    leaf source-port {
                      description
                        "Source port";
                      type uint16 {
                        range "1..65535";
                      }
                    }
                    leaf name-server {
                      description
                        "Hostname or A.B.C.D/X:X:X:X::X  IPv4/IPv6 address";
                      type union {
                        type string;
                        type inet:ip-address;
                        type inet:ipv6-address;
                      }
                    }
                    leaf proxy {
                      description "Proxy information string";
                      type string;
                    }
                    leaf version {
                      description "Http Version";
                      type enumeration {
                        enum "1.0" {
                        }
                        enum "1.1" {
                        }
                      }
                    }//end of version
                  }//end of raw
                }//end of http-raw-case
              }
              //http submode CMDs:
              uses ip-sla-sub-mode-commands-grouping;
              container history {
                description
                  "History and Distribution Data";
                leaf distributions-of-statistics-kept {
                  description
                    "Maximum number of statistics distribution buckets to capture";
                  type uint8 {
                    range "1..20";
                  }
                  default 1;
                }
                leaf hours-of-statistics-kept {
                  description
                    "Maximum number of statistics hour groups to capture";
                  type uint8 {
                    range "0..25";
                  }
                }
                leaf statistics-distribution-interval {
                  description
                    "Statistics distribution interval size";
                  type uint8 {
                    range "1..100";
                  }
                }
              }
              leaf http-status-code-ignore {
                description "HTTP Status Code Check Disable";
                type boolean;
              }
              leaf vrf {
                description
                  "Configure IP SLAs for a new VPN Routing/Forwarding instance";
                type string;
              }
              choice tos-param {
                case tos {
                  leaf tos {
                    description
                      "Type Of Service";
                    type uint8 {
                      range "0..255";
                    }
                  }
                }
                case traffic-class {
                  leaf traffic-class {
                    description
                      "Traffic class";
                    type uint8 {
                      range "0..255";
                    }
                  }
                }
              }
              container http-raw-request {
                description "HTTP Raw Request configuration";
                leaf raw-request-string {
                   description "HTTP Raw string";
                   type string;
                }
              }
            } // end ip sla http
          } // end http-case
          case dhcp-case {
            container dhcp {
              description
                "DHCP Operation";
              leaf dst-ip {
                description
                  "Destination IP address or hostname, broadcast disallowed";
                type union {
                  type string;
                  type inet:ipv4-address;
                }
              }
              leaf source-ip {
                description
                  "IP address or hostname, broadcast disallowed";
                type union {
                  type string;
                  type inet:ipv4-address;
                }
              }
              uses ip-sla-sub-mode-commands-grouping;
              uses ip-sla-history-without-enhanced-grouping;
            } //end ip sla dhcp
          }//end dhcp-case
          case tcp-connect-case {
            container tcp-connect {
              description
               "TCP connect operation";
              leaf dest-addr {
                description
                 "Destination IPv6/IP address or hostname";
                type union {
                  type inet:ip-address;
                  type inet:ipv6-address;
                  type string;
                }
              }
              leaf dest-port {
                description
                 "Port Number (Recommended ports greater than 1023)";
                type uint16 {
                  range "1..65535";
                }
              }
              leaf source-ip {
                description
                 "Source IPv6/IP address or hostname";
                type union {
                  type inet:ip-address;
                  type inet:ipv6-address;
                  type string;
                }
              }
              leaf source-port {
                description
                 "Source Port: Port Number (Recommended ports greater than 1023)";
                type uint16 {
                  range "1..65535";
                }
              }
              leaf control {
                description "Enable or disable control packets";
                type enumeration {
                  enum "enable" {
                  }
                  enum "disable" {
                  }
                }
              }
              uses ip-sla-sub-mode-commands-grouping;
              uses ip-sla-full-history-grouping;
              choice tos-param {
                case tos {
                  leaf tos {
                    description
                      "Type Of Service";
                    type uint8 {
                      range "0..255";
                    }
                  }
                }
                case traffic-class {
                  leaf traffic-class {
                    description
                      "Traffic class";
                    type uint8 {
                      range "0..255";
                    }
                  }
                }
              }
              leaf vrf {
                description
                  "Configure IP SLAs for a VPN Routing/Forwarding instance";
                type string;
              }
            } // tcp-connect
          } // end choice tcp
          case dns-case {
            container dns {
              description
               "DNS operation";
              leaf dest-addr {
                description
                 "Destination IPv6/IP address or hostname";
                type union {
                  type inet:ip-address;
                  type inet:ipv6-address;
                  type string;
                }
              }
              leaf name-server {
                description
                 "Name Server: IPv6/IP address or hostname";
                type union {
                  type inet:ip-address;
                  type inet:ipv6-address;
                  type string;
                }
              }
              leaf source-ip {
                description
                 "Source IPv6/IP address or hostname";
                type union {
                  type inet:ip-address;
                  type inet:ipv6-address;
                  type string;
                }
              }
              leaf source-port {
                description
                 "Source Port: Port Number (Recommended ports greater than 1023)";
                type uint16 {
                  range "1..65535";
                }
              }
              uses ip-sla-sub-mode-commands-grouping;
              uses ip-sla-history-without-enhanced-grouping;
              leaf vrf {
                description
                  "Configure IP SLAs for a VPN Routing/Forwarding instance";
                type string;
              }
            } // end dns
          } // end dns case
          case ftp-case {
            container ftp {
              description
               "DNS operation";
              container get {
                presence true;
                description
                  "FTP get operation";
                leaf url {
                  description
                   "URL";
                  type union {
                    type string;
                  }
                }
                leaf mode {
                  description
                   "Specify mode to be used";
                  type enumeration {
                    enum "active" {
                    }
                    enum "passive" {
                    }
                  }
                }
                leaf source-ip {
                  description
                   "Source IPv6/IP address or hostname";
                  type union {
                    type inet:ip-address;
                    type inet:ipv6-address;
                    type string;
                  }
                }
                leaf owner {
                  description
                    "Owner of Entry";
                  status obsolete;
                  type string;
                }
                leaf tag {
                  description
                    "User defined tag";
                  status obsolete;
                  type string;
                }
                leaf frequency {
                  description
                    "Frequency of an operation";
                  status obsolete;
                  units seconds;
                  type uint32 {
                    range "1..604800";
                  }
                  default 60;
                }
                leaf timeout {
                  description
                    "Timeout of an operation";
                  status obsolete;
                  units miliseconds;
                  type uint32 {
                    range "0..604800000";
                  }
                  default 5000;
                }
                leaf threshold {
                  description
                    "Operation threshold in milliseconds";
                  status obsolete;
                  units miliseconds;
                  type uint32 {
                    range "0..60000";
                  }
                  default 5000;
                }
                container history {
                  description
                    "History and Distribution Data";
                  status obsolete;
                  container enhanced {
                    description
                      "Enable enhanced history collection";
                    leaf interval {
                      description
                        "Aggregation interval";
                      type uint16 {
                        range "1..3600";
                      }
                      default 900;
                    }
                    leaf buckets {
                      description
                        "Number of buckets to collect data";
                      type uint8 {
                        range "1..100";
                      }
                      default 100;
                    }
                  }
                  leaf buckets-kept {
                      description
                        "Maximum number of history buckets to collect";
                      type uint8;
                      default 50;
                  }
                  leaf distributions-of-statistics-kept {
                    description
                      "Maximum number of statistics distribution buckets to capture";
                    type uint8;
                    default 1;
                  }
                  leaf filter {
                    description
                      "Add operation to History when...";
                    type enumeration {
                      enum "all";
                      enum "failures";
                      enum "none";
                      enum "overThreshold";
                    }
                    default none;
                  }
                  leaf hours-of-statistics-kept {
                    description
                      "Maximum number of statistics hour groups to capture";
                    type uint8 {
                      range "0..25";
                    }
                    default 2;
                  }
                  leaf lives-kept {
                    description
                      "Maximum number of history lives to collect";
                    type uint8 {
                      range "0..2";
                    }
                    default 0;
                  }
                  leaf statistics-distribution-interval {
                    description
                      "Statistics distribution interval size";
                    type uint8 {
                      range "1..100";
                    }
                    default 20;
                  }
                }
              } // end ftp get
              uses ip-sla-sub-mode-commands-grouping;
              uses ip-sla-history-without-enhanced-grouping;
            } // end ftp
          } // end ftp case
          case ethernet-case {
            container ethernet {
              description
                "Ethernet Operations";
              choice ethernet-probe-type {
                case echo-case {
                  container echo {
                    description "Ethernet Echo Operation 802.11 ag Loopback";
                    leaf mpid {
                      description "Maintenance Point ID";
                      type uint16 {
                        range "1..8191";
                      }
                    }
                    leaf domain {
                      description "Domain Name";
                      type string;                            //TODO: To accept only the available domains.
                    }
                    choice param {
                      case evc-case {
                        leaf evc {
                          description "EVC ID";
                          type string;
                        }
                      }
                      case port {
                        leaf port {
                          description "DOWN service direction with no vlan association";
                          type empty;
                        }
                      }
                      case vlan {
                        leaf vlan {
                          description "VLAN ID";
                          type uint16 {
                            range "1..4094";
                          }
                        }
                      }
                    }//end of choice
                    leaf cos {
                      description "Class Of Service";
                      type uint8 {
                        range "0..7";
                      }
                    }
                    leaf request-data-size {
                      description "Request data size";
                      type uint16 {
                        range "0..1400";
                      }
                    }
                    leaf owner {
                      description
                        "Owner of Entry";
                      type string;
                    }
                    leaf tag {
                      description
                        "User defined tag";
                      type string;
                    }
                    leaf threshold {
                      description
                        "Operation threshold in milliseconds";
                      units miliseconds;
                      type uint32 {
                        range "0..60000";
                      }
                      default 5000;
                    }
                    leaf timeout {
                      description
                        "Timeout of an operation";
                      units miliseconds;
                      type uint32 {
                        range "0..604800000";
                      }
                      default 5000;
                    }
                    leaf frequency {
                      description
                        "Frequency of an operation";
                      units seconds;
                      type uint32 {
                        range "1..604800";
                      }
                      default 60;
                    }
                    container history {
                      description
                      "History and Distribution Data";
                      container enhanced {
                        description
                          "Enable enhanced history collection";
                        leaf interval {
                          description
                            "Aggregation interval";
                          type uint16 {
                            range "1..3600";
                          }
                          default 900;
                        }
                        leaf buckets {
                          description
                            "Number of buckets to collect data";
                          type uint8 {
                            range "1..100";
                          }
                          default 100;
                        }
                      }
                      leaf buckets-kept {
                          description
                            "Maximum number of history buckets to collect";
                          type uint8 {
                            range "1..60";
                          }
                          default 50;
                      }
                      leaf distributions-of-statistics-kept {
                        description
                          "Maximum number of statistics distribution buckets to capture";
                        type uint8 {
                          range "1..20";
                        }
                        default 1;
                      }
                      leaf filter {
                        description
                          "Add operation to History when...";
                        type enumeration {
                          enum "all";
                          enum "failures";
                          enum "none";
                          enum "overThreshold";
                        }
                        default none;
                      }
                      leaf hours-of-statistics-kept {
                        description
                          "Maximum number of statistics hour groups to capture";
                        type uint8 {
                          range "0..25";
                        }
                        default 2;
                      }
                      leaf lives-kept {
                        description
                          "Maximum number of history lives to collect";
                        type uint8 {
                          range "0..2";
                        }
                        default 0;
                      }
                      leaf statistics-distribution-interval {
                        description
                          "Statistics distribution interval size";
                        type uint8 {
                          range "1..100";
                        }
                        default 20;
                      }
                    }
                  }//end of echo
                }
                case jitter-case {
                  container jitter {
                    description "Ethernet Jitter Operation";
                    leaf mpid {
                      description "Maintenance Point ID";
                      type uint16 {
                        range "1..8191";
                      }
                    }
                    leaf domain {
                      description "Domain Name";
                      type string;
                    }
                    choice param {
                      case evc-case {
                        leaf evc {
                          description "EVC ID";
                          type string;
                        }
                      }
                      case port {
                        leaf port {
                          description "DOWN service direction with no vlan association";
                          type empty;
                        }
                      }
                      case vlan {
                        leaf vlan {
                          description "VLAN ID";
                          type uint16 {
                            range "1..4094";
                          }
                        }
                      }
                    }//end of choice
                    container jitter-params {
                      
                      leaf interval {
                        description "Inter Packet Interval";
                        type uint16 {
                          range "4..60000";
                        }
                      }
                      leaf num-frames {
                        description "Number of Frames to be transmitted";
                        type uint16 {
                          range "1..60000";
                        }
                      }
                    }
                    leaf cos {
                      description "Class Of Service";
                      type uint8 {
                        range "0..7";
                      }
                    }
                    
                    leaf request-data-size {
                      description "Request data size";
                      type uint16 {
                        range "0..1400";
                      }
                    }
                    container percentile {
                      description
                        "Set percentile statistics levels";
                      leaf jitteravg {
                        description
                          "% of Average Jitter values to use (default 100%)";
                        type uint8 {
                          range "90..100";
                        }
                      }
                      leaf jitterds {
                        description
                          "% of Destination to source jitter value to use (default 100%)";
                        type uint8 {
                          range "90..100";
                        }
                      }
                      leaf jittersd {
                        description
                          "% of Source to destination jitter value to use (default 100%)";
                        type uint8 {
                          range "90..100";
                        }
                      }
                      leaf owds {
                        description
                          "% of One way destination to source value to use (default 100%)";
                        type uint8 {
                          range "90..100";
                        }
                      }
                      leaf owsd {
                        description
                          "% of One way source to destination value to use (default 100%)";
                        type uint8 {
                          range "90..100";
                        }
                      }
                      leaf rtt {
                        description
                          "% of Round Trip Time value to use (default 100%)";
                        type uint8 {
                          range "90..100";
                        }
                      }
                    }
                    leaf owner {
                      description
                        "Owner of Entry";
                      type string;
                    }
                    leaf tag {
                      description
                        "User defined tag";
                      type string;
                    }
                    leaf threshold {
                      description
                        "Operation threshold in milliseconds";
                      units miliseconds;
                      type uint32 {
                        range "0..60000";
                      }
                      default 5000;
                    }
                    leaf timeout {
                      description
                        "Timeout of an operation";
                      units miliseconds;
                      type uint32 {
                        range "0..604800000";
                      }
                      default 6000;
                    }
                    leaf frequency {
                      description
                        "Frequency of an operation";
                      units seconds;
                      type uint32 {
                        range "1..604800";
                      }
                      default 60;
                    }
                    
                    container history {
                      description
                      "History and Distribution Data";
                      container enhanced {
                        description
                          "Enable enhanced history collection";
                        leaf interval {
                          description
                            "Aggregation interval";
                          type uint16 {
                            range "1..3600";
                          }
                          default 900;
                        }
                        leaf buckets {
                          description
                            "Number of buckets to collect data";
                          type uint8 {
                            range "1..100";
                          }
                          default 100;
                        }
                      }
                      leaf distributions-of-statistics-kept {
                        description
                          "Maximum number of statistics distribution buckets to capture";
                        type uint8 {
                          range "1..20";
                        }
                        default 1;
                      }
                      leaf hours-of-statistics-kept {
                        description
                          "Maximum number of statistics hour groups to capture";
                        type uint8 {
                          range "0..25";
                        }
                        default 2;
                      }
                      leaf statistics-distribution-interval {
                        description
                          "Statistics distribution interval size";
                        type uint8 {
                          range "1..100";
                        }
                        default 20;
                      }
                    }//end of history
                  }//end of jitter
                }//end of jitter-case
                case y1731-case {
                  container y1731-config {
                    description
                      "Y1731 Ethernet OAM Performance Measurement Operations";
                    uses ip-sla-ethernet-y1731-grouping;
                  }
                }//end of y1731-case
              }//end of choice-ethernet-probe-type
              container y1731 {
                status deprecated;
                description "Y1731 Ethernet OAM Performance Measurement Operations (DEPRECATED, use y1731-config container inside the choice statement)";
                container delay {
                  description
                    "Y1731 Delay and Delay Variation Operation";
                  leaf name {
                    description
                      "Y1731 Delay option";
                    type enumeration {
                      enum "1DM";
                      enum "DMM";
                      enum "DMMv1";
                    }
                  }

                  leaf burst {
                    description
                      "Enable bursting of delay frames";
                    type empty;
                  }

                  leaf domain {
                    description
                      "Specify the Ethernet OAM domain";
                    type string;
                  }

                  choice evc-or-vlan {
                     leaf evc {
                        description
                          "Specify the Ethernet Virtual Circuit Identifier";
                        type string;
                     }
                     leaf vlan {
                       description
                         "Specify the VLAN";
                       type uint16 {
                         range "1..4096";
                       }
                     }
                  }//evc-or-vlan-choice

                  choice mac-or-mpid {
                    leaf mac-address {
                      description
                        "Specify the remote mac-address";
                      type ios-types:cisco-mac-address-type;
                    }
                    leaf mpid {
                      description
                        "Specify the remote MPID";
                      type uint16 {
                        range "1..8191";
                      }
                    }
                  }//mac-or-mpid

                  leaf cos {
                    description
                      "Specify the Class of Service";
                    type uint8 {
                      range "0..7";
                    }
                  }

                  container source {
                    description
                      "Specify the local MPID or MAC-Address";
                    choice mac-or-mpid {
                        leaf mac-address {
                            description
                              "Specify the local mac-address";
                            type ios-types:cisco-mac-address-type;
                        }
                        leaf mpid {
                          description
                            "Specify the local MPID";
                          type uint16 {
                            range "1..8191";
                          }
                        }
                    }
                  }//source
                }//delay
                container loss {
                  description
                    "Y1731 Loss Operation";

                  leaf name {
                    description
                      "Y1731 Delay option";
                      type enumeration {
                        enum "LMM";
                        enum "SLM";
                      }
                    }

                    leaf burst {
                      description
                        "Enable bursting of delay frames. Applicable only to SLM option";
                      type empty;
                    }

                    leaf domain {
                      description
                        "Specify the Ethernet OAM domain";
                      type string;
                    }

                    choice evc-or-vlan {
                      leaf evc {
                        description
                          "Specify the Ethernet Virtual Circuit Identifier";
                        type string;
                      }
                      leaf vlan {
                        description
                          "Specify the VLAN";
                        type uint16 {
                          range "1..4096";
                        }
                      }
                    }//evc-or-vlan-choice

                    choice mac-or-mpid {
                      leaf mac-address {
                        description
                          "Specify the remote mac-address";
                        type ios-types:cisco-mac-address-type;
                      }
                      leaf mpid {
                        description
                          "Specify the remote MPID";
                        type uint16 {
                          range "1..8191";
                        }
                      }
                    }//mac-or-mpid

                    leaf cos {
                      description
                        "Specify the Class of Service";
                      type uint8 {
                        range "0..7";
                      }
                    }//cos

                    container source {
                      description
                        "Specify the local MPID or MAC-Address";
                      choice mac-or-mpid {
                        leaf mac-address {
                          description
                            "Specify the local mac-address";
                              type ios-types:cisco-mac-address-type;
                        }
                        leaf mpid {
                          description
                            "Specify the local MPID";
                          type uint16 {
                            range "1..8191";
                        }
                      }
                    }//mac-or-mpid
                  }//source
                }//loss
              }//y1731
              uses ip-sla-ethernet-delay-grouping {
                status obsolete;
                refine aggregate {
                  description "Aggregate parameters (OBSOLETE)";
                }
                refine history {
                  description "History parameters (OBSOLETE)";
                }
              }//end of ip-sla-ethernet-delay-grouping
            }//end of ethernet
          }//case
          
          case service-performance-case {
            container service-performance {
              description "Service Performance Operation";
              container type {
                description "Server Performance identifier";
                choice service-type {
                  case ethernet-case {
                    container ethernet {
                      description "Service Performance Ethernet";
                      leaf dest-mac-addr {
                        description "Specify the remote mac-address";
                        type ios-types:cisco-mac-address-type;
                      }
                      leaf bridge-domain {
                        description "Specify the Bridge Domain";
                        type uint16 {
                          range "1..65535";
                        }
                      }
                      leaf interface {
                        description "Interface Name";
                        type string;                                    //TODO: Change to accept avaiable interfaces.
                      }
                      leaf service {
                        description "Specify the Service Instance";
                        type empty;
                      }
                      leaf instance {
                        description "Specify the Service Instance";
                        type uint16 {
                          range "1..16000";
                        }
                      }
                      leaf ethernet {
                        description "Configure an Ethernet Instance";
                        type string;
                      }
                      uses ip-sla-service-performance-sub-command-grouping {
                        augment profile {
                          uses ip-sla-service-performance-packet-direction-sub-command-grouping {
                            augment packet {
                              leaf dscp {
                                description "Configure DSCP";
                                type union {
                                  type uint8 {
                                    range "0..63";
                                  }
                                  type reply-dscp-bits-type;
                                }
                              }//end of dscp
                              leaf ethertype {
                                description "Frame type";
                                type enumeration {
                                  enum "ipv4";
                                  enum "ipv6";
                                }
                              }//end of ethertype
                              leaf inner-cos {
                                description "Inner COS";
                                type uint8 {
                                  range "0..7";
                                }
                              }
                              leaf inner-vlan {
                                description "Specify Inner VLAN";
                                type uint16 {
                                  range "0..4095";
                                }
                              }//end of inner-vlan
                              leaf outer-cos {
                                description "Outer COS";
                                type uint8 {
                                  range "0..7";
                                }
                              }//end of outer-cos
                              leaf src-mac-addr {
                                description "The source mac-address";
                                type ios-types:cisco-mac-address-type;
                              }//end of src-mac-addr
                            }//end of packet
                          }//end of ip-sla-service-performance-packet-direction-sub-command-grouping
                          uses ip-sla-service-performance-traffic-direction-sub-command-grouping;
                        }//end of profile
                        augment measurement-type {
                          uses ip-sla-service-performance-measurement-type-sub-command-grouping {
                            augment conform-color {
                              leaf cos {
                                description "configure conform COS";
                                type uint8 {
                                  range "0..7";
                                }
                              }//end of cos
                            }
                            augment exceed-color {
                              leaf cos {
                                description "configure conform COS";
                                type uint8 {
                                  range "0..7";
                                }
                              }//end of cos
                            }//end of exceed-color
                          }//end of ip-sla-service-performance-measurement-type-sub-command-grouping
                        }//end of measurement-type
                      }//end of ip-sla-service-performance-sub-command-grouping
                    }//end of ethernet
                  }//end of ethernet-case
                  case ip-case {
                    container ip {
                      description "Service Performance IP";
                      leaf dest-ip-addr {
                        description "Specify the target ip";
                        type union {
                          type string;
                          type inet:ip-address;
                        }
                      }
                      leaf bridge-domain {
                        description "Specify the Bridge Domain";
                        type uint16 {
                          range "1..65535";
                        }
                      }
                      choice option {
                        case interface-case {
                          leaf interface {
                            description "Interface Name";
                            type string;                                    //TODO: Change to accept avaiable interfaces.
                          }
                          leaf service {
                            description "Specify the Service Instance";
                            type empty;
                          }
                          leaf instance {
                            description "Specify the Service Instance";
                            type uint16 {
                              range "1..16000";
                            }
                          }
                          leaf ethernet {
                            description "Configure an Ethernet Instance";
                            type string;
                          }
                        }//end of interface-case
                        case vrf-case {
                          leaf vrf {
                            description "Configure an VRF";
                            type uint16 {
                              range "1..4096";
                            }
                          }//end of vrf
                        }//end of vrf-case
                      }//end of choice option
                      uses ip-sla-service-performance-sub-command-grouping {
                        augment profile {
                          uses ip-sla-service-performance-packet-direction-sub-command-grouping {
                            augment packet {
                              container tunnel {
                                description "Tunnel type";
                                leaf exp {
                                  description "Exp value";
                                  type uint8 {
                                    range "0..7";
                                  }
                                }//end of exp
                              }//end of tunnel
                              leaf source-ip-addr {
                                description "ip address";
                                type union {
                                  type string;
                                  type inet:ip-address;
                                }
                              }//end of source-ip-addr
                            }//end of packet
                          }//end of ip-sla-service-performance-packet-direction-sub-command-grouping
                          uses ip-sla-service-performance-traffic-direction-sub-command-grouping;
                        }//end of profile
                        augment measurement-type {
                          uses ip-sla-service-performance-measurement-type-sub-command-grouping {
                            augment conform-color {
                              leaf dscp {
                                description "configure conform DSCP";
                                type union {
                                  type uint8 {
                                    range "0..63";
                                  }
                                  type reply-dscp-bits-type;
                                }
                              }//end of dscp
                            }
                            augment exceed-color {
                              leaf dscp {
                                description "configure conform DSCP";
                                type union {
                                  type uint8 {
                                    range "0..63";
                                  }
                                  type reply-dscp-bits-type;
                                }
                              }//end of dscp
                            }//end of exceed-color
                          }//end of ip-sla-service-performance-measurement-type-sub-command-grouping
                        }//end of measurement-type
                      }//end of ip-sla-service-performance-sub-command-grouping
                    }//end of ip
                  }//end of ip-case
                }//choice of service-type
              }//end of type
            }//end of service-performance
          }//end of service-performance-case
        }// end choice sla-param
        
        container modification-configuration {
          leaf owner {
            description
              "Owner of Entry";
            when "../../icmp-echo or
              ../../icmp-jitter or
              ../../path-echo or
              ../../path-jitter or
              ../../udp-echo or
              ../../udp-jitter or
              ../../http or
              ../../dhcp or
              ../../tcp-connect or
              ../../dns or
              ../../ftp or
              ../../ethernet/echo or
              ../../ethernet/jitter or
              ../../ethernet/y1731-config";
            type string;
          }
          leaf tag {
            description
              "User defined tag";
            when "../../icmp-echo or
              ../../icmp-jitter or
              ../../path-echo or
              ../../path-jitter or
              ../../udp-echo or
              ../../udp-jitter or
              ../../http or
              ../../dhcp or
              ../../tcp-connect or
              ../../dns or
              ../../ftp or
              ../../ethernet/echo or
              ../../ethernet/jitter";
            type string;
          }
          leaf threshold {
            description
              "Operation threshold in milliseconds";
            when "../../icmp-echo or
              ../../icmp-jitter or
              ../../path-echo or
              ../../path-jitter or
              ../../udp-echo or
              ../../udp-jitter or
              ../../http or
              ../../dhcp or
              ../../tcp-connect or
              ../../dns or
              ../../ftp or
              ../../ethernet/echo or
              ../../ethernet/jitter";
            units miliseconds;
            type uint32 {
              range "0..60000";
            }
            default 5000;
          }
          leaf timeout {
            description
              "Timeout of an operation";
            when "../../icmp-echo or
              ../../icmp-jitter or
              ../../path-echo or
              ../../path-jitter or
              ../../udp-echo or
              ../../udp-jitter or
              ../../http or
              ../../dhcp or
              ../../tcp-connect or
              ../../dns or
              ../../ftp or
              ../../ethernet/echo or
              ../../ethernet/jitter";
            units miliseconds;
            type uint32 {
              range "0..604800000";
            }
            default 5000;
          }
          leaf frequency {
            description
              "Frequency of an operation";
            when "../../icmp-echo or
              ../../icmp-jitter or
              ../../path-echo or
              ../../path-jitter or
              ../../udp-echo or
              ../../udp-jitter or
              ../../http or
              ../../dhcp or
              ../../tcp-connect or
              ../../dns or
              ../../ftp or
              ../../ethernet/echo or
              ../../ethernet/jitter or
              ../../ethernet/y1731-config/delay/sender/burst or
              ../../ethernet/y1731-config/loss/wrapper-container/burst";
            units seconds;
            type uint32 {
              range "1..604800";
            }
            default 60;
          }
          
          container history {
            description
              "History and Distribution Data";
            container enhanced {
              description
                "Enable enhanced history collection";
              when "../../../icmp-echo or
                ../../../icmp-jitter or
                ../../../udp-echo or
                ../../../udp-jitter or
                ../../../tcp-connect or
                ../../../ethernet/echo or
                ../../../ethernet/jitter";
              leaf interval {
                description
                  "Aggregation interval";
                type uint16 {
                  range "1..3600";
                }
              }
              leaf buckets {
                description
                  "Number of buckets to collect data";
                type uint8 {
                  range "1..100";
                }
              }
            }
            leaf buckets-kept {
                description
                  "Maximum number of history buckets to collect";
                when "../../../icmp-echo or
                  ../../../path-echo or
                  ../../../udp-echo or
                  ../../../dhcp or
                  ../../../tcp-connect or
                  ../../../dns or
                  ../../../ftp or
                  ../../../ethernet/echo";
                type uint8 {
                  range "1..60";
                }
                default 15;
            }
            leaf distributions-of-statistics-kept {
              description
                "Maximum number of statistics distribution buckets to capture";
              when "../../../icmp-echo or
                ../../../icmp-jitter or
                ../../../path-echo or
                ../../../udp-echo or
                ../../../udp-jitter or
                ../../../dhcp or
                ../../../http or
                ../../../tcp-connect or
                ../../../dns or
                ../../../ftp or
                ../../../ethernet/echo or
                ../../../ethernet/jitter";
              type uint8 {
                range "1..20";
              }
              default 1;
            }
            leaf filter {
              description
                "Add operation to History when...";
              when "../../../icmp-echo or
                ../../../path-echo or
                ../../../udp-echo or
                ../../../dhcp or
                ../../../tcp-connect or
                ../../../dns or
                ../../../ftp or
                ../../../ethernet/echo";
              type enumeration {
                enum "all";
                enum "failures";
                enum "none";
                enum "overThreshold";
              }
              default none;
            }
            leaf hours-of-statistics-kept {
              description
                "Maximum number of statistics hour groups to capture";
              when "../../../icmp-echo or
                ../../../icmp-jitter or
                ../../../path-echo or
                ../../../udp-echo or
                ../../../udp-jitter or
                ../../../dhcp or
                ../../../http or
                ../../../tcp-connect or
                ../../../dns or
                ../../../ftp or
                ../../../ethernet/echo or
                ../../../ethernet/jitter";
              type uint8 {
                range "0..25";
              }
              default 2;
            }
            leaf lives-kept {
              description
                "Maximum number of history lives to collect";
              when "../../../icmp-echo or
                ../../../path-echo or
                ../../../udp-echo or
                ../../../dhcp or
                ../../../tcp-connect or
                ../../../dns or
                ../../../ftp or
                ../../../ethernet/echo";
              type uint8 {
                range "0..2";
              }
              default 0;
            }
            leaf statistics-distribution-interval {
              description
                "Statistics distribution interval size";
              when "../../../icmp-echo or
                ../../../icmp-jitter or
                ../../../path-echo or
                ../../../udp-echo or
                ../../../udp-jitter or
                ../../../dhcp or
                ../../../http or
                ../../../tcp-connect or
                ../../../dns or
                ../../../ftp or
                ../../../ethernet/echo or
                ../../../ethernet/jitter";
              type uint8 {
                range "1..100";
              }
              default 20;
            }
            leaf interval {
              description
                "Specify number of intervals";
              when "../../../ethernet/y1731-config";
              type uint8 {
                range "1..10";
              }
            }
          }//end of history
              
          leaf paths-of-statistics-kept {
            description
                    "Maximum number of statistics paths to capture";
            when "../../path-echo";
            type uint8 {
              range "1..128";
            }
            default 5;
          }
          leaf samples-of-history-kept {
            description
              "Maximum number of history samples to collect";
            when "../../path-echo";
            type uint8 {
              range "1..30";
            }
            default 16;
          }
          leaf hops-of-statistics-kept {
            description
              "Maximum number of statistics hops to capture";
            when "../../path-echo";
            type uint8 {
              range "1..30";
            }
            default 16;
          }
          leaf-list lsr-path {
            description
              "Loose Source Routing Path";
            when "../../path-echo or
              ../../path-jitter";
            type union {
              type string;
              type inet:ipv4-address;
            }
          }
          leaf request-data-size {
            description
              "Request data size";
            when "../../icmp-echo or
              ../../path-echo or
              ../../path-jitter or
              ../../udp-echo or
              ../../udp-jitter or
              ../../ethernet/echo or
              ../../ethernet/jitter";
            type uint32 {
              range "0..16384";
            }
            default 28;
          }
          choice tos-param {
            case tos {
              leaf tos {
                description
                  "Type Of Service";
                when "../../icmp-echo or
                  ../../icmp-jitter or
                  ../../path-echo or
                  ../../path-jitter or
                  ../../udp-echo or
                  ../../udp-jitter or
                  ../../http or
                  ../../tcp-connect";
                type uint8 {
                  range "0..255";
                }
              }
            }
            case traffic-class {
              leaf traffic-class {
                description
                  "Traffic class";
                when "../../icmp-echo or
                  ../../path-echo or
                  ../../path-jitter or
                  ../../udp-echo or
                  ../../udp-jitter or
                  ../../http or
                  ../../tcp-connect";
               type uint8 {
                  range "0..255";
                }
              }
            }
          }
          leaf verify-data {
            description
              "Verify data";
            when "../../icmp-echo or
              ../../path-echo or
              ../../path-jitter or
              ../../udp-echo or
              ../../udp-jitter";
            type boolean;
          }
          leaf vrf {
            description
              "Configure IP SLAs for a VPN Routing/Forwarding instance";
            when "../../icmp-echo or
              ../../icmp-jitter or
              ../../path-echo or
              ../../path-jitter or
              ../../udp-echo or
              ../../udp-jitter or
              ../../http or
              ../../tcp-connect or
              ../../dns";
            must "/ios:native/ios:vrf/ios:definition[ios:name=current()] or /ios:native/ios:ip/ios:vrf[ios:name=current()]" {
              error-message "VRF must be created 1st, deleted last";
            }
            type string;
          }
          
          leaf flow-label {
            description "Flow Label Value for IPv6 destination";
            when "../../path-jitter";
            type uint64 {
              range "0..1048575";
            }
          }
          
          leaf data-pattern {
            description
              "Data Pattern in Hex 0-FFFFFFFF";
            when "../../icmp-echo or
              ../../udp-echo or
              ../../udp-jitter";
            type string;
          }
          leaf response-data-size {
            description
              "Number of bytes in response payload";
            when "../../udp-jitter";
            type uint16 {
              range "20..17512";
            }
          }
          leaf precision {
            description "Set precision of measurement";
            when "../../udp-jitter";
            type enumeration {
              enum "microseconds" {
              }
              enum "milliseconds" {
              }
            }
            default milliseconds;
          }
          leaf optimize{
            description
              "Optimize timestamp of measurement";
            when "../../udp-jitter";
            type enumeration {
              enum "timestamp" {
              }
            }
          }
          leaf enhanced {
            description
              "Improve the accuracy of measurement";
            when "../../udp-jitter";
            type enumeration {
              enum "timestamp" {
              }
            }
          }
          leaf operation-packet-priority {
            description
              "Set operation packet properties";
            when "../../udp-jitter";
            type enumeration {
              enum "high" {
              }
              enum "normal" {
              }
            }
          }
          container clock-tolerance {
            description "Set acceptable clock synchronization error";
            when "../../udp-jitter";
            container ntp {
              description
                "Acceptable clock synchronization error due to NTP";
              container oneway {
                description
                  "Acceptable clock synchronization error in one-way measurement";
                choice clock-tolerance-param {
                  case absolute-type {
                    leaf absolute {
                      description "Acceptable error in microseconds";
                      type uint32 {
                        range "0..100000";
                      }
                    }
                  }
                  case percent-type {
                    leaf percent {
                      description
                        "Acceptable error as percent of value measured";
                      type uint8 {
                        range "0..100";
                      }
                    }
                  }
                } // end choice
              } // end container oneway
            } // end ntp
          } // end clock-tolerance
          
          container percentile {
            description
              "Set percentile statistics levels";
            when "../../udp-jitter or
              ../../ethernet/jitter";
            
            leaf jitteravg {
              description
                "% of Average Jitter values to use (default 100%)";
              type uint8 {
                range "90..100";
              }
            }
            leaf jitterds {
              description
                "% of Destination to source jitter value to use (default 100%)";
              type uint8 {
                range "90..100";
              }
            }
            leaf jittersd {
              description
                "% of Source to destination jitter value to use (default 100%)";
              type uint8 {
                range "90..100";
              }
            }
            leaf owds {
              description
                "% of One way destination to source value to use (default 100%)";
              type uint8 {
                range "90..100";
              }
            }
            leaf owsd {
              description
                "% of One way source to destination value to use (default 100%)";
              type uint8 {
                range "90..100";
              }
            }
            leaf rtt {
              description
                "% of Round Trip Time value to use (default 100%)";
              type uint8 {
                range "90..100";
              }
            }
          }
          
          container http-raw-request {
            description "HTTP Raw Request configuration";
            when "../../http";
            leaf raw-request-string {
               description "HTTP Raw string";
               type string;
            }
          }
          
          leaf http-status-code-ignore {
            description "HTTP Status Code Check Disable";
            when "../../http";
            type boolean;
          }
          
          leaf cos {
            description "Class Of Service";
            when "../../ethernet/echo or
              ../../ethernet/jitter ";
            type uint8 {
              range "0..7";
            }
          }
          container aggregate {
            description
              "Aggregate parameters";
            when "../../ethernet/y1731-config";
            leaf interval_leaf {
              description "Specify interval period";
              when "../../../ethernet/y1731-config/delay/receive";
              type uint16 {
                range "1..65535";
              }
            }//end of interval
            container interval {
              description "Specify interval period";
              when "../../../ethernet/y1731-config/delay/sender or 
                ../../../ethernet/y1731-config/loss";
              leaf interval-period {
                description "Specify interval period";
                when "not (../../../../ethernet/y1731-config/delay/sender/burst) and
                  not (../../../../ethernet/y1731-config/loss/wrapper-container/burst)";
                type uint32 {
                  range "1..65535";
                }
              }//end of interval
              leaf burst-cycles {
                description "Specify number of burst cycles";
                when "(../../../../ethernet/y1731-config/delay/sender/burst) or
                  (../../../../ethernet/y1731-config/loss/wrapper-container/burst)";
                type uint16 {
                  range "1..900";
                }
              }//end of burst-cycle
            }//end of interval
          }//end of aggregate
          container clock {
            description "Specify clock parameters";
            when "../../ethernet/y1731-config/delay/sender/name='DMM' or 
                  ../../ethernet/y1731-config/delay/sender/name='DMMv1'";
            leaf sync {
              description "Clocks are in sync on sender and responder";
              type boolean;
            }
          }
          container distribution {
            description "Specify the distribution statistics parameters";
            when "../../ethernet/y1731-config";
            container delay {
              description "Specify delay distribution parameters";
              container one-way {
                leaf one-way {
                  description "Specify one-way distribution parameters";
                  type uint8 {
                    range "1..10";
                  }
                }//end of one-way
                leaf bin-upper-boundry {
                  description "Specify a comma separated list of bin upper boundaries in micro-second";
                  type string;
                }//end of bin-upper-boundry
              }//end of one-way
              container two-way {
                when "../../../../ethernet/y1731-config/delay/sender/name='DMM' or 
                      ../../../../ethernet/y1731-config/delay/sender/name='DMMv1'";
                leaf two-way {
                  description "Specify two-way distribution parameters";
                  type uint8 {
                    range "1..10";
                  }
                }//end of two-way
                leaf bin-upper-boundry {
                  description "Specify a comma separated list of bin upper boundaries in micro-second";
                  type string;
                }//end of bin-upper-boundry
              }//end of two-way
            }//end of delay
            container delay-variation {
              description "Specify delay-variation distribution parameters";
              container one-way {
                leaf one-way {
                  description "Specify one-way distribution parameters";
                  type uint8 {
                    range "1..10";
                  }
                }//end of one-way
                leaf bin-upper-boundry {
                  description "Specify a comma separated list of bin upper boundaries in micro-second";
                  type string;
                }//end of bin-upper-boundry
              }//end of one-way
              container two-way {
                when "../../../../ethernet/y1731-config/delay/sender/name='DMM' or 
                      ../../../../ethernet/y1731-config/delay/sender/name='DMMv1'";
                leaf two-way {
                  description "Specify two-way distribution parameters";
                  type uint8 {
                    range "1..10";
                  }
                }//end of two-way
                leaf bin-upper-boundry {
                  description "Specify a comma separated list of bin upper boundaries in micro-second";
                  type string;
                }//end of bin-upper-boundry
              }//end of two-way
            }//end of delay-variation
          }//end of distribution
          container frame {
            description "Specify frame parameters";
            when "../../ethernet/y1731-config";
            leaf interval {
              description "Specify inter-frame period";
              when "../../../ethernet/y1731-config/delay/sender or
                ../../../ethernet/y1731-config/loss";
              type frame-interval-type;
            }//end of interval
            leaf size {
              description "Specify payload size in 4 octet increments";
              when "../../../ethernet/y1731-config/delay/sender or
                ../../../ethernet/y1731-config/loss/wrapper-container/name='SLM'";
              type uint16 {
                range "64..384";
              }
            }//end of size
            leaf offset {
              description "Specify the frame offset to be used for calculations";
              when "(../../../ethernet/y1731-config/delay/receive or
                ../../../ethernet/y1731-config/delay/sender/name = 'DMM' or
                ../../../ethernet/y1731-config/delay/sender/name = 'DMMv1')"; 
              type uint8 {
                range "1..10";
              }
            }//end of offset
            leaf consecutive {
              description "Specify the consecutive frames to be used for calculations";
              when "../../../ethernet/y1731-config/loss";
              type uint16 {
                range "1..10";
              }
            }//end of consecutive
            leaf burst {
              description "Number of frames to send per burst";
              when "(../../../ethernet/y1731-config/delay/sender/burst) or
                (../../../ethernet/y1731-config/loss/wrapper-container/burst)";
              type uint16 {
                range "1..65535";
              }
            }//end of burst 
          }//end of frame
          container availability {
            description "Specify the availability parameters";
            when "../../ethernet/y1731-config/loss";
            container algorithm {
              description "Specify the algorithm to use";
              leaf sliding-window {
                description "Use a sliding window";
                type boolean;
              }
              leaf static-window {
                description "Use a static window";
                type boolean;
              }
            }//end of alogorithm
          }//end of availability
          leaf max-delay {
            description "Specify the max delay";
            when  "../../ethernet/y1731-config/loss/wrapper-container/name='LMM' or 
                   ../../ethernet/y1731-config/delay/receive/name='1DM' or 
                   ../../ethernet/y1731-config/delay/sender/name='DMM' or 
                   ../../ethernet/y1731-config/delay/sender/name='DMMv1' or 
                   ../../ethernet/y1731-config/delay/sender/name='1DM'";
            type uint16 {
              range "1..65535";
            }
          }//end of max-delay
          container aggregation {
            description "Statistics aggregation";
            when "../../service-performance";
            container interval {
              description "Statistics aggregation period";
              leaf buckets {
                description "interval statistic buckets";
                type uint8 {
                  range "1..30";
                }
              }
            }
          }//end of aggregation
          leaf description {
            description "Operation Description";
            when "../../service-performance";
            type string;
          }//end of description
          container duration {
            description "Service Performance duration configuration";
            when "../../service-performance";
            leaf time {
              description "Time based duration";
              type uint16 {
                range "10..40950";
              }
            }
          }//end of duration
          container frequency_serv_perf {
            description "Scheduled frequency";
            when "../../service-performance";
            leaf time {
              description "Frequency period";
              type uint32 {
                range "20..604800";
              }
            }//end of time
            container frequency-iteration {
              description
                "Frequency iteration configuration";
              leaf iteration {
                description "Iteration number";
                type uint8 {
                  range "1..100";
                }
              }//end of iteration
              leaf delay {
                description "Delay between interactions";
                type uint8 {
                  range "0..10";
                }
              }//end of delay
            }//end of frequency-iteration
          }//end of frequency
          container loopback {
            description "loopback";
            when "../../service-performance";
            container direction {
              description "loopback direction";
              leaf internal {
                description "internal direction";
                type boolean;
              }//end of internal
              leaf external {
                description "external direction";
                type boolean;
              }//end of external
            }//end of direction
          }//end of loopback
          container measurement-type {
            description "Measurement";
            when "../../service-performance";
            leaf direction {
              description "Measurement direction";
              type enumeration {
                enum "external" {
                  description "external direction";
                }
                enum "internal" {
                  description "internal direction";
                }
              }
            }//end of direction
            container conform-color {
              description "conform-color";
              leaf cos {
                description "configure conform COS";
                when "../../../../service-performance/type/ethernet";
                type uint8 {
                  range "0..7";
                }
              }//end of cos
              leaf dscp {
                description "configure conform DSCP";
                when "../../../../service-performance/type/ip";
                type union {
                  type uint8 {
                    range "0..63";
                  }
                  type reply-dscp-bits-type;
                }
              }//end of dscp
            }//end of conform-color
            container exceed-color {
              description "exceed-color";
              leaf cos {
                description "configure conform COS";
                when "../../../../service-performance/type/ethernet";
                type uint8 {
                  range "0..7";
                }
              }//end of cos
              leaf dscp {
                description "configure conform DSCP";
                when "../../../../service-performance/type/ip";
                type union {
                  type uint8 {
                    range "0..63";
                  }
                  type reply-dscp-bits-type;
                }
              }//end of dscp
            }//end of exceed-color
            leaf delay {
              description "Delay measurement";
              type empty;
            }//end of delay
            leaf jitter {
              description "Jitter measurement";
              type empty;
            }//end of jitter
            leaf loss {
              description "loss measurement";
              type empty;
            }//end of loss
            leaf receive {
              description "Received bytes/packets measurement";
              type empty;
            }//end of receive
            leaf throughput {
              description "Throughput measurement";
              type empty;
            }//end of throughput
          }//end of measurement-type
          container profile {
            when "../../service-performance";
            description "Service Performance Profile";
            container packet {
              description "Packet Profiles";
              leaf dscp {
                description "Configure DSCP";
                type union {
                  type uint8 {
                    range "0..63";
                  }
                  type reply-dscp-bits-type;
                }
              }//end of dscp
              leaf ethertype {
                description "Frame type";
                type enumeration {
                  enum "ipv4";
                  enum "ipv6";
                }
              }//end of ethertype
              leaf inner-cos {
                description "Inner COS";
                type uint8 {
                  range "0..7";
                }
              }
              leaf inner-vlan {
                description "Specify Inner VLAN";
                type uint16 {
                  range "0..4095";
                }
              }//end of inner-vlan
              leaf outer-cos {
                description "Outer COS";
                type uint8 {
                  range "0..7";
                }
              }//end of outer-cos
              leaf outer-vlan {
                description "Specify the Outer VLAN";
                type uint16 {
                  range "0..4095";
                }
              }//end of outer-vlan
              leaf packet-size {
                description "Packet Size";
                type packet-size-type;
              }//end of packet-size
              leaf src-mac-addr {
                description "The source mac-address";
                when "../../../../service-performance/type/ethernet";
                type ios-types:cisco-mac-address-type;
              }//end of src-mac-addr
              leaf source-ip-addr {
                description "ip address";
                when "../../../../service-performance/type/ip";
                type union {
                  type string;
                  type inet:ip-address;
                }
              }//end of source-ip-addr
              container tunnel {
                description "Tunnel type";
                leaf exp {
                  description "Exp value";
                  type uint8 {
                    range "0..7";
                  }
                }//end of exp
              }//end of tunnel
            }//end of packet
            container traffic {
              description "Service Performance traffic profile";
              leaf direction {
                description "Traffic direction";
                type enumeration {
                  enum "external" {
                    description "external direction";
                  }
                  enum "internal" {
                    description "internal direction";
                  }
                }
              }//end of direction
              leaf cbs {
                description "Committed Burst Size";
                type uint32 {
                  range "0..16000000";
                }
                units Kbps;
              }
              leaf cir {
                description "Committed Information Rate. The range mentioned is for 10G interface. For 1G interface, the range is 0..1000000";
                type uint32 {
                  range "0..10000000";
                }
                units Kbps;
              }
              leaf ebs {
                description "Excess Burst Size";
                type uint32 {
                  range "0..16000000";
                }
                units Kbps;
              }
              leaf eir {
                description "Excess Information Rate. The range mentioned is for 10G interface. For 1G interface, the range is 0..1000000";
                type uint32 {
                  range "0..10000000";
                }
                units Kbps;
              }
              container rate-step {
                description "Rate Step";
                choice Kbps_or_pps {
                  container Kbps {
                    description "Kilobits per second rate. The range mentioned is for 10G interface. For 1G interface, the range is 0..1000000";
                    leaf step1 {
                      description "Step 1 (Kbps/pps)";
                      type uint32 {
                        range "1..10000000";
                      }
                      units Kbps/pps;
                    }//end of step1
                    leaf step2 {
                      description "Step 2 (Kbps/pps), Step 2 >= Step 1";
                      must "../step2 >= ../step1";
                      type uint32 {
                        range "1..10000000";
                      }
                      units Kbps/pps;
                    }//end of step2
                    leaf step3 {
                      description "Step 3 (Kbps/pps), Step 3 >= Step 2";
                      must "../step3 >= ../step2";
                      type uint32 {
                        range "1..10000000";
                      }
                      units Kbps/pps;
                    }//end of step3
                    leaf step4 {
                      description "Step 4 (Kbps/pps), Step 4 >= Step 3";
                      must "../step4 >= ../step3";
                      type uint32 {
                        range "1..10000000";
                      }
                      units Kbps/pps;
                    }//end of step4
                    leaf step5 {
                      description "Step 5 (Kbps/pps), Step 5 >= Step 4";
                      must "../step5 >= ../step4";
                      type uint32 {
                        range "1..10000000";
                      }
                      units Kbps/pps;
                    }//end of step5
                    leaf step6 {
                      description "Step 6 (Kbps/pps), Step 6 >= Step 5";
                      must "../step6 >= ../step5";
                      type uint32 {
                        range "1..10000000";
                      }
                      units Kbps/pps;
                    }//end of step6
                    leaf step7 {
                      description "Step 7 (Kbps/pps), Step 7 >= Step 6";
                      must "../step7 >= ../step6";
                      type uint32 {
                        range "1..10000000";
                      }
                      units Kbps/pps;
                    }//end of step7
                    leaf step8 {
                      description "Step 8 (Kbps/pps), Step 8 >= Step 7";
                      must "../step8 >= ../step7";
                      type uint32 {
                        range "1..10000000";
                      }
                      units Kbps/pps;
                    }//end of step8
                    leaf step9 {
                      description "Step 9 (Kbps/pps), Step 9 >= Step 8";
                      must "../step9 >= ../step8";
                      type uint32 {
                        range "1..10000000";
                      }
                      units Kbps/pps;
                    }//end of step9
                    leaf step10 {
                      description "Step 10 (Kbps/pps), Step 10 >= Step 9";
                      must "../step10 >= ../step9";
                      type uint32 {
                        range "1..10000000";
                      }
                      units Kbps/pps;
                    }//end of step10
                  }//end of Kbps
                  container pps {
                    description "Packet per second rate";
                    leaf step1 {
                      description "Step 1 (Kbps/pps)";
                      type uint32 {
                        range "1..15000000";
                      }
                      units Kbps/pps;
                    }//end of step1
                    leaf step2 {
                      description "Step 2 (Kbps/pps), Step 2 >= Step 1";
                      must "../step2 >= ../step1";
                      type uint32 {
                        range "1..15000000";
                      }
                      units Kbps/pps;
                    }//end of step2
                    leaf step3 {
                      description "Step 3 (Kbps/pps), Step 3 >= Step 2";
                      must "../step3 >= ../step2";
                      type uint32 {
                        range "1..15000000";
                      }
                      units Kbps/pps;
                    }//end of step3
                    leaf step4 {
                      description "Step 4 (Kbps/pps), Step 4 >= Step 3";
                      must "../step4 >= ../step3";
                      type uint32 {
                        range "1..15000000";
                      }
                      units Kbps/pps;
                    }//end of step4
                    leaf step5 {
                      description "Step 5 (Kbps/pps), Step 5 >= Step 4";
                      must "../step5 >= ../step4";
                      type uint32 {
                        range "1..15000000";
                      }
                      units Kbps/pps;
                    }//end of step5
                    leaf step6 {
                      description "Step 6 (Kbps/pps), Step 6 >= Step 5";
                      must "../step6 >= ../step5";
                      type uint32 {
                        range "1..15000000";
                      }
                      units Kbps/pps;
                    }//end of step6
                    leaf step7 {
                      description "Step 7 (Kbps/pps), Step 7 >= Step 6";
                      must "../step7 >= ../step6";
                      type uint32 {
                        range "1..15000000";
                      }
                      units Kbps/pps;
                    }//end of step7
                    leaf step8 {
                      description "Step 8 (Kbps/pps), Step 8 >= Step 7";
                      must "../step8 >= ../step7";
                      type uint32 {
                        range "1..15000000";
                      }
                      units Kbps/pps;
                    }//end of step8
                    leaf step9 {
                      description "Step 9 (Kbps/pps), Step 9 >= Step 8";
                      must "../step9 >= ../step8";
                      type uint32 {
                        range "1..15000000";
                      }
                      units Kbps/pps;
                    }//end of step9
                    leaf step10 {
                      description "Step 10 (Kbps/pps), Step 10 >= Step 9";
                      must "../step10 >= ../step9";
                      type uint32 {
                        range "1..15000000";
                      }
                      units Kbps/pps;
                    }//end of step10
                  }//end of pps
                }//end of choice Kbps_or_pps
              }//end of rate-step
            }//end of traffic
          }//end of profile
          leaf signature {
            description "Payload Contents";
            when "../../service-performance";
            type string;
          }//end of signature
          container control {
            description
              "Set control protocol parameters";
            leaf retry {
              description "How often the control message should do a retry (default 3 times)";
              when "../../../udp-jitter"; 
              type uint8 {
                range "1..5";
              }
              default 3;
            }
            leaf timeout {
              description "How long to wait for control message timeout (default 5 seconds)";
              when "../../../udp-jitter";
              type uint16 {
                range "1..10000";
              }
              default 5000;
            }
          }
        }//modification-configuration
      } // end ip sla entry

      // ip sla enable
      container enable {
        leaf reaction-alerts {
          type empty;
        }
      }
      
      // ip sla responder
      container responder {
        description "Enable IP SLAs Responder";
        presence true;
        container udp-echo {
          description "Setup udp-echo responder";
          leaf port {
            description "Permanent port";
            type uint16 {
              range "1..65535";
            }
          }
          list ipaddress {
            description "Permanent address";
            key "host";
            leaf host {
              type union {
                type inet:ipv4-address;
                type inet:ipv6-address;
              }
            }
            leaf port {
              description "Permanent port";
              type uint16 {
                range "1..65535";
              }
            }
          }
        }
        container tcp-connect {
          description "Setup tcp-connect responder";
          leaf port {
            description "Permanent port";
            type uint16 {
              range "1..65535";
            }
          }
          list ipaddress {
            description "Permanent address";
            key "host";
            leaf host {
              type union {
                type inet:ipv4-address;
                type inet:ipv6-address;
              }
            }
            leaf port {
              description "Permanent port";
              type uint16 {
                range "1..65535";
              }
            }
          }
        }
      }
      // ip sla logging
      container logging {
        description "low-memory";
        leaf traps {
          description "Enable syslog traps";
          type empty;
        }
      }
      
      // ip sla group
      container group {
        description "Group Configuration or Group Scheduling";
        list schedule {
          description "Group scheduling";
          key "entry-number";
          leaf entry-number {
            description "Group schedule entry number";
            type uint32 {
              range "1..2147483647";
            }
          }
          list probe-ids {
            key "word";
            leaf word {
              type string;
            }
            container schedule-period {
              description "Group schedule period range";
              leaf seconds {
                description "seconds";
                type uint32;
              }
              container frequency {
                description
                  "Group operation frequency";
                choice frequency-choice {
                  case frequency-value {
                    leaf frequency-val {
                      description
                        "Specify frequency in seconds";
                      type uint32;
                    }
                  }
                  case frequency-range {
                      leaf range {
                        description
                          "Group operation frequency-range for random scheduling";
                      type string;
                    }
                  }
                }
              }

              container start-time {
                description
                  "When to start this entry";
                leaf now {
                  description
                    "Start now";
                  type empty;
                }
              }

              leaf life {
                description
                  "Length of time to execute in seconds";
                type union {
                  type uint32;
                  type enumeration {
                    enum "forever";
                  }
                }
              }

            }// end container schedule-period

          }
        }
      }
      // ip sla schedule
      list schedule {
        description
          "Entry Scheduling";
        key "entry-number";
        leaf entry-number {
          type leafref {
            path "/ios:native/ios:ip/ios-sla:sla/ios-sla:entry/ios-sla:number";
          }
        }
        leaf ageout {
          description
            "How long to keep this Entry when inactive";
          type uint32 {
            range "0..2073600";
          }
          default 0;
        }
        leaf life {
          description
            "Length of time to execute in seconds";
          type union {
            type uint32 {
              range "0..2147483647";
            }
            type enumeration {
              enum "forever";
            }
          }
          default 3600;
        }
        leaf recurring {
          description
            "Probe to be scheduled automatically every day";
          type empty;
        }
        container start-time {
          description
            "When to start this entry.";
          choice start-time-param {
            default pending-type;
            case after-type {
              leaf after-config {
                description "Start after a certain amount of time from now";
                type ios-sla:hour-min-sec;
              }
            }
            case hour-min-type {
              container hour-min-config {
                
                leaf hour-min {
                  description "Start time (hh:mm)";
                  type ios-sla:hour-min;
                }
                leaf date-of-month {
                  description "Day of the month";
                  type uint8 {
                    range "1..31";
                  }
                }
                leaf month {
                  description "Month of the year";
                  type string {
                    pattern "(Jan|Feb|Mar|Apr|May|Jun|Jul|Aug|Sep|Oct|Nov|Dec)";
                  }
                }
              }
            }
            case hour-min-sec-type {
              container hour-min-sec-config {
                
                leaf hour-min-sec {
                  description "Start time (hh:mm)";
                  type ios-sla:hour-min-sec;
                }
                leaf date-of-month {
                  description "Day of the month";
                  type uint8 {
                    range "1..31";
                  }
                }
                leaf month {
                  description "Month of the year";
                  type string {
                    pattern "(Jan|Feb|Mar|Apr|May|Jun|Jul|Aug|Sep|Oct|Nov|Dec)";
                  }
                }
              }
            }
            case now-type {
              leaf now-config {
                description "Start now";
                type empty;
              }
            }
            case pending-type {
              leaf pending-config {
                description "Start pending";
                type empty;
              }
            }
            case random-type {
              leaf random-config {
                description "Start after random time (range)";
                type uint32 {
                  range "500..10000";
                }
              }
            }
          }//end of choice start-time-param
          leaf after {
            description
              "Start after a certain amount of time from now. (DEPRECATED, use after-config)";
            status deprecated;
            type string;
          }
          leaf hour-min {
            status deprecated;
            type string;
          }
          leaf hour-min-sec {
            status deprecated;
            type string;
          }
          leaf now {
            description
              "Start now. (DEPRECATED, use now-config)";
            status deprecated;
            type empty;
          }
          leaf pending {
            description
              "Start pending. (DEPRECATED, use pending-config)";
            status deprecated;
            type empty;
          }
          leaf random {
            description
              "Start after random time (range).  (DEPRECATED, use random-config)";
            status deprecated;
            type uint32 {
              range "500..10000";
            }
          }
        }
      }//end of schedule

      // ip sla reaction-configuration
      list reaction-configuration {
        description
          "IP SLA's reaction configuration";
        key "entry-number";
        leaf entry-number {
          description
            "Entry number";
          type leafref {
            path "/ios:native/ios:ip/ios-sla:sla/ios-sla:entry/ios-sla:number";
          }
        }

        // ip sla reaction-configuration * react
        container react {
          description "Reaction variable to be configured";
          container connectionLoss {
            description "Connection Loss";
            presence true;
            uses config-ip-sla-react-threshold-type-grouping;
            leaf action-type {
              type enumeration {
                enum "none";
                enum "trapAndTrigger";
                enum "trapOnly";
                enum "triggerOnly";
              }
            }
          }

          container rtt {
            description "Round Trip Time";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end rtt

          container timeout {
            description "Timeout";
            presence true;
            uses config-ip-sla-react-threshold-type-grouping;
            leaf action-type {
              type enumeration {
                enum "none";
                enum "trapAndTrigger";
                enum "trapOnly";
                enum "triggerOnly";
              }
            }
          } //end timeout
          
          container protocolSpecificError {
            description "Protocol Specific Error";
            presence true;
            uses config-ip-sla-react-threshold-type-grouping;
            leaf action-type {
              type enumeration {
                enum "none";
                enum "trapAndTrigger";
                enum "trapOnly";
                enum "triggerOnly";
              }
            }
          } //end protocolSpecificError 

          container verifyError {
            description "Verify error";
            presence true;
            uses config-ip-sla-react-threshold-type-grouping;
            leaf action-type {
              type enumeration {
                enum "none";
                enum "trapAndTrigger";
                enum "trapOnly";
                enum "triggerOnly";
              }
            }
          } //end verifyError 
          
          container icpif {
            description "Calculated Planning Impairment Factor";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end icpif 

          container jitterAvg {
            description "Jitter Average in both the directions";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end jitterAvg

          container jitterAvgPct {
            description "Percentile Jitter Average in both the directions";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end jitterAvgPct

          container jitterDSAvg {
            description "Jitter Average in the direction from Destination 
              to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end jitterDSAvg 

          container jitterDSAvgPct {
            description "Percentile Jitter Average in the direction from 
              Destination to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end jitterAvgPct 
          
          container jitterSDAvg {
            description "Jitter Average in the direction from Source 
              to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end jitterSDAvg 

          container jitterSDAvgPct {
            description "Percentile jitter Average in the direction from 
              Source to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end jitterSDAvgPct 
          
          container maxOfNegativeDS {
            description "Maximum negative jitter from Destination to Source"; 
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOfNegativeDS
 
          container maxOfNegativeSD {
            description "Maximum negative jitter from Source to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOfNegativeSD

          container maxOfPositiveDS {
            description "Maximum positive jitter from Destination to Source"; 
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOfPositiveDS
 
          container maxOfPositiveSD {
            description "Maximum positive jitter from Source to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOfPositiveSD 
          
          container mos {
            description "MOS Score";
            presence true;
            uses config-ip-sla-react-threshold-type-grouping;
            container threshold-value {
              description "Threshold value";
              leaf upper-limit-val {
                description
                  "Upper limit";
                type uint32 {
                  range "100..500";
                }
              }
              leaf lower-limit-val {
                description
                  "Lower limit";
                type uint32 {
                  range "100..500";
                }
              }
            }
            leaf action-type {
              type enumeration {
                enum "none";
                enum "trapAndTrigger";
                enum "trapOnly";
                enum "triggerOnly";
              }
            }
          } //end mos
          
          container overThreshold {
            description "Percent of Round Trip Times over threshold";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end overThreshold 

          container packetLateArrival {
            description "Packets arriving Late";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end packetLateArrival

          container packetLossDS {
            description "Packet Loss in the direction from Destination 
              to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end packetLossDS

          container packetLossSD {
            description "Packet Loss in the direction from Source
              to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end packetLossSD

          container packetMIA {
            description "Missing in Action";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end packetMIA 

          container packetOutOfSequence {
            description "Packet arriving out of sequence";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end packetOutOfSequence

          container rttPct {
            description "Percentile Round Trip Time";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end rttPct 

          container latencyDSAvg {
            description "Latency Average from Destination to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end latencyDSAvg

          container latencyDSAvgPct {
            description "Percentile Latency Average from Destination 
              to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end latencyDSAvgPct 

          container latencySDAvg {
            description "Latency Average from Source to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end latencySDAvg 

          container latencySDAvgPct {
            description "Percentile Latency Average from Source 
              to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end latencyDSAvgPct

          container maxOflatencySD {
            description "Maximum Latency from Source to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOflatencySD

          container maxOflatencySDPct {
            description "Percentile Maximum Latency from Source 
              to Destination";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOflatencySDPct

          container maxOflatencyDS {
            description "Maximum Latency from Destination to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOflatencyDS

          container maxOflatencyDSPct {
            description "Percentile Maximum Latency from Destination 
              to Source";
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end maxOflatencyDSPct

          container successivePacketLoss {
            description "Successive Packet Loss"; 
            presence true;
            uses config-ip-sla-react-threshold-type-grouping;
            uses config-ip-sla-react-threshold-value-grouping;
            leaf action-type {
              type enumeration {
                enum "none";
                enum "trapAndTrigger";
                enum "trapOnly";
                enum "triggerOnly";
              }
            }
          } //end successivePacketLoss 

          container loss-ratioDS {
            description "FLR % Destination to Source";
            presence true;
            uses config-ip-sla-react-threshold-type-grouping;
            container threshold-value {
              description "Threshold value";
              leaf upper-limit-val {
                description
                  "Upper limit";
                type uint32 {
                  range "0..100";
                }
              }
              leaf lower-limit-val {
                description
                  "Lower limit";
                type uint32 {
                  range "0..100";
                }
              }
            }
          } //end loss-ratioDS

          container loss-ratioSD {
            description "FLR % Source to Destination";
            presence true;
            uses config-ip-sla-react-threshold-type-grouping;
            container threshold-value {
              description "Threshold value";
              leaf upper-limit-val {
                description
                  "Upper limit";
                type uint32 {
                  range "0..100";
                }
              }
              leaf lower-limit-val {
                description
                  "Lower limit";
                type uint32 {
                  range "0..100";
                }
              }
            }
          } //end loss-ratioSD

          container unavailableDS {
            description "Unavailability % used for FLR Destination to 
              Source";
            presence true;
            uses config-ip-sla-react-threshold-type-grouping;
            container threshold-value {
              description "Threshold value";
              leaf upper-limit-val {
                description
                  "Upper limit";
                type uint32 {
                  range "0..100";
                }
              }
              leaf lower-limit-val {
                description
                  "Lower limit";
                type uint32 {
                  range "0..100";
                }
              }
            }
          } //end unavailableDS 

          container unavailableSD {
            description "Unavailability % used for FLR Source to 
              Destination";
            presence true;
            uses config-ip-sla-react-threshold-type-grouping;
            container threshold-value {
              description "Threshold value";
              leaf upper-limit-val {
                description
                  "Upper limit";
                type uint32 {
                  range "0..100";
                }
              }
              leaf lower-limit-val {
                description
                  "Lower limit";
                type uint32 {
                  range "0..100";
                }
              }
            }
          } //end unavailableSD 
        } //end react
      } //end reaction-configuration

      // ip sla server
      container server {
        description "IPPM server configuration";
        container twamp {
          description "IPPM TWAMP server configuration";
          presence "true";
        }
      }
    }
  }

  /////////////////////////////////////////////////////////
  // native / ip / sla
  /////////////////////////////////////////////////////////
  augment "/ios:native/ios:ip" {
    uses config-ip-sla-grouping;
  } //augment
  
  /////////////////////////////////////////////////////////
  // native / auto / ip / sla
  /////////////////////////////////////////////////////////
  augment "/ios:native" {
      uses config-auto-ip-sla-grouping;
  } //augment

}
