module Cisco-IOS-XE-wireless-radio-cfg {
  yang-version 1;
  namespace "http://cisco.com/ns/yang/Cisco-IOS-XE-wireless-radio-cfg";
  prefix wireless-radio-cfg;

  import Cisco-IOS-XE-wireless-types {
    prefix wireless-types;
  }
  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Model for managing radio configuration
     Copyright (c) 2019 by Cisco Systems, Inc.
     All rights reserved.";

  revision 2019-01-16 {
    description
      "Initial revision";
    reference "1.0.0";
    cisco-semver:module-version "1.0.0";
  }

  grouping st-ap-spec-config {
    description
      "AP specific configuration";
    leaf ap-eth-mac-addr {
      type yang:mac-address;
      description
        "AP ethernet mac address";
    }
    leaf ap-host-name {
      type string;
      description
        "AP host name";
    }
    leaf enable-bssid-stats {
      type boolean;
      default "false";
      description
        "Enable/Disable the receiving bssid stats from AP";
    }
    leaf primary-controller-name {
      type string;
      description
        "Primary controller name";
    }
    leaf primary-controller-ip-addr {
      type inet:ipv4-address;
      description
        "Primary controller IP address";
    }
    leaf primary-controller-v6-ip-addr {
      type inet:ipv6-address;
      description
        "Primary controller v6 IP address";
    }
    leaf secondary-controller-name {
      type string;
      description
        "Secondary controller name";
    }
    leaf secondary-controller-ip-addr {
      type inet:ipv4-address;
      description
        "Secondary controller IP address";
    }
    leaf secondary-controller-v6-ip-addr {
      type inet:ipv6-address;
      description
        "Secondary controller v6 IP address";
    }
    leaf tertiary-controller-name {
      type string;
      description
        "Tertiary controller name";
    }
    leaf tertiary-controller-ip-addr {
      type inet:ipv4-address;
      description
        "Tertiary controller IP address";
    }
    leaf tertiary-controller-v6-ip-addr {
      type inet:ipv6-address;
      description
        "Tertiary controller v6 IP address";
    }
  }

  grouping st-ap-specific-config {
    description
      "Container for radio configuration pertaining to an access point";
    leaf ap-ethernet-mac-addr {
      type yang:mac-address;
      description
        "Radio MAC address of the AP";
    }
    container ap-specific-slot-configs {
      description
        "List of Access-point specific slot configurations";
      list ap-specific-slot-config {
        key "slot-id";
        description
          "Access-point specific slot configurations";
        uses wireless-radio-cfg:st-ap-specific-slot-config;
      }
    }
  }

  grouping st-radio-params-24ghz {
    description
      "Radio parameters specific to 24 ghz radio";
    leaf admin-state {
      type boolean;
      default "true";
      description
        "Enable/disable the radio";
    }
    leaf transmit-power-level {
      type uint8;
      units "dBm";
      default "1";
      description
        "Transmit power level";
    }
    leaf channel {
      type uint8;
      default "1";
      description
        "Operating channel";
    }
    leaf channel-width {
      type uint8;
      default "20";
      description
        "Operating channel-width";
    }
    leaf dca {
      type boolean;
      default "true";
      description
        "Enable/disable dynamic channel allocation";
    }
    leaf dtp {
      type boolean;
      default "true";
      description
        "Enable/disable dynamic transmit power";
    }
    leaf antenna-gain {
      type uint8;
      units "dBi";
      default "0";
      description
        "Antenna gain applied to this Radio";
    }
  }

  grouping st-radio-params-5ghz {
    description
      "Radio parameters specific to 5GHz radio";
    leaf admin-state {
      type boolean;
      default "true";
      description
        "Radio admin state";
    }
    leaf transmit-power-level {
      type uint8;
      units "dBm";
      default "1";
      description
        "Transmit power level";
    }
    leaf channel {
      type uint8;
      default "36";
      description
        "Operating channel";
    }
    leaf channel-width {
      type uint8;
      default "20";
      description
        "Operating channel-width";
    }
    leaf dca {
      type boolean;
      default "true";
      description
        "Enable/disable dynamic channel allocation";
    }
    leaf dtp {
      type boolean;
      default "true";
      description
        "Enable/disable dynamic transmit power";
    }
    leaf antenna-gain {
      type uint8;
      units "dBm";
      default "0";
      description
        "Antenna gain applied to this Radio";
    }
  }

  grouping st-ap-specific-slot-config {
    description
      "Container holding the access point specific radio parameters";
    leaf slot-id {
      type uint8;
      description
        "Slot identifier for the radio";
    }
    leaf radio-band {
      type wireless-types:enm-radio-frequency;
      description
        "Radio band at which the radio is operating";
    }
    container radio-params-24ghz {
      description
        "Radio parameter specific to 24 ghz radio";
      uses wireless-radio-cfg:st-radio-params-24ghz;
    }
    container radio-params-5ghz {
      description
        "Radio parameter specific to 5GHz radio";
      uses wireless-radio-cfg:st-radio-params-5ghz;
    }
  }

  container radio-cfg-data {
    description
      "Top level container for AP specific radio configuration";
    container ap-specific-configs {
      description
        "List of Access-point specific configurations";
      list ap-specific-config {
        key "ap-ethernet-mac-addr";
        description
          "Access-point specific configurations";
        uses wireless-radio-cfg:st-ap-specific-config;
      }
    }
    container ap-spec-configs {
      description
        "List of Access-point specific radio configurations";
      list ap-spec-config {
        key "ap-eth-mac-addr";
        description
          "Access-point specific radio configurations";
        uses wireless-radio-cfg:st-ap-spec-config;
      }
    }
  }
}
