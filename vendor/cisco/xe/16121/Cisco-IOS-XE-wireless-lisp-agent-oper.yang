module Cisco-IOS-XE-wireless-lisp-agent-oper {
  yang-version 1;
  namespace "http://cisco.com/ns/yang/Cisco-IOS-XE-wireless-lisp-agent-oper";
  prefix wireless-lisp-agent-oper;

  import ietf-inet-types {
    prefix inet;
  }
  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "Wireless Fabric Control Plane oper data
     Copyright (c) 2016-2019 by Cisco Systems, Inc.
     All rights reserved.";

  revision 2019-05-01 {
    description
      "Added semantic version";
    reference "4.1.0";
    cisco-semver:module-version "4.1.0";
  }
  revision 2019-01-24 {
    description
      "-Cleaned up spelling errors in descriptions
       -Renaming LISP agent client history and WLC capabilities containers ";
    reference "4.0.0";
    cisco-semver:module-version "4.0.0";
  }
  revision 2018-03-22 {
    description
      "Base type change from uint32 to uint64";
    reference "3.0.0";
    cisco-semver:module-version "3.0.0";
  }
  revision 2018-01-24 {
    description
      "The first generally available version";
    reference "2.0.0";
    cisco-semver:module-version "2.0.0";
  }
  revision 2017-11-12 {
    description
      "Initial revision";
    reference "1.0.0";
    cisco-semver:module-version "1.0.0";
  }

  grouping st-lisp-agent-ap-data {
    description
      "Fabric AP's oper data";
    leaf wtp-mac {
      type yang:mac-address;
      description
        "Fabric AP's ethernet MAC address";
    }
    leaf wtp-ip {
      type inet:ip-address;
      description
        "Fabric AP's IP address";
    }
    leaf wtp-xtr-ip {
      type inet:ip-address;
      description
        "AP's Fabric Edge IP address";
    }
    leaf wtp-vnid {
      type uint32;
      description
        "AP's Virtual Network ID";
    }
    leaf wtp-radio-mac {
      type yang:mac-address;
      description
        "AP's radio MAC address";
    }
    leaf cp-name {
      type string;
      description
        "Fabric Control Plane name";
    }
  }

  grouping st-lisp-agent-client-data {
    description
      "Fabric client's oper data";
    leaf client-mac {
      type yang:mac-address;
      description
        "Fabric client's MAC address";
    }
    leaf client-ap-mac {
      type yang:mac-address;
      description
        "Fabric client's AP MAC address";
    }
    leaf client-ap-ip {
      type inet:ip-address;
      description
        "Fabric Client's AP IP address";
    }
    leaf client-xtr-ip {
      type inet:ip-address;
      description
        "Client's Fabric Edge IP address";
    }
    leaf client-assoc-time {
      type uint64;
      description
        "Fabric client's association time";
    }
    leaf client-ap-vnid {
      type uint32;
      description
        "Fabric Client's AP Virtual Network IP";
    }
    leaf client-vnid {
      type uint32;
      description
        "Fabric client's Virtual Network ID";
    }
    leaf client-sgt {
      type uint16;
      description
        "Fabric client's group tag";
    }
    leaf cp-name {
      type string;
      description
        "Fabric Control Plane name";
    }
  }

  grouping st-lisp-agent-ms-msg-stats {
    description
      "Fabric Control Plane Message statistics";
    leaf map-server-ip {
      type inet:ip-address;
      description
        "Control plane IP address";
    }
    leaf map-request-msg-count {
      type yang:counter64;
      description
        "Map request message count";
    }
    leaf map-reply-ack-msg-count {
      type yang:counter64;
      description
        "Map reply acknowledgement message count";
    }
    leaf map-reply-nack-msg-count {
      type yang:counter64;
      description
        "Negative Map reply message count";
    }
    leaf map-register-add-msg-count {
      type yang:counter64;
      description
        "Map register client add message count";
    }
    leaf map-register-delete-msg-count {
      type yang:counter64;
      description
        "Map register client delete message count";
    }
    leaf map-register-ack-msg-count {
      type yang:counter64;
      description
        "Map register acknowledgement message count";
    }
    leaf map-register-add-reject-msg-count {
      type yang:counter64;
      description
        "Map register client add reject message count";
    }
    leaf map-register-delete-reject-msg-count {
      type yang:counter64;
      description
        "Map register client delete reject message count";
    }
    leaf map-register-refresh-msg-count {
      type yang:counter64;
      description
        "Map register refresh message count";
    }
    leaf map-wlc-notify-msg-count {
      type yang:counter64;
      description
        "Map WLC notify message count";
    }
    leaf map-error-notify-msg-count {
      type yang:counter64;
      description
        "Map error notification message count";
    }
    leaf map-request-msg-send-failure-count {
      type yang:counter64;
      description
        "Map request message send failure count";
    }
    leaf map-register-msg-send-failure-count {
      type yang:counter64;
      description
        "Map register message send failure count";
    }
    leaf map-register-ack-msg-parse-failure-count {
      type yang:counter64;
      description
        "Map registration acknowledgement message parse failure count";
    }
    leaf map-register-reject-msg-parse-failure-count {
      type yang:counter64;
      description
        "Map register reject message parse failure count";
    }
    leaf map-register-refresh-msg-parse-failure-count {
      type yang:counter64;
      description
        "Map register refresh message parse failure count";
    }
    leaf map-reply-msg-parse-failure-count {
      type yang:counter64;
      description
        "Map reply message parse failure count";
    }
    leaf map-server-tcp-create-fail-count {
      type yang:counter64;
      description
        "TCP create failure count";
    }
    leaf map-server-tcp-read-fail-count {
      type yang:counter64;
      description
        "TCP read failure count";
    }
    leaf map-server-tcp-msg-parse-fail-count {
      type yang:counter64;
      description
        "TCP message parse failure count";
    }
    leaf map-server-tcp-write-fail-count {
      type yang:counter64;
      description
        "TCP write failure count";
    }
    leaf map-server-udp-create-fail-count {
      type yang:counter64;
      description
        "UDP create failure count";
    }
    leaf map-server-udp-read-fail-count {
      type yang:counter64;
      description
        "UDP read failure count";
    }
    leaf map-server-udp-msg-parse-fail-count {
      type yang:counter64;
      description
        "UDP message parse failure count";
    }
    leaf map-server-udp-write-fail-count {
      type yang:counter64;
      description
        "UDP write failure count";
    }
    leaf map-server-status {
      type boolean;
      description
        "Control Plane connection status";
    }
  }

  grouping st-lisp-agent-client-history-entry {
    description
      "Fabric Client history data";
    leaf wtp-mac {
      type yang:mac-address;
      description
        "Fabric Client's AP MAC address";
    }
    leaf client-xtr-ip {
      type inet:ip-address;
      description
        "Client's Fabric Edge IP address";
    }
    leaf ms-ip {
      type inet:ip-address;
      description
        "Control plane IP address";
    }
    leaf client-assoc-time {
      type uint64;
      description
        "Fabric Client's association time";
    }
    leaf data-entry-time {
      type uint64;
      description
        "Fabric client info update time";
    }
    leaf client-vnid {
      type uint32;
      description
        "Fabric client's Virtual Network ID";
    }
    leaf lisp-msg-type {
      type uint32;
      description
        "Fabric Control plane message type";
    }
    leaf client-sgt {
      type uint16;
      description
        "Fabric client's Group tag";
    }
  }

  grouping st-lisp-agent-client-history-list {
    description
      "Fabric client history list";
    list entry {
      description
        "Fabric client history entry";
      uses wireless-lisp-agent-oper:st-lisp-agent-client-history-entry;
    }
  }

  grouping st-lisp-agent-client-history {
    description
      "Fabric client history";
    leaf client-mac {
      type yang:mac-address;
      description
        "Fabric client MAC address";
    }
    container assoc-history {
      description
        "Fabric client association history";
      uses wireless-lisp-agent-oper:st-lisp-agent-client-history-list;
    }
  }

  grouping st-lisp-agent-memory-stats {
    description
      "Wireless fabric memory statistics";
    leaf malloc-psk-buf {
      type yang:counter64;
      description
        "Malloc count of psk buffer";
    }
    leaf free-psk-buf {
      type yang:counter64;
      description
        "Free count of psk buffer";
    }
    leaf malloc-map-reg-msg {
      type yang:counter64;
      description
        "Malloc count of map register message";
    }
    leaf free-map-reg-msg {
      type yang:counter64;
      description
        "Free count of map register message";
    }
    leaf malloc-map-req-msg {
      type yang:counter64;
      description
        "Malloc count of map request message";
    }
    leaf free-map-req-msg {
      type yang:counter64;
      description
        "Free count of map request message";
    }
    leaf malloc-lisp-ha-node {
      type yang:counter64;
      description
        "Malloc count of lisp HA node";
    }
    leaf free-lisp-ha-node {
      type yang:counter64;
      description
        "Free count of lisp HA node";
    }
    leaf malloc-map-server-ctxt {
      type yang:counter64;
      description
        "Malloc count of control plane context";
    }
    leaf free-map-server-ctxt {
      type yang:counter64;
      description
        "Free count of control plane context";
    }
  }

  grouping st-lisp-agent-ms-memory-stats {
    description
      "Wireless Fabric Control Plane memory statistics";
    leaf map-server-address {
      type inet:ip-address;
      description
        "Control Plane IP address";
    }
    leaf malloc-tcp-flow-control-msg-queue {
      type yang:counter64;
      description
        "Malloc count of TCP flow control message queue";
    }
    leaf free-tcp-flow-control-msg-queue {
      type yang:counter64;
      description
        "Free count of TCP flow control message queue";
    }
    leaf malloc-tcp-incomplete-msg-buffer {
      type yang:counter64;
      description
        "Malloc count of TCP incomplete message buffer";
    }
    leaf free-tcp-incomplete-msg-buffer {
      type yang:counter64;
      description
        "Free count of TCP incomplete message buffer";
    }
    leaf malloc-tcp-receive-buff {
      type yang:counter64;
      description
        "Malloc count of TCP receive buffer";
    }
    leaf free-tcp-receive-buff {
      type yang:counter64;
      description
        "Free count of TCP receive buffer";
    }
    leaf malloc-udp-receive-buff {
      type yang:counter64;
      description
        "Malloc count of UDP receive buffer";
    }
    leaf free-udp-receive-buff {
      type yang:counter64;
      description
        "Free count of UDP receive buffer";
    }
  }

  grouping st-lisp-wlc-capabilities {
    description
      "Wireless Fabric WLC Capabilities";
    leaf fabric-capable {
      type boolean;
      description
        "WLC Fabric capable";
    }
  }

  grouping st-lisp-ap-capabilities {
    description
      "Wireless Fabric AP Capabilities";
    leaf ap-type {
      type uint32;
      description
        "AP Type";
    }
    leaf fabric-capable {
      type boolean;
      description
        "AP Fabric capable";
    }
  }

  container lisp-agent-oper-data {
    config false;
    description
      "Lisp Agent operational data";
    container lisp-agent-memory-stats {
      presence "lisp-agent-memory-stats";
      description
        "Lisp Agent Memory Statistics";
      uses wireless-lisp-agent-oper:st-lisp-agent-memory-stats;
    }
    list lisp-agent-map-server-memory-stats {
      key "map-server-address";
      description
        "Control PLane memory statistics";
      uses wireless-lisp-agent-oper:st-lisp-agent-ms-memory-stats;
    }
    list lisp-agent-ap-data {
      key "wtp-radio-mac";
      unique "wtp-ip";
      description
        "Fabric AP data";
      uses wireless-lisp-agent-oper:st-lisp-agent-ap-data {
        refine "wtp-ip" {
          mandatory true;
        }
      }
    }
    list lisp-agent-client-data {
      key "client-mac";
      description
        "Fabric client data";
      uses wireless-lisp-agent-oper:st-lisp-agent-client-data;
    }
    list lisp-agent-client-history {
      key "client-mac";
      description
        "Fabric client history";
      uses wireless-lisp-agent-oper:st-lisp-agent-client-history;
    }
    list lisp-agent-ms-msg-stats-data {
      key "map-server-ip";
      description
        "Control Plane message data statistics";
      uses wireless-lisp-agent-oper:st-lisp-agent-ms-msg-stats;
    }
    container lisp-wlc-capabilities {
      presence "lisp-wlc-capabilities";
      description
        "Wireless Fabric WLC Capabilities";
      uses wireless-lisp-agent-oper:st-lisp-wlc-capabilities;
    }
    list lisp-ap-capabilities {
      key "ap-type";
      description
        "Wireless Fabric AP Capabilities";
      uses wireless-lisp-agent-oper:st-lisp-ap-capabilities;
    }
  }
}
