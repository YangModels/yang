module Cisco-IOS-XE-stack-oper {
  yang-version 1;
  namespace "http://cisco.com/ns/yang/Cisco-IOS-XE-stack-oper";
  prefix stack-ios-xe-oper;

  import ietf-yang-types {
    prefix yang;
  }
  import cisco-semver {
    prefix cisco-semver;
  }

  organization
    "Cisco Systems, Inc.";
  contact
    "Cisco Systems, Inc.
     Customer Service
     
     Postal: 170 W Tasman Drive
     San Jose, CA 95134
     
     Tel: +1 1800 553-NETS
     
     E-mail: cs-yang@cisco.com";
  description
    "This module contains a collection of YANG definitions
     for Stack operational data.
     Copyright (c) 2018-2019 by Cisco Systems, Inc.
     All rights reserved.";

  revision 2019-06-06 {
    description
      "- Added node role, state and stacking mode information.
       - Added high availability interface MTU value.
       - Added standby SSO flag.
       - Added stacking port state.
       - Added semantic version";
    reference "1.1.0";
    cisco-semver:module-version "1.1.0";
  }
  revision 2018-05-01 {
    description
      "Initial revision";
    reference "1.0.0";
    cisco-semver:module-version "1.0.0";
  }

  typedef stack-node-role-id {
    type enumeration {
      enum "role-unknown" {
        value 0;
        description
          "Role Unknown";
      }
      enum "role-active" {
        value 1;
        description
          "Role Active";
      }
      enum "role-standby" {
        value 2;
        description
          "Role Standby";
      }
      enum "role-member" {
        value 3;
        description
          "Role Member";
      }
    }
    description
      "Stack Node Role";
  }

  typedef stack-node-state {
    type enumeration {
      enum "state-configured" {
        value 0;
        description
          "State Configured";
      }
      enum "state-waiting" {
        value 1;
        description
          "State Waiting";
      }
      enum "state-progressing" {
        value 2;
        description
          "State Progressing";
      }
      enum "state-initializing" {
        value 3;
        description
          "State Initializing";
      }
      enum "state-ready" {
        value 4;
        description
          "State Ready";
      }
      enum "state-master-reinit" {
        value 5;
        description
          "State Master Re-initializing";
      }
      enum "state-feature-mismatch" {
        value 6;
        description
          "State Feature Mismatch";
      }
      enum "state-version-mismatch" {
        value 7;
        description
          "State Version Mismatch";
      }
      enum "state-license-mismatch" {
        value 8;
        description
          "State License Mismatch";
      }
      enum "state-platform-mismatch" {
        value 9;
        description
          "State Platform Mismatch";
      }
      enum "state-platform-and-license-mismatch" {
        value 10;
        description
          "State Platform and License Mismatch";
      }
      enum "state-invalid" {
        value 11;
        description
          "State Invalid";
      }
      enum "state-provisioned" {
        value 12;
        description
          "State Provisioned";
      }
      enum "state-removed" {
        value 13;
        description
          "State Removed";
      }
      enum "state-unprovisioned" {
        value 14;
        description
          "State Un-provisioned";
      }
      enum "state-os-mismatch" {
        value 15;
        description
          "State OS Mismatch";
      }
      enum "state-unknown" {
        value 16;
        description
          "State Unknown";
      }
    }
    description
      "Stack Node State";
  }

  typedef stacking-mode {
    type enumeration {
      enum "mode-stackwise-rear" {
        value 0;
        description
          "Mode Stackwise Rear";
      }
      enum "mode-active-standby" {
        value 1;
        description
          "Mode Active Standby";
      }
      enum "mode-stackwise-geo" {
        value 2;
        description
          "Mode Stackwise Geo";
      }
      enum "mode-stackwise-virtual" {
        value 3;
        description
          "Mode Stackwise Virtual";
      }
      enum "mode-unknown" {
        value 4;
        description
          "Mode Unknown";
      }
    }
    description
      "Stack Mode";
  }

  typedef stacking-port-state {
    type enumeration {
      enum "link-down" {
        value 0;
        description
          "Port State Down";
      }
      enum "link-up" {
        value 1;
        description
          "Port State Up";
      }
      enum "link-no-cable" {
        value 2;
        description
          "Port State No Cable";
      }
    }
    description
      "Stack Port State";
  }

  grouping stack-node-keepalive {
    description
      "Stack Node Keepalive Counters";
    leaf sent {
      type uint64;
      description
        "Keepalive Request Sent";
    }
    leaf received {
      type uint64;
      description
        "Keepalive Response Received";
    }
    leaf sent-failure {
      type uint64;
      description
        "Keepalive Request Sent Failure";
    }
    leaf receive-failure {
      type uint64;
      description
        "Keepalive Response Failure";
    }
    leaf consecutive-losses {
      type uint64;
      description
        "Keepalive Consecutive Losses";
    }
  }

  grouping stack-port-info {
    description
      "Stack port information";
    leaf port-num {
      type uint8;
      description
        "Stack Port Number";
    }
    leaf port-state {
      type stack-ios-xe-oper:stacking-port-state;
      description
        "Stack Port State";
    }
    leaf switch-nbr-port {
      type uint8;
      description
        "Switch Number connected to Stack Port";
    }
  }

  grouping stack-node-info {
    description
      "Stack Node Data";
    leaf chassis-number {
      type uint8;
      description
        "Chassis Number";
    }
    leaf priority {
      type uint8;
      description
        "Chassis Priority";
    }
    leaf serial-number {
      type string;
      description
        "Serial Number";
    }
    leaf latency {
      type uint32;
      units "nanoseconds";
      description
        "Latency in nanoseconds";
    }
    container keepalive-counters {
      description
        "Keepalive counters";
      uses stack-ios-xe-oper:stack-node-keepalive;
    }
    leaf interface-mtu {
      type uint32;
      units "bytes";
      description
        "Interface MTU";
    }
    leaf role {
      type stack-ios-xe-oper:stack-node-role-id;
      description
        "Chassis Role";
    }
    leaf node-state {
      type stack-ios-xe-oper:stack-node-state;
      description
        "Chassis State";
    }
    leaf stack-mode {
      type stack-ios-xe-oper:stacking-mode;
      description
        "Stack mode";
    }
    leaf sso-ready-flag {
      type boolean;
      description
        "Standby SSO Ready flag";
    }
    leaf mac-address {
      type yang:mac-address;
      description
        "MAC Address of the switch";
    }
    list stack-ports {
      description
        "Switch Stack Port link Status";
      uses stack-ios-xe-oper:stack-port-info;
    }
  }

  container stack-oper-data {
    config false;
    description
      "stack operational data";
    list stack-node {
      key "chassis-number";
      description
        "Stack Node Data";
      uses stack-ios-xe-oper:stack-node-info;
    }
  }
}
